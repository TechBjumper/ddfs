--
-- HUAWEI-UPS-MIB.mib
-- MIB generated by MG-SOFT Visual MIB Builder Version 6.0  Build 88
-- Monday, February 02, 2015 at 19:17:53
--

--  =================================================================
-- Copyright (C) 2012 by HUAWEI TECHNOLOGIES. All rights reserved
-- Description:  The mib is used for defining huawei's UPS MIB objects which provides UPS management NMS interfaces.
-- Reference:
-- Version: V1.01
-- ================================================================

	HUAWEI-UPS-MIB DEFINITIONS ::= BEGIN
 
		IMPORTS
			huaweiUtility			
				FROM HUAWEI-MIB			
			OBJECT-GROUP, NOTIFICATION-GROUP			
				FROM SNMPv2-CONF			
			Integer32, Unsigned32, OBJECT-TYPE, MODULE-IDENTITY, NOTIFICATION-TYPE			
				FROM SNMPv2-SMI			
			TEXTUAL-CONVENTION			
				FROM SNMPv2-TC;
	
	
-- October 21, 2011 at 12:10 GMT
-- June 14, 2012 at 10:54 GMT
		-- 1.3.6.1.4.1.2011.6.174
		hwUpsMIB MODULE-IDENTITY 
			LAST-UPDATED "201110211210Z"		-- October 21, 2011 at 12:10 GMT
			ORGANIZATION 
				"Huawei Technologies Co.,Ltd."
			CONTACT-INFO 
				"Contact-info."
			DESCRIPTION 
				"The mib is used for defining huawei's UPS MIB objects which provides UPS management NMS interfaces.
				Reference."
			REVISION "201207241530Z"		-- July 24, 2012 at 15:30 GMT
			DESCRIPTION 
				"UPS Monitor MIB defines MIB objects which provides load and backup management, patch management NMS interfaces."
			REVISION "201206110802Z"		-- June 11, 2012 at 08:02 GMT
			DESCRIPTION 
				"UPS Monitor MIB defines MIB objects which provides load and backup management, patch management NMS interfaces."
			::= { huaweiUtility 174 }

		
	
--
-- Textual conventions
--
	
--  Textual conventions
-- 
		RowStatus ::= TEXTUAL-CONVENTION
			STATUS current
			DESCRIPTION 
				"Used to manage the creation and deletion of rows in a table."
			SYNTAX INTEGER
				{
				active(1),
				notInService(2),
				notReady(3),
				createAndGo(4),
				createAndWait(5),
				destroy(6)
				}

	
--
-- Node definitions
--
	
-- Node definitions
-- 1.3.6.1.4.1.2011.6.174.1
		-- 1.3.6.1.4.1.2011.6.174.1
		hwUpsMIBObjects OBJECT IDENTIFIER ::= { hwUpsMIB 1 }

		
		-- 1.3.6.1.4.1.2011.6.174.1.1
		hwUpsSystem OBJECT IDENTIFIER ::= { hwUpsMIBObjects 1 }

		
		-- 1.3.6.1.4.1.2011.6.174.1.1.1
		hwUpsSysIdent OBJECT IDENTIFIER ::= { hwUpsSystem 1 }

		
		-- 1.3.6.1.4.1.2011.6.174.1.1.1.1
		hwUpsSystemMainDeviceESN OBJECT-TYPE
			SYNTAX OCTET STRING (SIZE (0..127))
			MAX-ACCESS read-only
			STATUS current
			DESCRIPTION
				"ESN of the master device used for setting up a NetEco model. A string of characters. "
			::= { hwUpsSysIdent 1 }

		
		-- 1.3.6.1.4.1.2011.6.174.1.1.1.2
		hwUpsSystemType OBJECT-TYPE
			SYNTAX OCTET STRING (SIZE (0..127))
			MAX-ACCESS read-only
			STATUS current
			DESCRIPTION
				"Name of the UPS system. A string of characters. Configurable."
			::= { hwUpsSysIdent 2 }

		
		-- 1.3.6.1.4.1.2011.6.174.1.1.1.3
		hwUpsSysInerProtVersion OBJECT-TYPE
			SYNTAX OCTET STRING (SIZE (0..127))
			MAX-ACCESS read-only
			STATUS current
			DESCRIPTION
				"Version number of the system interface protocol between the NetEco and NEs. 
				A string of characters."
			::= { hwUpsSysIdent 3 }

		
		-- 1.3.6.1.4.1.2011.6.174.1.1.1.4
		hwUpsSysDeviceNum OBJECT-TYPE
			SYNTAX Unsigned32 (0..63)
			MAX-ACCESS read-only
			STATUS current
			DESCRIPTION
				"Number of devices in the system. An integer ranging from 0 to 63."
			::= { hwUpsSysIdent 4 }

		
		-- 1.3.6.1.4.1.2011.6.174.1.1.1.5
		hwUpsParallelSysNum OBJECT-TYPE
			SYNTAX Unsigned32 (0..63)
			MAX-ACCESS read-only
			STATUS current
			DESCRIPTION
				"Number of parallel systems. An integer ranging from 0 to 63."
			::= { hwUpsSysIdent 5 }

		
		-- 1.3.6.1.4.1.2011.6.174.1.1.1.6
		hwUpsEnvTemper OBJECT-TYPE
			SYNTAX Integer32 (-500..1200)
			UNITS "℃"
			MAX-ACCESS read-only
			STATUS current
			DESCRIPTION
				"Ambient temperature. An integer ranging from -50 to 120.
				The value is accurate to one decimal place on the NetEco. The unit is °C."
			::= { hwUpsSysIdent 6 }

		
		-- 1.3.6.1.4.1.2011.6.174.1.1.1.7
		hwUpsEnvHumidity OBJECT-TYPE
			SYNTAX Unsigned32 (0..1000)
			UNITS "%"
			MAX-ACCESS read-only
			STATUS current
			DESCRIPTION
				"Ambient humidity. An integer ranging from 0 to 100. 
				The value is accurate to one decimal place on the NetEco. The unit is %."
			::= { hwUpsSysIdent 7 }

		
		-- 1.3.6.1.4.1.2011.6.174.1.2
		hwUpsDevice OBJECT IDENTIFIER ::= { hwUpsMIBObjects 2 }

		
		-- 1.3.6.1.4.1.2011.6.174.1.2.100
		hwUpsDeviceIdentTable OBJECT-TYPE
			SYNTAX SEQUENCE OF HwUpsDeviceIdentEntry
			MAX-ACCESS not-accessible
			STATUS current
			DESCRIPTION
				"The device identification table. Use this table to get device ID, and to get device type,
				the soft version, the iner prot version, the ESN, the rating power of device, 
				the parallel system index of device. This table's index is hwUpsDeviceId."
			::= { hwUpsDevice 100 }

		
		-- 1.3.6.1.4.1.2011.6.174.1.2.100.1
		hwUpsDeviceIdentEntry OBJECT-TYPE
			SYNTAX HwUpsDeviceIdentEntry
			MAX-ACCESS not-accessible
			STATUS current
			DESCRIPTION
				"Device identification table entry."
			INDEX { hwUpsDeviceId }
			::= { hwUpsDeviceIdentTable 1 }

		
		HwUpsDeviceIdentEntry ::=
			SEQUENCE { 
				hwUpsDeviceId
					Unsigned32,
				hwUpsDeviceType
					OCTET STRING,
				hwUpsDeviceSoftVersion
					OCTET STRING,
				hwUpsDeviceInerProtVersion
					OCTET STRING,
				hwUpsDeviceESN
					OCTET STRING,
				hwUpsDevicePowerRating
					INTEGER,
				hwUpsDeviceParaSysIndex
					Unsigned32,
				hwUpsDeviceSysGrant
					Unsigned32,
				hwUpsDeviceMonitorSoftVersion
					OCTET STRING,
				hwUpsDevicePowerSoftVersion
					OCTET STRING,
				hwUpsDeviceIdentRowStatus
					RowStatus
			 }

		-- 1.3.6.1.4.1.2011.6.174.1.2.100.1.1
		hwUpsDeviceId OBJECT-TYPE
			SYNTAX Unsigned32 (1..100)
			MAX-ACCESS read-only
			STATUS current
			DESCRIPTION
				"Rack ID, ranging from 1 to 100. This node is referenced as an index node 
				by hwUpsDeviceIdentTable, hwUpsDeviceOperInfoTable, hwUpsInputTable, 
				hwUpsOutputTable,hwUpsBypassTable, hwUpsBatteryTable, hwUpsControlTable, 
				and hwUpsBattScheduleTestTable."
			::= { hwUpsDeviceIdentEntry 1 }

		
		-- 1.3.6.1.4.1.2011.6.174.1.2.100.1.2
		hwUpsDeviceType OBJECT-TYPE
			SYNTAX OCTET STRING (SIZE (0..127))
			MAX-ACCESS read-only
			STATUS current
			DESCRIPTION
				"Device model. A string of characters."
			::= { hwUpsDeviceIdentEntry 2 }

		
		-- 1.3.6.1.4.1.2011.6.174.1.2.100.1.3
		hwUpsDeviceSoftVersion OBJECT-TYPE
			SYNTAX OCTET STRING (SIZE (0..127))
			MAX-ACCESS read-only
			STATUS current
			DESCRIPTION
				"Device software version number. A string of characters."
			::= { hwUpsDeviceIdentEntry 3 }

		
		-- 1.3.6.1.4.1.2011.6.174.1.2.100.1.4
		hwUpsDeviceInerProtVersion OBJECT-TYPE
			SYNTAX OCTET STRING (SIZE (0..127))
			MAX-ACCESS read-only
			STATUS current
			DESCRIPTION
				"Interface protocol version number for the current device. A string of characters. "
			::= { hwUpsDeviceIdentEntry 4 }

		
		-- 1.3.6.1.4.1.2011.6.174.1.2.100.1.5
		hwUpsDeviceESN OBJECT-TYPE
			SYNTAX OCTET STRING (SIZE (0..127))
			MAX-ACCESS read-only
			STATUS current
			DESCRIPTION
				"ESN. A string of characters."
			::= { hwUpsDeviceIdentEntry 5 }

		
		-- 1.3.6.1.4.1.2011.6.174.1.2.100.1.6
		hwUpsDevicePowerRating OBJECT-TYPE
			SYNTAX INTEGER
				{
				level80(1),
				level100(2),
				level120(3),
				level160(4),
				level200(5),
				level30(6),
				level40(7),
				level60(8),
				level240(9),
				level250(10),
				level280(11),
				level300(12)
				}
			UNITS "kVA"
			MAX-ACCESS read-only
			STATUS obsolete
			DESCRIPTION
				"System capacity. Enumeration type. The default value is 5. The unit is kVA.
				Value 1 indicates 80 kVA
				Value 2 indicates 100 kVA.
				Value 3 indicates 120 kVA.
				Value 4 indicates 160 kVA.
				Value 5 indicates 200 kVA."
			::= { hwUpsDeviceIdentEntry 6 }

		
		-- 1.3.6.1.4.1.2011.6.174.1.2.100.1.7
		hwUpsDeviceParaSysIndex OBJECT-TYPE
			SYNTAX Unsigned32 (0..63)
			MAX-ACCESS read-only
			STATUS current
			DESCRIPTION
				"ID of the parallel system that the current device belongs to. An integer ranging from 0 to 63."
			::= { hwUpsDeviceIdentEntry 7 }

		
		-- 1.3.6.1.4.1.2011.6.174.1.2.100.1.8
		hwUpsDeviceSysGrant OBJECT-TYPE
			SYNTAX Unsigned32 (0..10000)
			MAX-ACCESS read-only
			STATUS current
			DESCRIPTION
				"System grant.An integer ranging from 0 to 10000."
			::= { hwUpsDeviceIdentEntry 8 }

		
		-- 1.3.6.1.4.1.2011.6.174.1.2.100.1.9
		hwUpsDeviceMonitorSoftVersion OBJECT-TYPE
			SYNTAX OCTET STRING (SIZE (0..127))
			MAX-ACCESS read-only
			STATUS current
			DESCRIPTION
				"Monitor software version number. A string of characters."
			::= { hwUpsDeviceIdentEntry 9 }

		
		-- 1.3.6.1.4.1.2011.6.174.1.2.100.1.10
		hwUpsDevicePowerSoftVersion OBJECT-TYPE
			SYNTAX OCTET STRING (SIZE (0..127))
			MAX-ACCESS read-only
			STATUS current
			DESCRIPTION
				"Power software version number. A string of characters."
			::= { hwUpsDeviceIdentEntry 10 }

		
		-- 1.3.6.1.4.1.2011.6.174.1.2.100.1.100
		hwUpsDeviceIdentRowStatus OBJECT-TYPE
			SYNTAX RowStatus
			MAX-ACCESS read-only
			STATUS current
			DESCRIPTION
				"RowStatus of UPS device Identification table."
			::= { hwUpsDeviceIdentEntry 100 }

		
		-- 1.3.6.1.4.1.2011.6.174.1.2.101
		hwUpsDeviceOperInfoTable OBJECT-TYPE
			SYNTAX SEQUENCE OF HwUpsDeviceOperInfoEntry
			MAX-ACCESS not-accessible
			STATUS current
			DESCRIPTION
				"Device running information table. It's index is hwUpsDeviceId"
			::= { hwUpsDevice 101 }

		
		-- 1.3.6.1.4.1.2011.6.174.1.2.101.1
		hwUpsDeviceOperInfoEntry OBJECT-TYPE
			SYNTAX HwUpsDeviceOperInfoEntry
			MAX-ACCESS not-accessible
			STATUS current
			DESCRIPTION
				"Device running information table entry."
			INDEX { hwUpsDeviceId }
			::= { hwUpsDeviceOperInfoTable 1 }

		
		HwUpsDeviceOperInfoEntry ::=
			SEQUENCE { 
				hwUpsDevicePowerSupplyMethod
					INTEGER,
				hwUpsDeviceRunningStatus
					INTEGER,
				hwUpsDeviceBatteryState
					INTEGER,
				hwUpsDeviceTemperature
					Unsigned32,
				hwUpsDeviceEnergyFloatState
					Unsigned32,
				hwUpsDeviceRedundantNumber
					Unsigned32,
				hwUpsDeviceDelayShutdownState
					Unsigned32,
				hwUpsDeviceDelayShutdownOrder
					INTEGER,
				hwUpsDeviceWorkMode
					INTEGER,
				hwUpsDeviceSmartPowerMode
					INTEGER,
				hwUpsDeviceOperInfoRowStatus
					RowStatus
			 }

		-- 1.3.6.1.4.1.2011.6.174.1.2.101.1.1
		hwUpsDevicePowerSupplyMethod OBJECT-TYPE
			SYNTAX INTEGER
				{
				noOutput(1),
				bypass(2),
				normal(3),
				battery(4),
				sourceShare(5),
				normalECO(6),
				batteryECO(7)
				}
			MAX-ACCESS read-only
			STATUS current
			DESCRIPTION
				"Device power supply mode. Enumeration type.
				Value 1 indicates no power supply.
				Value 2 indicates bypass mode.
				Value 3 indicates normal mode.
				Value 4 indicates battery mode.
				Value 5 indicates combined mode.
				Value 6 indicates mains ECO mode.
				Value 7 indicates battery ECO mode."
			::= { hwUpsDeviceOperInfoEntry 1 }

		
		-- 1.3.6.1.4.1.2011.6.174.1.2.101.1.2
		hwUpsDeviceRunningStatus OBJECT-TYPE
			SYNTAX INTEGER
				{
				single(1),
				parallel(2),
				singleECO(3),
				parallelECO(4),
				aging(5)
				}
			MAX-ACCESS read-only
			STATUS current
			DESCRIPTION
				"UPS operating status. Enumeration type.
				Value 1 indicates that a single UPS is operating.
				Value 2 indicates that the parallel system is operating.
				Value 3 indicates that a single UPS is operating in ECO mode.
				Value 4 indicates that the parallel system is operating in ECO mode.
				Value 5 indicates aging."
			::= { hwUpsDeviceOperInfoEntry 2 }

		
		-- 1.3.6.1.4.1.2011.6.174.1.2.101.1.3
		hwUpsDeviceBatteryState OBJECT-TYPE
			SYNTAX INTEGER
				{
				notExist(1),
				temperaryMode(2),
				sleep(3),
				floatCharge(4),
				boostCharge(5),
				discharge(6)
				}
			MAX-ACCESS read-only
			STATUS current
			DESCRIPTION
				"Battery status. Enumeration type.
				Value 1 indicates that no battery is connected.
				Value 2 indicates that the battery is not charging or discharging.
				Value 3 indicates hibernation.
				Value 4 indicates float charging.
				Value 5 indicates equalized charging.
				Value 6 indicates discharging."
			::= { hwUpsDeviceOperInfoEntry 3 }

		
		-- 1.3.6.1.4.1.2011.6.174.1.2.101.1.4
		hwUpsDeviceTemperature OBJECT-TYPE
			SYNTAX Unsigned32 (0..3000)
			UNITS "℃"
			MAX-ACCESS read-only
			STATUS current
			DESCRIPTION
				"Maximum temperature of the modules in the current device. An integer ranging from 0 to 300. "
			::= { hwUpsDeviceOperInfoEntry 4 }

		
		-- 1.3.6.1.4.1.2011.6.174.1.2.101.1.5
		hwUpsDeviceEnergyFloatState OBJECT-TYPE
			SYNTAX Unsigned32 (0..70000)
			MAX-ACCESS read-only
			STATUS current
			DESCRIPTION
				"Current flow status. An integer ranging from 0 to 70000. "
			::= { hwUpsDeviceOperInfoEntry 5 }

		
		-- 1.3.6.1.4.1.2011.6.174.1.2.101.1.6
		hwUpsDeviceRedundantNumber OBJECT-TYPE
			SYNTAX Unsigned32 (0..3)
			MAX-ACCESS read-only
			STATUS current
			DESCRIPTION
				"Redundant number of the parallel system. An integer ranging from 0 to 3."
			::= { hwUpsDeviceOperInfoEntry 6 }

		
		-- 1.3.6.1.4.1.2011.6.174.1.2.101.1.7
		hwUpsDeviceDelayShutdownState OBJECT-TYPE
			SYNTAX Unsigned32 (0..4294967295)
			MAX-ACCESS read-only
			STATUS current
			DESCRIPTION
				"Delay to shutdown state. An integer ranging from 0 to 4294967295"
			::= { hwUpsDeviceOperInfoEntry 7 }

		
		-- 1.3.6.1.4.1.2011.6.174.1.2.101.1.8
		hwUpsDeviceDelayShutdownOrder OBJECT-TYPE
			SYNTAX INTEGER
				{
				invalid(1),
				valid(2)
				}
			MAX-ACCESS read-only
			STATUS current
			DESCRIPTION
				"Delay to shutdown state.  Enumeration type.
				Value 1 indicates invalid.
				Value 2 indicates valid.
				"
			::= { hwUpsDeviceOperInfoEntry 8 }

		
		-- 1.3.6.1.4.1.2011.6.174.1.2.101.1.9
		hwUpsDeviceWorkMode OBJECT-TYPE
			SYNTAX INTEGER
				{
				normalMode(1),
				ecoMode(2),
				selfloadMode(3),
				converterMode(4)
				}
			MAX-ACCESS read-only
			STATUS current
			DESCRIPTION
				"Work Mode. Enumeration type.
				Value 1 indicates that normal mode.
				Value 2 indicates that eco mode.
				Value 3 indicates that self load mode.
				Value 4 indicates that converter mode."
			::= { hwUpsDeviceOperInfoEntry 9 }

		
		-- 1.3.6.1.4.1.2011.6.174.1.2.101.1.10
		hwUpsDeviceSmartPowerMode OBJECT-TYPE
			SYNTAX INTEGER
				{
				disable(1),
				enable(2)
				}
			MAX-ACCESS read-only
			STATUS current
			DESCRIPTION
				"Smart Power Mode.Enumeration type.
				Value 1 indicates that disable.
				Value 2 indicates that enable.
				"
			::= { hwUpsDeviceOperInfoEntry 10 }

		
		-- 1.3.6.1.4.1.2011.6.174.1.2.101.1.101
		hwUpsDeviceOperInfoRowStatus OBJECT-TYPE
			SYNTAX RowStatus
			MAX-ACCESS read-only
			STATUS current
			DESCRIPTION
				"RowStatus of UPS device running information table."
			::= { hwUpsDeviceOperInfoEntry 101 }

		
		-- 1.3.6.1.4.1.2011.6.174.1.3
		hwUpsInput OBJECT IDENTIFIER ::= { hwUpsMIBObjects 3 }

		
		-- 1.3.6.1.4.1.2011.6.174.1.3.100
		hwUpsInputTable OBJECT-TYPE
			SYNTAX SEQUENCE OF HwUpsInputEntry
			MAX-ACCESS not-accessible
			STATUS current
			DESCRIPTION
				"UPS input information table. It's index is hwUpsDeviceId."
			::= { hwUpsInput 100 }

		
		-- 1.3.6.1.4.1.2011.6.174.1.3.100.1
		hwUpsInputEntry OBJECT-TYPE
			SYNTAX HwUpsInputEntry
			MAX-ACCESS not-accessible
			STATUS current
			DESCRIPTION
				"Input information table entry."
			INDEX { hwUpsDeviceId }
			::= { hwUpsInputTable 1 }

		
		HwUpsInputEntry ::=
			SEQUENCE { 
				hwUpsInputVoltageA
					Unsigned32,
				hwUpsInputVoltageB
					Unsigned32,
				hwUpsInputVoltageC
					Unsigned32,
				hwUpsInputFrequency
					Unsigned32,
				hwUpsInputCurrentA
					Unsigned32,
				hwUpsInputCurrentB
					Unsigned32,
				hwUpsInputCurrentC
					Unsigned32,
				hwUpsInputPowerFactorA
					Integer32,
				hwUpsInputPowerFactorB
					Integer32,
				hwUpsInputPowerFactorC
					Integer32,
				hwUpsInputRowStatus
					RowStatus
			 }

		-- 1.3.6.1.4.1.2011.6.174.1.3.100.1.1
		hwUpsInputVoltageA OBJECT-TYPE
			SYNTAX Unsigned32 (0..10000)
			UNITS "V"
			MAX-ACCESS read-only
			STATUS current
			DESCRIPTION
				"Input voltage phase A. The value ranges from 0 to 10000. 
				The value is accurate to one decimal place on the NetEco. The unit is V."
			::= { hwUpsInputEntry 1 }

		
		-- 1.3.6.1.4.1.2011.6.174.1.3.100.1.2
		hwUpsInputVoltageB OBJECT-TYPE
			SYNTAX Unsigned32 (0..10000)
			UNITS "V"
			MAX-ACCESS read-only
			STATUS current
			DESCRIPTION
				"Input voltage phase B. The value ranges from 0 to 10000. 
				The value is accurate to one decimal place on the NetEco. The unit is V."
			::= { hwUpsInputEntry 2 }

		
		-- 1.3.6.1.4.1.2011.6.174.1.3.100.1.3
		hwUpsInputVoltageC OBJECT-TYPE
			SYNTAX Unsigned32 (0..10000)
			UNITS "V"
			MAX-ACCESS read-only
			STATUS current
			DESCRIPTION
				"Input voltage phase C. The value ranges from 0 to 10000. 
				The value is accurate to one decimal place on the NetEco. The unit is V."
			::= { hwUpsInputEntry 3 }

		
		-- 1.3.6.1.4.1.2011.6.174.1.3.100.1.4
		hwUpsInputFrequency OBJECT-TYPE
			SYNTAX Unsigned32 (0..10000)
			UNITS "Hz"
			MAX-ACCESS read-only
			STATUS current
			DESCRIPTION
				"Input frequency. The value ranges from 0 to 10000. 
				The value is accurate to two decimal place on the NetEco. The unit is Hz."
			::= { hwUpsInputEntry 4 }

		
		-- 1.3.6.1.4.1.2011.6.174.1.3.100.1.5
		hwUpsInputCurrentA OBJECT-TYPE
			SYNTAX Unsigned32 (0..10000)
			UNITS "A"
			MAX-ACCESS read-only
			STATUS current
			DESCRIPTION
				"Input current phase A. The value ranges from 0 to 10000. 
				The value is accurate to one decimal place on the NetEco. The unit is A."
			::= { hwUpsInputEntry 5 }

		
		-- 1.3.6.1.4.1.2011.6.174.1.3.100.1.6
		hwUpsInputCurrentB OBJECT-TYPE
			SYNTAX Unsigned32 (0..10000)
			UNITS "A"
			MAX-ACCESS read-only
			STATUS current
			DESCRIPTION
				"Input current phase B. The value ranges from 0 to 10000. 
				The value is accurate to one decimal place on the NetEco. The unit is A."
			::= { hwUpsInputEntry 6 }

		
		-- 1.3.6.1.4.1.2011.6.174.1.3.100.1.7
		hwUpsInputCurrentC OBJECT-TYPE
			SYNTAX Unsigned32 (0..10000)
			UNITS "A"
			MAX-ACCESS read-only
			STATUS current
			DESCRIPTION
				"Input current phase C. The value ranges from 0 to 10000. 
				The value is accurate to one decimal place on the NetEco. The unit is A."
			::= { hwUpsInputEntry 7 }

		
		-- 1.3.6.1.4.1.2011.6.174.1.3.100.1.8
		hwUpsInputPowerFactorA OBJECT-TYPE
			SYNTAX Integer32 (-100..100)
			MAX-ACCESS read-only
			STATUS current
			DESCRIPTION
				"Phase A input power factor. The value ranges from -100 to 100. 
				The value is accurate to two decimal place on the NetEco."
			::= { hwUpsInputEntry 8 }

		
		-- 1.3.6.1.4.1.2011.6.174.1.3.100.1.9
		hwUpsInputPowerFactorB OBJECT-TYPE
			SYNTAX Integer32 (-100..100)
			MAX-ACCESS read-only
			STATUS current
			DESCRIPTION
				"Phase B input power factor. The value ranges from -100 to 100. 
				The value is accurate to two decimal place on the NetEco."
			::= { hwUpsInputEntry 9 }

		
		-- 1.3.6.1.4.1.2011.6.174.1.3.100.1.10
		hwUpsInputPowerFactorC OBJECT-TYPE
			SYNTAX Integer32 (-100..100)
			MAX-ACCESS read-only
			STATUS current
			DESCRIPTION
				"Phase C input power factor. The value ranges from -100 to 100. 
				The value is accurate to two decimal place on the NetEco."
			::= { hwUpsInputEntry 10 }

		
		-- 1.3.6.1.4.1.2011.6.174.1.3.100.1.100
		hwUpsInputRowStatus OBJECT-TYPE
			SYNTAX RowStatus
			MAX-ACCESS read-only
			STATUS current
			DESCRIPTION
				"RowStatus of UPS input information table."
			::= { hwUpsInputEntry 100 }

		
		-- 1.3.6.1.4.1.2011.6.174.1.4
		hwUpsOutput OBJECT IDENTIFIER ::= { hwUpsMIBObjects 4 }

		
		-- 1.3.6.1.4.1.2011.6.174.1.4.100
		hwUpsOutputTable OBJECT-TYPE
			SYNTAX SEQUENCE OF HwUpsOutputEntry
			MAX-ACCESS not-accessible
			STATUS current
			DESCRIPTION
				"UPS output information table. It's index is hwUpsDeviceId."
			::= { hwUpsOutput 100 }

		
		-- 1.3.6.1.4.1.2011.6.174.1.4.100.1
		hwUpsOutputEntry OBJECT-TYPE
			SYNTAX HwUpsOutputEntry
			MAX-ACCESS not-accessible
			STATUS current
			DESCRIPTION
				"Output information table entry."
			INDEX { hwUpsDeviceId }
			::= { hwUpsOutputTable 1 }

		
		HwUpsOutputEntry ::=
			SEQUENCE { 
				hwUpsOutputVoltageA
					Unsigned32,
				hwUpsOutputVoltageB
					Unsigned32,
				hwUpsOutputVoltageC
					Unsigned32,
				hwUpsOutputCurrentA
					Unsigned32,
				hwUpsOutputCurrentB
					Unsigned32,
				hwUpsOutputCurrentC
					Unsigned32,
				hwUpsOutputFrequency
					Unsigned32,
				hwUpsOutputActivePowerA
					Integer32,
				hwUpsOutputActivePowerB
					Integer32,
				hwUpsOutputActivePowerC
					Integer32,
				hwUpsOutputAppearancePowerA
					Integer32,
				hwUpsOutputAppearancePowerB
					Integer32,
				hwUpsOutputAppearancePowerC
					Integer32,
				hwUpsOutputLoadA
					Unsigned32,
				hwUpsOutputLoadB
					Unsigned32,
				hwUpsOutputLoadC
					Unsigned32,
				hwUpsOutputPowerRating
					INTEGER,
				hwUpsOutputFrequencyRating
					INTEGER,
				hwUpsOutputPowerFactorA
					Integer32,
				hwUpsOutputPowerFactorB
					Integer32,
				hwUpsOutputPowerFactorC
					Integer32,
				hwUpsOutputRowStatus
					RowStatus
			 }

		-- 1.3.6.1.4.1.2011.6.174.1.4.100.1.1
		hwUpsOutputVoltageA OBJECT-TYPE
			SYNTAX Unsigned32 (0..10000)
			UNITS "V"
			MAX-ACCESS read-only
			STATUS current
			DESCRIPTION
				"Rack phase A output voltage. The value ranges from 0 to 10000. 
				The value is accurate to one decimal place on the NetEco. The unit is V."
			::= { hwUpsOutputEntry 1 }

		
		-- 1.3.6.1.4.1.2011.6.174.1.4.100.1.2
		hwUpsOutputVoltageB OBJECT-TYPE
			SYNTAX Unsigned32 (0..10000)
			UNITS "V"
			MAX-ACCESS read-only
			STATUS current
			DESCRIPTION
				"Rack phase B output voltage. The value ranges from 0 to 10000. 
				The value is accurate to one decimal place on the NetEco. The unit is V."
			::= { hwUpsOutputEntry 2 }

		
		-- 1.3.6.1.4.1.2011.6.174.1.4.100.1.3
		hwUpsOutputVoltageC OBJECT-TYPE
			SYNTAX Unsigned32 (0..10000)
			UNITS "V"
			MAX-ACCESS read-only
			STATUS current
			DESCRIPTION
				"Rack phase C output voltage. The value ranges from 0 to 10000. 
				The value is accurate to one decimal place on the NetEco. The unit is V."
			::= { hwUpsOutputEntry 3 }

		
		-- 1.3.6.1.4.1.2011.6.174.1.4.100.1.4
		hwUpsOutputCurrentA OBJECT-TYPE
			SYNTAX Unsigned32 (0..10000)
			UNITS "A"
			MAX-ACCESS read-only
			STATUS current
			DESCRIPTION
				"Rack phase A output current. The value ranges from 0 to 10000. 
				The value is accurate to one decimal place on the NetEco. The unit is A."
			::= { hwUpsOutputEntry 4 }

		
		-- 1.3.6.1.4.1.2011.6.174.1.4.100.1.5
		hwUpsOutputCurrentB OBJECT-TYPE
			SYNTAX Unsigned32 (0..10000)
			UNITS "A"
			MAX-ACCESS read-only
			STATUS current
			DESCRIPTION
				"Rack phase B output current. The value ranges from 0 to 10000. 
				The value is accurate to one decimal place on the NetEco. The unit is A."
			::= { hwUpsOutputEntry 5 }

		
		-- 1.3.6.1.4.1.2011.6.174.1.4.100.1.6
		hwUpsOutputCurrentC OBJECT-TYPE
			SYNTAX Unsigned32 (0..10000)
			UNITS "A"
			MAX-ACCESS read-only
			STATUS current
			DESCRIPTION
				"Rack phase C output current. The value ranges from 0 to 10000. 
				The value is accurate to one decimal place on the NetEco. The unit is A."
			::= { hwUpsOutputEntry 6 }

		
		-- 1.3.6.1.4.1.2011.6.174.1.4.100.1.7
		hwUpsOutputFrequency OBJECT-TYPE
			SYNTAX Unsigned32 (0..10000)
			UNITS "Hz"
			MAX-ACCESS read-only
			STATUS current
			DESCRIPTION
				"Rack output frequency. The value ranges from 0 to 10000. 
				The value is accurate to two decimal place on the NetEco. The unit is Hz."
			::= { hwUpsOutputEntry 7 }

		
		-- 1.3.6.1.4.1.2011.6.174.1.4.100.1.8
		hwUpsOutputActivePowerA OBJECT-TYPE
			SYNTAX Integer32 (-12000..12000)
			UNITS "kW"
			MAX-ACCESS read-only
			STATUS current
			DESCRIPTION
				"Rack phase A output active power. The value ranges from -12000 to 12000. 
				The value is accurate to one decimal place on the NetEco. The unit is kW."
			::= { hwUpsOutputEntry 8 }

		
		-- 1.3.6.1.4.1.2011.6.174.1.4.100.1.9
		hwUpsOutputActivePowerB OBJECT-TYPE
			SYNTAX Integer32 (-12000..12000)
			UNITS "kW"
			MAX-ACCESS read-only
			STATUS current
			DESCRIPTION
				"Rack phase B output active power. The value ranges from -12000 to 12000. 
				The value is accurate to one decimal place on the NetEco. The unit is kW."
			::= { hwUpsOutputEntry 9 }

		
		-- 1.3.6.1.4.1.2011.6.174.1.4.100.1.10
		hwUpsOutputActivePowerC OBJECT-TYPE
			SYNTAX Integer32 (-12000..12000)
			UNITS "kW"
			MAX-ACCESS read-only
			STATUS current
			DESCRIPTION
				"Rack phase C output active power. The value ranges from -12000 to 12000. 
				The value is accurate to one decimal place on the NetEco. The unit is kW."
			::= { hwUpsOutputEntry 10 }

		
		-- 1.3.6.1.4.1.2011.6.174.1.4.100.1.11
		hwUpsOutputAppearancePowerA OBJECT-TYPE
			SYNTAX Integer32 (-12000..12000)
			UNITS "kVA"
			MAX-ACCESS read-only
			STATUS current
			DESCRIPTION
				"Rack phase A output apparent power. The value ranges from -12000 to 12000. 
				The value is accurate to one decimal place on the NetEco. The unit is kVA."
			::= { hwUpsOutputEntry 11 }

		
		-- 1.3.6.1.4.1.2011.6.174.1.4.100.1.12
		hwUpsOutputAppearancePowerB OBJECT-TYPE
			SYNTAX Integer32 (-12000..12000)
			UNITS "kVA"
			MAX-ACCESS read-only
			STATUS current
			DESCRIPTION
				"Rack phase B output apparent power. The value ranges from -12000 to 12000. 
				The value is accurate to one decimal place on the NetEco. The unit is kVA."
			::= { hwUpsOutputEntry 12 }

		
		-- 1.3.6.1.4.1.2011.6.174.1.4.100.1.13
		hwUpsOutputAppearancePowerC OBJECT-TYPE
			SYNTAX Integer32 (-12000..12000)
			UNITS "kVA"
			MAX-ACCESS read-only
			STATUS current
			DESCRIPTION
				"Rack phase C output apparent power. The value ranges from -12000 to 12000. 
				The value is accurate to one decimal place on the NetEco. The unit is kVA."
			::= { hwUpsOutputEntry 13 }

		
		-- 1.3.6.1.4.1.2011.6.174.1.4.100.1.14
		hwUpsOutputLoadA OBJECT-TYPE
			SYNTAX Unsigned32 (0..5000)
			UNITS "%"
			MAX-ACCESS read-only
			STATUS current
			DESCRIPTION
				"Rack phase A output load ratio. The value ranges from 0 to 5000 The value is accurate to one decimal place on the NetEco."
			::= { hwUpsOutputEntry 14 }

		
		-- 1.3.6.1.4.1.2011.6.174.1.4.100.1.15
		hwUpsOutputLoadB OBJECT-TYPE
			SYNTAX Unsigned32 (0..5000)
			UNITS "%"
			MAX-ACCESS read-only
			STATUS current
			DESCRIPTION
				"Rack phase B output load ratio. The value ranges from 0 to 5000 The value is accurate to one decimal place on the NetEco."
			::= { hwUpsOutputEntry 15 }

		
		-- 1.3.6.1.4.1.2011.6.174.1.4.100.1.16
		hwUpsOutputLoadC OBJECT-TYPE
			SYNTAX Unsigned32 (0..5000)
			UNITS "%"
			MAX-ACCESS read-only
			STATUS current
			DESCRIPTION
				"Rack phase C output load ratio. The value ranges from 0 to 5000 The value is accurate to one decimal place on the NetEco."
			::= { hwUpsOutputEntry 16 }

		
		-- 1.3.6.1.4.1.2011.6.174.1.4.100.1.17
		hwUpsOutputPowerRating OBJECT-TYPE
			SYNTAX INTEGER
				{
				level200(1),
				level208(2),
				level220(3),
				level380(4),
				level400(5),
				level415(6),
				level480(7),
				level600(8),
				level690(9)
				}
			UNITS "V"
			MAX-ACCESS read-only
			STATUS current
			DESCRIPTION
				"Rated output voltage (system voltage level). Enumeration type. The default value is 6. The unit is V.
				Value 1 indicates 200 V.
				Value 2 indicates 208 V.
				Value 3 indicates 220 V. 
				Value 4 indicates 380 V.
				Value 5 indicates 400 V.
				Value 6 indicates 415 V.
				Value 7 indicates 480 V.
				Value 8 indicates 600 V.
				Value 9 indicates 690 V."
			::= { hwUpsOutputEntry 17 }

		
		-- 1.3.6.1.4.1.2011.6.174.1.4.100.1.18
		hwUpsOutputFrequencyRating OBJECT-TYPE
			SYNTAX INTEGER
				{
				level50(1),
				level60(2)
				}
			UNITS "Hz"
			MAX-ACCESS read-only
			STATUS current
			DESCRIPTION
				"Rated output frequency. Enumeration type. The default value is 2. The unit is Hz.
				Value 1 indicates 50 Hz.
				Value 2 indicates 60 Hz."
			::= { hwUpsOutputEntry 18 }

		
		-- 1.3.6.1.4.1.2011.6.174.1.4.100.1.19
		hwUpsOutputPowerFactorA OBJECT-TYPE
			SYNTAX Integer32 (-100..100)
			MAX-ACCESS read-only
			STATUS current
			DESCRIPTION
				"Rack phase A output power factor. 
				The value ranges from -100 to 100 The value is accurate to two decimal place on the NetEco."
			::= { hwUpsOutputEntry 19 }

		
		-- 1.3.6.1.4.1.2011.6.174.1.4.100.1.20
		hwUpsOutputPowerFactorB OBJECT-TYPE
			SYNTAX Integer32 (-100..100)
			MAX-ACCESS read-only
			STATUS current
			DESCRIPTION
				"Rack phase B output power factor. 
				The value ranges from -100 to 100 The value is accurate to two decimal place on the NetEco."
			::= { hwUpsOutputEntry 20 }

		
		-- 1.3.6.1.4.1.2011.6.174.1.4.100.1.21
		hwUpsOutputPowerFactorC OBJECT-TYPE
			SYNTAX Integer32 (-100..100)
			MAX-ACCESS read-only
			STATUS current
			DESCRIPTION
				"Rack phase C output power factor. 
				The value ranges from -100 to 100 The value is accurate to two decimal place on the NetEco."
			::= { hwUpsOutputEntry 21 }

		
		-- 1.3.6.1.4.1.2011.6.174.1.4.100.1.100
		hwUpsOutputRowStatus OBJECT-TYPE
			SYNTAX RowStatus
			MAX-ACCESS read-only
			STATUS current
			DESCRIPTION
				"RowStatus of UPS output information table."
			::= { hwUpsOutputEntry 100 }

		
		-- 1.3.6.1.4.1.2011.6.174.1.5
		hwUpsBypass OBJECT IDENTIFIER ::= { hwUpsMIBObjects 5 }

		
		-- 1.3.6.1.4.1.2011.6.174.1.5.100
		hwUpsBypassTable OBJECT-TYPE
			SYNTAX SEQUENCE OF HwUpsBypassEntry
			MAX-ACCESS not-accessible
			STATUS current
			DESCRIPTION
				"UPS bypass information table. It's index is hwUpsDeviceId."
			::= { hwUpsBypass 100 }

		
		-- 1.3.6.1.4.1.2011.6.174.1.5.100.1
		hwUpsBypassEntry OBJECT-TYPE
			SYNTAX HwUpsBypassEntry
			MAX-ACCESS not-accessible
			STATUS current
			DESCRIPTION
				"Bypass information table entry."
			INDEX { hwUpsDeviceId }
			::= { hwUpsBypassTable 1 }

		
		HwUpsBypassEntry ::=
			SEQUENCE { 
				hwUpsBypassInputVoltageA
					Unsigned32,
				hwUpsBypassInputVoltageB
					Unsigned32,
				hwUpsBypassInputVoltageC
					Unsigned32,
				hwUpsBypassInputFrequency
					Unsigned32,
				hwUpsBypassRowStatus
					RowStatus
			 }

		-- 1.3.6.1.4.1.2011.6.174.1.5.100.1.1
		hwUpsBypassInputVoltageA OBJECT-TYPE
			SYNTAX Unsigned32 (0..10000)
			UNITS "V"
			MAX-ACCESS read-only
			STATUS current
			DESCRIPTION
				"Bypass input voltage phase A. The value ranges from 0 to 10000 
				The value is accurate to one decimal place on the NetEco. The unit is V."
			::= { hwUpsBypassEntry 1 }

		
		-- 1.3.6.1.4.1.2011.6.174.1.5.100.1.2
		hwUpsBypassInputVoltageB OBJECT-TYPE
			SYNTAX Unsigned32 (0..10000)
			UNITS "V"
			MAX-ACCESS read-only
			STATUS current
			DESCRIPTION
				"Bypass input voltage phase B. The value ranges from 0 to 10000 
				The value is accurate to one decimal place on the NetEco. The unit is V."
			::= { hwUpsBypassEntry 2 }

		
		-- 1.3.6.1.4.1.2011.6.174.1.5.100.1.3
		hwUpsBypassInputVoltageC OBJECT-TYPE
			SYNTAX Unsigned32 (0..10000)
			UNITS "V"
			MAX-ACCESS read-only
			STATUS current
			DESCRIPTION
				"Bypass input voltage phase C. The value ranges from 0 to 10000 
				The value is accurate to one decimal place on the NetEco. The unit is V."
			::= { hwUpsBypassEntry 3 }

		
		-- 1.3.6.1.4.1.2011.6.174.1.5.100.1.4
		hwUpsBypassInputFrequency OBJECT-TYPE
			SYNTAX Unsigned32 (0..10000)
			UNITS "Hz"
			MAX-ACCESS read-only
			STATUS current
			DESCRIPTION
				"Bypass input frequency. The value ranges from 0 to 10000 
				The value is accurate to two decimal place on the NetEco. The unit is Hz."
			::= { hwUpsBypassEntry 4 }

		
		-- 1.3.6.1.4.1.2011.6.174.1.5.100.1.100
		hwUpsBypassRowStatus OBJECT-TYPE
			SYNTAX RowStatus
			MAX-ACCESS read-only
			STATUS current
			DESCRIPTION
				"RowStatus of UPS bypass information table."
			::= { hwUpsBypassEntry 100 }

		
		-- 1.3.6.1.4.1.2011.6.174.1.6
		hwUpsBattery OBJECT IDENTIFIER ::= { hwUpsMIBObjects 6 }

		
		-- 1.3.6.1.4.1.2011.6.174.1.6.100
		hwUpsBatteryTable OBJECT-TYPE
			SYNTAX SEQUENCE OF HwUpsBatteryEntry
			MAX-ACCESS not-accessible
			STATUS current
			DESCRIPTION
				"UPS battery information table. It's index is hwUpsDeviceId."
			::= { hwUpsBattery 100 }

		
		-- 1.3.6.1.4.1.2011.6.174.1.6.100.1
		hwUpsBatteryEntry OBJECT-TYPE
			SYNTAX HwUpsBatteryEntry
			MAX-ACCESS not-accessible
			STATUS current
			DESCRIPTION
				"Battery information table entry.Its index is hwUpsDeviceId."
			INDEX { hwUpsDeviceId }
			::= { hwUpsBatteryTable 1 }

		
		HwUpsBatteryEntry ::=
			SEQUENCE { 
				hwUpsBatteryVoltage
					Unsigned32,
				hwUpsBatteryCurrent
					Integer32,
				hwUpsBatteryCapacityLeft
					Unsigned32,
				hwUpsBatteryBackupTime
					Unsigned32,
				hwUpsBatteryNumber
					Unsigned32,
				hwUpsBatterytemperature
					Integer32,
				hwUpsBatteryRowStatus
					RowStatus
			 }

		-- 1.3.6.1.4.1.2011.6.174.1.6.100.1.1
		hwUpsBatteryVoltage OBJECT-TYPE
			SYNTAX Unsigned32 (0..20000)
			UNITS "V"
			MAX-ACCESS read-only
			STATUS current
			DESCRIPTION
				"Battery Voltage. It is a real-time analog parameter. 
				Value range: 0 to 20000, Unit: V, and the value is accurate to one decimal place (.1). "
			::= { hwUpsBatteryEntry 1 }

		
		-- 1.3.6.1.4.1.2011.6.174.1.6.100.1.2
		hwUpsBatteryCurrent OBJECT-TYPE
			SYNTAX Integer32 (-60000..60000)
			UNITS "A"
			MAX-ACCESS read-only
			STATUS current
			DESCRIPTION
				"Battery Total Current. It is a real-time analog parameter. 
				Value range: -60000 to 60000, Unit: A, and the value is accurate to one decimal place (.1). "
			::= { hwUpsBatteryEntry 2 }

		
		-- 1.3.6.1.4.1.2011.6.174.1.6.100.1.3
		hwUpsBatteryCapacityLeft OBJECT-TYPE
			SYNTAX Unsigned32 (0..100)
			UNITS "%"
			MAX-ACCESS read-only
			STATUS current
			DESCRIPTION
				"Battery Capacity Left. Value range: 0 to 100, Unit: %, and the value is an integer."
			::= { hwUpsBatteryEntry 3 }

		
		-- 1.3.6.1.4.1.2011.6.174.1.6.100.1.4
		hwUpsBatteryBackupTime OBJECT-TYPE
			SYNTAX Unsigned32 (0..172800)
			UNITS "S"
			MAX-ACCESS read-only
			STATUS current
			DESCRIPTION
				"Battery Backup Time. Value range: 0 to 172800, Unit: S, and the value is an integer."
			::= { hwUpsBatteryEntry 4 }

		
		-- 1.3.6.1.4.1.2011.6.174.1.6.100.1.5
		hwUpsBatteryNumber OBJECT-TYPE
			SYNTAX Unsigned32 (1..240)
			MAX-ACCESS read-only
			STATUS obsolete
			DESCRIPTION
				"Battery group number.Value range: 1 to 240,and the value is an integer."
			::= { hwUpsBatteryEntry 5 }

		
		-- 1.3.6.1.4.1.2011.6.174.1.6.100.1.6
		hwUpsBatterytemperature OBJECT-TYPE
			SYNTAX Integer32 (-200..800)
			UNITS "℃"
			MAX-ACCESS read-only
			STATUS current
			DESCRIPTION
				"Battery temperature.Value range: -20 to 80, Unit:℃,  and the value is accurate to one decimal place (.1). "
			::= { hwUpsBatteryEntry 6 }

		
		-- 1.3.6.1.4.1.2011.6.174.1.6.100.1.100
		hwUpsBatteryRowStatus OBJECT-TYPE
			SYNTAX RowStatus
			MAX-ACCESS read-only
			STATUS current
			DESCRIPTION
				"RowStatus of UPS battery information table."
			::= { hwUpsBatteryEntry 100 }

		
		-- 1.3.6.1.4.1.2011.6.174.1.10
		hwUpsParallelSystem OBJECT IDENTIFIER ::= { hwUpsMIBObjects 10 }

		
		-- 1.3.6.1.4.1.2011.6.174.1.10.1
		hwUpsParaSysTable OBJECT-TYPE
			SYNTAX SEQUENCE OF HwUpsParaSysEntry
			MAX-ACCESS not-accessible
			STATUS current
			DESCRIPTION
				"UPS parallel system table. Its index is hwUpsDeviceId."
			::= { hwUpsParallelSystem 1 }

		
		-- 1.3.6.1.4.1.2011.6.174.1.10.1.1
		hwUpsParaSysEntry OBJECT-TYPE
			SYNTAX HwUpsParaSysEntry
			MAX-ACCESS not-accessible
			STATUS current
			DESCRIPTION
				"UPS parallel system table entry."
			INDEX { hwUpsDeviceId }
			::= { hwUpsParaSysTable 1 }

		
		HwUpsParaSysEntry ::=
			SEQUENCE { 
				hwUpsParaSysId
					Unsigned32,
				hwUpsParaSysOutActivePowA
					Integer32,
				hwUpsParaSysOutActivePowB
					Integer32,
				hwUpsParaSysOutActivePowC
					Integer32,
				hwUpsParaSysOutAppearPowA
					Integer32,
				hwUpsParaSysOutAppearPowB
					Integer32,
				hwUpsParaSysOutAppearPowC
					Integer32,
				hwUpsParaSysOutLoadFactorA
					Unsigned32,
				hwUpsParaSysOutLoadFactorB
					Unsigned32,
				hwUpsParaSysOutLoadFactorC
					Unsigned32,
				hwUpsParallelSystemRowStatus
					RowStatus
			 }

		-- 1.3.6.1.4.1.2011.6.174.1.10.1.1.1
		hwUpsParaSysId OBJECT-TYPE
			SYNTAX Unsigned32 (0..127)
			MAX-ACCESS read-only
			STATUS current
			DESCRIPTION
				"ID of the parallel system that the current rack belongs to. "
			::= { hwUpsParaSysEntry 1 }

		
		-- 1.3.6.1.4.1.2011.6.174.1.10.1.1.2
		hwUpsParaSysOutActivePowA OBJECT-TYPE
			SYNTAX Integer32 (-120000..120000)
			UNITS "kW"
			MAX-ACCESS read-only
			STATUS current
			DESCRIPTION
				"System phase A output active power.The value ranges from -12000 to 12000, 
				The value is accurate to one decimal place on the NetEco. The unit is kW."
			::= { hwUpsParaSysEntry 2 }

		
		-- 1.3.6.1.4.1.2011.6.174.1.10.1.1.3
		hwUpsParaSysOutActivePowB OBJECT-TYPE
			SYNTAX Integer32 (-120000..120000)
			UNITS "kW"
			MAX-ACCESS read-only
			STATUS current
			DESCRIPTION
				"System phase B output active power.The value ranges from -12000 to 12000, 
				The value is accurate to one decimal place on the NetEco. The unit is kW."
			::= { hwUpsParaSysEntry 3 }

		
		-- 1.3.6.1.4.1.2011.6.174.1.10.1.1.4
		hwUpsParaSysOutActivePowC OBJECT-TYPE
			SYNTAX Integer32 (-120000..120000)
			UNITS "kW"
			MAX-ACCESS read-only
			STATUS current
			DESCRIPTION
				"System phase C output active power.The value ranges from -12000 to 12000, 
				The value is accurate to one decimal place on the NetEco. The unit is kW."
			::= { hwUpsParaSysEntry 4 }

		
		-- 1.3.6.1.4.1.2011.6.174.1.10.1.1.5
		hwUpsParaSysOutAppearPowA OBJECT-TYPE
			SYNTAX Integer32 (-120000..120000)
			UNITS "kVA"
			MAX-ACCESS read-only
			STATUS current
			DESCRIPTION
				"System phase A output apparent power.The value ranges from -12000 to 12000, 
				The value is accurate to one decimal place on the NetEco. The unit is kVA."
			::= { hwUpsParaSysEntry 5 }

		
		-- 1.3.6.1.4.1.2011.6.174.1.10.1.1.6
		hwUpsParaSysOutAppearPowB OBJECT-TYPE
			SYNTAX Integer32 (-120000..120000)
			UNITS "kVA"
			MAX-ACCESS read-only
			STATUS current
			DESCRIPTION
				"System phase B output apparent power.The value ranges from -12000 to 12000, 
				The value is accurate to one decimal place on the NetEco. The unit is kVA."
			::= { hwUpsParaSysEntry 6 }

		
		-- 1.3.6.1.4.1.2011.6.174.1.10.1.1.7
		hwUpsParaSysOutAppearPowC OBJECT-TYPE
			SYNTAX Integer32 (-120000..120000)
			UNITS "kVA"
			MAX-ACCESS read-only
			STATUS current
			DESCRIPTION
				"System phase C output apparent power.The value ranges from -12000 to 12000, 
				The value is accurate to one decimal place on the NetEco. The unit is kVA."
			::= { hwUpsParaSysEntry 7 }

		
		-- 1.3.6.1.4.1.2011.6.174.1.10.1.1.8
		hwUpsParaSysOutLoadFactorA OBJECT-TYPE
			SYNTAX Unsigned32 (0..5000)
			UNITS "%"
			MAX-ACCESS read-only
			STATUS current
			DESCRIPTION
				"System A output load factor.The value ranges from 0 to 500, 
				The value is accurate to one decimal place on the NetEco. The unit is %."
			::= { hwUpsParaSysEntry 8 }

		
		-- 1.3.6.1.4.1.2011.6.174.1.10.1.1.9
		hwUpsParaSysOutLoadFactorB OBJECT-TYPE
			SYNTAX Unsigned32 (0..5000)
			UNITS "%"
			MAX-ACCESS read-only
			STATUS current
			DESCRIPTION
				"System B output load factor.The value ranges from 0 to 500, 
				The value is accurate to one decimal place on the NetEco. The unit is %."
			::= { hwUpsParaSysEntry 9 }

		
		-- 1.3.6.1.4.1.2011.6.174.1.10.1.1.10
		hwUpsParaSysOutLoadFactorC OBJECT-TYPE
			SYNTAX Unsigned32 (0..5000)
			UNITS "%"
			MAX-ACCESS read-only
			STATUS current
			DESCRIPTION
				"System C output load factor.The value ranges from 0 to 500, 
				The value is accurate to one decimal place on the NetEco. The unit is %."
			::= { hwUpsParaSysEntry 10 }

		
		-- 1.3.6.1.4.1.2011.6.174.1.10.1.1.100
		hwUpsParallelSystemRowStatus OBJECT-TYPE
			SYNTAX RowStatus
			MAX-ACCESS read-only
			STATUS current
			DESCRIPTION
				"RowStatus of ups parallel System Identification table."
			::= { hwUpsParaSysEntry 100 }

		
		-- 1.3.6.1.4.1.2011.6.174.1.11
		hwUpsSiteTime OBJECT IDENTIFIER ::= { hwUpsMIBObjects 11 }

		
		-- 1.3.6.1.4.1.2011.6.174.1.11.1
		hwUpsSiteTimeUTC OBJECT-TYPE
			SYNTAX Unsigned32 (0..4294967295)
			MAX-ACCESS read-write
			STATUS current
			DESCRIPTION
				"UTC time, ranging from 0 to 4294967295.  The unit is seconds."
			::= { hwUpsSiteTime 1 }

		
		-- 1.3.6.1.4.1.2011.6.174.1.11.2
		hwUpsSiteTimeZone OBJECT-TYPE
			SYNTAX Unsigned32
			MAX-ACCESS read-write
			STATUS current
			DESCRIPTION
				"UTC time zone that the current rack belongs to. "
			::= { hwUpsSiteTime 2 }

		
		-- 1.3.6.1.4.1.2011.6.174.1.12
		hwUpsAlarm OBJECT IDENTIFIER ::= { hwUpsMIBObjects 12 }

		
		-- 1.3.6.1.4.1.2011.6.174.1.12.1
		hwUpsAlarmSynchronNum OBJECT-TYPE
			SYNTAX Unsigned32 (0..4294967295)
			MAX-ACCESS read-write
			STATUS current
			DESCRIPTION
				"Alarm synchronization ID. The value ranges from 0 to 4294967295. 
				This value is used by the NetEco to obtain the active alarm synchronization ID and synchronize alarms."
			::= { hwUpsAlarm 1 }

		
		-- 1.3.6.1.4.1.2011.6.174.1.12.2
		hwUpsAlarmCurrActiveNum OBJECT-TYPE
			SYNTAX Unsigned32 (0..8000)
			MAX-ACCESS read-only
			STATUS current
			DESCRIPTION
				"Number of active alarms, ranging from 0 to 8000."
			::= { hwUpsAlarm 2 }

		
		-- 1.3.6.1.4.1.2011.6.174.1.13
		hwUpsActiveAlarm OBJECT IDENTIFIER ::= { hwUpsMIBObjects 13 }

		
		-- 1.3.6.1.4.1.2011.6.174.1.13.1
		hwUpsActiveAlarmTable OBJECT-TYPE
			SYNTAX SEQUENCE OF HwUpsActiveAlarmEntry
			MAX-ACCESS not-accessible
			STATUS current
			DESCRIPTION
				"UPS active alarm table. It's indexs are hwUpsActiveAlarmDeviceId and hwUpsActiveAlarmSeqId"
			::= { hwUpsActiveAlarm 1 }

		
		-- 1.3.6.1.4.1.2011.6.174.1.13.1.1
		hwUpsActiveAlarmEntry OBJECT-TYPE
			SYNTAX HwUpsActiveAlarmEntry
			MAX-ACCESS not-accessible
			STATUS current
			DESCRIPTION
				"UPS active alarm table "
			INDEX { hwUpsActiveAlarmDeviceId, hwUpsActiveAlarmSeqId }
			::= { hwUpsActiveAlarmTable 1 }

		
		HwUpsActiveAlarmEntry ::=
			SEQUENCE { 
				hwUpsActiveAlarmDeviceId
					Unsigned32,
				hwUpsActiveAlarmSeqId
					Unsigned32,
				hwUpsActiveAlarmEquipID
					Unsigned32,
				hwUpsActiveAlarmID
					Unsigned32,
				hwUpsActiveAlarmReasonId
					Unsigned32,
				hwUpsActiveAlarmText
					OCTET STRING,
				hwUpsActiveAlarmLevel
					INTEGER,
				hwUpsActiveAlarmFlag
					INTEGER,
				hwUpsActiveAlarmSynchronNum
					Unsigned32,
				hwUpsActiveAlarmTime
					Unsigned32,
				hwUpsActiveAlarmRowStatus
					RowStatus
			 }

		-- 1.3.6.1.4.1.2011.6.174.1.13.1.1.1
		hwUpsActiveAlarmDeviceId OBJECT-TYPE
			SYNTAX Unsigned32 (1..100)
			MAX-ACCESS read-only
			STATUS current
			DESCRIPTION
				"ID of the device on which the active alarm is generated. An integer ranging from 1 to 100."
			::= { hwUpsActiveAlarmEntry 1 }

		
		-- 1.3.6.1.4.1.2011.6.174.1.13.1.1.2
		hwUpsActiveAlarmSeqId OBJECT-TYPE
			SYNTAX Unsigned32 (1..4294967295)
			MAX-ACCESS read-only
			STATUS current
			DESCRIPTION
				"Sequence number of an active alarm, ranging from 1 to 4294967295. "
			::= { hwUpsActiveAlarmEntry 2 }

		
		-- 1.3.6.1.4.1.2011.6.174.1.13.1.1.3
		hwUpsActiveAlarmEquipID OBJECT-TYPE
			SYNTAX Unsigned32 (0..154)
			MAX-ACCESS read-only
			STATUS current
			DESCRIPTION
				"Active alarm module ID, ranging from 1 to 154. "
			::= { hwUpsActiveAlarmEntry 3 }

		
		-- 1.3.6.1.4.1.2011.6.174.1.13.1.1.4
		hwUpsActiveAlarmID OBJECT-TYPE
			SYNTAX Unsigned32 (0..4294967295)
			MAX-ACCESS read-only
			STATUS current
			DESCRIPTION
				"ID of an active alarm, ranging from 0 to 4294967295. "
			::= { hwUpsActiveAlarmEntry 4 }

		
		-- 1.3.6.1.4.1.2011.6.174.1.13.1.1.5
		hwUpsActiveAlarmReasonId OBJECT-TYPE
			SYNTAX Unsigned32 (0..100)
			MAX-ACCESS read-only
			STATUS current
			DESCRIPTION
				"Reason ID of an active alarm, ranging from 1 to 100."
			::= { hwUpsActiveAlarmEntry 5 }

		
		-- 1.3.6.1.4.1.2011.6.174.1.13.1.1.6
		hwUpsActiveAlarmText OBJECT-TYPE
			SYNTAX OCTET STRING (SIZE (0..127))
			MAX-ACCESS read-only
			STATUS current
			DESCRIPTION
				"English name of an active alarm. A string of characters. "
			::= { hwUpsActiveAlarmEntry 6 }

		
		-- 1.3.6.1.4.1.2011.6.174.1.13.1.1.7
		hwUpsActiveAlarmLevel OBJECT-TYPE
			SYNTAX INTEGER
				{
				critical(1),
				major(2),
				minor(3),
				warning(4)
				}
			MAX-ACCESS read-only
			STATUS current
			DESCRIPTION
				"Severity of an active alarm. Enumeration type.
				Value 1 indicates a critical alarm.
				Value 2 indicates a major alarm.
				Value 3 indicates a minor alarm.
				Value 4 indicates a warning."
			::= { hwUpsActiveAlarmEntry 7 }

		
		-- 1.3.6.1.4.1.2011.6.174.1.13.1.1.8
		hwUpsActiveAlarmFlag OBJECT-TYPE
			SYNTAX INTEGER
				{
				occur(1),
				resume(2)
				}
			MAX-ACCESS read-only
			STATUS current
			DESCRIPTION
				"Flag bit of an active alarm. Enumeration type.
				Value 1 indicates that an active alarm is generated.
				Value 2 indicates that an active alarm is cleared."
			::= { hwUpsActiveAlarmEntry 8 }

		
		-- 1.3.6.1.4.1.2011.6.174.1.13.1.1.9
		hwUpsActiveAlarmSynchronNum OBJECT-TYPE
			SYNTAX Unsigned32 (0..4294967295)
			MAX-ACCESS read-only
			STATUS current
			DESCRIPTION
				"Active alarm synchronization ID, ranging from 0 to 4294967295."
			::= { hwUpsActiveAlarmEntry 9 }

		
		-- 1.3.6.1.4.1.2011.6.174.1.13.1.1.10
		hwUpsActiveAlarmTime OBJECT-TYPE
			SYNTAX Unsigned32 (0..4294967295)
			MAX-ACCESS read-only
			STATUS current
			DESCRIPTION
				"Time when an active alarm is generated, ranging from 0 to 4294967295. The unit is seconds."
			::= { hwUpsActiveAlarmEntry 10 }

		
		-- 1.3.6.1.4.1.2011.6.174.1.13.1.1.11
		hwUpsActiveAlarmRowStatus OBJECT-TYPE
			SYNTAX RowStatus
			MAX-ACCESS read-only
			STATUS current
			DESCRIPTION
				"RowStatus of ups active alarm table."
			::= { hwUpsActiveAlarmEntry 11 }

		
		-- 1.3.6.1.4.1.2011.6.174.1.102
		hwUpsControl OBJECT IDENTIFIER ::= { hwUpsMIBObjects 102 }

		
		-- 1.3.6.1.4.1.2011.6.174.1.102.100
		hwUpsControlTable OBJECT-TYPE
			SYNTAX SEQUENCE OF HwUpsControlEntry
			MAX-ACCESS not-accessible
			STATUS current
			DESCRIPTION
				"UPS control table. It's index is hwUpsRackId."
			::= { hwUpsControl 100 }

		
		-- 1.3.6.1.4.1.2011.6.174.1.102.100.1
		hwUpsControlEntry OBJECT-TYPE
			SYNTAX HwUpsControlEntry
			MAX-ACCESS not-accessible
			STATUS current
			DESCRIPTION
				"Control table entry."
			INDEX { hwUpsDeviceId }
			::= { hwUpsControlTable 1 }

		
		HwUpsControlEntry ::=
			SEQUENCE { 
				hwUpsCtrlECOSwitch
					INTEGER,
				hwUpsCtrlPowerOn
					INTEGER,
				hwUpsCtrlPowerOff
					INTEGER,
				hwUpsCtrlPowerOffDelay
					Unsigned32,
				hwUpsCtrlPowerBatCapacity
					Unsigned32,
				hwUpsCtrlPowerBatType
					INTEGER,
				hwUpsCtrlModelType
					INTEGER,
				hwUpsCtrlInputStandard
					INTEGER,
				hwUpsCtrlOutputStandard
					INTEGER,
				hwUpsCtrlPowerOnState
					INTEGER,
				hwUpsCtrlBatteryToBoostState
					INTEGER,
				hwUpsCtrlBatteryToFloatState
					INTEGER,
				hwUpsCtrlBatteryToTestState
					INTEGER,
				hwUpsCtrlBatteryStopTestState
					INTEGER,
				hwUpsCtrlBatteryManualBoostCharge
					INTEGER,
				hwUpsCtrlBatteryManualFloatCharge
					INTEGER,
				hwUpsCtrlBatteryShallowTest
					INTEGER,
				hwUpsCtrlBatteryVerifyCapTest
					INTEGER,
				hwUpsCtrlBatteryEndTest
					INTEGER,
				hwUpsCtrlModelCapacity
					Unsigned32,
				hwUpsCtrlEPO
					INTEGER,
				hwUpsSmartParallelSleepMode
					INTEGER,
				hwUpsCtrlRowStatus
					RowStatus
			 }

		-- 1.3.6.1.4.1.2011.6.174.1.102.100.1.1
		hwUpsCtrlECOSwitch OBJECT-TYPE
			SYNTAX INTEGER
				{
				noECO(1),
				eco(2)
				}
			MAX-ACCESS read-only
			STATUS current
			DESCRIPTION
				"ECO settings. Enumeration type. The default value is 1.
				Value 1 indicates ECO mode.
				Value 2 indicates Non ECO mode."
			::= { hwUpsControlEntry 1 }

		
		-- 1.3.6.1.4.1.2011.6.174.1.102.100.1.2
		hwUpsCtrlPowerOn OBJECT-TYPE
			SYNTAX INTEGER
				{
				powerOn(1),
				unknown(255)
				}
			MAX-ACCESS read-write
			STATUS current
			DESCRIPTION
				"Power on settings. Enumeration type. 
				Value 1 indicates power on .
				Value 2 indicates unknow."
			::= { hwUpsControlEntry 2 }

		
		-- 1.3.6.1.4.1.2011.6.174.1.102.100.1.3
		hwUpsCtrlPowerOff OBJECT-TYPE
			SYNTAX INTEGER
				{
				powerOff(1),
				unknown(255)
				}
			MAX-ACCESS read-write
			STATUS current
			DESCRIPTION
				"Power off settings. Enumeration type. 
				Value 1 indicates power off .
				Value 2 indicates unknow."
			::= { hwUpsControlEntry 3 }

		
		-- 1.3.6.1.4.1.2011.6.174.1.102.100.1.4
		hwUpsCtrlPowerOffDelay OBJECT-TYPE
			SYNTAX Unsigned32 (0..120000000)
			UNITS "S"
			MAX-ACCESS read-write
			STATUS current
			DESCRIPTION
				"Delay power off.The value ranges from 0 to 120000000 . The unit is S."
			::= { hwUpsControlEntry 4 }

		
		-- 1.3.6.1.4.1.2011.6.174.1.102.100.1.5
		hwUpsCtrlPowerBatCapacity OBJECT-TYPE
			SYNTAX Unsigned32 (5..3000)
			UNITS "AH"
			MAX-ACCESS read-only
			STATUS current
			DESCRIPTION
				"Battery capacity, ranging from 5 to 3000. "
			::= { hwUpsControlEntry 5 }

		
		-- 1.3.6.1.4.1.2011.6.174.1.102.100.1.6
		hwUpsCtrlPowerBatType OBJECT-TYPE
			SYNTAX INTEGER { vrla(1) }
			MAX-ACCESS read-only
			STATUS current
			DESCRIPTION
				"Battery type.ECO settings. Enumeration type. The default value is 1.
				Value 1 indicates VRLA batteries."
			::= { hwUpsControlEntry 6 }

		
		-- 1.3.6.1.4.1.2011.6.174.1.102.100.1.7
		hwUpsCtrlModelType OBJECT-TYPE
			SYNTAX INTEGER
				{
				model6K(17),
				mode110K(33),
				model20K(65)
				}
			MAX-ACCESS read-only
			STATUS current
			DESCRIPTION
				"Model type,Enumeration type. 
				Value 17 indicates 6K.
				Value 33 indicates 10K.
				Value 65 indicates 20K."
			::= { hwUpsControlEntry 7 }

		
		-- 1.3.6.1.4.1.2011.6.174.1.102.100.1.8
		hwUpsCtrlInputStandard OBJECT-TYPE
			SYNTAX INTEGER
				{
				singlePhase(1),
				threePhase(2)
				}
			MAX-ACCESS read-only
			STATUS current
			DESCRIPTION
				"Input Standard,Enumeration type. 
				Value 1 indicates single phase.
				Value 2 indicates three phase."
			::= { hwUpsControlEntry 8 }

		
		-- 1.3.6.1.4.1.2011.6.174.1.102.100.1.9
		hwUpsCtrlOutputStandard OBJECT-TYPE
			SYNTAX INTEGER
				{
				singlePhase(1),
				threePhase(2)
				}
			MAX-ACCESS read-only
			STATUS current
			DESCRIPTION
				"Output Standard,Enumeration type. 
				Value 1 indicates single phase.
				Value 2 indicates three phase."
			::= { hwUpsControlEntry 9 }

		
		-- 1.3.6.1.4.1.2011.6.174.1.102.100.1.10
		hwUpsCtrlPowerOnState OBJECT-TYPE
			SYNTAX INTEGER
				{
				powerOff(1),
				powerOn(2),
				powerOnFail(3),
				powerOnComplete(4)
				}
			MAX-ACCESS read-only
			STATUS current
			DESCRIPTION
				"Power On State,Enumeration type. 
				Value 1 indicates power off.
				Value 2 indicates booting.
				Value 3 indicates failed to power on.
				Value 4 indicates succeed tp power on."
			::= { hwUpsControlEntry 10 }

		
		-- 1.3.6.1.4.1.2011.6.174.1.102.100.1.11
		hwUpsCtrlBatteryToBoostState OBJECT-TYPE
			SYNTAX INTEGER
				{
				enable(1),
				disable(2)
				}
			MAX-ACCESS read-only
			STATUS current
			DESCRIPTION
				"Battery Change to Boost Charge State,Enumeration type. 
				Value 1 indicates enabled.
				Value 2 indicates disabled."
			::= { hwUpsControlEntry 11 }

		
		-- 1.3.6.1.4.1.2011.6.174.1.102.100.1.12
		hwUpsCtrlBatteryToFloatState OBJECT-TYPE
			SYNTAX INTEGER
				{
				enable(1),
				disable(2)
				}
			MAX-ACCESS read-only
			STATUS current
			DESCRIPTION
				"Battery Change to Float Charge State,Enumeration type. 
				Value 1 indicates enabled.
				Value 2 indicates disabled."
			::= { hwUpsControlEntry 12 }

		
		-- 1.3.6.1.4.1.2011.6.174.1.102.100.1.13
		hwUpsCtrlBatteryToTestState OBJECT-TYPE
			SYNTAX INTEGER
				{
				enable(1),
				disable(2)
				}
			MAX-ACCESS read-only
			STATUS current
			DESCRIPTION
				"Battery Change to Test State,Enumeration type. 
				Value 1 indicates enabled.
				Value 2 indicates disabled."
			::= { hwUpsControlEntry 13 }

		
		-- 1.3.6.1.4.1.2011.6.174.1.102.100.1.14
		hwUpsCtrlBatteryStopTestState OBJECT-TYPE
			SYNTAX INTEGER
				{
				enable(1),
				disable(2)
				}
			MAX-ACCESS read-only
			STATUS current
			DESCRIPTION
				"Battery Stop Test State,Enumeration type. 
				Value 1 indicates enabled.
				Value 2 indicates disabled."
			::= { hwUpsControlEntry 14 }

		
		-- 1.3.6.1.4.1.2011.6.174.1.102.100.1.15
		hwUpsCtrlBatteryManualBoostCharge OBJECT-TYPE
			SYNTAX INTEGER
				{
				toBoostCharge(1),
				unknown(255)
				}
			MAX-ACCESS read-write
			STATUS current
			DESCRIPTION
				"Battery Manual to Boost Charge,Enumeration type. 
				Value 1 indicates enabled.
				Value 2 indicates disabled."
			::= { hwUpsControlEntry 15 }

		
		-- 1.3.6.1.4.1.2011.6.174.1.102.100.1.16
		hwUpsCtrlBatteryManualFloatCharge OBJECT-TYPE
			SYNTAX INTEGER
				{
				toFloatCharge(1),
				unknown(255)
				}
			MAX-ACCESS read-write
			STATUS current
			DESCRIPTION
				"Battery Manual to Float Charge,Enumeration type. 
				Value 1 indicates enabled.
				Value 2 indicates unknown"
			::= { hwUpsControlEntry 16 }

		
		-- 1.3.6.1.4.1.2011.6.174.1.102.100.1.17
		hwUpsCtrlBatteryShallowTest OBJECT-TYPE
			SYNTAX INTEGER
				{
				toShallowTest(1),
				unknown(255)
				}
			MAX-ACCESS read-write
			STATUS current
			DESCRIPTION
				"Battery Shallow Test,Enumeration type. 
				Value 1 indicates enabled.
				Value 2 indicates unknown"
			::= { hwUpsControlEntry 17 }

		
		-- 1.3.6.1.4.1.2011.6.174.1.102.100.1.18
		hwUpsCtrlBatteryVerifyCapTest OBJECT-TYPE
			SYNTAX INTEGER
				{
				toVerifyCapTest(1),
				unknown(255)
				}
			MAX-ACCESS read-write
			STATUS current
			DESCRIPTION
				"Battery Verify Cap Test,Enumeration type. 
				Value 1 indicates enabled.
				Value 2 indicates unknown"
			::= { hwUpsControlEntry 18 }

		
		-- 1.3.6.1.4.1.2011.6.174.1.102.100.1.19
		hwUpsCtrlBatteryEndTest OBJECT-TYPE
			SYNTAX INTEGER
				{
				toEndTest(1),
				unknown(255)
				}
			MAX-ACCESS read-write
			STATUS current
			DESCRIPTION
				"Battery End Test,Enumeration type. 
				Value 1 indicates enabled.
				Value 2 indicates unknown"
			::= { hwUpsControlEntry 19 }

		
		-- 1.3.6.1.4.1.2011.6.174.1.102.100.1.20
		hwUpsCtrlModelCapacity OBJECT-TYPE
			SYNTAX Unsigned32 (0..200)
			MAX-ACCESS read-only
			STATUS current
			DESCRIPTION
				"Model Capacity.The value ranges from 0 to 200, The value is accurate to one decimal place on the NetEco. The unit is kVA."
			::= { hwUpsControlEntry 20 }

		
		-- 1.3.6.1.4.1.2011.6.174.1.102.100.1.21
		hwUpsCtrlEPO OBJECT-TYPE
			SYNTAX INTEGER
				{
				epo(1),
				unknown(2)
				}
			MAX-ACCESS read-write
			STATUS current
			DESCRIPTION
				"EPO. Enumeration type. 
				Value 1 indicates EPO .
				Value 255 indicates unknown."
			::= { hwUpsControlEntry 21 }

		
		-- 1.3.6.1.4.1.2011.6.174.1.102.100.1.22
		hwUpsSmartParallelSleepMode OBJECT-TYPE
			SYNTAX INTEGER
				{
				disable(0),
				enable(1)
				}
			MAX-ACCESS read-write
			STATUS current
			DESCRIPTION
				"Smart Parallel Sleep Mode.Enumeration type.The default value is 0.
				Value 0 indicates disable.
				Value 1 indicates enable."
			::= { hwUpsControlEntry 22 }

		
		-- 1.3.6.1.4.1.2011.6.174.1.102.100.1.100
		hwUpsCtrlRowStatus OBJECT-TYPE
			SYNTAX RowStatus
			MAX-ACCESS read-only
			STATUS current
			DESCRIPTION
				"RowStatus of UPS rack control table."
			::= { hwUpsControlEntry 100 }

		
		-- 1.3.6.1.4.1.2011.6.174.1.103
		hwUpsTest OBJECT IDENTIFIER ::= { hwUpsMIBObjects 103 }

		
		-- 1.3.6.1.4.1.2011.6.174.1.103.101
		hwUpsBattScheduleTestTable OBJECT-TYPE
			SYNTAX SEQUENCE OF HwUpsBattScheduleTestEntry
			MAX-ACCESS not-accessible
			STATUS current
			DESCRIPTION
				"Battery schedule test table. It's index is hwUpsDeviceId."
			::= { hwUpsTest 101 }

		
		-- 1.3.6.1.4.1.2011.6.174.1.103.101.1
		hwUpsBattScheduleTestEntry OBJECT-TYPE
			SYNTAX HwUpsBattScheduleTestEntry
			MAX-ACCESS not-accessible
			STATUS current
			DESCRIPTION
				"Battery schedule test table. "
			INDEX { hwUpsDeviceId }
			::= { hwUpsBattScheduleTestTable 1 }

		
		HwUpsBattScheduleTestEntry ::=
			SEQUENCE { 
				hwUpsBattAutoTest
					INTEGER,
				hwUpsBattAutoTestTimeLimit
					INTEGER,
				hwUpsBattAutoTestTimeInterval
					Unsigned32,
				hwUpsBattAutoTestDischargeRate
					Unsigned32,
				hwUpsBattAutoTestEndVol
					Unsigned32,
				hwUpsBattTest
					INTEGER,
				hwUpsBattScheduleTestRowStatus
					RowStatus
			 }

		-- 1.3.6.1.4.1.2011.6.174.1.103.101.1.1
		hwUpsBattAutoTest OBJECT-TYPE
			SYNTAX INTEGER
				{
				disable(1),
				enalbe(2)
				}
			MAX-ACCESS read-write
			STATUS current
			DESCRIPTION
				"Scheduled shallow discharge test enabled or disabled. Enumeration value.
				The value 1 indicates that the test is disabled.
				The value 2 indicates that the test is enabled."
			::= { hwUpsBattScheduleTestEntry 1 }

		
		-- 1.3.6.1.4.1.2011.6.174.1.103.101.1.2
		hwUpsBattAutoTestTimeLimit OBJECT-TYPE
			SYNTAX INTEGER
				{
				from0to6(1),
				from6to12(2),
				from12to18(3),
				from18to24(4)
				}
			MAX-ACCESS read-write
			STATUS current
			DESCRIPTION
				"Scheduled shallow discharge test time. Enumeration value.
				Value 1 indicates 00:00 to 06:00.
				Value 2 indicates 06:00 to 12:00.
				Value 3 indicates 12:00 to 18:00.
				Value 4 indicates 18:00 to 00:00."
			::= { hwUpsBattScheduleTestEntry 2 }

		
		-- 1.3.6.1.4.1.2011.6.174.1.103.101.1.3
		hwUpsBattAutoTestTimeInterval OBJECT-TYPE
			SYNTAX Unsigned32 (30..90)
			UNITS "Day"
			MAX-ACCESS read-write
			STATUS current
			DESCRIPTION
				"Scheduled shallow discharge test interval. An integer ranging from 30 to 90. The unit is days."
			::= { hwUpsBattScheduleTestEntry 3 }

		
		-- 1.3.6.1.4.1.2011.6.174.1.103.101.1.4
		hwUpsBattAutoTestDischargeRate OBJECT-TYPE
			SYNTAX Unsigned32 (10..50)
			MAX-ACCESS read-write
			STATUS current
			DESCRIPTION
				"Shallow discharge test discharge ratio. An integer ranging from 10 to 50. ."
			::= { hwUpsBattScheduleTestEntry 4 }

		
		-- 1.3.6.1.4.1.2011.6.174.1.103.101.1.5
		hwUpsBattAutoTestEndVol OBJECT-TYPE
			SYNTAX Unsigned32 (160..195)
			UNITS "V/Cell"
			MAX-ACCESS read-write
			STATUS current
			DESCRIPTION
				"Maximum battery discharge time. An integer ranging from 160 to 195. The value is accurate to one decimal place on the NetEco. The unit is V/Cell."
			::= { hwUpsBattScheduleTestEntry 5 }

		
		-- 1.3.6.1.4.1.2011.6.174.1.103.101.1.6
		hwUpsBattTest OBJECT-TYPE
			SYNTAX INTEGER
				{
				noTestInit(1),
				stopTest(2),
				scheduleTest(3),
				shallowDsgTest(4),
				verufyDsgTest(5)
				}
			MAX-ACCESS read-write
			STATUS current
			DESCRIPTION
				"If you set the value to shallowDsgTest(4), you can perform a shallow discharge test; if you set the value to verifyDsgTest(5), you can perform a capacity test; if you set the value to stopTest(2), you can stop the test. Other settings are invalid. If you start a test when other tests are in progress, error code 4 is returned.
				During test, you can use this node to obtain the current or previous test type.
				If you have never started the battery test sheduleTest(3), shallowDsgTest(4), or verifyDsgTest(5), this node returns noTestInit(1)."
			::= { hwUpsBattScheduleTestEntry 6 }

		
		-- 1.3.6.1.4.1.2011.6.174.1.103.101.1.100
		hwUpsBattScheduleTestRowStatus OBJECT-TYPE
			SYNTAX RowStatus
			MAX-ACCESS read-only
			STATUS current
			DESCRIPTION
				"RowStatus of UPS Battery control table. "
			::= { hwUpsBattScheduleTestEntry 100 }

		
		-- 1.3.6.1.4.1.2011.6.174.1.104
		hwUpsFtpsTransport OBJECT IDENTIFIER ::= { hwUpsMIBObjects 104 }

		
		-- 1.3.6.1.4.1.2011.6.174.1.104.1
		hwUpsFtpsNode OBJECT IDENTIFIER ::= { hwUpsFtpsTransport 1 }

		
		-- 1.3.6.1.4.1.2011.6.174.1.104.1.1
		hwUpsFtpsTransportID OBJECT-TYPE
			SYNTAX Unsigned32 (1..4294967295)
			MAX-ACCESS read-write
			STATUS obsolete
			DESCRIPTION
				"Ups Ftps Transport Id.Generated by NetEco."
			::= { hwUpsFtpsNode 1 }
-- Ftps Transport Id.Allocated by NetEco.
		
		-- 1.3.6.1.4.1.2011.6.174.1.104.1.2
		hwUpsFtpsExecuteControl OBJECT-TYPE
			SYNTAX INTEGER
				{
				startupNormal(1),
				additionalAcquisitonStart(2),
				stop(3)
				}
			MAX-ACCESS read-write
			STATUS obsolete
			DESCRIPTION
				"Ftps Execute Control.Enumeration type.
				Value 1 indicates Startup Normal.
				Value 2 indicates Additional Acquisiton Start.
				Value 3 indicates Stop."
			::= { hwUpsFtpsNode 2 }

		
		-- 1.3.6.1.4.1.2011.6.174.1.104.1.3
		hwUpsFtpsTransportState OBJECT-TYPE
			SYNTAX INTEGER
				{
				inTrans(1),
				idle(2),
				transComplete(3),
				transFail(4)
				}
			MAX-ACCESS read-write
			STATUS obsolete
			DESCRIPTION
				"Ftps Transport State.Enumeration type.
				Value 1 indicates In Transmission.
				Value 2 indicates Idle.
				Value 3 indicates Transmit Complete.
				Value 4 indicates Transmit Failure."
			::= { hwUpsFtpsNode 3 }

		
		-- 1.3.6.1.4.1.2011.6.174.1.104.1.4
		hwUpsFtpsServerIp OBJECT-TYPE
			SYNTAX OCTET STRING (SIZE (0..128))
			MAX-ACCESS read-write
			STATUS obsolete
			DESCRIPTION
				"Ftps Server Ip.Value Type is OCTET STRING.Value Length range from 0 to 128."
			::= { hwUpsFtpsNode 4 }

		
		-- 1.3.6.1.4.1.2011.6.174.1.104.1.5
		hwUpsFtpsPort OBJECT-TYPE
			SYNTAX Unsigned32 (1..4294967295)
			MAX-ACCESS read-write
			STATUS obsolete
			DESCRIPTION
				"Ftps Port."
			::= { hwUpsFtpsNode 5 }

		
		-- 1.3.6.1.4.1.2011.6.174.1.104.1.6
		hwUpsFtpsUserName OBJECT-TYPE
			SYNTAX OCTET STRING (SIZE (0..128))
			MAX-ACCESS read-write
			STATUS obsolete
			DESCRIPTION
				"Ftps UserName.Value Type is OCTET STRING.Value Length range from 0 to 128."
			::= { hwUpsFtpsNode 6 }

		
		-- 1.3.6.1.4.1.2011.6.174.1.104.1.7
		hwUpsFtpsPassword OBJECT-TYPE
			SYNTAX OCTET STRING (SIZE (0..128))
			MAX-ACCESS read-write
			STATUS obsolete
			DESCRIPTION
				"Ftps Password.Value Type is OCTET STRING.Value Length range from 0 to 128."
			::= { hwUpsFtpsNode 7 }

		
		-- 1.3.6.1.4.1.2011.6.174.1.104.1.8
		hwUpsFtpsFileType OBJECT-TYPE
			SYNTAX INTEGER
				{
				analogData(1),
				dischargeCurve(2),
				elabel(3)
				}
			MAX-ACCESS read-write
			STATUS obsolete
			DESCRIPTION
				"Ftps File Type.Enumeration type.
				Value 1 indicates Analog Data.
				Value 2 indicates Discharge Curve.
				Value 3 indicates Elabel."
			::= { hwUpsFtpsNode 8 }

		
		-- 1.3.6.1.4.1.2011.6.174.1.104.1.9
		hwUpsFtpsCompressedFormat OBJECT-TYPE
			SYNTAX Unsigned32 (0..4294967295)
			MAX-ACCESS read-write
			STATUS obsolete
			DESCRIPTION
				"Ftps File Compressed Format.
				Value 0 indicates Binary.
				Value 1 indicates Txt.
				Value 2 indicates gzip."
			::= { hwUpsFtpsNode 9 }

		
		-- 1.3.6.1.4.1.2011.6.174.1.104.1.10
		hwUpsFtpsFileFullPath OBJECT-TYPE
			SYNTAX OCTET STRING (SIZE (0..128))
			MAX-ACCESS read-write
			STATUS obsolete
			DESCRIPTION
				"Ftps File Full Path.Value Type is OCTET STRING.Value Length range from 0 to 128."
			::= { hwUpsFtpsNode 10 }

		
		-- 1.3.6.1.4.1.2011.6.174.1.104.1.11
		hwUpsFtpsExtendParameter OBJECT-TYPE
			SYNTAX OCTET STRING (SIZE (0..128))
			MAX-ACCESS read-write
			STATUS obsolete
			DESCRIPTION
				"Ftps Extend Parameter."
			::= { hwUpsFtpsNode 11 }

		
		-- 1.3.6.1.4.1.2011.6.174.1.106
		hwUpsCIMMonitormgr OBJECT IDENTIFIER ::= { hwUpsMIBObjects 106 }

		
		-- 1.3.6.1.4.1.2011.6.174.1.106.1
		hwUpsCIMNum OBJECT-TYPE
			SYNTAX Unsigned32 (0..4)
			MAX-ACCESS read-only
			STATUS current
			DESCRIPTION
				"Ups CIM Num.Value range from 0 to 4."
			::= { hwUpsCIMMonitormgr 1 }

		
		-- 1.3.6.1.4.1.2011.6.174.1.106.2
		hwUpsCIM1BIMNum OBJECT-TYPE
			SYNTAX Unsigned32 (0..300)
			MAX-ACCESS read-write
			STATUS current
			DESCRIPTION
				"Ups BIM Num in CIM1.Value range from 0 to 300."
			::= { hwUpsCIMMonitormgr 2 }

		
		-- 1.3.6.1.4.1.2011.6.174.1.106.3
		hwUpsCIM2BIMNum OBJECT-TYPE
			SYNTAX Unsigned32 (0..300)
			MAX-ACCESS read-only
			STATUS current
			DESCRIPTION
				"Ups BIM Num in CIM2.Value range from 0 to 300."
			::= { hwUpsCIMMonitormgr 3 }

		
		-- 1.3.6.1.4.1.2011.6.174.1.106.4
		hwUpsCIM3BIMNUm OBJECT-TYPE
			SYNTAX Unsigned32 (0..300)
			MAX-ACCESS read-only
			STATUS current
			DESCRIPTION
				"Ups BIM Num in CIM3.Value range from 0 to 300."
			::= { hwUpsCIMMonitormgr 4 }

		
		-- 1.3.6.1.4.1.2011.6.174.1.106.5
		hwUpsCIM4BIMNum OBJECT-TYPE
			SYNTAX Unsigned32 (0..300)
			MAX-ACCESS read-write
			STATUS current
			DESCRIPTION
				"Ups BIM Num in CIM4.Value range from 0 to 300."
			::= { hwUpsCIMMonitormgr 5 }

		
		-- 1.3.6.1.4.1.2011.6.174.1.106.6
		hwUpsCIMNote OBJECT IDENTIFIER ::= { hwUpsCIMMonitormgr 6 }

		
		-- 1.3.6.1.4.1.2011.6.174.1.106.6.1
		hwUpsCIMSelect OBJECT-TYPE
			SYNTAX Unsigned32 (1..4)
			MAX-ACCESS read-write
			STATUS current
			DESCRIPTION
				"Ups CIM Select.Use to select CIM No.Value range from 1 to 4."
			::= { hwUpsCIMNote 1 }

		
		-- 1.3.6.1.4.1.2011.6.174.1.106.6.2
		hwUpsBIMSelect OBJECT-TYPE
			SYNTAX Unsigned32 (1..300)
			MAX-ACCESS read-write
			STATUS current
			DESCRIPTION
				"Ups BIM Select.Use to select BIM No.Value range from 1 to 300."
			::= { hwUpsCIMNote 2 }

		
		-- 1.3.6.1.4.1.2011.6.174.1.106.6.3
		hwUpsCIMESN OBJECT-TYPE
			SYNTAX OCTET STRING (SIZE (1..127))
			MAX-ACCESS read-only
			STATUS current
			DESCRIPTION
				"Ups CIM ESN."
			::= { hwUpsCIMNote 3 }

		
		-- 1.3.6.1.4.1.2011.6.174.1.106.6.4
		hwUpsBIMESN OBJECT-TYPE
			SYNTAX OCTET STRING (SIZE (1..127))
			MAX-ACCESS read-only
			STATUS current
			DESCRIPTION
				"Ups BIM ESN."
			::= { hwUpsCIMNote 4 }

		
		-- 1.3.6.1.4.1.2011.6.174.1.107
		hwUpsModule OBJECT IDENTIFIER ::= { hwUpsMIBObjects 107 }

		
		-- 1.3.6.1.4.1.2011.6.174.1.107.1
		hwUpsModuleTable OBJECT-TYPE
			SYNTAX SEQUENCE OF HwUpsModuleEntry
			MAX-ACCESS not-accessible
			STATUS current
			DESCRIPTION
				"Description."
			::= { hwUpsModule 1 }

		
		-- 1.3.6.1.4.1.2011.6.174.1.107.1.1
		hwUpsModuleEntry OBJECT-TYPE
			SYNTAX HwUpsModuleEntry
			MAX-ACCESS not-accessible
			STATUS current
			DESCRIPTION
				"Description."
			INDEX { hwUpsModuleRackId, hwUpsPowerModuleId }
			::= { hwUpsModuleTable 1 }

		
		HwUpsModuleEntry ::=
			SEQUENCE { 
				hwUpsModuleRackId
					Unsigned32,
				hwUpsPowerModuleId
					Unsigned32,
				hwUpsBusCapacitorLife
					Unsigned32,
				hwUpsInvACur
					Unsigned32,
				hwUpsInvBCur
					Unsigned32,
				hwUpsInvCCur
					Unsigned32,
				hwUpsModuleAUnevenFlow
					Unsigned32,
				hwUpsModuleBUnevenFlow
					Unsigned32,
				hwUpsModuleCUnevenFlow
					Unsigned32,
				hwUpsInvPowerStat
					INTEGER,
				hwUpsModuleUnevneCurValueTag
					Unsigned32,
				hwUpsModuleSleepState
					Unsigned32,
				hwUpsModuleRowStatus
					RowStatus
			 }

		-- 1.3.6.1.4.1.2011.6.174.1.107.1.1.1
		hwUpsModuleRackId OBJECT-TYPE
			SYNTAX Unsigned32 (1..6)
			MAX-ACCESS read-only
			STATUS current
			DESCRIPTION
				"Ups Rack Id.Range from 1 to 6.This node is referenced as an index node 
				by hwUpsModuleTable."
			::= { hwUpsModuleEntry 1 }

		
		-- 1.3.6.1.4.1.2011.6.174.1.107.1.1.2
		hwUpsPowerModuleId OBJECT-TYPE
			SYNTAX Unsigned32 (1..20)
			MAX-ACCESS read-only
			STATUS current
			DESCRIPTION
				"Ups Power Module Id.Range from 1 to 20.This node is referenced as an index node 
				by hwUpsModuleTable."
			::= { hwUpsModuleEntry 2 }

		
		-- 1.3.6.1.4.1.2011.6.174.1.107.1.1.3
		hwUpsBusCapacitorLife OBJECT-TYPE
			SYNTAX Unsigned32 (0..10000)
			UNITS "Y"
			MAX-ACCESS read-only
			STATUS current
			DESCRIPTION
				"Inv C Cap Life.Value range: 0 to 10000, Unit: Y, and the value is accurate to one decimal place (.1). "
			::= { hwUpsModuleEntry 3 }

		
		-- 1.3.6.1.4.1.2011.6.174.1.107.1.1.4
		hwUpsInvACur OBJECT-TYPE
			SYNTAX Unsigned32 (0..10000)
			UNITS "A"
			MAX-ACCESS read-only
			STATUS current
			DESCRIPTION
				"Inv A Current.Value range: 0 to 10000.The value is accurate to one decimal place (.1).The unit is A.
				"
			::= { hwUpsModuleEntry 4 }

		
		-- 1.3.6.1.4.1.2011.6.174.1.107.1.1.5
		hwUpsInvBCur OBJECT-TYPE
			SYNTAX Unsigned32 (0..10000)
			UNITS "A"
			MAX-ACCESS read-only
			STATUS current
			DESCRIPTION
				"Inv B Current.Value range: 0 to 10000.The value is accurate to one decimal place (.1).The unit is A."
			::= { hwUpsModuleEntry 5 }

		
		-- 1.3.6.1.4.1.2011.6.174.1.107.1.1.6
		hwUpsInvCCur OBJECT-TYPE
			SYNTAX Unsigned32 (0..10000)
			UNITS "A"
			MAX-ACCESS read-only
			STATUS current
			DESCRIPTION
				"Inv C Current.Value range: 0 to 10000.The value is accurate to one decimal place (.1).The unit is A."
			::= { hwUpsModuleEntry 6 }

		
		-- 1.3.6.1.4.1.2011.6.174.1.107.1.1.7
		hwUpsModuleAUnevenFlow OBJECT-TYPE
			SYNTAX Unsigned32 (0..10000)
			MAX-ACCESS read-only
			STATUS current
			DESCRIPTION
				"Module A Uneven Flow.Value range: 0 to 10000,and the value is accurate to one decimal place (.1)."
			::= { hwUpsModuleEntry 7 }

		
		-- 1.3.6.1.4.1.2011.6.174.1.107.1.1.8
		hwUpsModuleBUnevenFlow OBJECT-TYPE
			SYNTAX Unsigned32 (0..10000)
			MAX-ACCESS read-only
			STATUS current
			DESCRIPTION
				"Module B Uneven Flow.Value range: 0 to 10000,and the value is accurate to one decimal place (.1)."
			::= { hwUpsModuleEntry 8 }

		
		-- 1.3.6.1.4.1.2011.6.174.1.107.1.1.9
		hwUpsModuleCUnevenFlow OBJECT-TYPE
			SYNTAX Unsigned32 (0..1000)
			MAX-ACCESS read-only
			STATUS current
			DESCRIPTION
				"Module C Uneven Flow.Value range: 0 to 10000,and the value is accurate to one decimal place (.1)."
			::= { hwUpsModuleEntry 9 }

		
		-- 1.3.6.1.4.1.2011.6.174.1.107.1.1.10
		hwUpsInvPowerStat OBJECT-TYPE
			SYNTAX INTEGER
				{
				noOutput(0),
				bypass(1),
				normal(2)
				}
			MAX-ACCESS read-only
			STATUS current
			DESCRIPTION
				"Inv Power Stat.Enumeration type.
				Value 0 indicates no power supply.
				Value 1 indicates bypass mode.
				Value 2 indicates normal mode.
				"
			::= { hwUpsModuleEntry 10 }

		
		-- 1.3.6.1.4.1.2011.6.174.1.107.1.1.11
		hwUpsModuleUnevneCurValueTag OBJECT-TYPE
			SYNTAX Unsigned32 (0..1)
			MAX-ACCESS read-only
			STATUS current
			DESCRIPTION
				"Module uneven current value tag.range 0 to 1,0 indicates invalid,1 indicates valid."
			::= { hwUpsModuleEntry 11 }

		
		-- 1.3.6.1.4.1.2011.6.174.1.107.1.1.12
		hwUpsModuleSleepState OBJECT-TYPE
			SYNTAX Unsigned32 (0..1)
			MAX-ACCESS read-only
			STATUS current
			DESCRIPTION
				"Module Sleep State.Range 0 to 1,0 indicates not sleep,1 indicates sleep."
			::= { hwUpsModuleEntry 12 }

		
		-- 1.3.6.1.4.1.2011.6.174.1.107.1.1.100
		hwUpsModuleRowStatus OBJECT-TYPE
			SYNTAX RowStatus
			MAX-ACCESS read-only
			STATUS current
			DESCRIPTION
				"RowStatus of UPS module information table."
			::= { hwUpsModuleEntry 100 }

		
		-- 1.3.6.1.4.1.2011.6.174.1.108
		hwUpsRackUnevenCur OBJECT IDENTIFIER ::= { hwUpsMIBObjects 108 }

		
		-- 1.3.6.1.4.1.2011.6.174.1.108.1
		hwUpsRackUnevenCurTable OBJECT-TYPE
			SYNTAX SEQUENCE OF HwUpsRackUnevenCurEntry
			MAX-ACCESS not-accessible
			STATUS current
			DESCRIPTION
				"Description."
			::= { hwUpsRackUnevenCur 1 }

		
		-- 1.3.6.1.4.1.2011.6.174.1.108.1.1
		hwUpsRackUnevenCurEntry OBJECT-TYPE
			SYNTAX HwUpsRackUnevenCurEntry
			MAX-ACCESS not-accessible
			STATUS current
			DESCRIPTION
				"Description."
			INDEX { hwUpsRackUnevenCurRackId }
			::= { hwUpsRackUnevenCurTable 1 }

		
		HwUpsRackUnevenCurEntry ::=
			SEQUENCE { 
				hwUpsRackUnevenCurRackId
					Unsigned32,
				hwUpsRackUnevenCurSysGrant
					Unsigned32,
				hwUpsRackUnevenCurPowerSupplyMode
					INTEGER,
				hwUpsRackUnevenCurPowerOnModNum
					Unsigned32,
				hwUpsRackUnevenCurSleepModNum
					Unsigned32,
				hwUpsRackOutputCurrentA
					Unsigned32,
				hwUpsRackOutputCurrentB
					Unsigned32,
				hwUpsRackOutputCurrentC
					Unsigned32,
				hwUpsRackUnevenCurA
					Unsigned32,
				hwUpsRackUnevenCurB
					Unsigned32,
				hwUpsRackUnevenCurC
					Unsigned32,
				hwUpsRackUnevenCurValueTag
					Unsigned32,
				hwUpsRackUnevenCurRowStatus
					RowStatus
			 }

		-- 1.3.6.1.4.1.2011.6.174.1.108.1.1.1
		hwUpsRackUnevenCurRackId OBJECT-TYPE
			SYNTAX Unsigned32 (1..6)
			MAX-ACCESS read-only
			STATUS current
			DESCRIPTION
				"Ups Rack Id.Range from 1 to 6.This node is referenced as an index node 
				by hwUpsRackUnevenCurTable"
			::= { hwUpsRackUnevenCurEntry 1 }

		
		-- 1.3.6.1.4.1.2011.6.174.1.108.1.1.2
		hwUpsRackUnevenCurSysGrant OBJECT-TYPE
			SYNTAX Unsigned32 (0..10000)
			MAX-ACCESS read-only
			STATUS current
			DESCRIPTION
				"System grant.An integer ranging from 0 to 10000."
			::= { hwUpsRackUnevenCurEntry 2 }

		
		-- 1.3.6.1.4.1.2011.6.174.1.108.1.1.3
		hwUpsRackUnevenCurPowerSupplyMode OBJECT-TYPE
			SYNTAX INTEGER
				{
				noOutput(1),
				bypass(2),
				normal(3),
				battery(4),
				sourceShare(5),
				normalECO(6),
				batteryECO(7)
				}
			MAX-ACCESS read-only
			STATUS current
			DESCRIPTION
				"Device power supply mode. Enumeration type.
				Value 1 indicates no power supply.
				Value 2 indicates bypass mode.
				Value 3 indicates normal mode.
				Value 4 indicates battery mode.
				Value 5 indicates combined mode.
				Value 6 indicates mains ECO mode.
				Value 7 indicates battery ECO mode."
			::= { hwUpsRackUnevenCurEntry 3 }

		
		-- 1.3.6.1.4.1.2011.6.174.1.108.1.1.4
		hwUpsRackUnevenCurPowerOnModNum OBJECT-TYPE
			SYNTAX Unsigned32 (0..20)
			MAX-ACCESS read-only
			STATUS current
			DESCRIPTION
				"Rack PowerOn Module Num.Range from 0 to 20."
			::= { hwUpsRackUnevenCurEntry 4 }

		
		-- 1.3.6.1.4.1.2011.6.174.1.108.1.1.5
		hwUpsRackUnevenCurSleepModNum OBJECT-TYPE
			SYNTAX Unsigned32 (0..20)
			MAX-ACCESS read-only
			STATUS current
			DESCRIPTION
				"Rack Sleep Module Num.Range from 0 to 20."
			::= { hwUpsRackUnevenCurEntry 5 }

		
		-- 1.3.6.1.4.1.2011.6.174.1.108.1.1.6
		hwUpsRackOutputCurrentA OBJECT-TYPE
			SYNTAX Unsigned32 (0..10000)
			UNITS "A"
			MAX-ACCESS read-only
			STATUS current
			DESCRIPTION
				"Rack phase A output current. The value ranges from 0 to 10000. 
				The value is accurate to one decimal place on the NetEco. The unit is A."
			::= { hwUpsRackUnevenCurEntry 6 }

		
		-- 1.3.6.1.4.1.2011.6.174.1.108.1.1.7
		hwUpsRackOutputCurrentB OBJECT-TYPE
			SYNTAX Unsigned32 (0..10000)
			UNITS "A"
			MAX-ACCESS read-only
			STATUS current
			DESCRIPTION
				"Rack phase B output current. The value ranges from 0 to 10000. 
				The value is accurate to one decimal place on the NetEco. The unit is A."
			::= { hwUpsRackUnevenCurEntry 7 }

		
		-- 1.3.6.1.4.1.2011.6.174.1.108.1.1.8
		hwUpsRackOutputCurrentC OBJECT-TYPE
			SYNTAX Unsigned32 (0..10000)
			UNITS "A"
			MAX-ACCESS read-only
			STATUS current
			DESCRIPTION
				"Rack phase C output current. The value ranges from 0 to 10000. 
				The value is accurate to one decimal place on the NetEco. The unit is A."
			::= { hwUpsRackUnevenCurEntry 8 }

		
		-- 1.3.6.1.4.1.2011.6.174.1.108.1.1.9
		hwUpsRackUnevenCurA OBJECT-TYPE
			SYNTAX Unsigned32 (0..10000)
			MAX-ACCESS read-only
			STATUS current
			DESCRIPTION
				"Rack phase A uneven current. The value ranges from 0 to 10000. 
				The value is accurate to one decimal place on the NetEco. "
			::= { hwUpsRackUnevenCurEntry 9 }

		
		-- 1.3.6.1.4.1.2011.6.174.1.108.1.1.10
		hwUpsRackUnevenCurB OBJECT-TYPE
			SYNTAX Unsigned32 (0..10000)
			MAX-ACCESS read-only
			STATUS current
			DESCRIPTION
				"Rack phase B uneven current. The value ranges from 0 to 10000. 
				The value is accurate to one decimal place on the NetEco. "
			::= { hwUpsRackUnevenCurEntry 10 }

		
		-- 1.3.6.1.4.1.2011.6.174.1.108.1.1.11
		hwUpsRackUnevenCurC OBJECT-TYPE
			SYNTAX Unsigned32 (0..1000)
			MAX-ACCESS read-only
			STATUS current
			DESCRIPTION
				"Rack phase C uneven current. The value ranges from 0 to 10000. 
				The value is accurate to one decimal place on the NetEco. "
			::= { hwUpsRackUnevenCurEntry 11 }

		
		-- 1.3.6.1.4.1.2011.6.174.1.108.1.1.12
		hwUpsRackUnevenCurValueTag OBJECT-TYPE
			SYNTAX Unsigned32 (0..1)
			MAX-ACCESS read-only
			STATUS current
			DESCRIPTION
				"Rack uneven current value tag.range 0 to 1,0 indicates invalid,1 indicates valid."
			::= { hwUpsRackUnevenCurEntry 12 }

		
		-- 1.3.6.1.4.1.2011.6.174.1.108.1.1.100
		hwUpsRackUnevenCurRowStatus OBJECT-TYPE
			SYNTAX RowStatus
			MAX-ACCESS read-only
			STATUS current
			DESCRIPTION
				"RowStatus of UPS Rack Uneven Current table."
			::= { hwUpsRackUnevenCurEntry 100 }

		
		-- 1.3.6.1.4.1.2011.6.174.1.109
		hwUpsBatteryString OBJECT IDENTIFIER ::= { hwUpsMIBObjects 109 }

		
-- Ups Battery String Num.Value range from 0 to 4.
		-- 1.3.6.1.4.1.2011.6.174.1.109.1
		hwUpsBatteryStringNum OBJECT-TYPE
			SYNTAX Unsigned32 (0..4)
			MAX-ACCESS read-only
			STATUS current
			DESCRIPTION
				"Ups Battery String Num.Value range from 0 to 4."
			::= { hwUpsBatteryString 1 }

		
-- Ups Battery Num in Battery String.Value range from 0 to 300.
		-- 1.3.6.1.4.1.2011.6.174.1.109.2
		hwUpsBatteryNumInBatteryString OBJECT-TYPE
			SYNTAX Unsigned32 (0..300)
			MAX-ACCESS read-only
			STATUS current
			DESCRIPTION
				"Ups Battery Num In Battery String.Value range from 0 to 300."
			::= { hwUpsBatteryString 2 }

		
		-- 1.3.6.1.4.1.2011.6.174.1.109.3
		hwUpsBatteryStringParamTable OBJECT-TYPE
			SYNTAX SEQUENCE OF HwUpsBatteryStringParamEntry
			MAX-ACCESS not-accessible
			STATUS current
			DESCRIPTION
				"Description."
			::= { hwUpsBatteryString 3 }

		
		-- 1.3.6.1.4.1.2011.6.174.1.109.3.1
		hwUpsBatteryStringParamEntry OBJECT-TYPE
			SYNTAX HwUpsBatteryStringParamEntry
			MAX-ACCESS not-accessible
			STATUS current
			DESCRIPTION
				"Description."
			INDEX { hwUpsBatteryStringNo, hwUpsBatteryUnitNo }
			::= { hwUpsBatteryStringParamTable 1 }

		
		HwUpsBatteryStringParamEntry ::=
			SEQUENCE { 
				hwUpsBatteryStringNo
					Unsigned32,
				hwUpsBatteryUnitNo
					Unsigned32,
				hwUpsBatteryUnitTemperature
					Integer32,
				hwUpsBatteryUnitVolt
					Unsigned32,
				hwUpsBatteryUnitResistance
					Unsigned32,
				hwUpsCIMRelaNode
					Unsigned32,
				hwUpsBIMRelaNode
					Unsigned32,
				hwUpsBatteryStringParamRowStatus
					RowStatus
			 }

		-- 1.3.6.1.4.1.2011.6.174.1.109.3.1.1
		hwUpsBatteryStringNo OBJECT-TYPE
			SYNTAX Unsigned32 (1..4)
			MAX-ACCESS read-only
			STATUS current
			DESCRIPTION
				"Ups Battery String No.Range from 1 to 4.This node is referenced as an index node 
				by hwUpsBatteryStringRelationTable."
			::= { hwUpsBatteryStringParamEntry 1 }

		
		-- 1.3.6.1.4.1.2011.6.174.1.109.3.1.2
		hwUpsBatteryUnitNo OBJECT-TYPE
			SYNTAX Unsigned32 (1..301)
			MAX-ACCESS read-only
			STATUS current
			DESCRIPTION
				"Ups Battery No.Range from 1 to 300.This node is referenced as an index node 
				by hwUpsBatteryStringRelationTable."
			::= { hwUpsBatteryStringParamEntry 2 }

		
		-- 1.3.6.1.4.1.2011.6.174.1.109.3.1.3
		hwUpsBatteryUnitTemperature OBJECT-TYPE
			SYNTAX Integer32 (-200..800)
			UNITS "℃"
			MAX-ACCESS read-only
			STATUS current
			DESCRIPTION
				"Ups BIM Temperature.The value ranges from -200 to 800. 
				The value is accurate to one decimal place on the NetEco. The unit is ℃."
			::= { hwUpsBatteryStringParamEntry 3 }

		
		-- 1.3.6.1.4.1.2011.6.174.1.109.3.1.4
		hwUpsBatteryUnitVolt OBJECT-TYPE
			SYNTAX Unsigned32 (0..300)
			UNITS "V"
			MAX-ACCESS read-only
			STATUS current
			DESCRIPTION
				"Ups BIM Volt.The value ranges from 0 to 300. 
				The value is accurate to one decimal place on the NetEco. The unit is V."
			::= { hwUpsBatteryStringParamEntry 4 }

		
		-- 1.3.6.1.4.1.2011.6.174.1.109.3.1.5
		hwUpsBatteryUnitResistance OBJECT-TYPE
			SYNTAX Unsigned32 (0..3000)
			UNITS "mΩ"
			MAX-ACCESS read-only
			STATUS current
			DESCRIPTION
				"Ups BIM Resistance.The value ranges from 0 to 3000. 
				The value is accurate to one decimal place on the NetEco. The unit is mΩ."
			::= { hwUpsBatteryStringParamEntry 5 }

		
		-- 1.3.6.1.4.1.2011.6.174.1.109.3.1.6
		hwUpsCIMRelaNode OBJECT-TYPE
			SYNTAX Unsigned32 (0..4)
			MAX-ACCESS read-only
			STATUS current
			DESCRIPTION
				"Ups Battery Rela CIM Node.Value range from 0 to 4."
			::= { hwUpsBatteryStringParamEntry 6 }

		
		-- 1.3.6.1.4.1.2011.6.174.1.109.3.1.7
		hwUpsBIMRelaNode OBJECT-TYPE
			SYNTAX Unsigned32 (0..300)
			MAX-ACCESS read-only
			STATUS current
			DESCRIPTION
				"Ups Battery Rela BIM Node.Value range from 0 to 300."
			::= { hwUpsBatteryStringParamEntry 7 }

		
		-- 1.3.6.1.4.1.2011.6.174.1.109.3.1.100
		hwUpsBatteryStringParamRowStatus OBJECT-TYPE
			SYNTAX RowStatus
			MAX-ACCESS read-only
			STATUS current
			DESCRIPTION
				"Row status of hwUpsBatteryStringParamTable."
			::= { hwUpsBatteryStringParamEntry 100 }

		
		-- 1.3.6.1.4.1.2011.6.174.2
		hwUpsMIBTraps OBJECT IDENTIFIER ::= { hwUpsMIB 2 }

		
		-- 1.3.6.1.4.1.2011.6.174.2.1
		hwUpsTrapsVbOids OBJECT IDENTIFIER ::= { hwUpsMIBTraps 1 }

		
		-- 1.3.6.1.4.1.2011.6.174.2.1.1
		hwUpsTrapsDeviceId OBJECT-TYPE
			SYNTAX Unsigned32 (1..100)
			MAX-ACCESS accessible-for-notify
			STATUS current
			DESCRIPTION
				"ID of the device on which the active alarm is generated. An integer ranging from 1 to 100."
			::= { hwUpsTrapsVbOids 1 }
-- The alarm device number.Value range: 1 to 100.it specifies the device id of the alarm.
		
		-- 1.3.6.1.4.1.2011.6.174.2.1.2
		hwUpsTrapsModuleSeqId OBJECT-TYPE
			SYNTAX Unsigned32 (1..4294967295)
			MAX-ACCESS accessible-for-notify
			STATUS current
			DESCRIPTION
				"The alarm module name, which produces alarm. 
				This name may be one of Monitor module name,Bypass module name,ECU module name and Power module name. 
				If it's value is empty, it indicates the alarm is a synthetical alarm and not belong to any module device."
			::= { hwUpsTrapsVbOids 2 }
-- The alarm sequence number.Value range: 1 to 42949672925.it specifies the alarm sequence number of the alarm.
		
		-- 1.3.6.1.4.1.2011.6.174.2.1.3
		hwUpsTrapsEquipID OBJECT-TYPE
			SYNTAX Unsigned32 (0..154)
			MAX-ACCESS accessible-for-notify
			STATUS current
			DESCRIPTION
				"Active alarm module ID, ranging from 1 to 154."
			::= { hwUpsTrapsVbOids 3 }
-- The alarm equip id.Value range: 1 to 154.it specifies the alarm equip id of the alarm.
		
		-- 1.3.6.1.4.1.2011.6.174.2.1.4
		hwUpsTrapsID OBJECT-TYPE
			SYNTAX Unsigned32 (0..4294967295)
			MAX-ACCESS accessible-for-notify
			STATUS current
			DESCRIPTION
				"ID of an active alarm, ranging from 0 to 4294967295."
			::= { hwUpsTrapsVbOids 4 }
-- The alarm Id.Value range: 0 to 4294967295.it specifies the alarm id of the alarm.
		
		-- 1.3.6.1.4.1.2011.6.174.2.1.5
		hwUpsTrapsReasonId OBJECT-TYPE
			SYNTAX Unsigned32 (0..100)
			MAX-ACCESS accessible-for-notify
			STATUS current
			DESCRIPTION
				"Alarm reason ID.  Value range: 0 to 100, and the value is an integer (.0)."
			::= { hwUpsTrapsVbOids 5 }
-- The active reason Id.Value range: 1 to 100.it specifies the alarm reason id of the alarm.
		
		-- 1.3.6.1.4.1.2011.6.174.2.1.6
		hwUpsTrapsText OBJECT-TYPE
			SYNTAX OCTET STRING (SIZE (0..127))
			MAX-ACCESS accessible-for-notify
			STATUS current
			DESCRIPTION
				"Alarm name. It is of the character string type, and used to specify the content of a specific alarm."
			::= { hwUpsTrapsVbOids 6 }
-- The alarm name, it is the character string type..it specifies the English name of the alarm.
		
		-- 1.3.6.1.4.1.2011.6.174.2.1.7
		hwUpsTrapsLevel OBJECT-TYPE
			SYNTAX INTEGER
				{
				critical(1),
				major(2),
				minor(3),
				warning(4)
				}
			MAX-ACCESS accessible-for-notify
			STATUS current
			DESCRIPTION
				"Alarm level, which users can configure the alarm severity, is an enumeration type:
				If the enumeration value is 1, it indicates a critical alarm;
				If the enumeration value is 2, it indicates a major alarm;
				If the enumeration value is 3, it indicates a minor alarm;
				If the enumeration value is 4, it indicates a warning."
			::= { hwUpsTrapsVbOids 7 }
-- The alarm level, It is an enumeration type.
-- If the enumeration value is 1, it indicates that the current alarm level is critical;
-- If the enumeration value is 2, it indicates that the current alarm level is major;  
-- If the enumeration value is 3, it indicates that the current alarm level is minor;   
-- If the enumeration value is 4, it indicates that the current alarm level is warrning; 
		
		-- 1.3.6.1.4.1.2011.6.174.2.1.8
		hwUpsTrapsFlag OBJECT-TYPE
			SYNTAX INTEGER
				{
				occur(1),
				resume(2)
				}
			MAX-ACCESS accessible-for-notify
			STATUS current
			DESCRIPTION
				"Flag bit of an active alarm. Enumeration type.
				Value 1 indicates that an active alarm is generated.
				Value 2 indicates that an active alarm is cleared."
			::= { hwUpsTrapsVbOids 8 }
-- The alarm flag, it is an enumeration type.
-- If the enumeration value is 1, it indicates that the current alarm is occured;
-- If the enumeration value is 2, it indicates that the current alarm is resumed;  
		
		-- 1.3.6.1.4.1.2011.6.174.2.1.9
		hwUpsTrapsSynchronNum OBJECT-TYPE
			SYNTAX Unsigned32
			MAX-ACCESS accessible-for-notify
			STATUS current
			DESCRIPTION
				"Active alarm synchronization ID, ranging from 0 to 4294967295."
			::= { hwUpsTrapsVbOids 9 }
-- The alarm synchronization number.Value range: 0 to 4294967295.
		
		-- 1.3.6.1.4.1.2011.6.174.2.1.10
		hwUpsTrapsTime OBJECT-TYPE
			SYNTAX Unsigned32 (0..4294967295)
			MAX-ACCESS accessible-for-notify
			STATUS current
			DESCRIPTION
				"Time when an active alarm is generated, ranging from 0 to 4294967295. The unit is seconds."
			::= { hwUpsTrapsVbOids 10 }
-- The happen time of an active alarm.Value range: 0 to 4294967295. it specifies what is the local time of the current alarm. 
		
--   UPS system or module running status changed traps and alarm with warning level traps.
-- 
-- 
		-- 1.3.6.1.4.1.2011.6.174.2.2
		hwUpsCommonTraps OBJECT IDENTIFIER ::= { hwUpsMIBTraps 2 }

		
--   1.3.6.1.4.1.2011.6.174.2.2.0
-- 1.3.6.1.4.1.2011.6.174.2.2.0
		-- 1.3.6.1.4.1.2011.6.174.2.2.0
		hwUpsCommonTrapsPrefix OBJECT IDENTIFIER ::= { hwUpsCommonTraps 0 }

		
--   1.3.6.1.4.1.2011.6.174.2.2.0.1
-- 1.3.6.1.4.1.2011.6.174.2.2.0.1
		-- 1.3.6.1.4.1.2011.6.174.2.2.0.1
		hwUpsSummaryAlarmTrap NOTIFICATION-TYPE
			STATUS current
			DESCRIPTION 
				"UPS Summary Alarm status changed. Its correlation binding parameters: Device ID, Sequence ID, Equip ID, Trap ID, 
				Trap Reason ID, Trap Text, Trap Level, Trap Flag, Synchron NO and the time. 
				Additionally, in order to identify the status, UPS system operate status are also include in VB(variable bondings):
				If the enumeration value is Normal(2), it indicates that UPS system  resumes form alarm.  
				If the enumeration value is Alarm(3), it indicates that a new alarm occurs on the UPS sytem."
			::= { hwUpsCommonTrapsPrefix 1 }

		
--   1.3.6.1.4.1.2011.6.174.2.2.0.2
-- 1.3.6.1.4.1.2011.6.174.2.2.0.2
		-- 1.3.6.1.4.1.2011.6.174.2.2.0.2
		hwUpsPowerModInslotChangeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Power module inslot status changed.
				Its correlation binding parameters: Device ID, Sequence ID, Equip ID, Trap ID, 
				Trap Reason ID, Trap Text, Trap Level, Trap Flag, Synchron NO and the time. 
				Additionally, in order to identify the operation, power module operate status are also include in VB(variable bondings):
				If the enumeration value is Normal(2), it indicates that a new power module is inserted in slot; 
				If the enumeration value is Alarm(3), it indicates that communication of the power module module fails or module is not in slot. "
			::= { hwUpsCommonTrapsPrefix 2 }

		
--   1.3.6.1.4.1.2011.6.174.2.2.0.3
-- 1.3.6.1.4.1.2011.6.174.2.2.0.3
		-- 1.3.6.1.4.1.2011.6.174.2.2.0.3
		hwUpsPowerStatusWarnTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When UPS Power Status changed, a warn trap will be send. 
				Its correlation binding parameters: Device ID, Sequence ID, Equip ID, Trap ID, 
				Trap Reason ID, Trap Text, Trap Level, Trap Flag, Synchron NO and the time.  "
			::= { hwUpsCommonTrapsPrefix 3 }

		
--   1.3.6.1.4.1.2011.6.174.2.2.0.4
-- 1.3.6.1.4.1.2011.6.174.2.2.0.4
		-- 1.3.6.1.4.1.2011.6.174.2.2.0.4
		hwUpsPowerStatusWarnResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"UPS Power Status warn resume trap. 
				Its correlation binding parameters: Device ID, Sequence ID, Equip ID, Trap ID, 
				Trap Reason ID, Trap Text, Trap Level, Trap Flag, Synchron NO and the time. "
			::= { hwUpsCommonTrapsPrefix 4 }

		
--   1.3.6.1.4.1.2011.6.174.2.2.0.5
-- 1.3.6.1.4.1.2011.6.174.2.2.0.5
		-- 1.3.6.1.4.1.2011.6.174.2.2.0.5
		hwUpsSwitchStatusWarnTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When contactor or switch status changed, a warn trap will be send. 
				Its correlation binding parameters: Device ID, Sequence ID, Equip ID, Trap ID, 
				Trap Reason ID, Trap Text, Trap Level, Trap Flag, Synchron NO and the time. "
			::= { hwUpsCommonTrapsPrefix 5 }

		
--   1.3.6.1.4.1.2011.6.174.2.2.0.6
-- 1.3.6.1.4.1.2011.6.174.2.2.0.6
		-- 1.3.6.1.4.1.2011.6.174.2.2.0.6
		hwUpsSwitchStatusWarnResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Contactor or switch warn resume trap. 
				Its correlation binding parameters: Device ID, Sequence ID, Equip ID, Trap ID, 
				Trap Reason ID, Trap Text, Trap Level, Trap Flag, Synchron NO and the time. "
			::= { hwUpsCommonTrapsPrefix 6 }

		
--   1.3.6.1.4.1.2011.6.174.2.2.0.7
-- 1.3.6.1.4.1.2011.6.174.2.2.0.7
		-- 1.3.6.1.4.1.2011.6.174.2.2.0.7
		hwUpsModCommFailedTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When module communicates failed, a trap will be send. 
				Its correlation binding parameters: Device ID, Sequence ID, Equip ID, Trap ID, 
				Trap Reason ID, Trap Text, Trap Level, Trap Flag, Synchron NO and the time. "
			::= { hwUpsCommonTrapsPrefix 7 }

		
--   1.3.6.1.4.1.2011.6.174.2.2.0.8
-- 1.3.6.1.4.1.2011.6.174.2.2.0.8
		-- 1.3.6.1.4.1.2011.6.174.2.2.0.8
		hwUpsModCommFailedResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Module communication failed Resume. 
				Its correlation binding parameters: Device ID, Sequence ID, Equip ID, Trap ID, 
				Trap Reason ID, Trap Text, Trap Level, Trap Flag, Synchron NO and the time. "
			::= { hwUpsCommonTrapsPrefix 8 }

		
--   1.3.6.1.4.1.2011.6.174.2.2.0.9
-- 1.3.6.1.4.1.2011.6.174.2.2.0.9
		-- 1.3.6.1.4.1.2011.6.174.2.2.0.9
		hwUpsModConfigWarnTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When module config status changed, a warn trap will be send. 
				Its correlation binding parameters: Device ID, Sequence ID, Equip ID, Trap ID, 
				Trap Reason ID, Trap Text, Trap Level, Trap Flag, Synchron NO and the time. "
			::= { hwUpsCommonTrapsPrefix 9 }

		
--   1.3.6.1.4.1.2011.6.174.2.2.0.10
-- 1.3.6.1.4.1.2011.6.174.2.2.0.10
		-- 1.3.6.1.4.1.2011.6.174.2.2.0.10
		hwUpsModConfigWarnResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Module config warn resume trap. 
				Its correlation binding parameters:Device ID, Sequence ID, Equip ID, Trap ID, 
				Trap Reason ID, Trap Text, Trap Level, Trap Flag, Synchron NO and the time. "
			::= { hwUpsCommonTrapsPrefix 10 }

		
--   1.3.6.1.4.1.2011.6.174.2.2.0.11
-- 1.3.6.1.4.1.2011.6.174.2.2.0.11
		-- 1.3.6.1.4.1.2011.6.174.2.2.0.11
		hwUpsRecWarnTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When rectifier status changed, a warn trap will be send. 
				Its correlation binding parameters: Device ID, Sequence ID, Equip ID, Trap ID, 
				Trap Reason ID, Trap Text, Trap Level, Trap Flag, Synchron NO and the time. "
			::= { hwUpsCommonTrapsPrefix 11 }

		
--   1.3.6.1.4.1.2011.6.174.2.2.0.12
-- 1.3.6.1.4.1.2011.6.174.2.2.0.12
		-- 1.3.6.1.4.1.2011.6.174.2.2.0.12
		hwUpsRecWarnResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Rectifier warn resume trap. 
				Its correlation binding parameters: Device ID, Sequence ID, Equip ID, Trap ID, 
				Trap Reason ID, Trap Text, Trap Level, Trap Flag, Synchron NO and the time. "
			::= { hwUpsCommonTrapsPrefix 12 }

		
--   1.3.6.1.4.1.2011.6.174.2.2.0.13
-- 1.3.6.1.4.1.2011.6.174.2.2.0.13
		-- 1.3.6.1.4.1.2011.6.174.2.2.0.13
		hwUpsChargerPowerWarnTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When charger power status changed, a warn trap will be send. 
				Its correlation binding parameters: Device ID, Sequence ID, Equip ID, Trap ID, 
				Trap Reason ID, Trap Text, Trap Level, Trap Flag, Synchron NO and the time. "
			::= { hwUpsCommonTrapsPrefix 13 }

		
--   1.3.6.1.4.1.2011.6.174.2.2.0.14
-- 1.3.6.1.4.1.2011.6.174.2.2.0.14
		-- 1.3.6.1.4.1.2011.6.174.2.2.0.14
		hwUpsChargerPowerWarnResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Charger power warn resume trap. 
				Its correlation binding parameters: Device ID, Sequence ID, Equip ID, Trap ID, 
				Trap Reason ID, Trap Text, Trap Level, Trap Flag, Synchron NO and the time. "
			::= { hwUpsCommonTrapsPrefix 14 }

		
--   1.3.6.1.4.1.2011.6.174.2.2.0.15
-- 1.3.6.1.4.1.2011.6.174.2.2.0.15
		-- 1.3.6.1.4.1.2011.6.174.2.2.0.15
		hwUpsGeneratorWarnTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When generator status changed, a warn trap will be send. 
				Its correlation binding parameters: Device ID, Sequence ID, Equip ID, Trap ID, 
				Trap Reason ID, Trap Text, Trap Level, Trap Flag, Synchron NO and the time. "
			::= { hwUpsCommonTrapsPrefix 15 }

		
--   1.3.6.1.4.1.2011.6.174.2.2.0.16
-- 1.3.6.1.4.1.2011.6.174.2.2.0.16
		-- 1.3.6.1.4.1.2011.6.174.2.2.0.16
		hwUpsGeneratorWarnResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Generator warn resume trap. 
				Its correlation binding parameters: Device ID, Sequence ID, Equip ID, Trap ID, 
				Trap Reason ID, Trap Text, Trap Level, Trap Flag, Synchron NO and the time. "
			::= { hwUpsCommonTrapsPrefix 16 }

		
--   1.3.6.1.4.1.2011.6.174.2.2.0.17
-- 1.3.6.1.4.1.2011.6.174.2.2.0.17
		-- 1.3.6.1.4.1.2011.6.174.2.2.0.17
		hwUpsInvWarnTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When inverter status changed, a warn trap will be send.
				Its correlation binding parameters: Device ID, Sequence ID, Equip ID, Trap ID, 
				Trap Reason ID, Trap Text, Trap Level, Trap Flag, Synchron NO and the time. "
			::= { hwUpsCommonTrapsPrefix 17 }

		
--   1.3.6.1.4.1.2011.6.174.2.2.0.18
-- 1.3.6.1.4.1.2011.6.174.2.2.0.18
		-- 1.3.6.1.4.1.2011.6.174.2.2.0.18
		hwUpsInvWarnResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Inverter warn resume trap. 
				Its correlation binding parameters: Device ID, Sequence ID, Equip ID, Trap ID, 
				Trap Reason ID, Trap Text, Trap Level, Trap Flag, Synchron NO and the time. "
			::= { hwUpsCommonTrapsPrefix 18 }

		
--   1.3.6.1.4.1.2011.6.174.2.2.0.19
-- 1.3.6.1.4.1.2011.6.174.2.2.0.19
		-- 1.3.6.1.4.1.2011.6.174.2.2.0.19
		hwUpsLBSWarnTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When LBS status changed, a warn trap will be send.
				Its correlation binding parameters: Device ID, Sequence ID, Equip ID, Trap ID, 
				Trap Reason ID, Trap Text, Trap Level, Trap Flag, Synchron NO and the time. "
			::= { hwUpsCommonTrapsPrefix 19 }

		
--   1.3.6.1.4.1.2011.6.174.2.2.0.20
-- 1.3.6.1.4.1.2011.6.174.2.2.0.20
		-- 1.3.6.1.4.1.2011.6.174.2.2.0.20
		hwUpsLBSWarnResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"LBS warn resume trap. 
				Its correlation binding parameters: Device ID, Sequence ID, Equip ID, Trap ID, 
				Trap Reason ID, Trap Text, Trap Level, Trap Flag, Synchron NO and the time. "
			::= { hwUpsCommonTrapsPrefix 20 }

		
--   1.3.6.1.4.1.2011.6.174.2.2.0.21
-- 1.3.6.1.4.1.2011.6.174.2.2.0.21
		-- 1.3.6.1.4.1.2011.6.174.2.2.0.21
		hwUpsSwitchTipWarnTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When switch method changed or there is a switch tip, a warn trap will be send.
				Its correlation binding parameters: Device ID, Sequence ID, Equip ID, Trap ID, 
				Trap Reason ID, Trap Text, Trap Level, Trap Flag, Synchron NO and the time. "
			::= { hwUpsCommonTrapsPrefix 21 }

		
--   1.3.6.1.4.1.2011.6.174.2.2.0.22
-- 1.3.6.1.4.1.2011.6.174.2.2.0.22
		-- 1.3.6.1.4.1.2011.6.174.2.2.0.22
		hwUpsSwitchTipWarnResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Switch method or switch tip warn resume trap.
				Its correlation binding parameters:Device ID, Sequence ID, Equip ID, Trap ID, 
				Trap Reason ID, Trap Text, Trap Level, Trap Flag, Synchron NO and the time. "
			::= { hwUpsCommonTrapsPrefix 22 }

		
--   1.3.6.1.4.1.2011.6.174.2.2.0.23
-- 1.3.6.1.4.1.2011.6.174.2.2.0.23
		-- 1.3.6.1.4.1.2011.6.174.2.2.0.23
		hwUpsBattDetachWarnTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When battery detach, a warn trap will be send.
				Its correlation binding parameters: Device ID, Sequence ID, Equip ID, Trap ID, 
				Trap Reason ID, Trap Text, Trap Level, Trap Flag, Synchron NO and the time. "
			::= { hwUpsCommonTrapsPrefix 23 }

		
--   1.3.6.1.4.1.2011.6.174.2.2.0.24
-- 1.3.6.1.4.1.2011.6.174.2.2.0.24
		-- 1.3.6.1.4.1.2011.6.174.2.2.0.24
		hwUpsBattDetachWarnResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Battery detach warn resume trap.
				Its correlation binding parameters: Device ID, Sequence ID, Equip ID, Trap ID, 
				Trap Reason ID, Trap Text, Trap Level, Trap Flag, Synchron NO and the time. "
			::= { hwUpsCommonTrapsPrefix 24 }

		
--   1.3.6.1.4.1.2011.6.174.2.2.0.25
-- 1.3.6.1.4.1.2011.6.174.2.2.0.25
		-- 1.3.6.1.4.1.2011.6.174.2.2.0.25
		hwUpsBattStatusWarnTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When battery status abnormal, a warn trap will be send through this OID. 
				Its correlation binding parameters: Device ID, Sequence ID, Equip ID, Trap ID, 
				Trap Reason ID, Trap Text, Trap Level, Trap Flag, Synchron NO and the time. "
			::= { hwUpsCommonTrapsPrefix 25 }

		
--   1.3.6.1.4.1.2011.6.174.2.2.0.26
-- 1.3.6.1.4.1.2011.6.174.2.2.0.26
		-- 1.3.6.1.4.1.2011.6.174.2.2.0.26
		hwUpsBattStatusWarnResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When battery status abnormal resume, a trap will be send through this OID. 
				Its correlation binding parameters: Device ID, Sequence ID, Equip ID, Trap ID, 
				Trap Reason ID, Trap Text, Trap Level, Trap Flag, Synchron NO and the time. "
			::= { hwUpsCommonTrapsPrefix 26 }

		
--   1.3.6.1.4.1.2011.6.174.2.2.0.27
-- 1.3.6.1.4.1.2011.6.174.2.2.0.27
		-- 1.3.6.1.4.1.2011.6.174.2.2.0.27
		hwUpsBatteryTestWarnTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When battery test start, a warn trap will be send through this OID. 
				Its correlation binding parameters: Device ID, Sequence ID, Equip ID, Trap ID, 
				Trap Reason ID, Trap Text, Trap Level, Trap Flag, Synchron NO and the time. "
			::= { hwUpsCommonTrapsPrefix 27 }

		
--   1.3.6.1.4.1.2011.6.174.2.2.0.28
-- 1.3.6.1.4.1.2011.6.174.2.2.0.28
		-- 1.3.6.1.4.1.2011.6.174.2.2.0.28
		hwUpsBatteryTestWarnResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When battery test end, a trap will be send through this OID. 
				Its correlation binding parameters: Device ID, Sequence ID, Equip ID, Trap ID, 
				Trap Reason ID, Trap Text, Trap Level, Trap Flag, Synchron NO and the time. "
			::= { hwUpsCommonTrapsPrefix 28 }

		
--   1.3.6.1.4.1.2011.6.174.2.2.0.29
-- 1.3.6.1.4.1.2011.6.174.2.2.0.29
		-- 1.3.6.1.4.1.2011.6.174.2.2.0.29
		hwUpsRackComFailedTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When Rack communication fail happen, a alarm trap will be send. 
				Its correlation binding parameters: Device ID, Sequence ID, Equip ID, Trap ID, 
				Trap Reason ID, Trap Text, Trap Level, Trap Flag, Synchron NO and the time. "
			::= { hwUpsCommonTrapsPrefix 29 }

		
--   1.3.6.1.4.1.2011.6.174.2.2.0.30
-- 1.3.6.1.4.1.2011.6.174.2.2.0.30
		-- 1.3.6.1.4.1.2011.6.174.2.2.0.30
		hwUpsRackComFaiedResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Rack communication fail alarm resume. 
				Its correlation binding parameters: Device ID, Sequence ID, Equip ID, Trap ID, 
				Trap Reason ID, Trap Text, Trap Level, Trap Flag, Synchron NO and the time. "
			::= { hwUpsCommonTrapsPrefix 30 }

		
--   1.3.6.1.4.1.2011.6.174.2.2.0.31
-- 1.3.6.1.4.1.2011.6.174.2.2.0.31
		-- 1.3.6.1.4.1.2011.6.174.2.2.0.31
		hwUpsRackMasterConflictTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When Rack Master Conflict alarm happen, a alarm trap will be send. 
				Its correlation binding parameters: Device ID, Sequence ID, Equip ID, Trap ID, 
				Trap Reason ID, Trap Text, Trap Level, Trap Flag, Synchron NO and the time. "
			::= { hwUpsCommonTrapsPrefix 31 }

		
--   1.3.6.1.4.1.2011.6.174.2.2.0.32
-- 1.3.6.1.4.1.2011.6.174.2.2.0.32
		-- 1.3.6.1.4.1.2011.6.174.2.2.0.32
		hwUpsRackMasterConflictResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Rack Master Conflict alarm resume. 
				Its correlation binding parameters: Device ID, Sequence ID, Equip ID, Trap ID, 
				Trap Reason ID, Trap Text, Trap Level, Trap Flag, Synchron NO and the time. "
			::= { hwUpsCommonTrapsPrefix 32 }

		
--   1.3.6.1.4.1.2011.6.174.2.2.0.33
-- 1.3.6.1.4.1.2011.6.174.2.2.0.33
		-- 1.3.6.1.4.1.2011.6.174.2.2.0.33
		hwUpsRackNumNoMatchTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"UPS Rack num dismatch warn. Its correlation binding parameters: Device ID, Sequence ID, Equip ID, Trap ID, 
				Trap Reason ID, Trap Text, Trap Level, Trap Flag, Synchron NO and the time. 
				Additionally, in order to identify the status, UPS system operate status are also include in VB(variable bondings):
				If the enumeration value is Normal(2), it indicates that UPS system  resumes form alarm.  
				If the enumeration value is Alarm(3), it indicates that a new alarm occurs on the UPS sytem."
			::= { hwUpsCommonTrapsPrefix 33 }

		
--   1.3.6.1.4.1.2011.6.174.2.2.0.34
-- 1.3.6.1.4.1.2011.6.174.2.2.0.34
		-- 1.3.6.1.4.1.2011.6.174.2.2.0.34
		hwUpsRackNumNoMatchResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"UPS Rack num dismatch warn resume. Its correlation binding parameters: Device ID, Sequence ID, Equip ID, Trap ID, 
				Trap Reason ID, Trap Text, Trap Level, Trap Flag, Synchron NO and the time. 
				Additionally, in order to identify the status, UPS system operate status are also include in VB(variable bondings):
				If the enumeration value is Normal(2), it indicates that UPS system  resumes form alarm.  
				If the enumeration value is Alarm(3), it indicates that a new alarm occurs on the UPS sytem."
			::= { hwUpsCommonTrapsPrefix 34 }

		
		-- 1.3.6.1.4.1.2011.6.174.2.2.1
		hwUpsCommonStateTrapsPrefix OBJECT IDENTIFIER ::= { hwUpsCommonTraps 1 }

		
--   1.3.6.1.4.1.2011.6.174.2.2.0.35
-- 1.3.6.1.4.1.2011.6.174.2.2.0.35
		-- 1.3.6.1.4.1.2011.6.174.2.2.1.1
		hwUpsRackOnlineStateChangeTrap NOTIFICATION-TYPE
			STATUS current
			DESCRIPTION 
				"Ups Rack Online State Change Trap. Its correlation binding parameters: NULL"
			::= { hwUpsCommonStateTrapsPrefix 1 }

		
--   1.3.6.1.4.1.2011.6.174.2.2.0.36
-- 1.3.6.1.4.1.2011.6.174.2.2.0.36
		-- 1.3.6.1.4.1.2011.6.174.2.2.1.2
		hwUpsRackConfigChangeTrap NOTIFICATION-TYPE
			OBJECTS { hwUpsTrapsDeviceId }
			STATUS current
			DESCRIPTION 
				"Ups Rack Config Change.Its correlation binding parameters: Device ID"
			::= { hwUpsCommonStateTrapsPrefix 2 }

		
--   1.3.6.1.4.1.2011.6.174.2.2.0.37
-- 1.3.6.1.4.1.2011.6.174.2.2.0.37
		-- 1.3.6.1.4.1.2011.6.174.2.2.1.3
		hwUpsRackRunningStateChangeTrap NOTIFICATION-TYPE
			OBJECTS { hwUpsDeviceRunningStatus, hwUpsTrapsDeviceId }
			STATUS current
			DESCRIPTION 
				"Ups Rack Running State Change.Its correlation binding parameters: Device ID and Device running state."
			::= { hwUpsCommonStateTrapsPrefix 3 }

		
--   1.3.6.1.4.1.2011.6.174.2.2.0.38
-- 1.3.6.1.4.1.2011.6.174.2.2.0.38
		-- 1.3.6.1.4.1.2011.6.174.2.2.1.4
		hwUpsBatteryRunningStateChangeTrap NOTIFICATION-TYPE
			OBJECTS { hwUpsDeviceBatteryState, hwUpsTrapsDeviceId }
			STATUS current
			DESCRIPTION 
				"Ups Battery Running State Change,Its correlation binding parameters: Device ID and Battery Running State"
			::= { hwUpsCommonStateTrapsPrefix 4 }

		
		-- 1.3.6.1.4.1.2011.6.174.2.2.1.5
		hwUpsEnergyFloatChangeTrap NOTIFICATION-TYPE
			OBJECTS { hwUpsDeviceEnergyFloatState, hwUpsTrapsDeviceId }
			STATUS current
			DESCRIPTION 
				"Ups Energy Float Change,Its correlation binding parameters: Device ID and The Energy Float State"
			::= { hwUpsCommonStateTrapsPrefix 5 }

		
		-- 1.3.6.1.4.1.2011.6.174.2.2.1.6
		hwUpsVersionChangeTrap NOTIFICATION-TYPE
			OBJECTS { hwUpsTrapsDeviceId }
			STATUS current
			DESCRIPTION 
				"Ups Version Change,Its correlation binding parameters: Device ID"
			::= { hwUpsCommonStateTrapsPrefix 6 }

		
		-- 1.3.6.1.4.1.2011.6.174.2.2.1.7
		hwUpsPowerSupplyMethodChangeTrap NOTIFICATION-TYPE
			OBJECTS { hwUpsDevicePowerSupplyMethod, hwUpsTrapsDeviceId }
			STATUS current
			DESCRIPTION 
				"Ups Power Supply Method Change,Its correlation binding parameters: Device ID and Power Supply Method."
			::= { hwUpsCommonStateTrapsPrefix 7 }

		
--   Alarm that with critical or minor level traps.
-- 
-- 1.3.6.1.4.1.2011.6.174.2.3
-- 1.3.6.1.4.1.2011.6.174.2.3
		-- 1.3.6.1.4.1.2011.6.174.2.3
		hwUpsAlarmTraps OBJECT IDENTIFIER ::= { hwUpsMIBTraps 3 }

		
--   1.3.6.1.4.1.2011.6.174.2.3.0
-- 1.3.6.1.4.1.2011.6.174.2.3.0
		-- 1.3.6.1.4.1.2011.6.174.2.3.0
		hwUpsAlarmTrapsPrefix OBJECT IDENTIFIER ::= { hwUpsAlarmTraps 0 }

		
--   1.3.6.1.4.1.2011.6.174.2.3.0.1
-- 1.3.6.1.4.1.2011.6.174.2.3.0.1
		-- 1.3.6.1.4.1.2011.6.174.2.3.0.1
		hwUpsModNumAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When power module number dismatch, a alarm trap will be send. 
				Its correlation binding parameters:Device ID, Sequence ID, Equip ID, Trap ID, 
				Trap Reason ID, Trap Text, Trap Level, Trap Flag, Synchron NO and the time. "
			::= { hwUpsAlarmTrapsPrefix 1 }

		
--   1.3.6.1.4.1.2011.6.174.2.3.0.2
-- 1.3.6.1.4.1.2011.6.174.2.3.0.2
		-- 1.3.6.1.4.1.2011.6.174.2.3.0.2
		hwUpsModNumAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Power module number dismatch alarm resume trap. 
				Its correlation binding parameters: Device ID, Sequence ID, Equip ID, Trap ID, 
				Trap Reason ID, Trap Text, Trap Level, Trap Flag, Synchron NO and the time. "
			::= { hwUpsAlarmTrapsPrefix 2 }

		
--   1.3.6.1.4.1.2011.6.174.2.3.0.3
-- 1.3.6.1.4.1.2011.6.174.2.3.0.3
		-- 1.3.6.1.4.1.2011.6.174.2.3.0.3
		hwUpsBypassUnitAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Bypass Unit Abnormal Trap.
				Its correlation binding parameters: Device ID, Sequence ID, Equip ID, Trap ID, 
				Trap Reason ID, Trap Text, Trap Level, Trap Flag, Synchron NO and the time. "
			::= { hwUpsAlarmTrapsPrefix 3 }

		
--   1.3.6.1.4.1.2011.6.174.2.3.0.4
-- 1.3.6.1.4.1.2011.6.174.2.3.0.4
		-- 1.3.6.1.4.1.2011.6.174.2.3.0.4
		hwUpsBypassUnitAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Bypass Unit Abnormal Resume Trap.
				Its correlation binding parameters:Device ID, Sequence ID, Equip ID, Trap ID, 
				Trap Reason ID, Trap Text, Trap Level, Trap Flag, Synchron NO and the time. "
			::= { hwUpsAlarmTrapsPrefix 4 }

		
--   1.3.6.1.4.1.2011.6.174.2.3.0.5
-- 1.3.6.1.4.1.2011.6.174.2.3.0.5
		-- 1.3.6.1.4.1.2011.6.174.2.3.0.5
		hwUpsInRackParallelLineAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"In-Rack Parallel Line Abnormal Trap.
				Its correlation binding parameters: Device ID, Sequence ID, Equip ID, Trap ID, 
				Trap Reason ID, Trap Text, Trap Level, Trap Flag, Synchron NO and the time. "
			::= { hwUpsAlarmTrapsPrefix 5 }

		
--   1.3.6.1.4.1.2011.6.174.2.3.0.6
-- 1.3.6.1.4.1.2011.6.174.2.3.0.6
		-- 1.3.6.1.4.1.2011.6.174.2.3.0.6
		hwUpsInRackParallelLineAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"In-Rack Parallel Line Abnormal Resume Trap.
				Its correlation binding parameters: Device ID, Sequence ID, Equip ID, Trap ID, 
				Trap Reason ID, Trap Text, Trap Level, Trap Flag, Synchron NO and the time. "
			::= { hwUpsAlarmTrapsPrefix 6 }

		
--   1.3.6.1.4.1.2011.6.174.2.3.0.7
-- 1.3.6.1.4.1.2011.6.174.2.3.0.7
		-- 1.3.6.1.4.1.2011.6.174.2.3.0.7
		hwUpsBetweenRackParallelLineAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Between-Rack Parallel Line Abnormal Trap.
				Its correlation binding parameters: Device ID, Sequence ID, Equip ID, Trap ID, 
				Trap Reason ID, Trap Text, Trap Level, Trap Flag, Synchron NO and the time. "
			::= { hwUpsAlarmTrapsPrefix 7 }

		
--   1.3.6.1.4.1.2011.6.174.2.3.0.8
-- 1.3.6.1.4.1.2011.6.174.2.3.0.8
		-- 1.3.6.1.4.1.2011.6.174.2.3.0.8
		hwUpsBetweenRackParallelLineAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Between-Rack Parallel Line Abnormal Resume Trap.
				Its correlation binding parameters: Device ID, Sequence ID, Equip ID, Trap ID, 
				Trap Reason ID, Trap Text, Trap Level, Trap Flag, Synchron NO and the time. "
			::= { hwUpsAlarmTrapsPrefix 8 }

		
--   1.3.6.1.4.1.2011.6.174.2.3.0.9
-- 1.3.6.1.4.1.2011.6.174.2.3.0.9
		-- 1.3.6.1.4.1.2011.6.174.2.3.0.9
		hwUpsFanAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Fan Abnormal Trap.
				Its correlation binding parameters: Device ID, Sequence ID, Equip ID, Trap ID, 
				Trap Reason ID, Trap Text, Trap Level, Trap Flag, Synchron NO and the time. "
			::= { hwUpsAlarmTrapsPrefix 9 }

		
--   1.3.6.1.4.1.2011.6.174.2.3.0.10
-- 1.3.6.1.4.1.2011.6.174.2.3.0.10
		-- 1.3.6.1.4.1.2011.6.174.2.3.0.10
		hwUpsFanAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Fan Abnormal Resume Trap.
				Its correlation binding parameters: Device ID, Sequence ID, Equip ID, Trap ID, 
				Trap Reason ID, Trap Text, Trap Level, Trap Flag, Synchron NO and the time. "
			::= { hwUpsAlarmTrapsPrefix 10 }

		
--   1.3.6.1.4.1.2011.6.174.2.3.0.11
-- 1.3.6.1.4.1.2011.6.174.2.3.0.11
		-- 1.3.6.1.4.1.2011.6.174.2.3.0.11
		hwUpsAuxiliaryPowerAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Auxiliary Power Abnormal Trap.
				Its correlation binding parameters: Device ID, Sequence ID, Equip ID, Trap ID, 
				Trap Reason ID, Trap Text, Trap Level, Trap Flag, Synchron NO and the time. "
			::= { hwUpsAlarmTrapsPrefix 11 }

		
--   1.3.6.1.4.1.2011.6.174.2.3.0.12
-- 1.3.6.1.4.1.2011.6.174.2.3.0.12
		-- 1.3.6.1.4.1.2011.6.174.2.3.0.12
		hwUpsAuxiliaryPowerAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Auxiliary Power Abnormal Resume Trap.
				Its correlation binding parameters: Device ID, Sequence ID, Equip ID, Trap ID, 
				Trap Reason ID, Trap Text, Trap Level, Trap Flag, Synchron NO and the time. "
			::= { hwUpsAlarmTrapsPrefix 12 }

		
--   1.3.6.1.4.1.2011.6.174.2.3.0.13
-- 1.3.6.1.4.1.2011.6.174.2.3.0.13
		-- 1.3.6.1.4.1.2011.6.174.2.3.0.13
		hwUpsVersionMismatchAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"when version mismatch alarms happen, a alarm trap will be send.
				Its correlation binding parameters:Device ID, Sequence ID, Equip ID, Trap ID, 
				Trap Reason ID, Trap Text, Trap Level, Trap Flag, Synchron NO and the time. "
			::= { hwUpsAlarmTrapsPrefix 13 }

		
--   1.3.6.1.4.1.2011.6.174.2.3.0.14
-- 1.3.6.1.4.1.2011.6.174.2.3.0.14
		-- 1.3.6.1.4.1.2011.6.174.2.3.0.14
		hwUpsVersionMatchAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Version mismatch Abnormal Resume Trap.
				Its correlation binding parameters: Device ID, Sequence ID, Equip ID, Trap ID, 
				Trap Reason ID, Trap Text, Trap Level, Trap Flag, Synchron NO and the time. "
			::= { hwUpsAlarmTrapsPrefix 14 }

		
--   1.3.6.1.4.1.2011.6.174.2.3.0.15
-- 1.3.6.1.4.1.2011.6.174.2.3.0.15
		-- 1.3.6.1.4.1.2011.6.174.2.3.0.15
		hwUpsAddrConflictAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Address Conflict Trap.
				Its correlation binding parameters: Device ID, Sequence ID, Equip ID, Trap ID, 
				Trap Reason ID, Trap Text, Trap Level, Trap Flag, Synchron NO and the time. "
			::= { hwUpsAlarmTrapsPrefix 15 }

		
--   1.3.6.1.4.1.2011.6.174.2.3.0.16
-- 1.3.6.1.4.1.2011.6.174.2.3.0.16
		-- 1.3.6.1.4.1.2011.6.174.2.3.0.16
		hwUpsAddrConflictAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Address Conflict Resume Trap.
				Its correlation binding parameters: Device ID, Sequence ID, Equip ID, Trap ID, 
				Trap Reason ID, Trap Text, Trap Level, Trap Flag, Synchron NO and the time. "
			::= { hwUpsAlarmTrapsPrefix 16 }

		
--   1.3.6.1.4.1.2011.6.174.2.3.0.17
-- 1.3.6.1.4.1.2011.6.174.2.3.0.17
		-- 1.3.6.1.4.1.2011.6.174.2.3.0.17
		hwUpsEmergencyPowerOffAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Emergency Power Off Abnormal Trap.
				Its correlation binding parameters:Device ID, Sequence ID, Equip ID, Trap ID, 
				Trap Reason ID, Trap Text, Trap Level, Trap Flag, Synchron NO and the time. "
			::= { hwUpsAlarmTrapsPrefix 17 }

		
--   1.3.6.1.4.1.2011.6.174.2.3.0.18
-- 1.3.6.1.4.1.2011.6.174.2.3.0.18
		-- 1.3.6.1.4.1.2011.6.174.2.3.0.18
		hwUpsEmergencyPowerOffAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Emergency Power Off Abnormal Resume Trap.
				Its correlation binding parameters:Device ID, Sequence ID, Equip ID, Trap ID, 
				Trap Reason ID, Trap Text, Trap Level, Trap Flag, Synchron NO and the time. "
			::= { hwUpsAlarmTrapsPrefix 18 }

		
--   1.3.6.1.4.1.2011.6.174.2.3.0.19
-- 1.3.6.1.4.1.2011.6.174.2.3.0.19
		-- 1.3.6.1.4.1.2011.6.174.2.3.0.19
		hwUpsBypassInputAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Bypass Input Abnormal Trap.
				Its correlation binding parameters: Device ID, Sequence ID, Equip ID, Trap ID, 
				Trap Reason ID, Trap Text, Trap Level, Trap Flag, Synchron NO and the time. "
			::= { hwUpsAlarmTrapsPrefix 19 }

		
--   1.3.6.1.4.1.2011.6.174.2.3.0.20
-- 1.3.6.1.4.1.2011.6.174.2.3.0.20
		-- 1.3.6.1.4.1.2011.6.174.2.3.0.20
		hwUpsBypassInputAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Bypass Input Abnormal Resume Trap.
				Its correlation binding parameters: Device ID, Sequence ID, Equip ID, Trap ID, 
				Trap Reason ID, Trap Text, Trap Level, Trap Flag, Synchron NO and the time. "
			::= { hwUpsAlarmTrapsPrefix 20 }

		
--   1.3.6.1.4.1.2011.6.174.2.3.0.21
-- 1.3.6.1.4.1.2011.6.174.2.3.0.21
		-- 1.3.6.1.4.1.2011.6.174.2.3.0.21
		hwUpsInputIsolatingTransAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Transformer Abnormal Trap.
				Its correlation binding parameters: Device ID, Sequence ID, Equip ID, Trap ID, 
				Trap Reason ID, Trap Text, Trap Level, Trap Flag, Synchron NO and the time. "
			::= { hwUpsAlarmTrapsPrefix 21 }

		
--   1.3.6.1.4.1.2011.6.174.2.3.0.22
-- 1.3.6.1.4.1.2011.6.174.2.3.0.22
		-- 1.3.6.1.4.1.2011.6.174.2.3.0.22
		hwUpsInputIsolatingTransAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Transformer Abnormal Resume Trap.
				Its correlation binding parameters: Device ID, Sequence ID, Equip ID, Trap ID, 
				Trap Reason ID, Trap Text, Trap Level, Trap Flag, Synchron NO and the time. "
			::= { hwUpsAlarmTrapsPrefix 22 }

		
--   1.3.6.1.4.1.2011.6.174.2.3.0.23
-- 1.3.6.1.4.1.2011.6.174.2.3.0.23
		-- 1.3.6.1.4.1.2011.6.174.2.3.0.23
		hwUpsInternalAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Supervision Unit Internal Fault Trap.
				Its correlation binding parameters: Device ID, Sequence ID, Equip ID, Trap ID, 
				Trap Reason ID, Trap Text, Trap Level, Trap Flag, Synchron NO and the time. "
			::= { hwUpsAlarmTrapsPrefix 23 }

		
--   1.3.6.1.4.1.2011.6.174.2.3.0.24
-- 1.3.6.1.4.1.2011.6.174.2.3.0.24
		-- 1.3.6.1.4.1.2011.6.174.2.3.0.24
		hwUpsInternalAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Supervision Unit Internal Fault Resume Trap.
				Its correlation binding parameters: Device ID, Sequence ID, Equip ID, Trap ID, 
				Trap Reason ID, Trap Text, Trap Level, Trap Flag, Synchron NO and the time. "
			::= { hwUpsAlarmTrapsPrefix 24 }

		
--   1.3.6.1.4.1.2011.6.174.2.3.0.25
-- 1.3.6.1.4.1.2011.6.174.2.3.0.25
		-- 1.3.6.1.4.1.2011.6.174.2.3.0.25
		hwUpsRectifierAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Rectifier Abnormal Trap.
				Its correlation binding parameters: Device ID, Sequence ID, Equip ID, Trap ID, 
				Trap Reason ID, Trap Text, Trap Level, Trap Flag, Synchron NO and the time. "
			::= { hwUpsAlarmTrapsPrefix 25 }

		
--   1.3.6.1.4.1.2011.6.174.2.3.0.26
-- 1.3.6.1.4.1.2011.6.174.2.3.0.26
		-- 1.3.6.1.4.1.2011.6.174.2.3.0.26
		hwUpsRectifierAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Rectifier Abnormal Resume Trap.
				Its correlation binding parameters: Device ID, Sequence ID, Equip ID, Trap ID, 
				Trap Reason ID, Trap Text, Trap Level, Trap Flag, Synchron NO and the time. "
			::= { hwUpsAlarmTrapsPrefix 26 }

		
--   1.3.6.1.4.1.2011.6.174.2.3.0.27
-- 1.3.6.1.4.1.2011.6.174.2.3.0.27
		-- 1.3.6.1.4.1.2011.6.174.2.3.0.27
		hwUpsChargerAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Charger Abnormal Trap.
				Its correlation binding parameters: Device ID, Sequence ID, Equip ID, Trap ID, 
				Trap Reason ID, Trap Text, Trap Level, Trap Flag, Synchron NO and the time. "
			::= { hwUpsAlarmTrapsPrefix 27 }

		
--   1.3.6.1.4.1.2011.6.174.2.3.0.28
-- 1.3.6.1.4.1.2011.6.174.2.3.0.28
		-- 1.3.6.1.4.1.2011.6.174.2.3.0.28
		hwUpsChargerAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Charger Abnormal Resume Trap.
				Its correlation binding parameters:Device ID, Sequence ID, Equip ID, Trap ID, 
				Trap Reason ID, Trap Text, Trap Level, Trap Flag, Synchron NO and the time. "
			::= { hwUpsAlarmTrapsPrefix 28 }

		
--   1.3.6.1.4.1.2011.6.174.2.3.0.29
-- 1.3.6.1.4.1.2011.6.174.2.3.0.29
		-- 1.3.6.1.4.1.2011.6.174.2.3.0.29
		hwUpsDischargerAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Discharger Abnormal Trap.
				Its correlation binding parameters:Device ID, Sequence ID, Equip ID, Trap ID, 
				Trap Reason ID, Trap Text, Trap Level, Trap Flag, Synchron NO and the time. "
			::= { hwUpsAlarmTrapsPrefix 29 }

		
--   1.3.6.1.4.1.2011.6.174.2.3.0.30
-- 1.3.6.1.4.1.2011.6.174.2.3.0.30
		-- 1.3.6.1.4.1.2011.6.174.2.3.0.30
		hwUpsDischargerAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Discharger Abnormal Resume Trap.
				Its correlation binding parameters: Device ID, Sequence ID, Equip ID, Trap ID, 
				Trap Reason ID, Trap Text, Trap Level, Trap Flag, Synchron NO and the time. "
			::= { hwUpsAlarmTrapsPrefix 30 }

		
--   1.3.6.1.4.1.2011.6.174.2.3.0.31
-- 1.3.6.1.4.1.2011.6.174.2.3.0.31
		-- 1.3.6.1.4.1.2011.6.174.2.3.0.31
		hwUpsACAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"AC Abnormal Trap.
				Its correlation binding parameters: Device ID, Sequence ID, Equip ID, Trap ID, 
				Trap Reason ID, Trap Text, Trap Level, Trap Flag, Synchron NO and the time. "
			::= { hwUpsAlarmTrapsPrefix 31 }

		
--   1.3.6.1.4.1.2011.6.174.2.3.0.32
-- 1.3.6.1.4.1.2011.6.174.2.3.0.32
		-- 1.3.6.1.4.1.2011.6.174.2.3.0.32
		hwUpsACAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"AC Abnormal Resume Trap.
				Its correlation binding parameters: Device ID, Sequence ID, Equip ID, Trap ID, 
				Trap Reason ID, Trap Text, Trap Level, Trap Flag, Synchron NO and the time. "
			::= { hwUpsAlarmTrapsPrefix 32 }

		
--   1.3.6.1.4.1.2011.6.174.2.3.0.33
-- 1.3.6.1.4.1.2011.6.174.2.3.0.33
		-- 1.3.6.1.4.1.2011.6.174.2.3.0.33
		hwUpsModuleNotReadyAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Module Not Ready Abnormal Trap.
				Its correlation binding parameters: Device ID, Sequence ID, Equip ID, Trap ID, 
				Trap Reason ID, Trap Text, Trap Level, Trap Flag, Synchron NO and the time. "
			::= { hwUpsAlarmTrapsPrefix 33 }

		
--   1.3.6.1.4.1.2011.6.174.2.3.0.34
-- 1.3.6.1.4.1.2011.6.174.2.3.0.34
		-- 1.3.6.1.4.1.2011.6.174.2.3.0.34
		hwUpsModuleNotReadyAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Module Not Ready Abnormal Resume Trap.
				Its correlation binding parameters: Device ID, Sequence ID, Equip ID, Trap ID, 
				Trap Reason ID, Trap Text, Trap Level, Trap Flag, Synchron NO and the time. "
			::= { hwUpsAlarmTrapsPrefix 34 }

		
--   1.3.6.1.4.1.2011.6.174.2.3.0.35
-- 1.3.6.1.4.1.2011.6.174.2.3.0.35
		-- 1.3.6.1.4.1.2011.6.174.2.3.0.35
		hwUpsInverterAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Inverter Abnormal Trap.
				Its correlation binding parameters: Device ID, Sequence ID, Equip ID, Trap ID, 
				Trap Reason ID, Trap Text, Trap Level, Trap Flag, Synchron NO and the time. "
			::= { hwUpsAlarmTrapsPrefix 35 }

		
--   1.3.6.1.4.1.2011.6.174.2.3.0.36
-- 1.3.6.1.4.1.2011.6.174.2.3.0.36
		-- 1.3.6.1.4.1.2011.6.174.2.3.0.36
		hwUpsInverterAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Inverter Abnormal Resume Trap.
				Its correlation binding parameters: Device ID, Sequence ID, Equip ID, Trap ID, 
				Trap Reason ID, Trap Text, Trap Level, Trap Flag, Synchron NO and the time. "
			::= { hwUpsAlarmTrapsPrefix 36 }

		
--   1.3.6.1.4.1.2011.6.174.2.3.0.37
-- 1.3.6.1.4.1.2011.6.174.2.3.0.37
		-- 1.3.6.1.4.1.2011.6.174.2.3.0.37
		hwUpsECUAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"ECU Abnormal Trap.
				Its correlation binding parameters: Device ID, Sequence ID, Equip ID, Trap ID, 
				Trap Reason ID, Trap Text, Trap Level, Trap Flag, Synchron NO and the time. "
			::= { hwUpsAlarmTrapsPrefix 37 }

		
--   1.3.6.1.4.1.2011.6.174.2.3.0.38
-- 1.3.6.1.4.1.2011.6.174.2.3.0.38
		-- 1.3.6.1.4.1.2011.6.174.2.3.0.38
		hwUpsECUAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"ECU Abnormal Resume Trap.
				Its correlation binding parameters: Device ID, Sequence ID, Equip ID, Trap ID, 
				Trap Reason ID, Trap Text, Trap Level, Trap Flag, Synchron NO and the time. "
			::= { hwUpsAlarmTrapsPrefix 38 }

		
--   1.3.6.1.4.1.2011.6.174.2.3.0.39
-- 1.3.6.1.4.1.2011.6.174.2.3.0.39
		-- 1.3.6.1.4.1.2011.6.174.2.3.0.39
		hwUpsSPDAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"SPD Abnormal Trap.
				Its correlation binding parameters: Device ID, Sequence ID, Equip ID, Trap ID, 
				Trap Reason ID, Trap Text, Trap Level, Trap Flag, Synchron NO and the time. "
			::= { hwUpsAlarmTrapsPrefix 39 }

		
--   1.3.6.1.4.1.2011.6.174.2.3.0.40
-- 1.3.6.1.4.1.2011.6.174.2.3.0.40
		-- 1.3.6.1.4.1.2011.6.174.2.3.0.40
		hwUpsSPDAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"SPD Abnormal Resume Trap. 
				Its correlation binding parameters: Device ID, Sequence ID, Equip ID, Trap ID, 
				Trap Reason ID, Trap Text, Trap Level, Trap Flag, Synchron NO and the time. "
			::= { hwUpsAlarmTrapsPrefix 40 }

		
--   1.3.6.1.4.1.2011.6.174.2.3.0.41
-- 1.3.6.1.4.1.2011.6.174.2.3.0.41
		-- 1.3.6.1.4.1.2011.6.174.2.3.0.41
		hwUpsOperationFaultAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Operation Fault Abnormal Trap.
				Its correlation binding parameters: Device ID, Sequence ID, Equip ID, Trap ID, 
				Trap Reason ID, Trap Text, Trap Level, Trap Flag, Synchron NO and the time. "
			::= { hwUpsAlarmTrapsPrefix 41 }

		
--   1.3.6.1.4.1.2011.6.174.2.3.0.42
-- 1.3.6.1.4.1.2011.6.174.2.3.0.42
		-- 1.3.6.1.4.1.2011.6.174.2.3.0.42
		hwUpsOperationFaultAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Operation Fault Abnormal Resume Trap.
				Its correlation binding parameters: Device ID, Sequence ID, Equip ID, Trap ID, 
				Trap Reason ID, Trap Text, Trap Level, Trap Flag, Synchron NO and the time. "
			::= { hwUpsAlarmTrapsPrefix 42 }

		
--   1.3.6.1.4.1.2011.6.174.2.3.0.43
-- 1.3.6.1.4.1.2011.6.174.2.3.0.43
		-- 1.3.6.1.4.1.2011.6.174.2.3.0.43
		hwUpsOverLoadAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Over Load Abnormal Trap.
				Its correlation binding parameters: Device ID, Sequence ID, Equip ID, Trap ID, 
				Trap Reason ID, Trap Text, Trap Level, Trap Flag, Synchron NO and the time. "
			::= { hwUpsAlarmTrapsPrefix 43 }

		
--   1.3.6.1.4.1.2011.6.174.2.3.0.44
-- 1.3.6.1.4.1.2011.6.174.2.3.0.44
		-- 1.3.6.1.4.1.2011.6.174.2.3.0.44
		hwUpsOverLoadAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Over Load Abnormal Resume Trap.
				Its correlation binding parameters:Device ID, Sequence ID, Equip ID, Trap ID, 
				Trap Reason ID, Trap Text, Trap Level, Trap Flag, Synchron NO and the time. "
			::= { hwUpsAlarmTrapsPrefix 44 }

		
--   1.3.6.1.4.1.2011.6.174.2.3.0.45
-- 1.3.6.1.4.1.2011.6.174.2.3.0.45
		-- 1.3.6.1.4.1.2011.6.174.2.3.0.45
		hwUpsOverLoadOverTimeAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Over-Load Overtime Abnormal Trap.
				Its correlation binding parameters: Device ID, Sequence ID, Equip ID, Trap ID, 
				Trap Reason ID, Trap Text, Trap Level, Trap Flag, Synchron NO and the time. "
			::= { hwUpsAlarmTrapsPrefix 45 }

		
--   1.3.6.1.4.1.2011.6.174.2.3.0.46
-- 1.3.6.1.4.1.2011.6.174.2.3.0.46
		-- 1.3.6.1.4.1.2011.6.174.2.3.0.46
		hwUpsOverLoadOverTimeAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Over-Load Overtime Abnormal Resume Trap.
				Its correlation binding parameters: Device ID, Sequence ID, Equip ID, Trap ID, 
				Trap Reason ID, Trap Text, Trap Level, Trap Flag, Synchron NO and the time. "
			::= { hwUpsAlarmTrapsPrefix 46 }

		
--   1.3.6.1.4.1.2011.6.174.2.3.0.47
-- 1.3.6.1.4.1.2011.6.174.2.3.0.47
		-- 1.3.6.1.4.1.2011.6.174.2.3.0.47
		hwUpsLBSAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"LBS Abnormal Trap.
				Its correlation binding parameters: Device ID, Sequence ID, Equip ID, Trap ID, 
				Trap Reason ID, Trap Text, Trap Level, Trap Flag, Synchron NO and the time. "
			::= { hwUpsAlarmTrapsPrefix 47 }

		
--   1.3.6.1.4.1.2011.6.174.2.3.0.48
-- 1.3.6.1.4.1.2011.6.174.2.3.0.48
		-- 1.3.6.1.4.1.2011.6.174.2.3.0.48
		hwUpsLBSAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"LBS Abnormal Resume Trap.
				Its correlation binding parameters: Device ID, Sequence ID, Equip ID, Trap ID, 
				Trap Reason ID, Trap Text, Trap Level, Trap Flag, Synchron NO and the time. "
			::= { hwUpsAlarmTrapsPrefix 48 }

		
--   1.3.6.1.4.1.2011.6.174.2.3.0.49
-- 1.3.6.1.4.1.2011.6.174.2.3.0.49
		-- 1.3.6.1.4.1.2011.6.174.2.3.0.49
		hwUpsBypSwitchAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Bypass Switch Abnormal Resume Trap.
				Its correlation binding parameters: Device ID, Sequence ID, Equip ID, Trap ID, 
				Trap Reason ID, Trap Text, Trap Level, Trap Flag, Synchron NO and the time. "
			::= { hwUpsAlarmTrapsPrefix 49 }

		
--   1.3.6.1.4.1.2011.6.174.2.3.0.50
-- 1.3.6.1.4.1.2011.6.174.2.3.0.50
		-- 1.3.6.1.4.1.2011.6.174.2.3.0.50
		hwUpsBypSwitchAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Bypass Switch Abnormal Resume Trap.
				Its correlation binding parameters: Device ID, Sequence ID, Equip ID, Trap ID, 
				Trap Reason ID, Trap Text, Trap Level, Trap Flag, Synchron NO and the time. "
			::= { hwUpsAlarmTrapsPrefix 50 }

		
--   1.3.6.1.4.1.2011.6.174.2.3.0.51
-- 1.3.6.1.4.1.2011.6.174.2.3.0.51
		-- 1.3.6.1.4.1.2011.6.174.2.3.0.51
		hwUpsBatteryFault1AlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When battery reversed, no Battery, battery earth fault or battery stop discharge abnormal happen, an alarm trap will be send through this OID. 
				Its correlation binding parameters: Device ID, Sequence ID, Equip ID, Trap ID, 
				Trap Reason ID, Trap Text, Trap Level, Trap Flag, Synchron NO and the time. "
			::= { hwUpsAlarmTrapsPrefix 51 }

		
--   1.3.6.1.4.1.2011.6.174.2.3.0.52
-- 1.3.6.1.4.1.2011.6.174.2.3.0.52
		-- 1.3.6.1.4.1.2011.6.174.2.3.0.52
		hwUpsBatteryFault1AlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When battery reversed, no Battery, battery earth fault or battery stop discharge abnormal resume, a trap will be send through this OID. 
				Its correlation binding parameters: Device ID, Sequence ID, Equip ID, Trap ID, 
				Trap Reason ID, Trap Text, Trap Level, Trap Flag, Synchron NO and the time. "
			::= { hwUpsAlarmTrapsPrefix 52 }

		
--   1.3.6.1.4.1.2011.6.174.2.3.0.53
-- 1.3.6.1.4.1.2011.6.174.2.3.0.53
		-- 1.3.6.1.4.1.2011.6.174.2.3.0.53
		hwUpsBatteryFault2AlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When battery over temperature, battery need maintenance, or battery voltage low abnormal happen, an alarm trap will be send through this OID. 
				Its correlation binding parameters: Device ID, Sequence ID, Equip ID, Trap ID, 
				Trap Reason ID, Trap Text, Trap Level, Trap Flag, Synchron NO and the time. "
			::= { hwUpsAlarmTrapsPrefix 53 }

		
--   1.3.6.1.4.1.2011.6.174.2.3.0.54
-- 1.3.6.1.4.1.2011.6.174.2.3.0.54
		-- 1.3.6.1.4.1.2011.6.174.2.3.0.54
		hwUpsBatteryFault2AlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"When battery over temperature, battery need maintenance, or battery voltage low abnormal resume, a trap will be send through this OID. 
				Its correlation binding parameters:Device ID, Sequence ID, Equip ID, Trap ID, 
				Trap Reason ID, Trap Text, Trap Level, Trap Flag, Synchron NO and the time. "
			::= { hwUpsAlarmTrapsPrefix 54 }

		
		-- 1.3.6.1.4.1.2011.6.174.2.3.0.55
		hwUpsBatteryChangeLimitAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Battery Change Limit Trap.
				Its correlation binding parameters: Device ID, Sequence ID, Equip ID, Trap ID, 
				Trap Reason ID, Trap Text, Trap Level, Trap Flag, Synchron NO and the time. "
			::= { hwUpsAlarmTrapsPrefix 55 }

		
		-- 1.3.6.1.4.1.2011.6.174.2.3.0.56
		hwUpsBatteryChangeLimitAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Battery Change Limit Resume Trap.
				Its correlation binding parameters: Device ID, Sequence ID, Equip ID, Trap ID, 
				Trap Reason ID, Trap Text, Trap Level, Trap Flag, Synchron NO and the time. "
			::= { hwUpsAlarmTrapsPrefix 56 }

		
		-- 1.3.6.1.4.1.2011.6.174.2.3.0.57
		hwUpsRectifierStartLimitAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Rectifier Start Limit Trap.
				Its correlation binding parameters: Device ID, Sequence ID, Equip ID, Trap ID, 
				Trap Reason ID, Trap Text, Trap Level, Trap Flag, Synchron NO and the time. "
			::= { hwUpsAlarmTrapsPrefix 57 }

		
		-- 1.3.6.1.4.1.2011.6.174.2.3.0.58
		hwUpsRectifierStartLimitAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Rectifier Start Limit Resume Trap.
				Its correlation binding parameters: Device ID, Sequence ID, Equip ID, Trap ID, 
				Trap Reason ID, Trap Text, Trap Level, Trap Flag, Synchron NO and the time. "
			::= { hwUpsAlarmTrapsPrefix 58 }

		
		-- 1.3.6.1.4.1.2011.6.174.2.3.0.59
		hwUpsMainLoadCapicityAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Main Load Capicity Trap.
				Its correlation binding parameters: Device ID, Sequence ID, Equip ID, Trap ID, 
				Trap Reason ID, Trap Text, Trap Level, Trap Flag, Synchron NO and the time. "
			::= { hwUpsAlarmTrapsPrefix 59 }

		
		-- 1.3.6.1.4.1.2011.6.174.2.3.0.60
		hwUpsMainLoadCapicityAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Main Load Capicity Resume Trap.
				Its correlation binding parameters: Device ID, Sequence ID, Equip ID, Trap ID, 
				Trap Reason ID, Trap Text, Trap Level, Trap Flag, Synchron NO and the time. "
			::= { hwUpsAlarmTrapsPrefix 60 }

		
		-- 1.3.6.1.4.1.2011.6.174.2.3.0.61
		hwUpsBatteryChangeAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Batterry Change Trap.
				Its correlation binding parameters: Device ID, Sequence ID, Equip ID, Trap ID, 
				Trap Reason ID, Trap Text, Trap Level, Trap Flag, Synchron NO and the time. "
			::= { hwUpsAlarmTrapsPrefix 61 }

		
		-- 1.3.6.1.4.1.2011.6.174.2.3.0.62
		hwUpsBatteryChangeAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Batterry Change Resume Trap.
				Its correlation binding parameters: Device ID, Sequence ID, Equip ID, Trap ID, 
				Trap Reason ID, Trap Text, Trap Level, Trap Flag, Synchron NO and the time. "
			::= { hwUpsAlarmTrapsPrefix 62 }

		
		-- 1.3.6.1.4.1.2011.6.174.2.3.0.63
		hwUpsBatteryMaintainAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Batterry Maintain Trap.
				Its correlation binding parameters: Device ID, Sequence ID, Equip ID, Trap ID, 
				Trap Reason ID, Trap Text, Trap Level, Trap Flag, Synchron NO and the time. "
			::= { hwUpsAlarmTrapsPrefix 63 }

		
		-- 1.3.6.1.4.1.2011.6.174.2.3.0.64
		hwUpsBatteryMaintainAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Batterry Maintain Resume Trap.
				Its correlation binding parameters: Device ID, Sequence ID, Equip ID, Trap ID, 
				Trap Reason ID, Trap Text, Trap Level, Trap Flag, Synchron NO and the time. "
			::= { hwUpsAlarmTrapsPrefix 64 }

		
		-- 1.3.6.1.4.1.2011.6.174.2.3.0.65
		hwUpsMinorLoadOffAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Minor Load Off Trap.
				Its correlation binding parameters: Device ID, Sequence ID, Equip ID, Trap ID, 
				Trap Reason ID, Trap Text, Trap Level, Trap Flag, Synchron NO and the time. "
			::= { hwUpsAlarmTrapsPrefix 65 }

		
		-- 1.3.6.1.4.1.2011.6.174.2.3.0.66
		hwUpsMinorLoadOffAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Minor Load Off Resume Trap.
				Its correlation binding parameters: Device ID, Sequence ID, Equip ID, Trap ID, 
				Trap Reason ID, Trap Text, Trap Level, Trap Flag, Synchron NO and the time. "
			::= { hwUpsAlarmTrapsPrefix 66 }

		
		-- 1.3.6.1.4.1.2011.6.174.2.3.0.67
		hwUpsParaStatusSetAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Parallel Status Set Trap.
				Its correlation binding parameters: Device ID, Sequence ID, Equip ID, Trap ID, 
				Trap Reason ID, Trap Text, Trap Level, Trap Flag, Synchron NO and the time. "
			::= { hwUpsAlarmTrapsPrefix 67 }

		
		-- 1.3.6.1.4.1.2011.6.174.2.3.0.68
		hwUpsParaStatusSetAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Parallel Status Set Resume Trap.
				Its correlation binding parameters: Device ID, Sequence ID, Equip ID, Trap ID, 
				Trap Reason ID, Trap Text, Trap Level, Trap Flag, Synchron NO and the time. "
			::= { hwUpsAlarmTrapsPrefix 68 }

		
		-- 1.3.6.1.4.1.2011.6.174.2.3.0.69
		hwUpsRemainCapacityAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Remain Capacity Trap.
				Its correlation binding parameters: Device ID, Sequence ID, Equip ID, Trap ID, 
				Trap Reason ID, Trap Text, Trap Level, Trap Flag, Synchron NO and the time. "
			::= { hwUpsAlarmTrapsPrefix 69 }

		
		-- 1.3.6.1.4.1.2011.6.174.2.3.0.70
		hwUpsRemainCapacityAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Remain Capacity Resume Trap.
				Its correlation binding parameters: Device ID, Sequence ID, Equip ID, Trap ID, 
				Trap Reason ID, Trap Text, Trap Level, Trap Flag, Synchron NO and the time. "
			::= { hwUpsAlarmTrapsPrefix 70 }

		
		-- 1.3.6.1.4.1.2011.6.174.2.3.0.71
		hwUpsParParaAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Parallel Parameter Trap.
				Its correlation binding parameters: Device ID, Sequence ID, Equip ID, Trap ID, 
				Trap Reason ID, Trap Text, Trap Level, Trap Flag, Synchron NO and the time. "
			::= { hwUpsAlarmTrapsPrefix 71 }

		
		-- 1.3.6.1.4.1.2011.6.174.2.3.0.72
		hwUpsParParaAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Parallel Parameter Resume Trap.
				Its correlation binding parameters: Device ID, Sequence ID, Equip ID, Trap ID, 
				Trap Reason ID, Trap Text, Trap Level, Trap Flag, Synchron NO and the tim"
			::= { hwUpsAlarmTrapsPrefix 72 }

		
		-- 1.3.6.1.4.1.2011.6.174.2.3.0.73
		hwUpsFlashAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Flash Trap.
				Its correlation binding parameters: Device ID, Sequence ID, Equip ID, Trap ID, 
				Trap Reason ID, Trap Text, Trap Level, Trap Flag, Synchron NO and the time"
			::= { hwUpsAlarmTrapsPrefix 73 }

		
		-- 1.3.6.1.4.1.2011.6.174.2.3.0.74
		hwUpsFlashAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Flash Resume Trap.
				Its correlation binding parameters: Device ID, Sequence ID, Equip ID, Trap ID, 
				Trap Reason ID, Trap Text, Trap Level, Trap Flag, Synchron NO and the time"
			::= { hwUpsAlarmTrapsPrefix 74 }

		
		-- 1.3.6.1.4.1.2011.6.174.2.3.0.75
		hwUpsManulPowerOnOffTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Manul Power On Off Trap.
				Its correlation binding parameters: Device ID, Sequence ID, Equip ID, Trap ID, 
				Trap Reason ID, Trap Text, Trap Level, Trap Flag, Synchron NO and the time"
			::= { hwUpsAlarmTrapsPrefix 75 }

		
		-- 1.3.6.1.4.1.2011.6.174.2.3.0.76
		hwUpsManulPowerOnOffResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Manul Power On Off Resume Trap.
				Its correlation binding parameters: Device ID, Sequence ID, Equip ID, Trap ID, 
				Trap Reason ID, Trap Text, Trap Level, Trap Flag, Synchron NO and the time"
			::= { hwUpsAlarmTrapsPrefix 76 }

		
		-- 1.3.6.1.4.1.2011.6.174.2.3.0.77
		hwUpsIOAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"IO signal Trap.
				Its correlation binding parameters: Device ID, Sequence ID, Equip ID, Trap ID, 
				Trap Reason ID, Trap Text, Trap Level, Trap Flag, Synchron NO and the time"
			::= { hwUpsAlarmTrapsPrefix 77 }

		
		-- 1.3.6.1.4.1.2011.6.174.2.3.0.78
		hwUpsIOAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"IO Signal Resume Trap.
				Its correlation binding parameters: Device ID, Sequence ID, Equip ID, Trap ID, 
				Trap Reason ID, Trap Text, Trap Level, Trap Flag, Synchron NO and the time"
			::= { hwUpsAlarmTrapsPrefix 78 }

		
		-- 1.3.6.1.4.1.2011.6.174.2.3.0.79
		hwUpsEnvironmentDataAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Environment Date Trap.
				Its correlation binding parameters: Device ID, Sequence ID, Equip ID, Trap ID, 
				Trap Reason ID, Trap Text, Trap Level, Trap Flag, Synchron NO and the time"
			::= { hwUpsAlarmTrapsPrefix 79 }

		
		-- 1.3.6.1.4.1.2011.6.174.2.3.0.80
		hwUpsEnvironmentDataAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Environment Date Resume Trap.
				Its correlation binding parameters: Device ID, Sequence ID, Equip ID, Trap ID, 
				Trap Reason ID, Trap Text, Trap Level, Trap Flag, Synchron NO and the time"
			::= { hwUpsAlarmTrapsPrefix 80 }

		
		-- 1.3.6.1.4.1.2011.6.174.2.3.0.81
		hwUpsUpdatingAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Updating Trap.
				Its correlation binding parameters: Device ID, Sequence ID, Equip ID, Trap ID, 
				Trap Reason ID, Trap Text, Trap Level, Trap Flag, Synchron NO and the time"
			::= { hwUpsAlarmTrapsPrefix 81 }

		
		-- 1.3.6.1.4.1.2011.6.174.2.3.0.82
		hwUpsUpdatingAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Updating Resume Trap.
				Its correlation binding parameters: Device ID, Sequence ID, Equip ID, Trap ID, 
				Trap Reason ID, Trap Text, Trap Level, Trap Flag, Synchron NO and the time"
			::= { hwUpsAlarmTrapsPrefix 82 }

		
		-- 1.3.6.1.4.1.2011.6.174.2.3.0.83
		hwUpsProgramAbnormalTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Program Abnormal Trap.
				Its correlation binding parameters: Device ID, Sequence ID, Equip ID, Trap ID, 
				Trap Reason ID, Trap Text, Trap Level, Trap Flag, Synchron NO and the time"
			::= { hwUpsAlarmTrapsPrefix 83 }

		
		-- 1.3.6.1.4.1.2011.6.174.2.3.0.84
		hwUpsProgramAbnormalResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Program Abnormal Resume Trap.
				Its correlation binding parameters: Device ID, Sequence ID, Equip ID, Trap ID, 
				Trap Reason ID, Trap Text, Trap Level, Trap Flag, Synchron NO and the time"
			::= { hwUpsAlarmTrapsPrefix 84 }

		
		-- 1.3.6.1.4.1.2011.6.174.2.3.0.85
		hwUpsBcbFaultAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Bcb Fault Trap.
				Its correlation binding parameters: Device ID, Sequence ID, Equip ID, Trap ID, 
				Trap Reason ID, Trap Text, Trap Level, Trap Flag, Synchron NO and the time"
			::= { hwUpsAlarmTrapsPrefix 85 }

		
		-- 1.3.6.1.4.1.2011.6.174.2.3.0.86
		hwUpsBcbFaultAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Bcb Fault Resume Trap.
				Its correlation binding parameters: Device ID, Sequence ID, Equip ID, Trap ID, 
				Trap Reason ID, Trap Text, Trap Level, Trap Flag, Synchron NO and the time"
			::= { hwUpsAlarmTrapsPrefix 86 }

		
		-- 1.3.6.1.4.1.2011.6.174.2.3.0.87
		hwUpsEcoRangeAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"ECO Range Trap.
				Its correlation binding parameters: Device ID, Sequence ID, Equip ID, Trap ID, 
				Trap Reason ID, Trap Text, Trap Level, Trap Flag, Synchron NO and the time"
			::= { hwUpsAlarmTrapsPrefix 87 }

		
		-- 1.3.6.1.4.1.2011.6.174.2.3.0.88
		hwUpsEcoRangeAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"ECO Range Resume Trap.
				Its correlation binding parameters: Device ID, Sequence ID, Equip ID, Trap ID, 
				Trap Reason ID, Trap Text, Trap Level, Trap Flag, Synchron NO and the time"
			::= { hwUpsAlarmTrapsPrefix 88 }

		
		-- 1.3.6.1.4.1.2011.6.174.2.3.0.89
		hwUpsBMUAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Bmu Trap.
				Its correlation binding parameters: Device ID, Sequence ID, Equip ID, Trap ID, 
				Trap Reason ID, Trap Text, Trap Level, Trap Flag, Synchron NO and the time"
			::= { hwUpsAlarmTrapsPrefix 89 }

		
		-- 1.3.6.1.4.1.2011.6.174.2.3.0.90
		hwUpsBMUAlarmResumeTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Bmu Resume Trap.
				Its correlation binding parameters: Device ID, Sequence ID, Equip ID, Trap ID, 
				Trap Reason ID, Trap Text, Trap Level, Trap Flag, Synchron NO and the time"
			::= { hwUpsAlarmTrapsPrefix 90 }

		
		-- 1.3.6.1.4.1.2011.6.174.2.3.0.91
		hwUpsElableFailedAlarmTrap NOTIFICATION-TYPE
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime
				 }
			STATUS current
			DESCRIPTION 
				"Elable Failed Trap.
				Its correlation binding parameters: Device ID, Sequence ID, Equip ID, Trap ID, 
				Trap Reason ID, Trap Text, Trap Level, Trap Flag, Synchron NO and the time"
			::= { hwUpsAlarmTrapsPrefix 91 }

		
		-- 1.3.6.1.4.1.2011.6.174.2.3.0.92
		hwUpsElableFailedAlarmResumeTrap NOTIFICATION-TYPE
			STATUS current
			DESCRIPTION 
				"Elable Failed Resume Trap.
				Its correlation binding parameters: Device ID, Sequence ID, Equip ID, Trap ID, 
				Trap Reason ID, Trap Text, Trap Level, Trap Flag, Synchron NO and the time"
			::= { hwUpsAlarmTrapsPrefix 92 }

		
		-- 1.3.6.1.4.1.2011.6.174.2.3.0.93
		hwUpsDIPConflictAlarmTrap NOTIFICATION-TYPE
			STATUS current
			DESCRIPTION 
				"DIP Conflict Trap."
			::= { hwUpsAlarmTrapsPrefix 93 }

		
		-- 1.3.6.1.4.1.2011.6.174.2.3.0.94
		hwUpsDIPConflictAlarmResumeTrap NOTIFICATION-TYPE
			STATUS current
			DESCRIPTION 
				"DIP Conflict Resume Trap."
			::= { hwUpsAlarmTrapsPrefix 94 }

		
		-- 1.3.6.1.4.1.2011.6.174.2.3.0.95
		hwUpsSystemStatusTrap NOTIFICATION-TYPE
			STATUS current
			DESCRIPTION 
				"Ups System Status Trap."
			::= { hwUpsAlarmTrapsPrefix 95 }

		
		-- 1.3.6.1.4.1.2011.6.174.2.3.0.96
		hwUpsSystemStatusResumeTrap NOTIFICATION-TYPE
			STATUS current
			DESCRIPTION 
				"Ups System Status Resume Trap."
			::= { hwUpsAlarmTrapsPrefix 96 }

		
		-- 1.3.6.1.4.1.2011.6.174.2.3.0.97
		hwUpsIBOXAlarmTrap NOTIFICATION-TYPE
			STATUS current
			DESCRIPTION 
				"Ups IBOX Alarm Trap."
			::= { hwUpsAlarmTrapsPrefix 97 }

		
		-- 1.3.6.1.4.1.2011.6.174.2.3.0.98
		hwUpsIBOXAlarmResumeTrap NOTIFICATION-TYPE
			STATUS current
			DESCRIPTION 
				"Ups IBOX Alarm Resume Trap."
			::= { hwUpsAlarmTrapsPrefix 98 }

		
		-- 1.3.6.1.4.1.2011.6.174.4
		hwUpsMIBGroups OBJECT IDENTIFIER ::= { hwUpsMIB 4 }

		
--   1.3.6.1.4.1.2011.6.174.3.1
-- 1.3.6.1.4.1.2011.6.174.3.1
		-- 1.3.6.1.4.1.2011.6.174.4.1
		hwUpsSystemGroup OBJECT-GROUP
			OBJECTS { hwUpsSystemMainDeviceESN, hwUpsSystemType, hwUpsSysInerProtVersion, hwUpsSysDeviceNum, hwUpsParallelSysNum, 
				hwUpsEnvTemper, hwUpsEnvHumidity }
			STATUS current
			DESCRIPTION 
				"UPS system infomation group."
			::= { hwUpsMIBGroups 1 }

		
-- 1.3.6.1.4.1.2011.6.174.3.2
		-- 1.3.6.1.4.1.2011.6.174.4.2
		hwUpsRacksGroup OBJECT-GROUP
			OBJECTS { hwUpsDeviceId, hwUpsDeviceType, hwUpsDeviceSoftVersion, hwUpsDeviceInerProtVersion, hwUpsDeviceESN, 
				hwUpsDeviceParaSysIndex, hwUpsDeviceIdentRowStatus, hwUpsDevicePowerSupplyMethod, hwUpsDeviceRunningStatus, hwUpsDeviceTemperature, 
				hwUpsDeviceEnergyFloatState, hwUpsDeviceRedundantNumber, hwUpsDeviceDelayShutdownOrder, hwUpsDeviceDelayShutdownState, hwUpsDeviceSysGrant, 
				hwUpsDeviceWorkMode, hwUpsDeviceSmartPowerMode, hwUpsDevicePowerSoftVersion, hwUpsDeviceMonitorSoftVersion, hwUpsDeviceOperInfoRowStatus, 
				hwUpsDeviceBatteryState }
			STATUS current
			DESCRIPTION 
				"UPS racks information group."
			::= { hwUpsMIBGroups 2 }

		
--   1.3.6.1.4.1.2011.6.174.3.3
-- 1.3.6.1.4.1.2011.6.174.3.3
		-- 1.3.6.1.4.1.2011.6.174.4.3
		hwUpsInputGroup OBJECT-GROUP
			OBJECTS { hwUpsInputVoltageA, hwUpsInputVoltageB, hwUpsInputVoltageC, hwUpsInputFrequency, hwUpsInputRowStatus, 
				hwUpsInputCurrentA, hwUpsInputCurrentB, hwUpsInputCurrentC, hwUpsInputPowerFactorA, hwUpsInputPowerFactorB, 
				hwUpsInputPowerFactorC }
			STATUS current
			DESCRIPTION 
				"UPS input information group."
			::= { hwUpsMIBGroups 3 }

		
--   1.3.6.1.4.1.2011.6.174.3.4
-- 1.3.6.1.4.1.2011.6.174.3.4
		-- 1.3.6.1.4.1.2011.6.174.4.4
		hwUpsOutputGroup OBJECT-GROUP
			OBJECTS { hwUpsOutputVoltageA, hwUpsOutputVoltageB, hwUpsOutputVoltageC, hwUpsOutputCurrentA, hwUpsOutputCurrentB, 
				hwUpsOutputCurrentC, hwUpsOutputFrequency, hwUpsOutputActivePowerA, hwUpsOutputActivePowerB, hwUpsOutputActivePowerC, 
				hwUpsOutputAppearancePowerA, hwUpsOutputAppearancePowerB, hwUpsOutputAppearancePowerC, hwUpsOutputLoadA, hwUpsOutputLoadB, 
				hwUpsOutputLoadC, hwUpsOutputPowerFactorA, hwUpsOutputPowerFactorB, hwUpsOutputPowerFactorC, hwUpsOutputRowStatus, 
				hwUpsOutputPowerRating, hwUpsOutputFrequencyRating }
			STATUS current
			DESCRIPTION 
				"UPS output information group."
			::= { hwUpsMIBGroups 4 }

		
--   1.3.6.1.4.1.2011.6.174.3.5
-- 1.3.6.1.4.1.2011.6.174.3.5
		-- 1.3.6.1.4.1.2011.6.174.4.5
		hwUpsBypassGroup OBJECT-GROUP
			OBJECTS { hwUpsBypassInputVoltageA, hwUpsBypassInputVoltageB, hwUpsBypassInputVoltageC, hwUpsBypassInputFrequency, hwUpsBypassRowStatus
				 }
			STATUS current
			DESCRIPTION 
				"UPS bypass information group."
			::= { hwUpsMIBGroups 5 }

		
--   1.3.6.1.4.1.2011.6.174.3.6
-- 1.3.6.1.4.1.2011.6.174.3.6
		-- 1.3.6.1.4.1.2011.6.174.4.6
		hwUpsBatteryGroup OBJECT-GROUP
			OBJECTS { hwUpsBatteryVoltage, hwUpsBatteryCurrent, hwUpsBatterytemperature, hwUpsBatteryBackupTime, hwUpsBatteryCapacityLeft, 
				hwUpsBatteryRowStatus }
			STATUS current
			DESCRIPTION 
				"UPS battery information group."
			::= { hwUpsMIBGroups 6 }

		
--   1.3.6.1.4.1.2011.6.174.3.7
-- 1.3.6.1.4.1.2011.6.174.3.7
		-- 1.3.6.1.4.1.2011.6.174.4.7
		hwUpsParallelSystemGroup OBJECT-GROUP
			OBJECTS { hwUpsParaSysId, hwUpsParaSysOutActivePowA, hwUpsParaSysOutActivePowB, hwUpsParaSysOutActivePowC, hwUpsParaSysOutAppearPowA, 
				hwUpsParaSysOutAppearPowB, hwUpsParaSysOutAppearPowC, hwUpsParaSysOutLoadFactorA, hwUpsParaSysOutLoadFactorB, hwUpsParaSysOutLoadFactorC, 
				hwUpsParallelSystemRowStatus }
			STATUS current
			DESCRIPTION 
				"UPS parallel system group."
			::= { hwUpsMIBGroups 7 }

		
--   1.3.6.1.4.1.2011.6.174.3.8
-- 1.3.6.1.4.1.2011.6.174.3.8
		-- 1.3.6.1.4.1.2011.6.174.4.8
		hwUpsControlGroup OBJECT-GROUP
			OBJECTS { hwUpsCtrlPowerOffDelay, hwUpsCtrlECOSwitch, hwUpsCtrlPowerBatCapacity, hwUpsCtrlPowerBatType, hwUpsCtrlModelType, 
				hwUpsCtrlInputStandard, hwUpsCtrlOutputStandard, hwUpsCtrlPowerOnState, hwUpsCtrlBatteryToTestState, hwUpsCtrlBatteryStopTestState, 
				hwUpsCtrlBatteryShallowTest, hwUpsCtrlBatteryVerifyCapTest, hwUpsCtrlBatteryEndTest, hwUpsCtrlBatteryToBoostState, hwUpsCtrlBatteryToFloatState, 
				hwUpsCtrlBatteryManualBoostCharge, hwUpsCtrlModelCapacity, hwUpsCtrlEPO, hwUpsSmartParallelSleepMode, hwUpsCtrlBatteryManualFloatCharge, 
				hwUpsCtrlPowerOn, hwUpsCtrlPowerOff, hwUpsCtrlRowStatus }
			STATUS current
			DESCRIPTION 
				"UPS rack control information group."
			::= { hwUpsMIBGroups 8 }

		
		-- 1.3.6.1.4.1.2011.6.174.4.9
		hwUpsTestGroup OBJECT-GROUP
			OBJECTS { hwUpsBattAutoTest, hwUpsBattAutoTestTimeInterval, hwUpsBattAutoTestDischargeRate, hwUpsBattScheduleTestRowStatus, hwUpsBattAutoTestEndVol, 
				hwUpsBattTest, hwUpsBattAutoTestTimeLimit }
			STATUS current
			DESCRIPTION 
				"UPS rack test information group."
			::= { hwUpsMIBGroups 9 }

		
--   1.3.6.1.4.1.2011.6.174.3.10
-- 1.3.6.1.4.1.2011.6.174.3.10
		-- 1.3.6.1.4.1.2011.6.174.4.10
		hwUpsTrapsVbGroup OBJECT-GROUP
			OBJECTS { hwUpsTrapsDeviceId, hwUpsTrapsModuleSeqId, hwUpsTrapsEquipID, hwUpsTrapsID, hwUpsTrapsReasonId, 
				hwUpsTrapsText, hwUpsTrapsLevel, hwUpsTrapsFlag, hwUpsTrapsSynchronNum, hwUpsTrapsTime, 
				hwUpsDeviceId }
			STATUS current
			DESCRIPTION 
				"UPS traps vb information group."
			::= { hwUpsMIBGroups 10 }

		
--   1.3.6.1.4.1.2011.6.174.3.11
-- 1.3.6.1.4.1.2011.6.174.3.11
		-- 1.3.6.1.4.1.2011.6.174.4.11
		hwUpsSiteTimeGroup OBJECT-GROUP
			OBJECTS { hwUpsSiteTimeUTC, hwUpsSiteTimeZone }
			STATUS current
			DESCRIPTION 
				"UPS site time information group."
			::= { hwUpsMIBGroups 11 }

		
--   1.3.6.1.4.1.2011.6.174.3.12
-- 1.3.6.1.4.1.2011.6.174.3.12
		-- 1.3.6.1.4.1.2011.6.174.4.12
		hwUpsAlarmGroup OBJECT-GROUP
			OBJECTS { hwUpsAlarmSynchronNum, hwUpsAlarmCurrActiveNum }
			STATUS current
			DESCRIPTION 
				"UPS alarm information group."
			::= { hwUpsMIBGroups 12 }

		
--   1.3.6.1.4.1.2011.6.174.3.13
-- 1.3.6.1.4.1.2011.6.174.3.13
		-- 1.3.6.1.4.1.2011.6.174.4.13
		hwUpsActiveAlarmGroup OBJECT-GROUP
			OBJECTS { hwUpsActiveAlarmDeviceId, hwUpsActiveAlarmSeqId, hwUpsActiveAlarmEquipID, hwUpsActiveAlarmID, hwUpsActiveAlarmReasonId, 
				hwUpsActiveAlarmText, hwUpsActiveAlarmLevel, hwUpsActiveAlarmFlag, hwUpsActiveAlarmSynchronNum, hwUpsActiveAlarmTime, 
				hwUpsActiveAlarmRowStatus }
			STATUS current
			DESCRIPTION 
				"UPS active alarm information group."
			::= { hwUpsMIBGroups 13 }

		
		-- 1.3.6.1.4.1.2011.6.174.4.14
		hwUpsFtpsGroup OBJECT-GROUP
			OBJECTS { hwUpsFtpsTransportID, hwUpsFtpsExecuteControl, hwUpsFtpsTransportState, hwUpsFtpsServerIp, hwUpsFtpsPort, 
				hwUpsFtpsUserName, hwUpsFtpsFileType, hwUpsFtpsCompressedFormat, hwUpsFtpsFileFullPath, hwUpsFtpsExtendParameter, 
				hwUpsFtpsPassword }
			STATUS obsolete
			DESCRIPTION 
				"Ups Ftps Group."
			::= { hwUpsMIBGroups 14 }

		
		-- 1.3.6.1.4.1.2011.6.174.4.16
		hwUpsCommonTrapsGroup NOTIFICATION-GROUP
			NOTIFICATIONS { hwUpsSummaryAlarmTrap, hwUpsPowerModInslotChangeTrap, hwUpsPowerStatusWarnTrap, hwUpsPowerStatusWarnResumeTrap, hwUpsSwitchStatusWarnTrap, 
				hwUpsSwitchStatusWarnResumeTrap, hwUpsModCommFailedTrap, hwUpsModCommFailedResumeTrap, hwUpsModConfigWarnTrap, hwUpsModConfigWarnResumeTrap, 
				hwUpsRecWarnTrap, hwUpsRecWarnResumeTrap, hwUpsChargerPowerWarnTrap, hwUpsChargerPowerWarnResumeTrap, hwUpsGeneratorWarnTrap, 
				hwUpsGeneratorWarnResumeTrap, hwUpsInvWarnTrap, hwUpsInvWarnResumeTrap, hwUpsLBSWarnTrap, hwUpsLBSWarnResumeTrap, 
				hwUpsSwitchTipWarnTrap, hwUpsSwitchTipWarnResumeTrap, hwUpsBattDetachWarnTrap, hwUpsBattDetachWarnResumeTrap, hwUpsBattStatusWarnTrap, 
				hwUpsBattStatusWarnResumeTrap, hwUpsBatteryTestWarnTrap, hwUpsBatteryTestWarnResumeTrap, hwUpsRackComFailedTrap, hwUpsRackComFaiedResumeTrap, 
				hwUpsRackMasterConflictTrap, hwUpsRackMasterConflictResumeTrap, hwUpsRackNumNoMatchTrap, hwUpsRackNumNoMatchResumeTrap, hwUpsRackOnlineStateChangeTrap, 
				hwUpsRackConfigChangeTrap, hwUpsRackRunningStateChangeTrap, hwUpsBatteryRunningStateChangeTrap, hwUpsEnergyFloatChangeTrap, hwUpsVersionChangeTrap, 
				hwUpsPowerSupplyMethodChangeTrap }
			STATUS current
			DESCRIPTION 
				"UPS common traps group."
			::= { hwUpsMIBGroups 16 }

		
-- 
-- 1.3.6.1.4.1.2011.6.174.3.15
		-- 1.3.6.1.4.1.2011.6.174.4.17
		hwUpsAlarmTrapsGroup NOTIFICATION-GROUP
			NOTIFICATIONS { hwUpsModNumAlarmTrap, hwUpsModNumAlarmResumeTrap, hwUpsBypassUnitAlarmTrap, hwUpsBypassUnitAlarmResumeTrap, hwUpsInRackParallelLineAlarmTrap, 
				hwUpsInRackParallelLineAlarmResumeTrap, hwUpsBetweenRackParallelLineAlarmTrap, hwUpsBetweenRackParallelLineAlarmResumeTrap, hwUpsFanAlarmTrap, hwUpsFanAlarmResumeTrap, 
				hwUpsAuxiliaryPowerAlarmTrap, hwUpsAuxiliaryPowerAlarmResumeTrap, hwUpsVersionMismatchAlarmTrap, hwUpsVersionMatchAlarmResumeTrap, hwUpsAddrConflictAlarmTrap, 
				hwUpsAddrConflictAlarmResumeTrap, hwUpsEmergencyPowerOffAlarmTrap, hwUpsEmergencyPowerOffAlarmResumeTrap, hwUpsBypassInputAlarmTrap, hwUpsBypassInputAlarmResumeTrap, 
				hwUpsInputIsolatingTransAlarmTrap, hwUpsInputIsolatingTransAlarmResumeTrap, hwUpsInternalAlarmTrap, hwUpsInternalAlarmResumeTrap, hwUpsRectifierAlarmTrap, 
				hwUpsRectifierAlarmResumeTrap, hwUpsChargerAlarmTrap, hwUpsChargerAlarmResumeTrap, hwUpsDischargerAlarmTrap, hwUpsDischargerAlarmResumeTrap, 
				hwUpsACAlarmResumeTrap, hwUpsModuleNotReadyAlarmTrap, hwUpsModuleNotReadyAlarmResumeTrap, hwUpsInverterAlarmTrap, hwUpsInverterAlarmResumeTrap, 
				hwUpsECUAlarmResumeTrap, hwUpsECUAlarmTrap, hwUpsSPDAlarmTrap, hwUpsSPDAlarmResumeTrap, hwUpsOperationFaultAlarmTrap, 
				hwUpsOverLoadAlarmTrap, hwUpsOperationFaultAlarmResumeTrap, hwUpsOverLoadAlarmResumeTrap, hwUpsOverLoadOverTimeAlarmTrap, hwUpsOverLoadOverTimeAlarmResumeTrap, 
				hwUpsLBSAlarmResumeTrap, hwUpsLBSAlarmTrap, hwUpsBypSwitchAlarmResumeTrap, hwUpsBatteryFault1AlarmTrap, hwUpsBatteryFault1AlarmResumeTrap, 
				hwUpsBypSwitchAlarmTrap, hwUpsRectifierStartLimitAlarmTrap, hwUpsRectifierStartLimitAlarmResumeTrap, hwUpsMainLoadCapicityAlarmTrap, hwUpsMainLoadCapicityAlarmResumeTrap, 
				hwUpsMinorLoadOffAlarmTrap, hwUpsMinorLoadOffAlarmResumeTrap, hwUpsParaStatusSetAlarmTrap, hwUpsParaStatusSetAlarmResumeTrap, hwUpsRemainCapacityAlarmTrap, 
				hwUpsRemainCapacityAlarmResumeTrap, hwUpsParParaAlarmTrap, hwUpsParParaAlarmResumeTrap, hwUpsFlashAlarmTrap, hwUpsFlashAlarmResumeTrap, 
				hwUpsManulPowerOnOffTrap, hwUpsManulPowerOnOffResumeTrap, hwUpsIOAlarmTrap, hwUpsIOAlarmResumeTrap, hwUpsEnvironmentDataAlarmTrap, 
				hwUpsEnvironmentDataAlarmResumeTrap, hwUpsUpdatingAlarmTrap, hwUpsUpdatingAlarmResumeTrap, hwUpsProgramAbnormalTrap, hwUpsProgramAbnormalResumeTrap, 
				hwUpsBcbFaultAlarmTrap, hwUpsBcbFaultAlarmResumeTrap, hwUpsEcoRangeAlarmTrap, hwUpsEcoRangeAlarmResumeTrap, hwUpsBMUAlarmResumeTrap, 
				hwUpsBMUAlarmTrap, hwUpsBatteryFault2AlarmTrap, hwUpsACAlarmTrap, hwUpsBatteryFault2AlarmResumeTrap, hwUpsBatteryChangeAlarmTrap, 
				hwUpsBatteryChangeAlarmResumeTrap, hwUpsBatteryMaintainAlarmTrap, hwUpsElableFailedAlarmResumeTrap, hwUpsElableFailedAlarmTrap, hwUpsDIPConflictAlarmResumeTrap, 
				hwUpsDIPConflictAlarmTrap, hwUpsSystemStatusResumeTrap, hwUpsSystemStatusTrap, hwUpsIBOXAlarmResumeTrap, hwUpsIBOXAlarmTrap, 
				hwUpsBatteryMaintainAlarmResumeTrap, hwUpsBatteryChangeLimitAlarmTrap, hwUpsBatteryChangeLimitAlarmResumeTrap }
			STATUS current
			DESCRIPTION 
				"UPS alarm traps group."
			::= { hwUpsMIBGroups 17 }

		
		-- 1.3.6.1.4.1.2011.6.174.4.18
		hwUpsCIMMonitorMgrGroup OBJECT-GROUP
			OBJECTS { hwUpsCIM2BIMNum, hwUpsCIM1BIMNum, hwUpsCIMNum, hwUpsCIM3BIMNUm, hwUpsCIM4BIMNum, 
				hwUpsCIMSelect, hwUpsBIMSelect, hwUpsCIMESN, hwUpsBIMESN }
			STATUS current
			DESCRIPTION 
				"Ups CIM Monitor Mgr Group."
			::= { hwUpsMIBGroups 18 }

		
		-- 1.3.6.1.4.1.2011.6.174.4.19
		hwUpsModuleGroup OBJECT-GROUP
			OBJECTS { hwUpsBusCapacitorLife, hwUpsInvACur, hwUpsInvBCur, hwUpsInvCCur, hwUpsInvPowerStat, 
				hwUpsModuleAUnevenFlow, hwUpsModuleBUnevenFlow, hwUpsModuleCUnevenFlow, hwUpsModuleRowStatus, hwUpsModuleUnevneCurValueTag, 
				hwUpsModuleSleepState, hwUpsPowerModuleId, hwUpsModuleRackId }
			STATUS current
			DESCRIPTION 
				"Ups Module Group."
			::= { hwUpsMIBGroups 19 }

		
		-- 1.3.6.1.4.1.2011.6.174.4.20
		hwUpsObsolete OBJECT-GROUP
			OBJECTS { hwUpsDevicePowerRating, hwUpsBatteryNumber }
			STATUS obsolete
			DESCRIPTION 
				"Ups Obsolete."
			::= { hwUpsMIBGroups 20 }

		
		-- 1.3.6.1.4.1.2011.6.174.4.21
		hwUpsRackUnevenCurGroup OBJECT-GROUP
			OBJECTS { hwUpsRackUnevenCurRackId, hwUpsRackUnevenCurSysGrant, hwUpsRackUnevenCurPowerSupplyMode, hwUpsRackUnevenCurPowerOnModNum, hwUpsRackUnevenCurSleepModNum, 
				hwUpsRackOutputCurrentA, hwUpsRackOutputCurrentB, hwUpsRackOutputCurrentC, hwUpsRackUnevenCurA, hwUpsRackUnevenCurB, 
				hwUpsRackUnevenCurC, hwUpsRackUnevenCurRowStatus, hwUpsRackUnevenCurValueTag }
			STATUS current
			DESCRIPTION 
				"Ups Rack Uneven Cur Group."
			::= { hwUpsMIBGroups 21 }

		
		-- 1.3.6.1.4.1.2011.6.174.4.22
		hwUpsBatteryStringGroup OBJECT-GROUP
			OBJECTS { hwUpsBatteryStringNum, hwUpsBatteryNumInBatteryString, hwUpsBatteryStringNo, hwUpsBatteryUnitNo, hwUpsBatteryUnitTemperature, 
				hwUpsBatteryUnitVolt, hwUpsBatteryUnitResistance, hwUpsCIMRelaNode, hwUpsBIMRelaNode, hwUpsBatteryStringParamRowStatus
				 }
			STATUS current
			DESCRIPTION 
				"Description."
			::= { hwUpsMIBGroups 22 }

		
	
	END

--
-- HUAWEI-UPS-MIB.mib
--
