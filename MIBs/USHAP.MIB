-- ALlion USHA MIB
-- MIB for Uninterruptible Power Supplies
--
-- { iso org(3) dod(6) internet(1) private(4) enterprises(1) allion(2468)
-- product(1) webAppliance(2) upsAgent(1) usha(1)
-- ==============================================================================================
---
---     Revision History
---
---     v0.80   17-Apr-2000     Johnny Lin/Allion
---                             Created
--
---     v0.81   27-Apr-2000     Johnny Lin/Allion
---                             Add upsTest objects 8, 9 and 10
---     v1.00   09-Oct-2000     Johnny Lin/Allion
---                             Fix the problems that HPOV6.0 cann't read this
---                             mib file due to some incorrect ','
---                             Change upsControlEvent from DisplayString to
---                             enum INTEGER
---     v1.01   25-Oct-2001     Johnny Lin/Allion
---                             Change ENTERPRISE name from usha to ushap
---                             Add "usha" in every trap event name
---                             Change object (usha, upsObjects, upsTraps) name from usha to ushap
---
---     v1.02   30-Oct-2001     Kenneth/Allion
---                             1. Import PositiveInteger and NonNegativeInteger from RFC-1628.
---                             2. Fixed: The final item of SYNTAX must not have a comma ending.
---                             3. Correct upsInputmandatory to upsInputCurrent.
---                             4. Correct upsOutputmandatory to upsOutputCurrent.
---                             5. Correct upsBypassmandatory to upsBypassCurrent.
---                             6. Fixed: SYNTAX "DisplayString" must use "SIZE()" to define its range
---                             7. Change BatteryTestScheduleEntry to UpsBatteryTestScheduleEntry
---                             8. Fixed some SYNTAX error :
---                                  Exp: Change "SYNTAX upsControlWeeklyScheduleEntry" to "SYNTAX
---                                       UpsControlWeeklyScheduleEntry". And it can avoid conflict
---                                       between names.
---
---     v1.03   28-Dec-2001     Johnny/Allion
---                             1. Add Simplified Chinese support for agentConfigDefaultLanguage
---
---     v1.04   03-Jan-2002     Johnny/Allion
---                             1. Fixed some typo
---
---     v1.05   16-Jul-2003     Johnny/Ingrasys
---                             1. Fixed errors of
---                                     "mconfigUnmpEvent" for "upsBatteryTestScheduleEntry"
---                                     "mconfigUnmpEvent" for "shutdownParametersEntry"
---                                     "mconfigScheduleIndex" for "upsControlWeeklyScheduleEntry"
---                                     "mconfigScheduleIndex" for "upsControlSpecialScheduleEntry"
---
---                             2. Change "read/write" to "read-write" of Access table for
---                                some NMS which may not accept '/' within MIB file.
---
---     v2.00b1 20-Feb-2004     Johnny/Ingrasys
---                             1. Add EMD support, include emdStatus, emdConfig, and traps
---
---
---     v2.01   16-Jul-2004     Johnny/Ingrasys
---                             1. Change all traps Enterprise from ushap to upsTraps
---
---
---     v2.02   7-Dec-2006     Kevin/Ingrasys
---                             1. Remove the upsDevicesTable column "INDEX  { indexOfDevice }" for OPManager tools.
---                             2. Fixed the upsDevicesEntry column "trapsIndex -> indexOfDevice".
---
---
---     v2.03   5-Jan-2007     Kevin/Ingrasys
---                             1. Modified MIB error issue for http://www.simpleweb.org/ietf/mibs/validate/ web side.
---                             
---
---

USHA-MIB DEFINITIONS ::= BEGIN

IMPORTS
  enterprises,Counter
    FROM RFC1155-SMI
  OBJECT-TYPE
    FROM RFC-1212
  DisplayString
    FROM RFC1213-MIB
  TRAP-TYPE
    FROM RFC-1215
  PositiveInteger
    FROM UPS-MIB
  NonNegativeInteger
    FROM UPS-MIB;

allion          OBJECT IDENTIFIER ::= { enterprises 2468 }
product         OBJECT IDENTIFIER ::= { allion 1 }
upsAgent        OBJECT IDENTIFIER ::= { product 2 }
ushap           OBJECT IDENTIFIER ::= { upsAgent 1 }
upsObjects      OBJECT IDENTIFIER ::= { ushap 1 }
upsTraps        OBJECT IDENTIFIER ::= { ushap 2 }

upsIdent        OBJECT IDENTIFIER ::= { upsObjects 1 }
upsBattery      OBJECT IDENTIFIER ::= { upsObjects 2 }
upsInput        OBJECT IDENTIFIER ::= { upsObjects 3 }
upsOutput       OBJECT IDENTIFIER ::= { upsObjects 4 }
upsBypass       OBJECT IDENTIFIER ::= { upsObjects 5 }
upsTest         OBJECT IDENTIFIER ::= { upsObjects 6 }
upsControl      OBJECT IDENTIFIER ::= { upsObjects 7 }
upsConfig       OBJECT IDENTIFIER ::= { upsObjects 8 }
upsClients      OBJECT IDENTIFIER ::= { upsObjects 9 }
agentConfig     OBJECT IDENTIFIER ::= { upsObjects 10 }
emdStatus       OBJECT IDENTIFIER ::= { upsObjects 11 }
emdConfig       OBJECT IDENTIFIER ::= { upsObjects 12 }

-- ===========================================================================
--
-- upsIdentification
--
--     All objects in this group except for upsIdentName and
--     upsIdentAttachedDevices are set at device initialization
--     and remain static.
--
-- ===========================================================================

upsIdentManufacturer OBJECT-TYPE
       SYNTAX     DisplayString (SIZE (0..31))
       ACCESS read-only
       STATUS     mandatory
       DESCRIPTION
               "The name of the UPS manufacturer."
       ::= { upsIdent 1 }

upsIdentModel OBJECT-TYPE
      SYNTAX DisplayString (SIZE (0..63))
      ACCESS read-only
      STATUS mandatory
      DESCRIPTION
          "The UPS Model designation."
      ::= { upsIdent 2 }

upsIdentUPSFirmwareVersion OBJECT-TYPE
       SYNTAX     DisplayString (SIZE (0..63))
       ACCESS read-only
       STATUS     mandatory
       DESCRIPTION
               "The UPS firmware/software version(s).  This variable
               may or may not have the same value as
               upsIdentAgentSoftwareVersion in some implementations."
      ::= { upsIdent 3 }

upsIdentAgentSoftwareVersion OBJECT-TYPE
      SYNTAX DisplayString (SIZE(0..31))
      ACCESS read-only
      STATUS mandatory
      DESCRIPTION
               "The USHA software/firmware version.  This variable may or
               may not have the same value as
               upsIdentUPSSoftwareVersion in some implementations."
      ::= { upsIdent 4 }

upsIdentName OBJECT-TYPE
       SYNTAX     DisplayString (SIZE(0..63))
       ACCESS read-write
       STATUS     mandatory
       DESCRIPTION
               "A string identifying the UPS.  This object should be
               set by the administrator."
       ::= { upsIdent 5 }

upsIdentAttachedDevices OBJECT-TYPE
       SYNTAX     DisplayString (SIZE(0..63))
       ACCESS read-write
       STATUS     mandatory
       DESCRIPTION
               "A string identifying the devices attached to the
               output(s) of the UPS.  This object should be set by
               the administrator."
       ::= { upsIdent 6 }

upsIdentUpsSerialNumber OBJECT-TYPE
      SYNTAX DisplayString (SIZE(0..15))
      ACCESS read-only
      STATUS mandatory
      DESCRIPTION
          "The UPS serial no."
      ::= { upsIdent 7 }

-- ===========================================================================
-- upsBattery
--
--     The Battery group.
-- ===========================================================================

upsBatteryStatus OBJECT-TYPE
     SYNTAX     INTEGER {
           unknown(1),
           batteryNormal(2),
           batteryLow(3),
           batteryDepleted(4),
           batteryDischarging(5),
           batteryFailure(6)
     }
     ACCESS read-only
     STATUS mandatory
     DESCRIPTION
               "The indication of the status in the UPS system's batteries."
     ::= { upsBattery 1 }

upsSecondsOnBattery OBJECT-TYPE
     SYNTAX INTEGER
     ACCESS read-only
     STATUS mandatory
     DESCRIPTION
        "If the unit is on battery power, the elapsed time
        since the UPS last switched to battery power, or the
        time since the network management subsystem was last
        restarted, whichever is less.  -1 shall be returned
        if the unit is not on battery power."
     ::= { upsBattery 2 }

upsEstimatedMinutesRemaining OBJECT-TYPE
     SYNTAX INTEGER
     ACCESS read-only
     STATUS mandatory
     DESCRIPTION
        "An estimate of the time to battery charge depletion
        under the present load conditions if the utility power
        is off and remains off, or if it were to be lost and
        remain off."
     ::= { upsBattery 3 }

upsEstimatedChargeRemaining OBJECT-TYPE
     SYNTAX INTEGER
     ACCESS read-only
     STATUS mandatory
     DESCRIPTION
        "An estimate of the battery charge remaining expressed
         as a percent of full charge."
     ::= { upsBattery 4 }

upsBatteryVoltage OBJECT-TYPE
     SYNTAX INTEGER
     ACCESS read-only
     STATUS mandatory
     DESCRIPTION
         "The magnitude of the present battery voltage in 0.1 Volt DC."
     ::= { upsBattery 5 }

   upsBatterymandatory OBJECT-TYPE
       SYNTAX     INTEGER
       --      "0.1 Amp DC"
       ACCESS read-only
       STATUS     mandatory
       DESCRIPTION
               "The present battery mandatory."
       ::= { upsBattery 6 }

   upsBatteryTemperature OBJECT-TYPE
       SYNTAX     INTEGER
       --      "degrees 0.1 Centigrade"
       ACCESS read-only
       STATUS     mandatory
       DESCRIPTION
               "The ambient temperature at or near the UPS Battery
               casing."
       ::= { upsBattery 7 }

-- ===========================================================================
-- upsInput
--
-- Input group.
-- ===========================================================================

upsInputLineBads OBJECT-TYPE
       SYNTAX     Counter
       ACCESS     read-only
       STATUS     mandatory
       DESCRIPTION
               "A count of the number of times the input entered an
               out-of-tolerance condition as defined by the
               manufacturer.  This count is incremented by one each
               time the input transitions from zero out-of-tolerance
               lines to one or more input lines out-of-tolerance."
       ::= { upsInput 1 }

upsInputNumLines OBJECT-TYPE
     SYNTAX INTEGER
     ACCESS read-only
     STATUS mandatory
     DESCRIPTION
         "The number of input lines utilized in this device.
          This variable indicates the number of rows in the
          input table."
     ::= { upsInput 2 }

upsInputTable OBJECT-TYPE
    SYNTAX  SEQUENCE OF UpsInputEntry
    ACCESS  not-accessible
    STATUS  mandatory
    DESCRIPTION
        "A list of input table entries.  The number of entries
         is given by the value of upsInputNumLines."
    ::= { upsInput  3 }

upsInputEntry OBJECT-TYPE
    SYNTAX  UpsInputEntry
    ACCESS  not-accessible
    STATUS  mandatory
    DESCRIPTION
        "An entry containing information applicable to a
         particular input line."
    INDEX { upsInputLineIndex }
    ::= { upsInputTable  1 }

UpsInputEntry ::=
    SEQUENCE {
             upsInputLineIndex   PositiveInteger,
             upsInputFrequency   NonNegativeInteger,
             upsInputVoltage     NonNegativeInteger,
             upsInputCurrent     NonNegativeInteger,
             upsInputTruePower   NonNegativeInteger,
             upsInputVoltageMax  NonNegativeInteger,
             upsInputVoltageMin  NonNegativeInteger
             }

upsInputLineIndex OBJECT-TYPE
     SYNTAX PositiveInteger (0..65535)
     ACCESS read-only
     STATUS mandatory
     DESCRIPTION
         ""
     ::= { upsInputEntry 1 }

upsInputFrequency OBJECT-TYPE
       SYNTAX     NonNegativeInteger
       --      "0.1 Hertz"
       ACCESS read-only
       STATUS     mandatory
       DESCRIPTION
               "The present input frequency."
       ::= { upsInputEntry 2 }

upsInputVoltage OBJECT-TYPE
     SYNTAX NonNegativeInteger
     ACCESS read-only
     STATUS mandatory
     DESCRIPTION
         "The input utility line voltage in 0.1 volts."
     ::= { upsInputEntry 3 }

upsInputCurrent OBJECT-TYPE
     SYNTAX NonNegativeInteger
     ACCESS read-only
     STATUS mandatory
     DESCRIPTION
         "The magnitude of the present input current in 0.1 A."
     ::= { upsInputEntry 4 }

upsInputTruePower OBJECT-TYPE
       SYNTAX     NonNegativeInteger
       --      "Watts"
       ACCESS read-only
       STATUS     mandatory
       DESCRIPTION
               "The magnitude of the present input true power."
       ::= { upsInputEntry 5 }

upsInputVoltageMax OBJECT-TYPE
     SYNTAX NonNegativeInteger
     ACCESS read-only
     STATUS mandatory
     DESCRIPTION
         "The maximum utility line voltage in 0.1 VAC for last 1 minute."
     ::= { upsInputEntry 6 }

upsInputVoltageMin OBJECT-TYPE
     SYNTAX NonNegativeInteger
     ACCESS read-only
     STATUS mandatory
     DESCRIPTION
         "The minimum utility line voltage in 0.1 VAC for last 1 minute."
     ::= { upsInputEntry 7 }

-- ===========================================================================
-- upsOutput
--
-- Output group
-- ===========================================================================

upsOutputSource OBJECT-TYPE
     SYNTAX     INTEGER {
           other(1),
           none(2),
           normal(3),
           bypass(4),
           battery(5),
           booster(6),
           reducer(7)
     }
     ACCESS read-only
     STATUS mandatory
     DESCRIPTION
         "The present source of output power.  The enumeration
             none(2) indicates that there is no source of output
             power (and therefore no output power), for example,
             the system has opened the output breaker."
     ::= { upsOutput 1 }

upsOutputFrequency OBJECT-TYPE
     SYNTAX INTEGER
     ACCESS read-only
     STATUS mandatory
     DESCRIPTION
         "The current output frequency of the UPS system in 0.1 of HZ."
     ::= { upsOutput 2 }

upsOutputNumLines OBJECT-TYPE
     SYNTAX INTEGER
     ACCESS read-only
     STATUS mandatory
     DESCRIPTION
         "The number of output lines utilized in this device.
          This variable indicates the number of rows in the
          output table."
     ::= { upsOutput 3 }

upsOutputTable OBJECT-TYPE
    SYNTAX  SEQUENCE OF UpsOutputEntry
    ACCESS  not-accessible
    STATUS  mandatory
    DESCRIPTION
        "A list of output table entries.  The number of
         entries is given by the value of upsOutputNumLines."
    ::= { upsOutput  4 }

upsOutputEntry OBJECT-TYPE
    SYNTAX  UpsOutputEntry
    ACCESS  not-accessible
    STATUS  mandatory
    DESCRIPTION
        "An entry containing information applicable to a
         particular output line."
    INDEX { upsOutputLineIndex }
    ::= { upsOutputTable  1 }

UpsOutputEntry ::=
    SEQUENCE {
             upsOutputLineIndex   PositiveInteger,
             upsOutputVoltage     NonNegativeInteger,
             upsOutputCurrent     NonNegativeInteger,
             upsOutputPower       NonNegativeInteger,
             upsOutputPercentLoad INTEGER
             }

upsOutputLineIndex OBJECT-TYPE
     SYNTAX PositiveInteger (0..65535)
     ACCESS read-only
     STATUS mandatory
     DESCRIPTION
         "The output line identifier."
     ::= { upsOutputEntry 1 }

upsOutputVoltage OBJECT-TYPE
     SYNTAX NonNegativeInteger
     ACCESS read-only
     STATUS mandatory
     DESCRIPTION
         "The output voltage of the UPS system in 0.1 volts."
     ::= { upsOutputEntry 2 }

upsOutputCurrent OBJECT-TYPE
     SYNTAX NonNegativeInteger
     ACCESS read-only
     STATUS mandatory
     DESCRIPTION
         "The output current of the UPS system in 0.1 Amps."
     ::= { upsOutputEntry 3 }

upsOutputPower OBJECT-TYPE
       SYNTAX     NonNegativeInteger
       --      "Watts"
       ACCESS read-only
       STATUS     mandatory
       DESCRIPTION
               "The present output true power."
       ::= { upsOutputEntry 4 }

upsOutputPercentLoad OBJECT-TYPE
     SYNTAX INTEGER
     ACCESS read-only
     STATUS mandatory
     DESCRIPTION
         "The percentage of the UPS power capacity presently
             being used on this output line, i.e., the greater of
             the percent load of true power capacity and the
             percent load of VA."
     ::= { upsOutputEntry 5 }

-- ===========================================================================
-- upsBypass
-- ===========================================================================

upsBypassFrequency OBJECT-TYPE
     SYNTAX INTEGER
     ACCESS read-only
     STATUS mandatory
     DESCRIPTION
         "The present bypass frequency."
     ::= { upsBypass 1 }

upsBypassNumLines OBJECT-TYPE
     SYNTAX INTEGER
     ACCESS read-only
     STATUS mandatory
     DESCRIPTION
         "The number of bypass lines utilized in this device.
             This entry indicates the number of rows in the bypass
             table."
     ::= { upsBypass 2 }

upsBypassTable OBJECT-TYPE
    SYNTAX  SEQUENCE OF UpsBypassEntry
    ACCESS  not-accessible
    STATUS  mandatory
    DESCRIPTION
        "A list of bypass table entries.  The number of
         entries is given by the value of upsBypassNumLines."
    ::= { upsBypass  3 }

upsBypassEntry OBJECT-TYPE
    SYNTAX  UpsBypassEntry
    ACCESS  not-accessible
    STATUS  mandatory
    DESCRIPTION
           "An entry containing information applicable to a
               particular bypass input."
    INDEX { upsBypassLineIndex }
    ::= { upsBypassTable  1 }

UpsBypassEntry ::=
    SEQUENCE {
             upsBypassLineIndex          PositiveInteger,
             upsBypassVoltage            NonNegativeInteger,
             upsBypassCurrent            NonNegativeInteger,
             upsBypassPower              NonNegativeInteger
             }

upsBypassLineIndex OBJECT-TYPE
     SYNTAX PositiveInteger (0..65535)
     ACCESS read-only
     STATUS mandatory
     DESCRIPTION
         "The bypass line identifier."
     ::= { upsBypassEntry 1 }

upsBypassVoltage OBJECT-TYPE
     SYNTAX NonNegativeInteger
     ACCESS read-only
     STATUS mandatory
     DESCRIPTION
         "The present bypass voltage."
     ::= { upsBypassEntry 2 }

upsBypassCurrent OBJECT-TYPE
     SYNTAX NonNegativeInteger
     ACCESS read-only
     STATUS mandatory
     DESCRIPTION
         "The present bypass current."
     ::= { upsBypassEntry 3 }

upsBypassPower OBJECT-TYPE
       SYNTAX     NonNegativeInteger
       --      "Watts"
       ACCESS read-only
       STATUS     mandatory
       DESCRIPTION
               "The present true power conveyed by the bypass."
       ::= { upsBypassEntry 4 }

-- ===========================================================================
-- upsTest
--
-- ===========================================================================

upsTestBatteryTestSettingTime OBJECT-TYPE
        SYNTAX INTEGER
        ACCESS read-write
        STATUS mandatory
        DESCRIPTION
                "The object specify the test time for battery test."
     ::= { upsTest 1 }

upsBatteryTest OBJECT-TYPE
        SYNTAX INTEGER {
            none(1),
            battTest10sec(2),
            battTestUntilLow(3),
            battTestWithTime(4),
            battTestCancelTest(5),
            battTestClearInfo(6)
        }
        ACCESS read-write
        STATUS mandatory
        DESCRIPTION
                "This object specify the battery test type and initiate
                 battery test. If battTestWithTime selected, the test
                 time is refer to upsTestBatteryTestTime."
     ::= { upsTest 2 }

upsTestBatteryTestResult OBJECT-TYPE
        SYNTAX  INTEGER {
                donePassed(1),
                doneWarning(2),
                doneError(3),
                aborted(4),
                inProgress(5),
                noTestsInitiated(6)
        }
        ACCESS read-only
        STATUS mandatory
        DESCRIPTION
         "The results of the current or last UPS diagnostics
               test performed.  The values for donePassed(1),
               doneWarning(2), and doneError(3) indicate that the
               test completed either successfully, with a warning, or
               with an error, respectively.  The value aborted(4) is
               returned for tests which are aborted by setting the
               value of upsTestId to upsTestAbortTestInProgress.
               Tests which have not yet concluded are indicated by
               inProgress(5).  The value noTestsInitiated(6)
               indicates that no previous test results are available,
               such as is the case when no tests have been run since
               the last reinitialization of the network management
               subsystem and the system has no provision for non-
               volatile storage of test results."
     ::= { upsTest 3 }

upsTestBatteryTestStartTime OBJECT-TYPE
        SYNTAX DisplayString (SIZE(1..19))
        ACCESS read-only
        STATUS mandatory
        DESCRIPTION
         "The value of the time the test in progress was initiated,
          or, if no test is in progress, the time the previous test
          was initiated. If the value of upsTestBatteryTestResult
          is noTestsInitiated(6), upsTestStartTime has the value
          01/01/1970 00:00:00."
     ::= { upsTest 4 }

upsTestBatteryTestElapsedTime OBJECT-TYPE
        SYNTAX DisplayString (SIZE(11..11))
        ACCESS read-only
        STATUS mandatory
        DESCRIPTION
         "The amount of time, in TimeTicks, since the test in
          progress was initiated, or, if no test is in progress,
          the previous test took to complete.  If the value of
          upsTestResultsSummary is noTestsInitiated(6),
          upsTestElapsedTime has the value 00:00:00.00."
     ::= { upsTest 5 }

upsBatteryTestScheduleTable OBJECT-TYPE
        SYNTAX SEQUENCE OF UpsBatteryTestScheduleEntry
        ACCESS not-accessible
        STATUS mandatory
        DESCRIPTION
                "Table which describes the schedule for automatically battery
                 test."
     ::= { upsTest 6 }

upsBatteryTestScheduleEntry OBJECT-TYPE
        SYNTAX UpsBatteryTestScheduleEntry
        ACCESS not-accessible
        STATUS mandatory
        INDEX { upsBatteryTestScheduleIndex }
                ::= { upsBatteryTestScheduleTable 1 }

UpsBatteryTestScheduleEntry ::= SEQUENCE {
                upsBatteryTestScheduleIndex
                        INTEGER,
                upsBatteryTestScheduleDay
                        INTEGER,
                upsBatteryTestScheduleTime
                        DisplayString,
                upsBatteryTestScheduleType
                        INTEGER
        }

upsBatteryTestScheduleIndex OBJECT-TYPE
        SYNTAX INTEGER (0..65535)
        ACCESS read-only
        STATUS mandatory
        DESCRIPTION
                "The index of battery test scheduled."
        ::= { upsBatteryTestScheduleEntry 1 }

upsBatteryTestScheduleDay    OBJECT-TYPE
        SYNTAX  INTEGER {
                sunday(1),
                monday(2),
                tuesday(3),
                wednesday(4),
                thursday(5),
                friday(6),
                saturday(7),
                none(8)
                }
        ACCESS read-write
        STATUS mandatory
        DESCRIPTION
                "The weekday on which the UPS should start battery test."
        ::= { upsBatteryTestScheduleEntry 2 }

upsBatteryTestScheduleTime OBJECT-TYPE
        SYNTAX DisplayString (SIZE(5..5))
        ACCESS read-write
        STATUS mandatory
        DESCRIPTION
         "The time that the battery test will be initiated in hh:mm:ss format."
        ::= { upsBatteryTestScheduleEntry 3 }

upsBatteryTestScheduleType    OBJECT-TYPE
        SYNTAX  INTEGER {
            none(1),
            battTest10sec(2),
            battTestUntilLow(3),
            battTestWithTime(4)
                }
        ACCESS read-write
        STATUS mandatory
        DESCRIPTION
                "The type of battery test."
        ::= { upsBatteryTestScheduleEntry 4 }

-- ===========================================================================
-- upsControl
--
-- ===========================================================================

upsControlUpsShutdownDelay OBJECT-TYPE
        SYNTAX INTEGER
        ACCESS read-write
        STATUS mandatory
        DESCRIPTION
                "The delay in seconds the UPS remains on after being told
                 to turn off."
        ::= { upsControl 1 }

upsControlUpsSleepTime OBJECT-TYPE
        SYNTAX INTEGER
        ACCESS read-write
        STATUS mandatory
        DESCRIPTION
                "The time in minutes for the UPS to go to sleep  when
                 instructed.  When in sleep mode, the UPS will not provide
                 output power regardless of the input line state.  Once the
                 specified time has elapsed, output power will be restored.

                 This is a configuration setting.  The UPS will not go to
                 sleep until told to do so by the manager from a management
                 station.

                 Any input value is allowed, however the UPS only recognizes
                 0 - 9999 minutes in one minute increments.

                 If the provided value is higher than the highest acceptable
                 value, the highest acceptable value is used."
        ::= { upsControl 2 }

upsControlUpsOnOffControl OBJECT-TYPE
        SYNTAX  INTEGER {
                turnUpsOff(1),
                putUpsToSleep(2),
                turnOnUpsOrCancelShutdown(3),
                none(4)
           }
        ACCESS read-write
        STATUS mandatory
        DESCRIPTION
                "Setting this variable to control UPS output status.
                 turnUpsOff(1) will set UPS turn off output after
                 upsControlUpsShutdownDelay period expired.
                 putUpsToSleep(2) will set UPS turn off output after
                 upsControlUpsShutdownDelay period expired, UPS output
                 will stay off with the period defined by
                 upsControlUpsSleepTime, then turn output on.
                 turnOnUpsOrCancelShutdown(3) can used to turn on UPS
                 output, or cancel any shutdown process."
        ::= { upsControl 3 }

upsControlShutdownParametersTable OBJECT-TYPE
        SYNTAX SEQUENCE OF ShutdownParametersEntry
        ACCESS not-accessible
        STATUS mandatory
        DESCRIPTION
                "Table which describes the parametes for shutdown process
                 when shutdown event occurs"
                ::= { upsControl 4 }

shutdownParametersEntry OBJECT-TYPE
        SYNTAX ShutdownParametersEntry
        ACCESS not-accessible
        STATUS mandatory
        INDEX { upsControlEvent }
                ::= { upsControlShutdownParametersTable 1 }

ShutdownParametersEntry  ::= SEQUENCE {
                upsControlEvent            INTEGER,
                upsControlEventStatus      INTEGER,
                upsControlDelay            INTEGER,
                upsControlFirstWarning     INTEGER,
                upsControlWarningInterval  INTEGER
                }

upsControlEvent OBJECT-TYPE
--   SYNTAX DisplayString
        SYNTAX INTEGER {
            acFail(1),
            batteryLow (2),
            uPSOverload (3),
            uPSOverTempeature (4),
            weeklySchedule (5),
            specialDaySchedule (6)
        }
        ACCESS read-only
        STATUS mandatory
        DESCRIPTION
                " The shutdown event identification "
                ::= { shutdownParametersEntry 1 }

upsControlEventStatus OBJECT-TYPE
        SYNTAX INTEGER {
--          enable(1),
--          disable(2)
            disable(1),
            warning(2),
            clientShutdown(3),
            upsTurnOff(4)
        }
        ACCESS read-write
        STATUS mandatory
        DESCRIPTION
                "Status of the corresponding shutdown Event.
                 When set to disable(), shutdown process will not start when
                 corresponding event occured."
                 ::= { shutdownParametersEntry 2 }

upsControlDelay OBJECT-TYPE
        SYNTAX INTEGER (0..10080)
        ACCESS read-write
        STATUS mandatory
        DESCRIPTION
                "The Delay after the occurance of the curresponding shutdown
                 event that USHA should issue shutdown request to
                 connected clients. For WeeklyScheduledShutdown and
                 SpecialScheduledShutdown, this is the time before the
                 configured Shutdowntime when USHA will start sending the
                 warning message to the connected clients. The value is in
                 units of minutes."
                 ::= { shutdownParametersEntry 3 }

upsControlFirstWarning OBJECT-TYPE
        SYNTAX INTEGER (0..3600)
        ACCESS read-write
        STATUS mandatory
        DESCRIPTION
                "The delay after the occurance of the curresponding shutdown
                 event that the USHA will start sending the warning
                 message to the connected clients. The value is in units of
                 seconds"
                 ::= { shutdownParametersEntry 4 }

upsControlWarningInterval OBJECT-TYPE
        SYNTAX INTEGER (0..3600)
        ACCESS read-write
        STATUS mandatory
        DESCRIPTION
                "The frequency of sending warning messages to the connected
                clients when the curresponding shutdown event occurs.
                The value is in units of seconds."
                ::= { shutdownParametersEntry 5 }

upsControlWeeklyScheduleTable OBJECT-TYPE
        SYNTAX SEQUENCE OF UpsControlWeeklyScheduleEntry
        ACCESS not-accessible
        STATUS mandatory
        DESCRIPTION
                "The table to schedule shutting down the ups by weekly."
        ::= { upsControl 5 }

upsControlWeeklyScheduleEntry OBJECT-TYPE
        SYNTAX UpsControlWeeklyScheduleEntry
        ACCESS not-accessible
        STATUS mandatory
        DESCRIPTION
                "The entries for each day."
        INDEX  { upsControlWeeklyIndex }
        ::= {upsControlWeeklyScheduleTable 1 }

UpsControlWeeklyScheduleEntry ::= SEQUENCE {
                upsControlWeeklyIndex
                        INTEGER,
                upsControlWeeklyShutdownDay
                        INTEGER,
                upsControlWeeklyShutdownTime
                        DisplayString,
                upsControlWeeklyRestartDay
                        INTEGER,
                upsControlWeeklyRestartTime
                        DisplayString
        }

upsControlWeeklyIndex OBJECT-TYPE
        SYNTAX INTEGER (0..65535)
        ACCESS read-only
        STATUS mandatory
        DESCRIPTION
                "The index of scheduled events."
        ::= { upsControlWeeklyScheduleEntry 1 }

upsControlWeeklyShutdownDay    OBJECT-TYPE
        SYNTAX  INTEGER {
                sunday(1),
                monday(2),
                tuesday(3),
                wednesday(4),
                thursday(5),
                friday(6),
                saturday(7),
                none(8)
                }
        ACCESS read-write
        STATUS mandatory
        DESCRIPTION
                "The weekday on which the UPS should shut down."
        ::= { upsControlWeeklyScheduleEntry 2 }

upsControlWeeklyShutdownTime OBJECT-TYPE
        SYNTAX DisplayString (SIZE(5..5))
        ACCESS read-write
        STATUS mandatory
        DESCRIPTION
         "The time that the process of shutting down the UPS will be initiated
          in hh:mm:ss format."
        ::= { upsControlWeeklyScheduleEntry 3 }

upsControlWeeklyRestartDay     OBJECT-TYPE
        SYNTAX  INTEGER {
                sunday(1),
                monday(2),
                tuesday(3),
                wednesday(4),
                thursday(5),
                friday(6),
                saturday(7),
                none(8)
                }
        ACCESS read-write
        STATUS mandatory
        DESCRIPTION
                "The weekday on which the UPS should restart"

        ::= { upsControlWeeklyScheduleEntry 4 }

upsControlWeeklyRestartTime OBJECT-TYPE
        SYNTAX DisplayString (SIZE(5..5))
        ACCESS read-write
        STATUS mandatory
        DESCRIPTION
                "The time the UPS will restart in hh:mm:ss format."
        ::= { upsControlWeeklyScheduleEntry 5 }

upsControlSpecialScheduleTable OBJECT-TYPE
        SYNTAX SEQUENCE OF UpsControlSpecialScheduleEntry
        ACCESS not-accessible
        STATUS mandatory
        DESCRIPTION
                "The table to schedule shutting down the ups."
        ::= { upsControl 6 }

upsControlSpecialScheduleEntry OBJECT-TYPE
        SYNTAX UpsControlSpecialScheduleEntry
        ACCESS not-accessible
        STATUS mandatory
        DESCRIPTION
                "The entries for each day."
        INDEX  { upsControlSpecialIndex }
        ::= {upsControlSpecialScheduleTable 1 }

UpsControlSpecialScheduleEntry ::= SEQUENCE {
                upsControlSpecialIndex
                        INTEGER,
                upsControlSpecialShutdownDay
                        DisplayString,
                upsControlSpecialShutdownTime
                        DisplayString,
                upsControlSpecialRestartDay
                        DisplayString,
                upsControlSpecialRestartTime
                        DisplayString
        }

upsControlSpecialIndex OBJECT-TYPE
        SYNTAX INTEGER (0..65535)
        ACCESS read-only
        STATUS mandatory
        DESCRIPTION
                "The index of scheduled events."
        ::= { upsControlSpecialScheduleEntry 1 }

upsControlSpecialShutdownDay    OBJECT-TYPE
        SYNTAX DisplayString (SIZE(10..10))
        ACCESS read-write
        STATUS mandatory
        DESCRIPTION
                "The date on which the UPS should shut down in dd/mm/yyyy
                 format."
         ::= { upsControlSpecialScheduleEntry 2 }

upsControlSpecialShutdownTime OBJECT-TYPE
        SYNTAX DisplayString (SIZE(5..5))
        ACCESS read-write
        STATUS mandatory
        DESCRIPTION
         "The time that the process of shutting down the UPS will be initiated
          in hh:mm:ss format"
        ::= { upsControlSpecialScheduleEntry 3 }

upsControlSpecialRestartDay     OBJECT-TYPE
        SYNTAX DisplayString (SIZE(10..10))
        ACCESS read-write
        STATUS mandatory
        DESCRIPTION
                "The date on which the UPS should restart in dd/mm/yyyy format"

        ::= { upsControlSpecialScheduleEntry 4 }

upsControlSpecialRestartTime OBJECT-TYPE
        SYNTAX DisplayString (SIZE(5..5))
        ACCESS read-write
        STATUS mandatory
        DESCRIPTION
                "The time the UPS will restart in hh:mm:ss format."
        ::= { upsControlSpecialScheduleEntry 5 }

-- ===========================================================================
--
-- upsConfig
--
-- ===========================================================================

upsConfigInputVoltage OBJECT-TYPE
    SYNTAX  INTEGER
    ACCESS  read-only
    STATUS  mandatory
    DESCRIPTION
               "The magnitude of the nominal input voltage.  On those
               systems which support read-write access to this
               object, if there is an attempt to set this variable to
               a value that is not supported, the request must be
               rejected and the agent shall respond with an
               appropriate error message, i.e., badValue for SNMPv1,
               or inconsistentValue for SNMPv2."
     ::= { upsConfig 1 }

upsConfigInputFreq OBJECT-TYPE
    SYNTAX  INTEGER
    ACCESS  read-only
    STATUS  mandatory
    DESCRIPTION
               "The nominal input frequency.  On those systems which
               support read-write access to this object, if there is
               an attempt to set this variable to a value that is not
               supported, the request must be rejected and the agent
               shall respond with an appropriate error message, i.e.,
               badValue for SNMPv1, or inconsistentValue for SNMPv2."
     ::= { upsConfig 2 }

upsConfigOutputVoltage OBJECT-TYPE
    SYNTAX  INTEGER
    ACCESS  read-only
    STATUS  mandatory
    DESCRIPTION
               "The magnitude of the nominal output voltage.  On
               those systems which support read-write access to this
               object, if there is an attempt to set this variable to
               a value that is not supported, the request must be
               rejected and the agent shall respond with an
               appropriate error message, i.e., badValue for SNMPv1,
               or inconsistentValue for SNMPv2."
     ::= { upsConfig 3 }

upsConfigOutputFreq OBJECT-TYPE
    SYNTAX  INTEGER
    ACCESS  read-only
    STATUS  mandatory
    DESCRIPTION
               "The nominal output frequency.  On those systems which
               support read-write access to this object, if there is
               an attempt to set this variable to a value that is not
               supported, the request must be rejected and the agent
               shall respond with an appropriate error message, i.e.,
               badValue for SNMPv1, or inconsistentValue for SNMPv2."
     ::= { upsConfig 4 }

upsConfigOutputVA OBJECT-TYPE
       SYNTAX     NonNegativeInteger
       --      "Volt-Amps"
       ACCESS read-only
       STATUS     mandatory
       DESCRIPTION
               "The magnitude of the nominal Volt-Amp rating."
       ::= { upsConfig 5 }

upsConfigOutputPower OBJECT-TYPE
       SYNTAX     NonNegativeInteger
       --      "Watts"
       ACCESS read-only
       STATUS     mandatory
       DESCRIPTION
               "The magnitude of the nominal true power rating."
       ::= { upsConfig 6 }

upsConfigOverTemperatureSetPoint OBJECT-TYPE
       SYNTAX     NonNegativeInteger (10..70)
       ACCESS read-write
       STATUS     mandatory
       DESCRIPTION
               "The maximum temperature allowed before the UPS
               operation temperature is too high."
       ::= { upsConfig 7 }

upsConfigOverLoadSetPoint OBJECT-TYPE
       SYNTAX     NonNegativeInteger (0..120)
       ACCESS read-write
       STATUS     mandatory
       DESCRIPTION
               "The maximum output load allowed before the load is
               too high for UPS operation."
       ::= { upsConfig 8 }



-- ===========================================================================
--
-- upsClients
--
-- ===========================================================================

upsClientsConnectedNum OBJECT-TYPE
       SYNTAX     NonNegativeInteger
       ACCESS read-only
       STATUS     mandatory
       DESCRIPTION
               "The count of clients which have resgistered for UPS
               shutdown control."
       ::= { upsClients 1 }

upsDevicesTable OBJECT-TYPE
        SYNTAX SEQUENCE OF UpsDevicesEntry
        ACCESS not-accessible
        STATUS mandatory
        DESCRIPTION
                "The devices powered by UPS and registered to USHA"
        ::= { upsClients 2 }

upsDevicesEntry OBJECT-TYPE
        SYNTAX UpsDevicesEntry
        ACCESS not-accessible
        STATUS mandatory
        DESCRIPTION
                "The devices protected by USHA"
        INDEX  { indexOfDevice}
        ::= { upsDevicesTable 1 }

UpsDevicesEntry ::=
        SEQUENCE {
                indexOfDevice
                        INTEGER,
                addrOfDevice
                        IpAddress,
                nameOfDevice
                        DisplayString,
                timeOfConnection
                        DisplayString
        }

indexOfDevice OBJECT-TYPE
        SYNTAX INTEGER (0..65535)
        ACCESS read-only
        STATUS mandatory
        DESCRIPTION
                "The index of the device that is plugged into the UPS."
        ::= { upsDevicesEntry 1 }

addrOfDevice OBJECT-TYPE
        SYNTAX IpAddress
        ACCESS read-only
        STATUS mandatory
        DESCRIPTION
                "The ip address of the device."
        ::= { upsDevicesEntry 2 }

nameOfDevice OBJECT-TYPE
        SYNTAX DisplayString (SIZE(0..31))
        ACCESS read-only
        STATUS mandatory
        DESCRIPTION
                "The name/description of the device plugged into the UPS."
        ::= { upsDevicesEntry 3 }

timeOfConnection OBJECT-TYPE
        SYNTAX DisplayString
        ACCESS read-only
        STATUS mandatory
        DESCRIPTION
                "The that device registered to USHA"
        ::= { upsDevicesEntry 4 }

-- ===========================================================================
--
-- agentConfig
--
-- ===========================================================================

agentConfigIpaddress OBJECT-TYPE
        SYNTAX IpAddress
        ACCESS read-write
        STATUS mandatory
        DESCRIPTION
                " The ip address that NMS can identify the managed
                device"
        ::= { agentConfig 1}

agentConfigGateway OBJECT-TYPE
        SYNTAX IpAddress
        ACCESS read-write
        STATUS mandatory
        DESCRIPTION
                " The default gateway that allow device managed
                through routers "
        ::= { agentConfig 2}

agentConfigSubnetMask OBJECT-TYPE
        SYNTAX IpAddress
        ACCESS read-write
        STATUS mandatory
        DESCRIPTION
                " Internet address subnet mask"
        ::= { agentConfig 3}

agentConfigDate OBJECT-TYPE
        SYNTAX DisplayString (SIZE (10..10))
        ACCESS read-write
        STATUS mandatory
        DESCRIPTION
                "The date in agent, format is (dd/mm/yyyy)"
        ::= { agentConfig 4}

agentConfigTime OBJECT-TYPE
        SYNTAX DisplayString (SIZE (8..8))
        ACCESS read-write
        STATUS mandatory
        DESCRIPTION
                "The time in agent, format is (hh:mm:ss)"
        ::= { agentConfig 5}

agentConfigPrimaryTimeServer       OBJECT-TYPE
        SYNTAX  IpAddress
        ACCESS  read-write
        STATUS  mandatory
        DESCRIPTION
                "The primary time server is responsible for sending the
                 correct time to the agent."
        ::= { agentConfig 6 }

agentConfigSecondaryTimeServer     OBJECT-TYPE
        SYNTAX  IpAddress
        ACCESS  read-write
        STATUS  mandatory
        DESCRIPTION
                "The secondary time server is responsible for sending the
                 correct time to the agent."
        ::= { agentConfig 7 }

agentConfigHistoryLogFrequency OBJECT-TYPE
        SYNTAX INTEGER (5..28800) -- in seconds
        ACCESS read-write
        STATUS mandatory
        DESCRIPTION
                "The frequency of the updation of the history log. The value
                 is in seconds"
        ::= { agentConfig 8 }

agentConfigExtHistoryLogFrequency      OBJECT-TYPE
        SYNTAX INTEGER (1..10080) -- in minutes
        ACCESS read-write
        STATUS mandatory
        DESCRIPTION
                 "The ups parameters are sampled at the rate governed by the
                  mconfigHistroyLogFrequency. These sampled values are further
                  conslidated over period of time which is determined by this
                  object."
        ::= { agentConfig 9 }

agentConfigPollRate OBJECT-TYPE
        SYNTAX INTEGER (1..999) -- in seconds
        ACCESS read-write
        STATUS mandatory
        DESCRIPTION
                " The frequency that proxy agent polls the connected
                UPS in JBUS protocol. (unit : second)"
        ::= { agentConfig 10}

agentConfigBaudRate OBJECT-TYPE
        SYNTAX INTEGER
        ACCESS read-only
        STATUS mandatory
        DESCRIPTION
                "The serial port communication speed. only 9600 allowed"
        ::= { agentConfig 11}

agentConfigDhcpStatue OBJECT-TYPE
        SYNTAX  INTEGER {
                enabled(1),
                disabled(2)
                }
        ACCESS read-write
        STATUS mandatory
        DESCRIPTION
                "Enable or disable DHCP/BootP capability"
        ::= { agentConfig 12}

agentConfigTelnetStatue OBJECT-TYPE
        SYNTAX  INTEGER {
                enabled(1),
                disabled(2)
                }
        ACCESS read-write
        STATUS mandatory
        DESCRIPTION
                "Enable or disable telnet access"
        ::= { agentConfig 13}

agentConfigTftpStatue OBJECT-TYPE
        SYNTAX  INTEGER {
                enabled(1),
                disabled(2)
                }
        ACCESS read-write
        STATUS mandatory
        DESCRIPTION
                "Enable or disable network upgrade capability"
        ::= { agentConfig 14}

agentConfigResetToDefault OBJECT-TYPE
        SYNTAX  INTEGER {
                reset(1),
                nothing(2)
                }
        ACCESS read-write
        STATUS mandatory
        DESCRIPTION
                "Reset all parameters of USHA to default value"
        ::= { agentConfig 15}

agentConfigRestart OBJECT-TYPE
        SYNTAX  INTEGER {
                restart(1),
                nothing(2)
                }
        ACCESS read-write
        STATUS mandatory
        DESCRIPTION
                "Restart USHA"
        ::= { agentConfig 16}

agentConfigClearAgentLog OBJECT-TYPE
        SYNTAX  INTEGER {
                clear(1),
                nothing(2)
                }
        ACCESS read-write
        STATUS mandatory
        DESCRIPTION
                "Clear agent log data"
        ::= { agentConfig 17}

agentConfigClearEventLog OBJECT-TYPE
        SYNTAX  INTEGER {
                clear(1),
                nothing(2)
                }
        ACCESS read-write
        STATUS mandatory
        DESCRIPTION
                "Clear event log data"
        ::= { agentConfig 18}

agentConfigClearExtHistoryLog OBJECT-TYPE
        SYNTAX  INTEGER {
                clear(1),
                nothing(2)
                }
        ACCESS read-write
        STATUS mandatory
        DESCRIPTION
                "Clear extented history log data"
        ::= { agentConfig 19}

agentConfigClearHistoryLog OBJECT-TYPE
        SYNTAX  INTEGER {
                clear(1),
                nothing(2)
                }
        ACCESS read-write
        STATUS mandatory
        DESCRIPTION
                "Clear history log data"
        ::= { agentConfig 20}

agentConfigTrapRetryCount OBJECT-TYPE
        SYNTAX  INTEGER
        ACCESS read-write
        STATUS mandatory
        DESCRIPTION
                "The count of repeat traps to send to NMS before trap
                 acknowledge received."
        ::= { agentConfig 21}

agentConfigTrapRetryTime OBJECT-TYPE
        SYNTAX  INTEGER
        ACCESS read-write
        STATUS mandatory
        DESCRIPTION
                "The time between retry traps sned to NMS."
        ::= { agentConfig 22}

agentConfigTrapAckSignature OBJECT-TYPE
        SYNTAX  INTEGER
        ACCESS read-write
        STATUS mandatory
        DESCRIPTION
                "The signature of trap acknowledge."
        ::= { agentConfig 23}

agentConfigMibVersion OBJECT-TYPE
        SYNTAX INTEGER
        ACCESS read-only
        STATUS mandatory
        DESCRIPTION
                "The version of MIB spec."
        ::= { agentConfig 24 }

agentConfigTrapsReceiversTable OBJECT-TYPE
        SYNTAX SEQUENCE OF AgentConfigTrapsReceiversEntry
        ACCESS not-accessible
        STATUS mandatory
        DESCRIPTION
                "A list of managers to send traps to.  The number of
                 entries is given by the value of agentConfigNumTrapReceivers"
        ::= { agentConfig 25}

agentConfigTrapsReceiversEntry OBJECT-TYPE
        SYNTAX AgentConfigTrapsReceiversEntry
        ACCESS not-accessible
        STATUS mandatory
        DESCRIPTION
                "The managers to send traps to."
        INDEX  { trapsIndex}
        ::= { agentConfigTrapsReceiversTable 1 }

AgentConfigTrapsReceiversEntry ::=
        SEQUENCE {
                trapsIndex
                        INTEGER,
                trapsReceiverAddr
                        IpAddress,
                receiverCommunityString
                         DisplayString,
                receiverNmsType
                        INTEGER,
                receiverSeverityLevel
                        INTEGER,
                receiverDescription
                         DisplayString
        }

trapsIndex OBJECT-TYPE
        SYNTAX INTEGER (0..65535)
        ACCESS read-only
        STATUS mandatory
        DESCRIPTION
                "The index to a trap receiver entry."
        ::= { agentConfigTrapsReceiversEntry 1 }

trapsReceiverAddr OBJECT-TYPE
        SYNTAX IpAddress
        ACCESS read-write
        STATUS mandatory
        DESCRIPTION
                "The IP address of the manager to send a trap to."
        ::= { agentConfigTrapsReceiversEntry 2 }

receiverCommunityString OBJECT-TYPE
        SYNTAX DisplayString (SIZE(0..19))
        ACCESS read-write
        STATUS mandatory
        DESCRIPTION
                "The community name to use in the trap when
                 sent to the manager."
        ::= { agentConfigTrapsReceiversEntry 3 }

receiverNmsType OBJECT-TYPE
        SYNTAX  INTEGER {
                none(1),
                rfc1628-trap(2),
                usha-trap(3)
                }
        ACCESS read-write
        STATUS mandatory
        DESCRIPTION
                "The trap group that NMS desired."
        ::= { agentConfigTrapsReceiversEntry 4 }

receiverSeverityLevel OBJECT-TYPE
        SYNTAX  INTEGER {
                informational(1),
                warning(2),
                severe(3)
                }
        ACCESS read-write
        STATUS mandatory
        DESCRIPTION
                "The severity level of traps to be received by this manager."
        ::= { agentConfigTrapsReceiversEntry 5 }

receiverDescription OBJECT-TYPE
        SYNTAX DisplayString (SIZE(0..31))
        ACCESS read-write
        STATUS mandatory
        DESCRIPTION
                "Description of trap receivers"
        ::= { agentConfigTrapsReceiversEntry 6 }

agentConfigAccessControlTable OBJECT-TYPE
        SYNTAX SEQUENCE OF AgentConfigAccessControlEntry
        ACCESS not-accessible
        STATUS mandatory
        DESCRIPTION
                "A list of managers which can access USHA with private
                community string."
        ::= { agentConfig 26}

agentConfigAccessControlEntry OBJECT-TYPE
        SYNTAX AgentConfigAccessControlEntry
        ACCESS not-accessible
        STATUS mandatory
        DESCRIPTION
                "The managers."
        INDEX  { trapsIndex}
        ::= { agentConfigAccessControlTable 1 }

AgentConfigAccessControlEntry ::=
        SEQUENCE {
                accessIndex
                        INTEGER,
                accessControlAddr
                        IpAddress,
                accessCommunityString
                         DisplayString,
                accessControlMode
                        INTEGER
        }

accessIndex OBJECT-TYPE
        SYNTAX INTEGER
        ACCESS read-only
        STATUS mandatory
        DESCRIPTION
                "The index to a access control entry."
        ::= { agentConfigAccessControlEntry 1 }

accessControlAddr OBJECT-TYPE
        SYNTAX IpAddress
        ACCESS read-write
        STATUS mandatory
        DESCRIPTION
                "The IP address of the manager to access USHA"
        ::= { agentConfigAccessControlEntry 2 }

accessCommunityString OBJECT-TYPE
        SYNTAX DisplayString (SIZE(0..19))
        ACCESS read-write
        STATUS mandatory
        DESCRIPTION
                "The community name to use in the manager when
                 access USHA"
        ::= { agentConfigAccessControlEntry 3 }

accessControlMode OBJECT-TYPE
        SYNTAX  INTEGER {
                readOnly (1),
--v1.05                read/write (2),
                read-write (2),
                notAccess (3)
                }
        ACCESS read-write
        STATUS mandatory
        DESCRIPTION
                "Access type, only read/Write access type can change parameter
                 of USHA"
        ::= { agentConfigAccessControlEntry 4 }

agentConfigDefaultLanguage OBJECT-TYPE
        SYNTAX  INTEGER {
                                auto(1),
                                english(2),
                                traditionalChinese(3),
                                simplifiedChinese(4)
                        }
        ACCESS  read-write
        STATUS  mandatory
        DESCRIPTION
                        "The default languauge for browser, when set to auto(1)
                         USHA will send page in the language depends on the
                         request language of browser."
        ::= { agentConfig 27 }

emdSatatusEmdType OBJECT-TYPE
        SYNTAX  INTEGER {
                                unknown(1),
                                disabled(2),
                                eMD-HT(3),
                                eMD-T(4)
                        }
        ACCESS read-only
        STATUS mandatory
        DESCRIPTION
                "The type of EMD plugged into the port."
        ::= { emdStatus 1}

emdSatatusTemperature OBJECT-TYPE
        SYNTAX  INTEGER
        ACCESS read-only
        STATUS mandatory
        DESCRIPTION
                "The measurement of EMD temperature, in 0.1 degree"
        ::= { emdStatus 2}

emdSatatusHumidity OBJECT-TYPE
        SYNTAX  INTEGER
        ACCESS read-only
        STATUS mandatory
        DESCRIPTION
                "The measurement of EMD humidity, in 0.1 degree"
        ::= { emdStatus 3}

emdSatatusAlarm1 OBJECT-TYPE
        SYNTAX  INTEGER {
                                unknow(1),
                                disabled(2),
                                active(3),
                                inactive(4)
                        }
        ACCESS read-only
        STATUS mandatory
        DESCRIPTION
                "The EMD alarm-1 status"
        ::= { emdStatus 4}

emdSatatusAlarm2 OBJECT-TYPE
        SYNTAX  INTEGER {
                                unknow(1),
                                disabled(2),
                                active(3),
                                inactive(4)
                        }
        ACCESS read-only
        STATUS mandatory
        DESCRIPTION
                "The EMD alarm-2 status"
        ::= { emdStatus 5}

usahEmdConfigEmdConfig OBJECT-TYPE
        SYNTAX  INTEGER {
                                disabled(1),
                                auto(2)
                        }
        ACCESS read-write
        STATUS mandatory
        DESCRIPTION
                "Enable or disable to detect presence of EMD"
        ::= { emdConfig 1}

emdConfigEmdName    OBJECT-TYPE
        SYNTAX DisplayString (SIZE(0..15))
        ACCESS read-write
        STATUS mandatory
        DESCRIPTION
                "Description of EMD"
        ::= { emdConfig 2}

emdConfigTemperature OBJECT IDENTIFIER ::= { emdConfig 3 }

emdConfigTempName   OBJECT-TYPE
        SYNTAX DisplayString (SIZE(0..15))
        ACCESS read-write
        STATUS mandatory
        DESCRIPTION
                "Description of EMD temperature sensor"
        ::= { emdConfigTemperature 1}

emdConfigTempHighSetPoint OBJECT-TYPE
        SYNTAX  INTEGER
        ACCESS read-write
        STATUS mandatory
        DESCRIPTION
                "The set point for high temperature warning, in degrees"
        ::= { emdConfigTemperature 2}

emdConfigTempHighStatus   OBJECT-TYPE
        SYNTAX  INTEGER {
                                enabled(1),
                                disabled(2)
                        }
        ACCESS read-write
        STATUS mandatory
        DESCRIPTION
                "To enable/disable high set point check with emd temperature."
        ::= { emdConfigTemperature 3}

emdConfigTempLowSetPoint OBJECT-TYPE
        SYNTAX  INTEGER
        ACCESS read-write
        STATUS mandatory
        DESCRIPTION
                "The set point for low temperature warning, in degrees"
        ::= { emdConfigTemperature 4}

emdConfigTempLowStatus   OBJECT-TYPE
        SYNTAX  INTEGER {
                                enabled(1),
                                disabled(2)
                        }
        ACCESS read-write
        STATUS mandatory
        DESCRIPTION
                "To enable/disable low set point check with emd temperature."
        ::= { emdConfigTemperature 5}

emdConfigTempOffset OBJECT-TYPE
        SYNTAX  INTEGER
        ACCESS read-write
        STATUS mandatory
        DESCRIPTION
                "The offset to calibrate temperature of EMD, in degrees"
        ::= { emdConfigTemperature 6}

emdConfigHumidity OBJECT IDENTIFIER ::= { emdConfig 4 }

emdConfigHumidityName OBJECT-TYPE
        SYNTAX DisplayString (SIZE(0..15))
        ACCESS read-write
        STATUS mandatory
        DESCRIPTION
                "Description of EMD humidity sensor"
        ::= { emdConfigHumidity 1}

emdConfigHumidityHighSetPoint OBJECT-TYPE
        SYNTAX  INTEGER
        ACCESS read-write
        STATUS mandatory
        DESCRIPTION
                "The set point for high humidity warning, in %"
        ::= { emdConfigHumidity 2}

emdConfigHumidityLowStatus   OBJECT-TYPE
        SYNTAX  INTEGER {
                                enabled(1),
                                disabled(2)
                        }
        ACCESS read-write
        STATUS mandatory
        DESCRIPTION
                "To enable/disable high set point check with emd humidity."
        ::= { emdConfigHumidity 3}

emdConfigHumidityLowSetPoint OBJECT-TYPE
        SYNTAX  INTEGER
        ACCESS read-write
        STATUS mandatory
        DESCRIPTION
                "The set point for low humidity warning, in %"
        ::= { emdConfigHumidity 4}

emdConfigHumidityHighStatus   OBJECT-TYPE
        SYNTAX  INTEGER {
                                enabled(1),
                                disabled(2)
                        }
        ACCESS read-write
        STATUS mandatory
        DESCRIPTION
                "To enable/disable low set point check with emd humidity."
        ::= { emdConfigHumidity 5}

emdConfigHumidityOffset OBJECT-TYPE
        SYNTAX  INTEGER
        ACCESS read-write
        STATUS mandatory
        DESCRIPTION
                "The offset to calibrate humidity of EMD, in %"
        ::= { emdConfigHumidity 6}

emdConfigAlarm1 OBJECT IDENTIFIER ::= { emdConfig 5 }

emdConfigAlarm1Name OBJECT-TYPE
        SYNTAX DisplayString (SIZE(0..15))
        ACCESS read-write
        STATUS mandatory
        DESCRIPTION
                "Description of EMD alarm-1"
        ::= { emdConfigAlarm1 1}

emdConfigAlarm1Type OBJECT-TYPE
        SYNTAX  INTEGER {
                                disabled(1),
                                nomralOpen(2),
                                normalClose(3)
                        }
        ACCESS read-write
        STATUS mandatory
        DESCRIPTION
                "The alarm-1 operation type"
        ::= { emdConfigAlarm1 2 }

emdConfigAlarm2 OBJECT IDENTIFIER ::= { emdConfig 6 }

emdConfigAlarm2Name OBJECT-TYPE
        SYNTAX DisplayString (SIZE(0..15))
        ACCESS read-write
        STATUS mandatory
        DESCRIPTION
                "Description of EMD alarm-2"
        ::= { emdConfigAlarm2 1}

emdConfigAlarm2Type OBJECT-TYPE
        SYNTAX  INTEGER {
                                disabled(1),
                                nomralOpen(2),
                                normalClose(3)
                        }
        ACCESS read-write
        STATUS mandatory
        DESCRIPTION
                "The alarm-1 operation type"
        ::= { emdConfigAlarm2 2 }

-- ===========================================================================
-- upsTraps
--
-- Traps group
-- ===========================================================================

   -- This section defines the well-known notifications sent by
   -- UPS agents.
   -- Care must be taken to insure that no particular notification
   -- is sent to a single receiving entity more often than once
   -- every five seconds.

ushaPowerRestored TRAP-TYPE
        ENTERPRISE upsTraps
        DESCRIPTION
                "INFORMATION: Utility power has been restored."
        ::= 1

ushaPowerFail       TRAP-TYPE
        ENTERPRISE      upsTraps
        DESCRIPTION
                "WARNING: Utility power not available."
        ::= 2

ushaReturnFromLowBattery TRAP-TYPE
        ENTERPRISE upsTraps
        DESCRIPTION
                "INFORMATION: The UPS has returned from a low battery
                 condition."
        ::= 3

ushaLowBattery TRAP-TYPE
        ENTERPRISE upsTraps
        DESCRIPTION
                "SEVERE: The UPS batteries are low and will soon be exhausted.
                 If utility power is not restored the UPS will put itself
                 to 'sleep' and immediately cut power to the load."
        ::= 4

ushaUpsOk   TRAP-TYPE
        ENTERPRISE      upsTraps
        DESCRIPTION
                "INFORMATION: The ups is working fine."
        ::= 5

ushaUpsFailed       TRAP-TYPE
        ENTERPRISE      upsTraps
        DESCRIPTION
                "SEVERE: The ups is not working fine."
        ::= 6

ushaUpsNotOnBattery TRAP-TYPE
        ENTERPRISE upsTraps
        DESCRIPTION
                "INFORMATION: The UPS is not on battery power."
        ::= 7

ushaUpsOnBattery TRAP-TYPE
        ENTERPRISE upsTraps
        VARIABLES {
        upsEstimatedChargeRemaining,
        upsBatteryVoltage,
        upsSecondsOnBattery
        }
        DESCRIPTION
                "WARNING: The UPS has switched to battery backup power."
        ::= 8

ushaTestOver TRAP-TYPE
        ENTERPRISE upsTraps
        VARIABLES {
        upsBatteryTest,
        upsTestBatteryTestSettingTime,
        upsTestBatteryTestResult,
        upsTestBatteryTestStartTime,
        upsTestBatteryTestElapsedTime
        }
        DESCRIPTION
                "INFORMATION: The testing of UPS is completed."
        ::= 9

ushaTestInProgress TRAP-TYPE
        ENTERPRISE upsTraps
        DESCRIPTION
                "INFORMATION: The testing is going on ups."
        ::= 10

ushaBypassOn TRAP-TYPE
        ENTERPRISE upsTraps
        DESCRIPTION
                "INFORMATION: The UPS has enabled bypass."
        ::= 11

ushaUpsOnline TRAP-TYPE
        ENTERPRISE upsTraps
                DESCRIPTION
                        "INFORMATION: The ups is not on bypass."
        ::= 12

ushaCommunicationLost TRAP-TYPE
        ENTERPRISE upsTraps
        DESCRIPTION
                 "SEVERE: Communication to the UPS has been lost.  Steps
                  to reestablish communication are in progress."
        ::= 13

ushaCommunicationEstablished TRAP-TYPE
        ENTERPRISE upsTraps
        DESCRIPTION
                "INFORMATION: Communication with the UPS has been
                 established."
        ::= 14

ushaUpsGoingDown    TRAP-TYPE
        ENTERPRISE      upsTraps
        DESCRIPTION
                "WARNING: The ups has been given shutdown command
                by the management station."
        ::= 15

ushaUpsTurnedOff    TRAP-TYPE
        ENTERPRISE      upsTraps
        DESCRIPTION
                "INFORMATION: The ups has been turned off
                by the management station."
        ::= 16

ushaUpsSleeping             TRAP-TYPE
        ENTERPRISE      upsTraps
        VARIABLES {
        upsControlUpsSleepTime
        }
        DESCRIPTION
                "INFORMATION: The UPS has entered in 'sleep' mode. Power to the
                load has been cut off."
        ::= 17

ushaUpsWokeUp               TRAP-TYPE
        ENTERPRISE      upsTraps
        DESCRIPTION
                "INFORMATION: The UPS woke up from 'sleep' mode. Power to the
                load has been restored."
        ::= 18

ushaUpsRebooted             TRAP-TYPE
        ENTERPRISE      upsTraps
        DESCRIPTION
                "INFORMATION: The UPS is rebooted."
        ::= 19

ushaUpsShutdownCancelled TRAP-TYPE
        ENTERPRISE      upsTraps
        DESCRIPTION
                "INFORMATION: Shutdown command is cancelled."
        ::= 20

ushaUpsNotOverTemperature   TRAP-TYPE
        ENTERPRISE      upsTraps
        VARIABLES {
        upsBatteryTemperature,
        upsConfigOverTemperatureSetPoint
        }
        DESCRIPTION
                "INFORMATION: The UPS temperature is under setting point."
        ::= 21

ushaUpsOverTemperature   TRAP-TYPE
        ENTERPRISE      upsTraps
        VARIABLES {
        upsBatteryTemperature,
        upsConfigOverTemperatureSetPoint
        }
        DESCRIPTION
                "WARNING: The UPS temperature is over setting point."
        ::= 22

ushaUpsNotOverLoad       TRAP-TYPE
        ENTERPRISE      upsTraps
        VARIABLES {
        upsOutputPercentLoad,
        upsConfigOverLoadSetPoint
        }
        DESCRIPTION
                "INFORMATION: The UPS output load is under setting point."
        ::= 23

ushaUpsOverLoad   TRAP-TYPE
        ENTERPRISE      upsTraps
        VARIABLES {
        upsOutputPercentLoad,
        upsConfigOverLoadSetPoint
        }
        DESCRIPTION
                "WARNING: The UPS output load is over setting point."
        ::= 24

ushaUpsModuleInserted   TRAP-TYPE
        ENTERPRISE      upsTraps
        DESCRIPTION
                "WARNING: An UPS module had inserted."
        ::= 25

ushaUpsModuleRemoved    TRAP-TYPE
        ENTERPRISE      upsTraps
        DESCRIPTION
                "WARNING: An UPS module had removed."
        ::= 26

emdTemperatureNotHigh   TRAP-TYPE
        ENTERPRISE      upsTraps
        VARIABLES {
        emdSatatusTemperature,
        emdConfigTempHighSetPoint,
        emdConfigTempName
        }
        DESCRIPTION
                "INFORMATION: The temperature of EMD back to normal from high warning."
        ::= 27

emdTemperatureTooHigh   TRAP-TYPE
        ENTERPRISE      upsTraps
        VARIABLES {
        emdSatatusTemperature,
        emdConfigTempHighSetPoint,
        emdConfigTempName
        }
        DESCRIPTION
                "WARNING: The temperature of EMD higher than set point."
        ::= 28

emdTemperatureNotLow    TRAP-TYPE
        ENTERPRISE      upsTraps
        VARIABLES {
        emdSatatusTemperature,
        emdConfigTempLowSetPoint,
        emdConfigTempName
        }
        DESCRIPTION
                "INFORMATION: The temperature of EMD back to normal from low warning."
        ::= 29

emdTemperatureTooLow    TRAP-TYPE
        ENTERPRISE      upsTraps
        VARIABLES {
        emdSatatusTemperature,
        emdConfigTempLowSetPoint,
        emdConfigTempName
        }
        DESCRIPTION
                "WARNING: The temperature of EMD lower than set point."
        ::= 30

emdHumidityNotHigh      TRAP-TYPE
        ENTERPRISE      upsTraps
        VARIABLES {
        emdSatatusHumidity,
        emdConfigHumidityHighSetPoint,
        emdConfigHumidityName
        }
        DESCRIPTION
                "INFORMATION: The humidity of EMD back to normal from high warning."
        ::= 31

emdHumidityTooHigh      TRAP-TYPE
        ENTERPRISE      upsTraps
        VARIABLES {
        emdSatatusHumidity,
        emdConfigHumidityHighSetPoint,
        emdConfigHumidityName
        }
        DESCRIPTION
                "WARNING: The humidity of EMD higher than set point."
        ::= 32

emdHumidityNotLow       TRAP-TYPE
        ENTERPRISE      upsTraps
        VARIABLES {
        emdSatatusHumidity,
        emdConfigHumidityLowSetPoint,
        emdConfigHumidityName
        }
        DESCRIPTION
                "INFORMATION: The humidity of EMD back to normal from low warning."
        ::= 33

emdHumidityTooLow       TRAP-TYPE
        ENTERPRISE      upsTraps
        VARIABLES {
        emdSatatusHumidity,
        emdConfigHumidityLowSetPoint,
        emdConfigHumidityName
        }
        DESCRIPTION
                "WARNING: The humidity of EMD lower than set point."
        ::= 34

emdAlarm1Normal TRAP-TYPE
        ENTERPRISE      upsTraps
        VARIABLES {
        emdConfigAlarm1Type,
        emdConfigAlarm1Name
        }
        DESCRIPTION
                "INFORMATION: The status of emd alarm-1 back to normal from active."
        ::= 35

emdAlarm1Active TRAP-TYPE
        ENTERPRISE      upsTraps
        VARIABLES {
        emdConfigAlarm1Type,
        emdConfigAlarm1Name
        }
        DESCRIPTION
                "WARNING: The status of emd alarm-1 activated."
        ::= 36

emdAlarm2Normal TRAP-TYPE
        ENTERPRISE      upsTraps
        VARIABLES {
        emdConfigAlarm2Type,
        emdConfigAlarm2Name
        }
        DESCRIPTION
                "INFORMATION: The status of emd alarm-2 back to normal from active."
        ::= 37

emdAlarm2Active TRAP-TYPE
        ENTERPRISE      upsTraps
        VARIABLES {
        emdConfigAlarm2Type,
        emdConfigAlarm2Name
        }
        DESCRIPTION
                "WARNING: The status of emd alarm-2 activated."
        ::= 38

   END
