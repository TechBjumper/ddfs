--------------------------------------------------------------------------------
-- PDI SNMP MIB FOR 8212G
-- M4G,BCMS 
--
-- Revision 1.00
-- January 17, 2008
--------------------------------------------------------------------------------
D8212G-MBBBBBB DEFINITIONS ::= BEGIN

IMPORTS
  org, iso, dod, internet, directory, mgmt, experimental, private, enterprises
    FROM RFC-1155-SMI 
  OBJECT-TYPE
    FROM RFC-1212
  DisplayString
    FROM RFC-1213;

--------------------------------------------------------------------------------
-- OID hierarchy
--------------------------------------------------------------------------------

pdi         	OBJECT IDENTIFIER ::= { enterprises 24436 }
 products    	OBJECT IDENTIFIER ::= { pdi 1 }
  remdisplay	OBJECT IDENTIFIER ::= { products 5 }
   d8212g		OBJECT IDENTIFIER ::= { remdisplay 2 }
    display		OBJECT IDENTIFIER ::= { d8212g 1 }
    device1		OBJECT IDENTIFIER ::= { d8212g 2 }
     pdu1		OBJECT IDENTIFIER ::= { device1 4 }
    device2		OBJECT IDENTIFIER ::= { d8212g 3 }
     bcmsplus1	OBJECT IDENTIFIER ::= { device2 2 }
    device3		OBJECT IDENTIFIER ::= { d8212g 4 }
     bcmsplus2	OBJECT IDENTIFIER ::= { device3 2 }
    device4		OBJECT IDENTIFIER ::= { d8212g 5 }
     bcmsplus3	OBJECT IDENTIFIER ::= { device4 2 }
    device5		OBJECT IDENTIFIER ::= { d8212g 6 }
     bcmsplus4	OBJECT IDENTIFIER ::= { device5 2 }
    device6		OBJECT IDENTIFIER ::= { d8212g 7 }
     bcmsplus5	OBJECT IDENTIFIER ::= { device6 2 }
    device7		OBJECT IDENTIFIER ::= { d8212g 8 }
     bcmsplus6	OBJECT IDENTIFIER ::= { device7 2 }

--------------------------------------------------------------------------------
-- Display register values
--------------------------------------------------------------------------------

display-alarm
	OBJECT-TYPE
	SYNTAX  INTEGER
	ACCESS  read-only
	STATUS  mandatory
	DESCRIPTION "alarm register
				bit 0:	Communications Error 1
				bit 1:	Communications Error 2
				bit 2:	Communications Error 3
				bit 3:	Communications Error 4
				bit 4:	Communications Error 5
				bit 5:	Communications Error 6
				bit 6:	Communications Error 7
				bit 7:	Communications Error 8
				bit 8:	Communications Error 9
				bit 9:	Communications Error 10
				bit 10:	Communications Error 11
				bit 11:	Communications Error 12
				bit 12:	Summary Alarm
				bits 13 – 15: Always read as 0"
		::= { display 1 }

display-banner-1
	OBJECT-TYPE
	SYNTAX  INTEGER
	ACCESS  read-write
	STATUS  mandatory
	DESCRIPTION "Banner Character 1"
		::= { display 2 }

display-banner-2
	OBJECT-TYPE
	SYNTAX  INTEGER
	ACCESS  read-write
	STATUS  mandatory
	DESCRIPTION "Banner Character 2"
		::= { display 3 }

display-banner-3
	OBJECT-TYPE
	SYNTAX  INTEGER
	ACCESS  read-write
	STATUS  mandatory
	DESCRIPTION "Banner Character 3"
		::= { display 4 }

display-banner-4
	OBJECT-TYPE
	SYNTAX  INTEGER
	ACCESS  read-write
	STATUS  mandatory
	DESCRIPTION "Banner Character 4"
		::= { display 5 }

display-banner-5
	OBJECT-TYPE
	SYNTAX  INTEGER
	ACCESS  read-write
	STATUS  mandatory
	DESCRIPTION "Banner Character 5"
		::= { display 6 }

display-banner-6
	OBJECT-TYPE
	SYNTAX  INTEGER
	ACCESS  read-write
	STATUS  mandatory
	DESCRIPTION "Banner Character 6"
		::= { display 7 }

display-banner-7
	OBJECT-TYPE
	SYNTAX  INTEGER
	ACCESS  read-write
	STATUS  mandatory
	DESCRIPTION "Banner Character 7"
		::= { display 8 }

display-banner-8
	OBJECT-TYPE
	SYNTAX  INTEGER
	ACCESS  read-write
	STATUS  mandatory
	DESCRIPTION "Banner Character 8"
		::= { display 9 }

display-banner-9
	OBJECT-TYPE
	SYNTAX  INTEGER
	ACCESS  read-write
	STATUS  mandatory
	DESCRIPTION "Banner Character 9"
		::= { display 10 }

display-banner-10
	OBJECT-TYPE
	SYNTAX  INTEGER
	ACCESS  read-write
	STATUS  mandatory
	DESCRIPTION "Banner Character 10"
		::= { display 11 }

display-banner-11
	OBJECT-TYPE
	SYNTAX  INTEGER
	ACCESS  read-write
	STATUS  mandatory
	DESCRIPTION "Banner Character 11"
		::= { display 12 }

display-banner-12
	OBJECT-TYPE
	SYNTAX  INTEGER
	ACCESS  read-write
	STATUS  mandatory
	DESCRIPTION "Banner Character 12"
		::= { display 13 }

display-banner-13
	OBJECT-TYPE
	SYNTAX  INTEGER
	ACCESS  read-write
	STATUS  mandatory
	DESCRIPTION "Banner Character 13"
		::= { display 14 }

display-banner-14
	OBJECT-TYPE
	SYNTAX  INTEGER
	ACCESS  read-write
	STATUS  mandatory
	DESCRIPTION "Banner Character 14"
		::= { display 15 }

display-banner-15
	OBJECT-TYPE
	SYNTAX  INTEGER
	ACCESS  read-write
	STATUS  mandatory
	DESCRIPTION "Banner Character 15"
		::= { display 16 }

display-banner-16
	OBJECT-TYPE
	SYNTAX  INTEGER
	ACCESS  read-write
	STATUS  mandatory
	DESCRIPTION "Banner Character 16"
		::= { display 17 }

display-banner-17
	OBJECT-TYPE
	SYNTAX  INTEGER
	ACCESS  read-write
	STATUS  mandatory
	DESCRIPTION "Banner Character 17"
		::= { display 18 }

display-banner-18
	OBJECT-TYPE
	SYNTAX  INTEGER
	ACCESS  read-write
	STATUS  mandatory
	DESCRIPTION "Banner Character 18"
		::= { display 19 }

display-banner-19
	OBJECT-TYPE
	SYNTAX  INTEGER
	ACCESS  read-write
	STATUS  mandatory
	DESCRIPTION "Banner Character 19"
		::= { display 20 }

display-banner-20
	OBJECT-TYPE
	SYNTAX  INTEGER
	ACCESS  read-write
	STATUS  mandatory
	DESCRIPTION "Banner Character 20"
		::= { display 21 }

display-banner-21
	OBJECT-TYPE
	SYNTAX  INTEGER
	ACCESS  read-write
	STATUS  mandatory
	DESCRIPTION "Banner Character 21"
		::= { display 22 }

display-banner-22
	OBJECT-TYPE
	SYNTAX  INTEGER
	ACCESS  read-write
	STATUS  mandatory
	DESCRIPTION "Banner Character 22"
		::= { display 23 }

display-banner-23
	OBJECT-TYPE
	SYNTAX  INTEGER
	ACCESS  read-write
	STATUS  mandatory
	DESCRIPTION "Banner Character 23"
		::= { display 24 }

display-banner-24
	OBJECT-TYPE
	SYNTAX  INTEGER
	ACCESS  read-write
	STATUS  mandatory
	DESCRIPTION "Banner Character 24"
		::= { display 25 }

display-banner-25
	OBJECT-TYPE
	SYNTAX  INTEGER
	ACCESS  read-write
	STATUS  mandatory
	DESCRIPTION "Banner Character 25"
		::= { display 26 }

display-banner-26
	OBJECT-TYPE
	SYNTAX  INTEGER
	ACCESS  read-write
	STATUS  mandatory
	DESCRIPTION "Banner Character 26"
		::= { display 27 }

display-banner-27
	OBJECT-TYPE
	SYNTAX  INTEGER
	ACCESS  read-write
	STATUS  mandatory
	DESCRIPTION "Banner Character 27"
		::= { display 28 }

display-banner-28
	OBJECT-TYPE
	SYNTAX  INTEGER
	ACCESS  read-write
	STATUS  mandatory
	DESCRIPTION "Banner Character 28"
		::= { display 29 }

display-banner-29
	OBJECT-TYPE
	SYNTAX  INTEGER
	ACCESS  read-write
	STATUS  mandatory
	DESCRIPTION "Banner Character 29"
		::= { display 30 }

display-banner-30
	OBJECT-TYPE
	SYNTAX  INTEGER
	ACCESS  read-write
	STATUS  mandatory
	DESCRIPTION "Banner Character 30"
		::= { display 31 }

display-banner-31
	OBJECT-TYPE
	SYNTAX  INTEGER
	ACCESS  read-write
	STATUS  mandatory
	DESCRIPTION "Banner Character 31"
		::= { display 32 }

display-banner-32
	OBJECT-TYPE
	SYNTAX  INTEGER
	ACCESS  read-write
	STATUS  mandatory
	DESCRIPTION "Banner Character 32"
		::= { display 33 }

display-banner-33
	OBJECT-TYPE
	SYNTAX  INTEGER
	ACCESS  read-write
	STATUS  mandatory
	DESCRIPTION "Banner Character 33"
		::= { display 34 }

display-banner-34
	OBJECT-TYPE
	SYNTAX  INTEGER
	ACCESS  read-write
	STATUS  mandatory
	DESCRIPTION "Banner Character 34"
		::= { display 35 }

display-banner-35
	OBJECT-TYPE
	SYNTAX  INTEGER
	ACCESS  read-write
	STATUS  mandatory
	DESCRIPTION "Banner Character 35"
		::= { display 36 }

display-banner-36
	OBJECT-TYPE
	SYNTAX  INTEGER
	ACCESS  read-write
	STATUS  mandatory
	DESCRIPTION "Banner Character 36"
		::= { display 37 }

display-banner-37
	OBJECT-TYPE
	SYNTAX  INTEGER
	ACCESS  read-write
	STATUS  mandatory
	DESCRIPTION "Banner Character 37"
		::= { display 38 }

display-banner-38
	OBJECT-TYPE
	SYNTAX  INTEGER
	ACCESS  read-write
	STATUS  mandatory
	DESCRIPTION "Banner Character 38"
		::= { display 39 }

display-banner-39
	OBJECT-TYPE
	SYNTAX  INTEGER
	ACCESS  read-write
	STATUS  mandatory
	DESCRIPTION "Banner Character 39"
		::= { display 40 }

display-banner-40
	OBJECT-TYPE
	SYNTAX  INTEGER
	ACCESS  read-write
	STATUS  mandatory
	DESCRIPTION "Banner Character 40"
		::= { display 41 }

display-version
	OBJECT-TYPE
	SYNTAX  INTEGER
	ACCESS  read-only
	STATUS  mandatory
	DESCRIPTION "Software Version"
		::= { display 42 }

display-revision
	OBJECT-TYPE
	SYNTAX  INTEGER
	ACCESS  read-only
	STATUS  mandatory
	DESCRIPTION "Software Revision"
		::= { display 43 }

display-number-devices
	OBJECT-TYPE
	SYNTAX  INTEGER
	ACCESS  read-write
	STATUS  mandatory
	DESCRIPTION "Number of Devices"
		::= { display 44 }

display-device-1-options
	OBJECT-TYPE
	SYNTAX  INTEGER
	ACCESS  read-write
	STATUS  mandatory
	DESCRIPTION "Device 1 options - same for all devices below
			BCMS PLUS:        bit 0:	Panel Size (0=225, 1=400) 
bit 1:	CB Zero Current Alarms(1 = enable)
bit 2:	CB Warnings (1 = enable)
bit 3:	CB Alarms (1 = enable)
bit 4:	Total Currents Alarms(1 = enable)
bit 5:	Voltage Alarms(1 = enable)
bits 6 – 15: Always read as 0

			BCMS CB:		bit 1:	Total Currents Alarms(1 = enable)
bit 2:	Voltage Alarms(1 = enable)
bits 3 – 15: Always read as 0"
		::= { display 45 }

display-device-2-options
	OBJECT-TYPE
	SYNTAX  INTEGER
	ACCESS  read-write
	STATUS  mandatory
	DESCRIPTION "Device 2 options"
		::= { display 46 }

display-device-3-options
	OBJECT-TYPE
	SYNTAX  INTEGER
	ACCESS  read-write
	STATUS  mandatory
	DESCRIPTION "Device 3 options"
		::= { display 47 }

display-device-4-options
	OBJECT-TYPE
	SYNTAX  INTEGER
	ACCESS  read-write
	STATUS  mandatory
	DESCRIPTION "Device 4 options"
		::= { display 48 }

display-device-5-options
	OBJECT-TYPE
	SYNTAX  INTEGER
	ACCESS  read-write
	STATUS  mandatory
	DESCRIPTION "Device 5 options"
		::= { display 49 }

display-device-6-options
	OBJECT-TYPE
	SYNTAX  INTEGER
	ACCESS  read-write
	STATUS  mandatory
	DESCRIPTION "Device 6 options"
		::= { display 50 }

display-device-7-options
	OBJECT-TYPE
	SYNTAX  INTEGER
	ACCESS  read-write
	STATUS  mandatory
	DESCRIPTION "Device 7 options"
		::= { display 51 }

display-device-8-options
	OBJECT-TYPE
	SYNTAX  INTEGER
	ACCESS  read-write
	STATUS  mandatory
	DESCRIPTION "Device 8 options"
		::= { display 52 }

display-device-9-options
	OBJECT-TYPE
	SYNTAX  INTEGER
	ACCESS  read-write
	STATUS  mandatory
	DESCRIPTION "Device 9 options"
		::= { display 53 }

display-device-10-options
	OBJECT-TYPE
	SYNTAX  INTEGER
	ACCESS  read-write
	STATUS  mandatory
	DESCRIPTION "Device 10 options"
		::= { display 54 }

display-device-11-options
	OBJECT-TYPE
	SYNTAX  INTEGER
	ACCESS  read-write
	STATUS  mandatory
	DESCRIPTION "Device 11 options"
		::= { display 55 }

display-device-12-options
	OBJECT-TYPE
	SYNTAX  INTEGER
	ACCESS  read-write
	STATUS  mandatory
	DESCRIPTION "Device 12 options"
		::= { display 56 }

--------------------------------------------------------------------------------
-- PDU register values
--------------------------------------------------------------------------------

pdu1-input-voltage-1-ab
	OBJECT-TYPE
	SYNTAX  INTEGER
	ACCESS  read-only
	STATUS  mandatory
	DESCRIPTION "Input Voltage 1 AB"
		::= { pdu1 1 }

pdu1-input-voltage-1-bc
	OBJECT-TYPE
	SYNTAX  INTEGER
	ACCESS  read-only
	STATUS  mandatory
	DESCRIPTION "Input Voltage 1 BC"
		::= { pdu1 2 }

pdu1-input-voltage-1-ca
	OBJECT-TYPE
	SYNTAX  INTEGER
	ACCESS  read-only
	STATUS  mandatory
	DESCRIPTION "Input Voltage 1 CA"
		::= { pdu1 3 }

pdu1-input-voltage-1-frequency
	OBJECT-TYPE
	SYNTAX  INTEGER
	ACCESS  read-only
	STATUS  mandatory
	DESCRIPTION "Input Voltage 1 Frequency"
		::= { pdu1 4 }

pdu1-input-voltage-1-ab-thd
	OBJECT-TYPE
	SYNTAX  INTEGER
	ACCESS  read-only
	STATUS  mandatory
	DESCRIPTION "Input Voltage 1 AB THD"
		::= { pdu1 5 }

pdu1-input-voltage-1-bc-thd
	OBJECT-TYPE
	SYNTAX  INTEGER
	ACCESS  read-only
	STATUS  mandatory
	DESCRIPTION "Input Voltage 1 BC THD"
		::= { pdu1 6 }

pdu1-input-voltage-1-ca-thd
	OBJECT-TYPE
	SYNTAX  INTEGER
	ACCESS  read-only
	STATUS  mandatory
	DESCRIPTION "Input Voltage 1 CA THD"
		::= { pdu1 7 }

pdu1-input-voltage-2-ab
	OBJECT-TYPE
	SYNTAX  INTEGER
	ACCESS  read-only
	STATUS  mandatory
	DESCRIPTION "Input Voltage 2 AB - optional second input"
		::= { pdu1 8 }

pdu1-input-voltage-2-bc
	OBJECT-TYPE
	SYNTAX  INTEGER
	ACCESS  read-only
	STATUS  mandatory
	DESCRIPTION "Input Voltage 2 BC - optional second input"
		::= { pdu1 9 }

pdu1-input-voltage-2-ca
	OBJECT-TYPE
	SYNTAX  INTEGER
	ACCESS  read-only
	STATUS  mandatory
	DESCRIPTION "Input Voltage 2 CA - optional second input"
		::= { pdu1 10 }

pdu1-input-voltage-2-frequency
	OBJECT-TYPE
	SYNTAX  INTEGER
	ACCESS  read-only
	STATUS  mandatory
	DESCRIPTION "Input Voltage 2 Frequency - optional second input"
		::= { pdu1 11 }

pdu1-phase-difference-v1-to-v2
	OBJECT-TYPE
	SYNTAX  INTEGER
	ACCESS  read-only
	STATUS  mandatory
	DESCRIPTION "Phase difference input V1 to Input V2 - optional second input"
		::= { pdu1 12 }

pdu1-input-voltage-2-ab-thd
	OBJECT-TYPE
	SYNTAX  INTEGER
	ACCESS  read-only
	STATUS  mandatory
	DESCRIPTION "Input Voltage 2 AB THD - optional second input"
		::= { pdu1 13 }

pdu1-input-voltage-2-bc-thd
	OBJECT-TYPE
	SYNTAX  INTEGER
	ACCESS  read-only
	STATUS  mandatory
	DESCRIPTION "Input Voltage 2 BC THD - optional second input"
		::= { pdu1 14 }

pdu1-input-voltage-2-ca-thd
	OBJECT-TYPE
	SYNTAX  INTEGER
	ACCESS  read-only
	STATUS  mandatory
	DESCRIPTION "Input Voltage 2 CA THD - optional second input"
		::= { pdu1 15 }

pdu1-output-voltage-1-ab
	OBJECT-TYPE
	SYNTAX  INTEGER
	ACCESS  read-only
	STATUS  mandatory
	DESCRIPTION "Output Voltage 1 AB"
		::= { pdu1 16 }

pdu1-output-voltage-1-bc
	OBJECT-TYPE
	SYNTAX  INTEGER
	ACCESS  read-only
	STATUS  mandatory
	DESCRIPTION "Output Voltage 1 BC"
		::= { pdu1 17 }

pdu1-output-voltage-1-ca
	OBJECT-TYPE
	SYNTAX  INTEGER
	ACCESS  read-only
	STATUS  mandatory
	DESCRIPTION "Output Voltage 1 CA"
		::= { pdu1 18 }

pdu1-output-voltage-1-an
	OBJECT-TYPE
	SYNTAX  INTEGER
	ACCESS  read-only
	STATUS  mandatory
	DESCRIPTION "Output Voltage 1 AN"
		::= { pdu1 19 }

pdu1-output-voltage-1-bn
	OBJECT-TYPE
	SYNTAX  INTEGER
	ACCESS  read-only
	STATUS  mandatory
	DESCRIPTION "Output Voltage 1 BN"
		::= { pdu1 20 }

pdu1-output-voltage-1-cn
	OBJECT-TYPE
	SYNTAX  INTEGER
	ACCESS  read-only
	STATUS  mandatory
	DESCRIPTION "Output Voltage 1 CN"
		::= { pdu1 21 }

pdu1-output-current-1-a
	OBJECT-TYPE
	SYNTAX  INTEGER
	ACCESS  read-only
	STATUS  mandatory
	DESCRIPTION "Output Current 1 A"
		::= { pdu1 22 }

pdu1-output-current-1-b
	OBJECT-TYPE
	SYNTAX  INTEGER
	ACCESS  read-only
	STATUS  mandatory
	DESCRIPTION "Output Current 1 B"
		::= { pdu1 23 }

pdu1-output-current-1-c
	OBJECT-TYPE
	SYNTAX  INTEGER
	ACCESS  read-only
	STATUS  mandatory
	DESCRIPTION "Output Current 1 C"
		::= { pdu1 24 }

pdu1-output-1-kw-a
	OBJECT-TYPE
	SYNTAX  INTEGER
	ACCESS  read-only
	STATUS  mandatory
	DESCRIPTION "Output 1 KW A"
		::= { pdu1 25 }

pdu1-output-1-kw-b
	OBJECT-TYPE
	SYNTAX  INTEGER
	ACCESS  read-only
	STATUS  mandatory
	DESCRIPTION "Output 1 KW B"
		::= { pdu1 26 }

pdu1-output-1-kw-c
	OBJECT-TYPE
	SYNTAX  INTEGER
	ACCESS  read-only
	STATUS  mandatory
	DESCRIPTION "Output 1 KW C"
		::= { pdu1 27 }

pdu1-output-1-kw-total
	OBJECT-TYPE
	SYNTAX  INTEGER
	ACCESS  read-only
	STATUS  mandatory
	DESCRIPTION "Output 1 KW Total"
		::= { pdu1 28 }

pdu1-output-1-kva-a
	OBJECT-TYPE
	SYNTAX  INTEGER
	ACCESS  read-only
	STATUS  mandatory
	DESCRIPTION "Output 1 KVA A"
		::= { pdu1 29 }

pdu1-output-1-kva-b
	OBJECT-TYPE
	SYNTAX  INTEGER
	ACCESS  read-only
	STATUS  mandatory
	DESCRIPTION "Output 1 KVA B"
		::= { pdu1 30 }

pdu1-output-1-kva-c
	OBJECT-TYPE
	SYNTAX  INTEGER
	ACCESS  read-only
	STATUS  mandatory
	DESCRIPTION "Output 1 KVA C"
		::= { pdu1 31 }

pdu1-output-1-kva-total
	OBJECT-TYPE
	SYNTAX  INTEGER
	ACCESS  read-only
	STATUS  mandatory
	DESCRIPTION "Output 1 KVA Total"
		::= { pdu1 32 }

pdu1-output-1-kvar-a
	OBJECT-TYPE
	SYNTAX  INTEGER
	ACCESS  read-only
	STATUS  mandatory
	DESCRIPTION "Output 1 KVAR A"
		::= { pdu1 33 }

pdu1-output-1-kvar-b
	OBJECT-TYPE
	SYNTAX  INTEGER
	ACCESS  read-only
	STATUS  mandatory
	DESCRIPTION "Output 1 KVAR B"
		::= { pdu1 34 }

pdu1-output-1-kvar-c
	OBJECT-TYPE
	SYNTAX  INTEGER
	ACCESS  read-only
	STATUS  mandatory
	DESCRIPTION "Output 1 KVAR C"
		::= { pdu1 35 }

pdu1-output-1-kvar-total
	OBJECT-TYPE
	SYNTAX  INTEGER
	ACCESS  read-only
	STATUS  mandatory
	DESCRIPTION "Output 1 KVAR Total"
		::= { pdu1 36 }

pdu1-output-1-pf-a
	OBJECT-TYPE
	SYNTAX  INTEGER
	ACCESS  read-only
	STATUS  mandatory
	DESCRIPTION "Output 1 PF A"
		::= { pdu1 37 }

pdu1-output-1-pf-b
	OBJECT-TYPE
	SYNTAX  INTEGER
	ACCESS  read-only
	STATUS  mandatory
	DESCRIPTION "Output 1 PF B"
		::= { pdu1 38 }

pdu1-output-1-pf-c
	OBJECT-TYPE
	SYNTAX  INTEGER
	ACCESS  read-only
	STATUS  mandatory
	DESCRIPTION "Output 1 PF C"
		::= { pdu1 39 }

pdu1-output-1-kwh-low
	OBJECT-TYPE
	SYNTAX  INTEGER
	ACCESS  read-only
	STATUS  mandatory
	DESCRIPTION "Output 1 KWH low"
		::= { pdu1 40 }

pdu1-output-1-kwh-high
	OBJECT-TYPE
	SYNTAX  INTEGER
	ACCESS  read-only
	STATUS  mandatory
	DESCRIPTION "Output 1 KWH high"
		::= { pdu1 41 }

pdu1-neutral-current
	OBJECT-TYPE
	SYNTAX  INTEGER
	ACCESS  read-only
	STATUS  mandatory
	DESCRIPTION "Output Neutral current"
		::= { pdu1 42 }

pdu1-ground-current
	OBJECT-TYPE
	SYNTAX  INTEGER
	ACCESS  read-only
	STATUS  mandatory
	DESCRIPTION "Output Ground Current"
		::= { pdu1 43 }

pdu1-output-voltage-2-ab
	OBJECT-TYPE
	SYNTAX  INTEGER
	ACCESS  read-only
	STATUS  mandatory
	DESCRIPTION "Output Voltage 2 AB - Optional Second Output"
		::= { pdu1 44 }

pdu1-output-voltage-2-bc
	OBJECT-TYPE
	SYNTAX  INTEGER
	ACCESS  read-only
	STATUS  mandatory
	DESCRIPTION "Output Voltage 2 BC - Optional Second Output"
		::= { pdu1 45 }

pdu1-output-voltage-2-ca
	OBJECT-TYPE
	SYNTAX  INTEGER
	ACCESS  read-only
	STATUS  mandatory
	DESCRIPTION "Output Voltage 2 CA - Optional Second Output"
		::= { pdu1 46 }

pdu1-output-voltage-2-an
	OBJECT-TYPE
	SYNTAX  INTEGER
	ACCESS  read-only
	STATUS  mandatory
	DESCRIPTION "Output Voltage 2 AN - Optional Second Output"
		::= { pdu1 47 }

pdu1-output-voltage-2-bn
	OBJECT-TYPE
	SYNTAX  INTEGER
	ACCESS  read-only
	STATUS  mandatory
	DESCRIPTION "Output Voltage 2 BN - Optional Second Output"
		::= { pdu1 48 }

pdu1-output-voltage-2-cn
	OBJECT-TYPE
	SYNTAX  INTEGER
	ACCESS  read-only
	STATUS  mandatory
	DESCRIPTION "Output Voltage 2 CN - Optional Second Output"
		::= { pdu1 49 }

pdu1-output-current-2-a
	OBJECT-TYPE
	SYNTAX  INTEGER
	ACCESS  read-only
	STATUS  mandatory
	DESCRIPTION "Output Current 2 A - Optional Second Output"
		::= { pdu1 50 }

pdu1-output-current-2-b
	OBJECT-TYPE
	SYNTAX  INTEGER
	ACCESS  read-only
	STATUS  mandatory
	DESCRIPTION "Output Current 2 B - Optional Second Output"
		::= { pdu1 51 }

pdu1-output-current-2-c
	OBJECT-TYPE
	SYNTAX  INTEGER
	ACCESS  read-only
	STATUS  mandatory
	DESCRIPTION "Output Current 2 C - Optional Second Output"
		::= { pdu1 52 }

pdu1-output-2-kw-a
	OBJECT-TYPE
	SYNTAX  INTEGER
	ACCESS  read-only
	STATUS  mandatory
	DESCRIPTION "Output KW A - Optional Second Output"
		::= { pdu1 53 }

pdu1-output-2-kw-b
	OBJECT-TYPE
	SYNTAX  INTEGER
	ACCESS  read-only
	STATUS  mandatory
	DESCRIPTION "Output KW B - Optional Second Output"
		::= { pdu1 54 }

pdu1-output-2-kw-c
	OBJECT-TYPE
	SYNTAX  INTEGER
	ACCESS  read-only
	STATUS  mandatory
	DESCRIPTION "Output KW C - Optional Second Output"
		::= { pdu1 55 }

pdu1-output-2-kw-total
	OBJECT-TYPE
	SYNTAX  INTEGER
	ACCESS  read-only
	STATUS  mandatory
	DESCRIPTION "Output KW Total - Optional Second Output"
		::= { pdu1 56 }

pdu1-output-2-kva-a
	OBJECT-TYPE
	SYNTAX  INTEGER
	ACCESS  read-only
	STATUS  mandatory
	DESCRIPTION "Output KVA A - Optional Second Output"
		::= { pdu1 57 }

pdu1-output-2-kva-b
	OBJECT-TYPE
	SYNTAX  INTEGER
	ACCESS  read-only
	STATUS  mandatory
	DESCRIPTION "Output KVA B - Optional Second Output"
		::= { pdu1 58 }

pdu1-output-2-kva-c
	OBJECT-TYPE
	SYNTAX  INTEGER
	ACCESS  read-only
	STATUS  mandatory
	DESCRIPTION "Output KVA C - Optional Second Output"
		::= { pdu1 59 }

pdu1-output-2-kva-total
	OBJECT-TYPE
	SYNTAX  INTEGER
	ACCESS  read-only
	STATUS  mandatory
	DESCRIPTION "Output KVA Total - Optional Second Output"
		::= { pdu1 60 }

pdu1-output-2-kvar-a
	OBJECT-TYPE
	SYNTAX  INTEGER
	ACCESS  read-only
	STATUS  mandatory
	DESCRIPTION "Output KVAR A - Optional Second Output"
		::= { pdu1 61 }

pdu1-output-2-kvar-b
	OBJECT-TYPE
	SYNTAX  INTEGER
	ACCESS  read-only
	STATUS  mandatory
	DESCRIPTION "Output KVAR B - Optional Second Output"
		::= { pdu1 62 }

pdu1-output-2-kvar-c
	OBJECT-TYPE
	SYNTAX  INTEGER
	ACCESS  read-only
	STATUS  mandatory
	DESCRIPTION "Output KVAR C - Optional Second Output"
		::= { pdu1 63 }

pdu1-output-2-kvar-total
	OBJECT-TYPE
	SYNTAX  INTEGER
	ACCESS  read-only
	STATUS  mandatory
	DESCRIPTION "Output KVAR Total - Optional Second Output"
		::= { pdu1 64 }

pdu1-output-2-pf-a
	OBJECT-TYPE
	SYNTAX  INTEGER
	ACCESS  read-only
	STATUS  mandatory
	DESCRIPTION "Output PF A - Optional Second Output"
		::= { pdu1 65 }

pdu1-output-2-pf-b
	OBJECT-TYPE
	SYNTAX  INTEGER
	ACCESS  read-only
	STATUS  mandatory
	DESCRIPTION "Output PF B - Optional Second Output"
		::= { pdu1 66 }

pdu1-output-2-pf-c
	OBJECT-TYPE
	SYNTAX  INTEGER
	ACCESS  read-only
	STATUS  mandatory
	DESCRIPTION "Output PF C - Optional Second Output"
		::= { pdu1 67 }

pdu1-output-2-kwh-low
	OBJECT-TYPE
	SYNTAX  INTEGER
	ACCESS  read-only
	STATUS  mandatory
	DESCRIPTION "Output KWH low - Optional Second Output"
		::= { pdu1 68 }

pdu1-output-2-kwh-high
	OBJECT-TYPE
	SYNTAX  INTEGER
	ACCESS  read-only
	STATUS  mandatory
	DESCRIPTION "Output KWH high - Optional Second Output"
		::= { pdu1 69 }

pdu1-summary-alarms
	OBJECT-TYPE
	SYNTAX  INTEGER
	ACCESS  read-only
	STATUS  mandatory
	DESCRIPTION "Summary Alarm
                   bit 0: Voltage Alarm
                   bit 1: Current Alarm
                   bit 2: Power Alarm
                   bit 3: Building Alarm
                   bit 4: Digital Alarm
                   bit 5: EPO
                   bit 6: Remote EPO
                   bit 7: Thermal Overtemp
                   bit 8: Thermal Hightemp
                   bit 9: Phase Rotation
                   bit 10: S1-S2 Phase Angle - Dual Input Only
                   bit 11: Ground Current Trip - Optional
                   bit 12: Phase Rotation Trip - Optional
                   bit 13: Over Voltage Trip - Optional
                   bit 14: Under Voltage Trip - Optional
                   bit 15: not used"
		::= { pdu1 70 }

pdu1-summary-alarms-latched
	OBJECT-TYPE
	SYNTAX  INTEGER
	ACCESS  read-write
	STATUS  mandatory
	DESCRIPTION "Summary Alarm Latched
                    - Same bits as Summary Alarm"
		::= { pdu1 71 }

pdu1-input-voltage-1-alarms
	OBJECT-TYPE
	SYNTAX  INTEGER
	ACCESS  read-only
	STATUS  mandatory
	DESCRIPTION "Input Voltage 1 Alarms
                   bit 0: Volt AB High
                   bit 1: Volt AB Low
                   bit 2: Volt BC High
                   bit 3: Volt BC Low
                   bit 4: Volt CA High
                   bit 5: Volt CA Low
                   bits 6-15 not used"
		::= { pdu1 72 }

pdu1-input-voltage-1-alarms-latched
	OBJECT-TYPE
	SYNTAX  INTEGER
	ACCESS  read-write
	STATUS  mandatory
	DESCRIPTION "Input Voltage 1 Alarms Latched
                    - Same bits as Input Voltage 1 Alarms"
		::= { pdu1 73 }

pdu1-input-voltage-2-alarms
	OBJECT-TYPE
	SYNTAX  INTEGER
	ACCESS  read-only
	STATUS  mandatory
	DESCRIPTION "Input Voltage 2 Alarms
                   bit 0: Volt AB High
                   bit 1: Volt AB Low
                   bit 2: Volt BC High
                   bit 3: Volt BC Low
                   bit 4: Volt CA High
                   bit 5: Volt CA Low
                   bits 6-15 not used"
		::= { pdu1 74 }

pdu1-input-voltage-2-alarms-latched
	OBJECT-TYPE
	SYNTAX  INTEGER
	ACCESS  read-write
	STATUS  mandatory
	DESCRIPTION "Input Voltage 2 Alarms Latched
                    - Same bits as Input Voltage 2 Alarms"
		::= { pdu1 75 }

pdu1-output-voltage-1-alarms
	OBJECT-TYPE
	SYNTAX  INTEGER
	ACCESS  read-only
	STATUS  mandatory
	DESCRIPTION "Output Voltage 1 Alarms
                   bit 0: Volt AB High
                   bit 1: Volt AB Low
                   bit 2: Volt BC High
                   bit 3: Volt BC Low
                   bit 4: Volt CA High
                   bit 5: Volt CA Low
                   bit 6: Volt AN High
                   bit 7: Volt AN Low
                   bit 8: Volt BN High
                   bit 9: Volt BN Low
                   bit 10: Volt CN High
                   bit 11: Volt CN Low
                   bits 12-15 not used"
		::= { pdu1 76 }

pdu1-output-voltage-1-alarms-latched
	OBJECT-TYPE
	SYNTAX  INTEGER
	ACCESS  read-write
	STATUS  mandatory
	DESCRIPTION "Output Voltage 1 Alarms Latched
                    - Same bits as Output Voltage 1 Alarms"
		::= { pdu1 77 }

pdu1-output-voltage-2-alarms
	OBJECT-TYPE
	SYNTAX  INTEGER
	ACCESS  read-only
	STATUS  mandatory
	DESCRIPTION "Output Voltage 1 Alarms
			  - Optional Second Output
                   bit 0: Volt AB High
                   bit 1: Volt AB Low
                   bit 2: Volt BC High
                   bit 3: Volt BC Low
                   bit 4: Volt CA High
                   bit 5: Volt CA Low
                   bit 6: Volt AN High
                   bit 7: Volt AN Low
                   bit 8: Volt BN High
                   bit 9: Volt BN Low
                   bit 10: Volt CN High
                   bit 11: Volt CN Low
                   bits 12-15 not used"
		::= { pdu1 78 }

pdu1-output-voltage-2-alarms-latched
	OBJECT-TYPE
	SYNTAX  INTEGER
	ACCESS  read-write
	STATUS  mandatory
	DESCRIPTION "Output Voltage 2 Alarms Latched
                    - Same bits as Output Current 1 Alarms
                    - Optional Second Output"
		::= { pdu1 79 }

pdu1-output-current-1-alarms
	OBJECT-TYPE
	SYNTAX  INTEGER
	ACCESS  read-only
	STATUS  mandatory
	DESCRIPTION "Output Current 1 Alarms
                   bit 0: Current A High
                   bit 1: Current A Low
                   bit 2: Current B High
                   bit 3: Current B Low
                   bit 4: Current C High
                   bit 5: Current C Low
                   bit 6: Neutral Current High
                   bit 7: Neutral Current Low
                   bit 8: Ground Current High
                   bit 9: Ground Current Low
                   bits 10-15 not used"
		::= { pdu1 80 }

pdu1-output-current-1-alarms-latched
	OBJECT-TYPE
	SYNTAX  INTEGER
	ACCESS  read-write
	STATUS  mandatory
	DESCRIPTION "Output Current 1 Alarms Latched
                    - Same bits as Output Current 1 Alarms"
		::= { pdu1 81 }

pdu1-output-current-2-alarms
	OBJECT-TYPE
	SYNTAX  INTEGER
	ACCESS  read-only
	STATUS  mandatory
	DESCRIPTION "Output Current 2 Alarms
			  - Optional Second Output
                   bit 0: Current A High
                   bit 1: Current A Low
                   bit 2: Current B High
                   bit 3: Current B Low
                   bit 4: Current C High
                   bit 5: Current C Low
                   bits 6-15 not used"
		::= { pdu1 82 }

pdu1-output-current-2-alarms-latched
	OBJECT-TYPE
	SYNTAX  INTEGER
	ACCESS  read-write
	STATUS  mandatory
	DESCRIPTION "Output Current 2 Alarms Latched
                    - Same bits as Output Current 2 Alarms
                    - Optional Second Output"
		::= { pdu1 83 }

pdu1-output-power-1-alarms
	OBJECT-TYPE
	SYNTAX  INTEGER
	ACCESS  read-only
	STATUS  mandatory
	DESCRIPTION "Output Power 1 Alarms
                   bit 0: KW A High
                   bit 1: KW B High
                   bit 2: KW C High
                   bit 3: KW Total High
                   bit 4: KVA A High
                   bit 5: KVA B High
                   bit 6: KVA C High
                   bit 7: KVA Total High
                   bits 8-15 not used"
		::= { pdu1 84 }

pdu1-output-power-1-alarms-latched
	OBJECT-TYPE
	SYNTAX  INTEGER
	ACCESS  read-write
	STATUS  mandatory
	DESCRIPTION "Output Power 1 Alarms Latched
                    - Same bits as Output Power 1 Alarms"
		::= { pdu1 85 }

pdu1-output-power-2-alarms
	OBJECT-TYPE
	SYNTAX  INTEGER
	ACCESS  read-only
	STATUS  mandatory
	DESCRIPTION "Output Power 2 Alarms
                   - Optional Second Output
                   bit 0: KW A High
                   bit 1: KW B High
                   bit 2: KW C High
                   bit 3: KW Total High
                   bit 4: KVA A High
                   bit 5: KVA B High
                   bit 6: KVA C High
                   bit 7: KVA Total High
                   bits 8-15 not used"
		::= { pdu1 86 }

pdu1-output-power-2-alarms-latched
	OBJECT-TYPE
	SYNTAX  INTEGER
	ACCESS  read-write
	STATUS  mandatory
	DESCRIPTION "Output Power 2 Alarms Latched
                    - Same bits as Output Power 2 Alarms
                    - Optional Second Output"
		::= { pdu1 87 }

pdu-building-alarms
	OBJECT-TYPE
	SYNTAX  INTEGER
	ACCESS  read-only
	STATUS  mandatory
	DESCRIPTION "Building Alarms
                   bit 0: Building Alarm 1
                   bit 1: Building Alarm 2
                   bit 2: Building Alarm 3
                   bit 3: Building Alarm 4
                   bit 4: Building Alarm 5 - Optional Advanced Contractor
                   bit 5: Building Alarm 6 - Optional Advanced Contractor
                   bit 6: Building Alarm 7 - Optional Advanced Contractor
                   bit 7: Building Alarm 8 - Optional Advanced Contractor
                   bits 8-15 not used"
		::= { pdu1 88 }

pdu-building-alarms-latched
	OBJECT-TYPE
	SYNTAX  INTEGER
	ACCESS  read-write
	STATUS  mandatory
	DESCRIPTION "Building Alarms Latched
                    - Same bits as Building Alarms"
		::= { pdu1 89 }

pdu-digital-alarms
	OBJECT-TYPE
	SYNTAX  INTEGER
	ACCESS  read-only
	STATUS  mandatory
	DESCRIPTION "Digital Alarms
                   bit 0: Digital Alarm 1
                   bit 1: Digital Alarm 2
                   bit 2: Digital Alarm 3
                   bit 3: Digital Alarm 4
                   bits 4-15 not used"
		::= { pdu1 90 }

pdu-digital-alarms-latched
	OBJECT-TYPE
	SYNTAX  INTEGER
	ACCESS  read-write
	STATUS  mandatory
	DESCRIPTION "Digital Alarms Latched
                    - Same bits as Digital Alarms"
		::= { pdu1 91 }

pdu-output-percent-load-1-a
	OBJECT-TYPE
	SYNTAX  INTEGER
	ACCESS  read-only
	STATUS  mandatory
	DESCRIPTION "Precent Load Output 1 Phase A"
		::= { pdu1 92 }

pdu-output-percent-load-1-b
	OBJECT-TYPE
	SYNTAX  INTEGER
	ACCESS  read-only
	STATUS  mandatory
	DESCRIPTION "Precent Load Output 1 Phase B"
		::= { pdu1 93 }

pdu-output-percent-load-1-c
	OBJECT-TYPE
	SYNTAX  INTEGER
	ACCESS  read-only
	STATUS  mandatory
	DESCRIPTION "Precent Load Output 1 Phase C"
		::= { pdu1 94 }

pdu-output-percent-load-2-a
	OBJECT-TYPE
	SYNTAX  INTEGER
	ACCESS  read-only
	STATUS  mandatory
	DESCRIPTION "Precent Load Output 2 Phase A - Optional Dual Output Only"
		::= { pdu1 95 }

pdu-output-percent-load-2-b
	OBJECT-TYPE
	SYNTAX  INTEGER
	ACCESS  read-only
	STATUS  mandatory
	DESCRIPTION "Precent Load Output 2 Phase B - Optional Dual Output Only"
		::= { pdu1 96 }

pdu-output-percent-load-2-c
	OBJECT-TYPE
	SYNTAX  INTEGER
	ACCESS  read-only
	STATUS  mandatory
	DESCRIPTION "Precent Load Output 2 Phase C - Optional Dual Output Only"
		::= { pdu1 97 }

pdu-reserver-1
	OBJECT-TYPE
	SYNTAX  INTEGER
	ACCESS  read-only
	STATUS  mandatory
	DESCRIPTION "Reserved 1"
		::= { pdu1 98 }

pdu-reserver-2
	OBJECT-TYPE
	SYNTAX  INTEGER
	ACCESS  read-only
	STATUS  mandatory
	DESCRIPTION "Reserved 2"
		::= { pdu1 99 }

pdu1-enable
	OBJECT-TYPE
	SYNTAX  INTEGER
	ACCESS  read-write
	STATUS  mandatory
	DESCRIPTION "Enable - Enables write to calibration and limits"
		::= { pdu1 100 }

pdu1-setup
	OBJECT-TYPE
	SYNTAX  INTEGER
	ACCESS  read-write
	STATUS  mandatory
	DESCRIPTION "setup
                   bit 0: Second output enabled
                   bit 1: Second Input enabled
                   bit 2: Advanced Contractor enabled
                   bits 3-15 not used"
		::= { pdu1 101 }

pdu1-nominal-input-voltage-1
	OBJECT-TYPE
	SYNTAX  INTEGER
	ACCESS  read-write
	STATUS  mandatory
	DESCRIPTION "Nominal Input Voltage 1"
		::= { pdu1 102 }

pdu1-nominal-output-voltage-1
	OBJECT-TYPE
	SYNTAX  INTEGER
	ACCESS  read-write
	STATUS  mandatory
	DESCRIPTION "Nominal Output Voltage 1"
		::= { pdu1 103 }

pdu1-nominal-input-output-voltage-2
	OBJECT-TYPE
	SYNTAX  INTEGER
	ACCESS  read-write
	STATUS  mandatory
	DESCRIPTION "Nominal Input/Output Voltage 2"
		::= { pdu1 104 }

pdu1-rated-output-current-1
	OBJECT-TYPE
	SYNTAX  INTEGER
	ACCESS  read-write
	STATUS  mandatory
	DESCRIPTION "Rated Output Current 1"
		::= { pdu1 105 }

pdu1-rated-output-current-2
	OBJECT-TYPE
	SYNTAX  INTEGER
	ACCESS  read-write
	STATUS  mandatory
	DESCRIPTION "Rated Output Current 2"
		::= { pdu1 106 }

pdu1-rated-neutral-current
	OBJECT-TYPE
	SYNTAX  INTEGER
	ACCESS  read-write
	STATUS  mandatory
	DESCRIPTION "Nominal Input Voltage 1"
		::= { pdu1 107 }

pdu1-ct-ratio-output-1
	OBJECT-TYPE
	SYNTAX  INTEGER
	ACCESS  read-write
	STATUS  mandatory
	DESCRIPTION "CT Ratio Output 1"
		::= { pdu1 108 }

pdu1-ct-ratio-output-2
	OBJECT-TYPE
	SYNTAX  INTEGER
	ACCESS  read-write
	STATUS  mandatory
	DESCRIPTION "CT Ratio Output 2"
		::= { pdu1 109 }

pdu1-ct-ratio-neutral
	OBJECT-TYPE
	SYNTAX  INTEGER
	ACCESS  read-write
	STATUS  mandatory
	DESCRIPTION "CT ratio Neutral"
		::= { pdu1 110 }

pdu1-kva
	OBJECT-TYPE
	SYNTAX  INTEGER
	ACCESS  read-write
	STATUS  mandatory
	DESCRIPTION "KVA"
		::= { pdu1 111 }

pdu1-input-voltage-1-ll-high-limit
	OBJECT-TYPE
	SYNTAX  INTEGER
	ACCESS  read-write
	STATUS  mandatory
	DESCRIPTION "Input Voltage 1 LL High Limit"
		::= { pdu1 112 }

pdu1-input-voltage-1-ll-low-limit
	OBJECT-TYPE
	SYNTAX  INTEGER
	ACCESS  read-write
	STATUS  mandatory
	DESCRIPTION "Input Voltage 1 LL Low Limit"
		::= { pdu1 113 }

pdu1-frequency-v1-high-limit
	OBJECT-TYPE
	SYNTAX  INTEGER
	ACCESS  read-write
	STATUS  mandatory
	DESCRIPTION "Frequency Voltage 1 High Limit"
		::= { pdu1 114 }

pdu1-frequency-v1-low-limit
	OBJECT-TYPE
	SYNTAX  INTEGER
	ACCESS  read-write
	STATUS  mandatory
	DESCRIPTION "Frequency Voltage 1 Low Limit"
		::= { pdu1 115 }

pdu1-input-voltage-2-ll-high-limit
	OBJECT-TYPE
	SYNTAX  INTEGER
	ACCESS  read-write
	STATUS  mandatory
	DESCRIPTION "Input Voltage 2 LL High Limit - Optional Second Input"
		::= { pdu1 116 }

pdu1-input-voltage-2-ll-low-limit
	OBJECT-TYPE
	SYNTAX  INTEGER
	ACCESS  read-write
	STATUS  mandatory
	DESCRIPTION "Input Voltage 2 LL Low Limit - Optional Second Input"
		::= { pdu1 117 }

pdu1-frequency-v2-high-limit
	OBJECT-TYPE
	SYNTAX  INTEGER
	ACCESS  read-write
	STATUS  mandatory
	DESCRIPTION "Frequency Voltage 2 High Limit - Optional Second Input"
		::= { pdu1 118 }

pdu1-frequency-v2-low-limit
	OBJECT-TYPE
	SYNTAX  INTEGER
	ACCESS  read-write
	STATUS  mandatory
	DESCRIPTION "Frequency Voltage 2 Low Limit - Optional Second Input"
		::= { pdu1 119 }

pdu1-phase-input-1-and-input-2
	OBJECT-TYPE
	SYNTAX  INTEGER
	ACCESS  read-write
	STATUS  mandatory
	DESCRIPTION "Phase Input 1 and Input 2 - Optional Second Input"
		::= { pdu1 120 }

pdu1-output-voltage-1-ll-high-limit
	OBJECT-TYPE
	SYNTAX  INTEGER
	ACCESS  read-write
	STATUS  mandatory
	DESCRIPTION "Output Voltage 1 LL High Limit"
		::= { pdu1 121 }

pdu1-output-voltage-1-ll-low-limit
	OBJECT-TYPE
	SYNTAX  INTEGER
	ACCESS  read-write
	STATUS  mandatory
	DESCRIPTION "Output Voltage 1 LL Low Limit"
		::= { pdu1 122 }

pdu1-output-voltage-1-ln-high-limit
	OBJECT-TYPE
	SYNTAX  INTEGER
	ACCESS  read-write
	STATUS  mandatory
	DESCRIPTION "Output Voltage 1 LN High Limit"
		::= { pdu1 123 }

pdu1-output-voltage-1-ln-low-limit
	OBJECT-TYPE
	SYNTAX  INTEGER
	ACCESS  read-write
	STATUS  mandatory
	DESCRIPTION "Output Voltage 1 LN Low Limit"
		::= { pdu1 124 }

pdu1-output-current-1-high-limit
	OBJECT-TYPE
	SYNTAX  INTEGER
	ACCESS  read-write
	STATUS  mandatory
	DESCRIPTION "Output Current 1 High Limit"
		::= { pdu1 125 }

pdu1-output-current-1-low-limit
	OBJECT-TYPE
	SYNTAX  INTEGER
	ACCESS  read-write
	STATUS  mandatory
	DESCRIPTION "Output Current 1 Low Limit"
		::= { pdu1 126 }

pdu1-output-kw-1-high-limit
	OBJECT-TYPE
	SYNTAX  INTEGER
	ACCESS  read-write
	STATUS  mandatory
	DESCRIPTION "Output KW 1 High Limit"
		::= { pdu1 127 }

pdu1-output-kva-1-high-limit
	OBJECT-TYPE
	SYNTAX  INTEGER
	ACCESS  read-write
	STATUS  mandatory
	DESCRIPTION "Output KVA 1 High Limit"
		::= { pdu1 128 }

pdu1-output-neutral-high-limit
	OBJECT-TYPE
	SYNTAX  INTEGER
	ACCESS  read-write
	STATUS  mandatory
	DESCRIPTION "Output Neutral High Limit"
		::= { pdu1 129 }

pdu1-output-neutral-low-limit
	OBJECT-TYPE
	SYNTAX  INTEGER
	ACCESS  read-write
	STATUS  mandatory
	DESCRIPTION "Output Neutral Low Limit"
		::= { pdu1 130 }

pdu1-output-ground-high-limit
	OBJECT-TYPE
	SYNTAX  INTEGER
	ACCESS  read-write
	STATUS  mandatory
	DESCRIPTION "Output Ground High Limit"
		::= { pdu1 131 }

pdu1-output-ground-low-limit
	OBJECT-TYPE
	SYNTAX  INTEGER
	ACCESS  read-write
	STATUS  mandatory
	DESCRIPTION "Output Ground Low Limit"
		::= { pdu1 132 }

pdu1-output-voltage-2-ll-high-limit
	OBJECT-TYPE
	SYNTAX  INTEGER
	ACCESS  read-write
	STATUS  mandatory
	DESCRIPTION "Output Voltage 2 LL High Limit - Optional Second Output"
		::= { pdu1 133 }

pdu1-output-voltage-2-ll-low-limit
	OBJECT-TYPE
	SYNTAX  INTEGER
	ACCESS  read-write
	STATUS  mandatory
	DESCRIPTION "Output Voltage 2 LL Low Limit - Optional Second Output"
		::= { pdu1 134 }

pdu1-output-voltage-2-ln-high-limit
	OBJECT-TYPE
	SYNTAX  INTEGER
	ACCESS  read-write
	STATUS  mandatory
	DESCRIPTION "Output Voltage 2 LN High Limit - Optional Second Output"
		::= { pdu1 135 }

pdu1-output-voltage-2-ln-low-limit
	OBJECT-TYPE
	SYNTAX  INTEGER
	ACCESS  read-write
	STATUS  mandatory
	DESCRIPTION "Output Voltage 2 LN Low Limit - Optional Second Output"
		::= { pdu1 136 }

pdu1-output-current-2-high-limit
	OBJECT-TYPE
	SYNTAX  INTEGER
	ACCESS  read-write
	STATUS  mandatory
	DESCRIPTION "Output Current 2 High Limit"
		::= { pdu1 137 }

pdu1-output-current-2-low-limit
	OBJECT-TYPE
	SYNTAX  INTEGER
	ACCESS  read-write
	STATUS  mandatory
	DESCRIPTION "Output Current 2 Low Limit"
		::= { pdu1 138 }

pdu1-output-kw-2-high-limit
	OBJECT-TYPE
	SYNTAX  INTEGER
	ACCESS  read-write
	STATUS  mandatory
	DESCRIPTION "Output KW 2 High Limit"
		::= { pdu1 139 }

pdu1-output-kva-2-high-limit
	OBJECT-TYPE
	SYNTAX  INTEGER
	ACCESS  read-write
	STATUS  mandatory
	DESCRIPTION "Output KVA 2 High Limit"
		::= { pdu1 140 }

pdu1-building-alarm-enable
	OBJECT-TYPE
	SYNTAX  INTEGER
	ACCESS  read-write
	STATUS  mandatory
	DESCRIPTION "Building Alarm Enable - Enable is High
			 bit 0: Building Alarm 1
			 bit 1: Building Alarm 2
			 bit 2: Building Alarm 3
			 bit 3: Building Alarm 4
			 bit 4: Building Alarm 5 - Optional Advanced Contractor
			 bit 5: Building Alarm 6 - Optional Advanced Contractor
			 bit 6: Building Alarm 7 - Optional Advanced Contractor
			 bit 7: Building Alarm 8 - Optional Advanced Contractor
			 bits 8-15: not used"
		::= { pdu1 141 }

pdu1-building-alarm-nominal
	OBJECT-TYPE
	SYNTAX  INTEGER
	ACCESS  read-write
	STATUS  mandatory
	DESCRIPTION "Building Alarm Nominal - Nominal Closed is High
			 Bits same as Building Alarm Enable"
		::= { pdu1 142 }

pdu1-digital-alarm-enable
	OBJECT-TYPE
	SYNTAX  INTEGER
	ACCESS  read-write
	STATUS  mandatory
	DESCRIPTION "Digital Alarm Enable - Enable is High
			 bit 0: Digital Alarm 1
			 bit 1: Digital Alarm 2
			 bit 2: Digital Alarm 3
			 bit 3: Digital Alarm 4
                   bits 4-15: not used"
		::= { pdu1 143 }

pdu1-digital-alarm-nominal
	OBJECT-TYPE
	SYNTAX  INTEGER
	ACCESS  read-write
	STATUS  mandatory
	DESCRIPTION "Digital Alarm Nominal - Nominal Closed is High
			 Bits same as Digital Alarm Enable"
		::= { pdu1 144 }

pdu1-building-alarm-1-name-1-2
	OBJECT-TYPE
	SYNTAX  INTEGER
	ACCESS  read-write
	STATUS  mandatory
	DESCRIPTION "Building Alarm 1 Name 1-2 - 2 characters in one integer"
		::= { pdu1 145 }

pdu1-building-alarm-1-name-3-4
	OBJECT-TYPE
	SYNTAX  INTEGER
	ACCESS  read-write
	STATUS  mandatory
	DESCRIPTION "Building Alarm 1 Name 3-4 - 2 characters in one integer"
		::= { pdu1 146 }

pdu1-building-alarm-1-name-5-6
	OBJECT-TYPE
	SYNTAX  INTEGER
	ACCESS  read-write
	STATUS  mandatory
	DESCRIPTION "Building Alarm 1 Name 5-6 - 2 characters in one integer"
		::= { pdu1 147 }

pdu1-building-alarm-1-name-7-8
	OBJECT-TYPE
	SYNTAX  INTEGER
	ACCESS  read-write
	STATUS  mandatory
	DESCRIPTION "Building Alarm 1 Name 7-8 - 2 characters in one integer"
		::= { pdu1 148 }

pdu1-building-alarm-2-name-1-2
	OBJECT-TYPE
	SYNTAX  INTEGER
	ACCESS  read-write
	STATUS  mandatory
	DESCRIPTION "Building Alarm 2 Name 1-2 - 2 characters in one integer"
		::= { pdu1 149 }

pdu1-building-alarm-2-name-3-4
	OBJECT-TYPE
	SYNTAX  INTEGER
	ACCESS  read-write
	STATUS  mandatory
	DESCRIPTION "Building Alarm 2 Name 3-4 - 2 characters in one integer"
		::= { pdu1 150 }

pdu1-building-alarm-2-name-5-6
	OBJECT-TYPE
	SYNTAX  INTEGER
	ACCESS  read-write
	STATUS  mandatory
	DESCRIPTION "Building Alarm 2 Name 5-6 - 2 characters in one integer"
		::= { pdu1 151 }

pdu1-building-alarm-2-name-7-8
	OBJECT-TYPE
	SYNTAX  INTEGER
	ACCESS  read-write
	STATUS  mandatory
	DESCRIPTION "Building Alarm 2 Name 7-8 - 2 characters in one integer"
		::= { pdu1 152 }

pdu1-building-alarm-3-name-1-2
	OBJECT-TYPE
	SYNTAX  INTEGER
	ACCESS  read-write
	STATUS  mandatory
	DESCRIPTION "Building Alarm 3 Name 1-2 - 2 characters in one integer"
		::= { pdu1 153 }

pdu1-building-alarm-3-name-3-4
	OBJECT-TYPE
	SYNTAX  INTEGER
	ACCESS  read-write
	STATUS  mandatory
	DESCRIPTION "Building Alarm 3 Name 3-4 - 2 characters in one integer"
		::= { pdu1 154 }

pdu1-building-alarm-3-name-5-6
	OBJECT-TYPE
	SYNTAX  INTEGER
	ACCESS  read-write
	STATUS  mandatory
	DESCRIPTION "Building Alarm 3 Name 5-6 - 2 characters in one integer"
		::= { pdu1 155 }

pdu1-building-alarm-3-name-7-8
	OBJECT-TYPE
	SYNTAX  INTEGER
	ACCESS  read-write
	STATUS  mandatory
	DESCRIPTION "Building Alarm 3 Name 7-8 - 2 characters in one integer"
		::= { pdu1 156 }

pdu1-building-alarm-4-name-1-2
	OBJECT-TYPE
	SYNTAX  INTEGER
	ACCESS  read-write
	STATUS  mandatory
	DESCRIPTION "Building Alarm 4 Name 1-2 - 2 characters in one integer"
		::= { pdu1 157 }

pdu1-building-alarm-4-name-3-4
	OBJECT-TYPE
	SYNTAX  INTEGER
	ACCESS  read-write
	STATUS  mandatory
	DESCRIPTION "Building Alarm 4 Name 3-4 - 2 characters in one integer"
		::= { pdu1 158 }

pdu1-building-alarm-4-name-5-6
	OBJECT-TYPE
	SYNTAX  INTEGER
	ACCESS  read-write
	STATUS  mandatory
	DESCRIPTION "Building Alarm 4 Name 5-6 - 2 characters in one integer"
		::= { pdu1 159 }

pdu1-building-alarm-4-name-7-8
	OBJECT-TYPE
	SYNTAX  INTEGER
	ACCESS  read-write
	STATUS  mandatory
	DESCRIPTION "Building Alarm 4 Name 7-8 - 2 characters in one integer"
		::= { pdu1 160 }

pdu1-building-alarm-5-name-1-2
	OBJECT-TYPE
	SYNTAX  INTEGER
	ACCESS  read-write
	STATUS  mandatory
	DESCRIPTION "Building Alarm 5 Name 1-2 - 2 characters in one integer
                   - Optional Advanced Contractor"
		::= { pdu1 161 }

pdu1-building-alarm-5-name-3-4
	OBJECT-TYPE
	SYNTAX  INTEGER
	ACCESS  read-write
	STATUS  mandatory
	DESCRIPTION "Building Alarm 5 Name 3-4 - 2 characters in one integer
                   - Optional Advanced Contractor"
		::= { pdu1 162 }

pdu1-building-alarm-5-name-5-6
	OBJECT-TYPE
	SYNTAX  INTEGER
	ACCESS  read-write
	STATUS  mandatory
	DESCRIPTION "Building Alarm 5 Name 5-6 - 2 characters in one integer
                   - Optional Advanced Contractor"
		::= { pdu1 163 }

pdu1-building-alarm-5-name-7-8
	OBJECT-TYPE
	SYNTAX  INTEGER
	ACCESS  read-write
	STATUS  mandatory
	DESCRIPTION "Building Alarm 5 Name 7-8 - 2 characters in one integer
                   - Optional Advanced Contractor"
		::= { pdu1 164 }

pdu1-building-alarm-6-name-1-2
	OBJECT-TYPE
	SYNTAX  INTEGER
	ACCESS  read-write
	STATUS  mandatory
	DESCRIPTION "Building Alarm 5 Name 1-2 - 6 characters in one integer
                   - Optional Advanced Contractor"
		::= { pdu1 165 }

pdu1-building-alarm-6-name-3-4
	OBJECT-TYPE
	SYNTAX  INTEGER
	ACCESS  read-write
	STATUS  mandatory
	DESCRIPTION "Building Alarm 6 Name 3-4 - 2 characters in one integer
                   - Optional Advanced Contractor"
		::= { pdu1 166 }

pdu1-building-alarm-6-name-5-6
	OBJECT-TYPE
	SYNTAX  INTEGER
	ACCESS  read-write
	STATUS  mandatory
	DESCRIPTION "Building Alarm 6 Name 5-6 - 2 characters in one integer
                   - Optional Advanced Contractor"
		::= { pdu1 167 }

pdu1-building-alarm-6-name-7-8
	OBJECT-TYPE
	SYNTAX  INTEGER
	ACCESS  read-write
	STATUS  mandatory
	DESCRIPTION "Building Alarm 6 Name 7-8 - 2 characters in one integer
                   - Optional Advanced Contractor"
		::= { pdu1 168 }

pdu1-building-alarm-7-name-1-2
	OBJECT-TYPE
	SYNTAX  INTEGER
	ACCESS  read-write
	STATUS  mandatory
	DESCRIPTION "Building Alarm 7 Name 1-2 - 2 characters in one integer
                   - Optional Advanced Contractor"
		::= { pdu1 169 }

pdu1-building-alarm-7-name-3-4
	OBJECT-TYPE
	SYNTAX  INTEGER
	ACCESS  read-write
	STATUS  mandatory
	DESCRIPTION "Building Alarm 7 Name 3-4 - 2 characters in one integer
                   - Optional Advanced Contractor"
		::= { pdu1 170 }

pdu1-building-alarm-7-name-5-6
	OBJECT-TYPE
	SYNTAX  INTEGER
	ACCESS  read-write
	STATUS  mandatory
	DESCRIPTION "Building Alarm 7 Name 5-6 - 2 characters in one integer
                   - Optional Advanced Contractor"
		::= { pdu1 171 }

pdu1-building-alarm-7-name-7-8
	OBJECT-TYPE
	SYNTAX  INTEGER
	ACCESS  read-write
	STATUS  mandatory
	DESCRIPTION "Building Alarm 7 Name 7-8 - 2 characters in one integer
                   - Optional Advanced Contractor"
		::= { pdu1 172 }

pdu1-building-alarm-8-name-1-2
	OBJECT-TYPE
	SYNTAX  INTEGER
	ACCESS  read-write
	STATUS  mandatory
	DESCRIPTION "Building Alarm 8 Name 1-2 - 2 characters in one integer
                   - Optional Advanced Contractor"
		::= { pdu1 173 }

pdu1-building-alarm-8-name-3-4
	OBJECT-TYPE
	SYNTAX  INTEGER
	ACCESS  read-write
	STATUS  mandatory
	DESCRIPTION "Building Alarm 8 Name 3-4 - 2 characters in one integer
                   - Optional Advanced Contractor"
		::= { pdu1 174 }

pdu1-building-alarm-8-name-5-6
	OBJECT-TYPE
	SYNTAX  INTEGER
	ACCESS  read-write
	STATUS  mandatory
	DESCRIPTION "Building Alarm 8 Name 5-6 - 2 characters in one integer
                   - Optional Advanced Contractor"
		::= { pdu1 175 }

pdu1-building-alarm-8-name-7-8
	OBJECT-TYPE
	SYNTAX  INTEGER
	ACCESS  read-write
	STATUS  mandatory
	DESCRIPTION "Building Alarm 8 Name 7-8 - 2 characters in one integer
                   - Optional Advanced Contractor"
		::= { pdu1 176 }

pdu1-digital-alarm-1-name-1-2
	OBJECT-TYPE
	SYNTAX  INTEGER
	ACCESS  read-write
	STATUS  mandatory
	DESCRIPTION "Digital Alarm 1 Name 1-2 - 2 characters in one integer"
		::= { pdu1 177 }

pdu1-digital-alarm-1-name-3-4
	OBJECT-TYPE
	SYNTAX  INTEGER
	ACCESS  read-write
	STATUS  mandatory
	DESCRIPTION "Digital Alarm 1 Name 3-4 - 2 characters in one integer"
		::= { pdu1 178 }

pdu1-digital-alarm-1-name-5-6
	OBJECT-TYPE
	SYNTAX  INTEGER
	ACCESS  read-write
	STATUS  mandatory
	DESCRIPTION "Digital Alarm 1 Name 5-6 - 2 characters in one integer"
		::= { pdu1 179 }

pdu1-digital-alarm-1-name-7-8
	OBJECT-TYPE
	SYNTAX  INTEGER
	ACCESS  read-write
	STATUS  mandatory
	DESCRIPTION "Digital Alarm 1 Name 7-8 - 2 characters in one integer"
		::= { pdu1 180 }

pdu1-digital-alarm-2-name-1-2
	OBJECT-TYPE
	SYNTAX  INTEGER
	ACCESS  read-write
	STATUS  mandatory
	DESCRIPTION "Digital Alarm 2 Name 1-2 - 2 characters in one integer"
		::= { pdu1 181 }

pdu1-digital-alarm-2-name-3-4
	OBJECT-TYPE
	SYNTAX  INTEGER
	ACCESS  read-write
	STATUS  mandatory
	DESCRIPTION "Digital Alarm 2 Name 3-4 - 2 characters in one integer"
		::= { pdu1 182 }

pdu1-digital-alarm-2-name-5-6
	OBJECT-TYPE
	SYNTAX  INTEGER
	ACCESS  read-write
	STATUS  mandatory
	DESCRIPTION "Digital Alarm 2 Name 5-6 - 2 characters in one integer"
		::= { pdu1 183 }

pdu1-digital-alarm-2-name-7-8
	OBJECT-TYPE
	SYNTAX  INTEGER
	ACCESS  read-write
	STATUS  mandatory
	DESCRIPTION "Digital Alarm 2 Name 7-8 - 2 characters in one integer"
		::= { pdu1 184 }

pdu1-digital-alarm-3-name-1-2
	OBJECT-TYPE
	SYNTAX  INTEGER
	ACCESS  read-write
	STATUS  mandatory
	DESCRIPTION "Digital Alarm 3 Name 1-2 - 2 characters in one integer"
		::= { pdu1 185 }

pdu1-digital-alarm-3-name-3-4
	OBJECT-TYPE
	SYNTAX  INTEGER
	ACCESS  read-write
	STATUS  mandatory
	DESCRIPTION "Digital Alarm 3 Name 3-4 - 2 characters in one integer"
		::= { pdu1 186 }

pdu1-digital-alarm-3-name-5-6
	OBJECT-TYPE
	SYNTAX  INTEGER
	ACCESS  read-write
	STATUS  mandatory
	DESCRIPTION "Digital Alarm 3 Name 5-6 - 2 characters in one integer"
		::= { pdu1 187 }

pdu1-digital-alarm-3-name-7-8
	OBJECT-TYPE
	SYNTAX  INTEGER
	ACCESS  read-write
	STATUS  mandatory
	DESCRIPTION "Digital Alarm 3 Name 7-8 - 2 characters in one integer"
		::= { pdu1 188 }

pdu1-digital-alarm-4-name-1-2
	OBJECT-TYPE
	SYNTAX  INTEGER
	ACCESS  read-write
	STATUS  mandatory
	DESCRIPTION "Digital Alarm 4 Name 1-2 - 2 characters in one integer"
		::= { pdu1 189 }

pdu1-digital-alarm-4-name-3-4
	OBJECT-TYPE
	SYNTAX  INTEGER
	ACCESS  read-write
	STATUS  mandatory
	DESCRIPTION "Digital Alarm 4 Name 3-4 - 2 characters in one integer"
		::= { pdu1 190 }

pdu1-digital-alarm-4-name-5-6
	OBJECT-TYPE
	SYNTAX  INTEGER
	ACCESS  read-write
	STATUS  mandatory
	DESCRIPTION "Digital Alarm 4 Name 5-6 - 2 characters in one integer"
		::= { pdu1 191 }

pdu1-digital-alarm-4-name-7-8
	OBJECT-TYPE
	SYNTAX  INTEGER
	ACCESS  read-write
	STATUS  mandatory
	DESCRIPTION "Digital Alarm 4 Name 7-8 - 2 characters in one integer"
		::= { pdu1 192 }

pdu1-relay-1-alarm-point
	OBJECT-TYPE
	SYNTAX  INTEGER
	ACCESS  read-write
	STATUS  mandatory
	DESCRIPTION "Relay 1 Alarm Point"
		::= { pdu1 193 }

pdu1-relay-2-alarm-point
	OBJECT-TYPE
	SYNTAX  INTEGER
	ACCESS  read-write
	STATUS  mandatory
	DESCRIPTION "Relay 2 Alarm Point"
		::= { pdu1 194 }

pdu1-relay-3-alarm-point
	OBJECT-TYPE
	SYNTAX  INTEGER
	ACCESS  read-write
	STATUS  mandatory
	DESCRIPTION "Relay 3 Alarm Point"
		::= { pdu1 195 }

pdu1-relay-4-alarm-point
	OBJECT-TYPE
	SYNTAX  INTEGER
	ACCESS  read-write
	STATUS  mandatory
	DESCRIPTION "Relay 4 Alarm Point"
		::= { pdu1 196 }

pdu1-relay-5-alarm-point
	OBJECT-TYPE
	SYNTAX  INTEGER
	ACCESS  read-write
	STATUS  mandatory
	DESCRIPTION "Relay 5 Alarm Point - Optional Advanced Contractor"
		::= { pdu1 197 }

pdu1-relay-6-alarm-point
	OBJECT-TYPE
	SYNTAX  INTEGER
	ACCESS  read-write
	STATUS  mandatory
	DESCRIPTION "Relay 6 Alarm Point - Optional Advanced Contractor"
		::= { pdu1 198 }

pdu1-relay-7-alarm-point
	OBJECT-TYPE
	SYNTAX  INTEGER
	ACCESS  read-write
	STATUS  mandatory
	DESCRIPTION "Relay 7 Alarm Point - Optional Advanced Contractor"
		::= { pdu1 199 }

pdu1-relay-8-alarm-point
	OBJECT-TYPE
	SYNTAX  INTEGER
	ACCESS  read-write
	STATUS  mandatory
	DESCRIPTION "Relay 8 Alarm Point - Optional Advanced Contractor"
		::= { pdu1 200 }

pdu1-relay-1-alarm-bits
	OBJECT-TYPE
	SYNTAX  INTEGER
	ACCESS  read-write
	STATUS  mandatory
	DESCRIPTION "Relay 1 Alarm Bits - Which Bits of the Alarm Points will be Alarmed"
		::= { pdu1 201 }

pdu1-relay-2-alarm-bits
	OBJECT-TYPE
	SYNTAX  INTEGER
	ACCESS  read-write
	STATUS  mandatory
	DESCRIPTION "Relay 2 Alarm Bits"
		::= { pdu1 202 }

pdu1-relay-3-alarm-bits
	OBJECT-TYPE
	SYNTAX  INTEGER
	ACCESS  read-write
	STATUS  mandatory
	DESCRIPTION "Relay 3 Alarm Bits"
		::= { pdu1 203 }

pdu1-relay-4-alarm-bits
	OBJECT-TYPE
	SYNTAX  INTEGER
	ACCESS  read-write
	STATUS  mandatory
	DESCRIPTION "Relay 4 Alarm Bits"
		::= { pdu1 204 }

pdu1-relay-5-alarm-bits
	OBJECT-TYPE
	SYNTAX  INTEGER
	ACCESS  read-write
	STATUS  mandatory
	DESCRIPTION "Relay 5 Alarm Bits - Optional Advanced Contractor"
		::= { pdu1 205 }

pdu1-relay-6-alarm-bits
	OBJECT-TYPE
	SYNTAX  INTEGER
	ACCESS  read-write
	STATUS  mandatory
	DESCRIPTION "Relay 6 Alarm Bits - Optional Advanced Contractor"
		::= { pdu1 206 }

pdu1-relay-7-alarm-bits
	OBJECT-TYPE
	SYNTAX  INTEGER
	ACCESS  read-write
	STATUS  mandatory
	DESCRIPTION "Relay 7 Alarm Bits - Optional Advanced Contractor"
		::= { pdu1 207 }

pdu1-relay-8-alarm-bits
	OBJECT-TYPE
	SYNTAX  INTEGER
	ACCESS  read-write
	STATUS  mandatory
	DESCRIPTION "Relay 8 Alarm Bits - Optional Advanced Contractor"
		::= { pdu1 208 }

pdu1-input-current-a
	OBJECT-TYPE
	SYNTAX  INTEGER
	ACCESS  read-only
	STATUS  mandatory
	DESCRIPTION "Input Current A (Input Current values are optional)"
		::= { pdu1 209 }

pdu1-input-current-b
	OBJECT-TYPE
	SYNTAX  INTEGER
	ACCESS  read-only
	STATUS  mandatory
	DESCRIPTION "Input Current B"
		::= { pdu1 210 }

pdu1-input-current-c
	OBJECT-TYPE
	SYNTAX  INTEGER
	ACCESS  read-only
	STATUS  mandatory
	DESCRIPTION "Input Current C"
		::= { pdu1 211 }

pdu1-input-currnet-a-thd
	OBJECT-TYPE
	SYNTAX  INTEGER
	ACCESS  read-only
	STATUS  mandatory
	DESCRIPTION "Input Current A THD"
		::= { pdu1 212 }

pdu1-input-current-b-thd
	OBJECT-TYPE
	SYNTAX  INTEGER
	ACCESS  read-only
	STATUS  mandatory
	DESCRIPTION "Input Current B THD"
		::= { pdu1 213 }

pdu1-input-current-c-thd
	OBJECT-TYPE
	SYNTAX  INTEGER
	ACCESS  read-only
	STATUS  mandatory
	DESCRIPTION "Input Current C THD"
		::= { pdu1 214 }

pdu1-rated-input-current
	OBJECT-TYPE
	SYNTAX  INTEGER
	ACCESS  read-write
	STATUS  mandatory
	DESCRIPTION "Rated Input Current"
		::= { pdu1 215 }

pdu1-ct-ratio-input
	OBJECT-TYPE
	SYNTAX  INTEGER
	ACCESS  read-write
	STATUS  mandatory
	DESCRIPTION "CT Ratio Input"
		::= { pdu1 216 }

pdu1-input-current-high-limit
	OBJECT-TYPE
	SYNTAX  INTEGER
	ACCESS  read-write
	STATUS  mandatory
	DESCRIPTION "Output Current 1 High Limit"
		::= { pdu1 217 }

pdu1-input-current-low-limit
	OBJECT-TYPE
	SYNTAX  INTEGER
	ACCESS  read-write
	STATUS  mandatory
	DESCRIPTION "Output Current 1 Low Limit"
		::= { pdu1 218 }

pdu1-input-current-alarms
	OBJECT-TYPE
	SYNTAX  INTEGER
	ACCESS  read-only
	STATUS  mandatory
	DESCRIPTION "Input Current Alarms
                   bit 0: Current A High
                   bit 1: Current A Low
                   bit 2: Current B High
                   bit 3: Current B Low
                   bit 4: Current C High
                   bit 5: Current C Low
                   bits 6-15 not used"
		::= { pdu1 219 }

pdu1-input-current-alarms-latched
	OBJECT-TYPE
	SYNTAX  INTEGER
	ACCESS  read-write
	STATUS  mandatory
	DESCRIPTION "Input Current Alarms Latched
                    - Same bits as Input Curret Alarms"
		::= { pdu1 220 }

--------------------------------------------------------------------------------
-- BCMSPLUS register values
--------------------------------------------------------------------------------

bcms1-cb1-current
	OBJECT-TYPE
	SYNTAX  INTEGER
	ACCESS  read-only
	STATUS  mandatory
	DESCRIPTION "CB1 Current
		     Note for all currents 1-42: 100 = 10.0 amps"
		::= { bcmsplus1 1 }
  
bcms1-cb2-current
	OBJECT-TYPE
	SYNTAX  INTEGER
	ACCESS  read-only
	STATUS  mandatory
	DESCRIPTION "CB2 Current"
		::= { bcmsplus1 2 }

bcms1-cb3-current
	OBJECT-TYPE
	SYNTAX  INTEGER
	ACCESS  read-only
	STATUS  mandatory
	DESCRIPTION "CB3 Current"
		::= { bcmsplus1 3 }

bcms1-cb4-current
	OBJECT-TYPE
	SYNTAX  INTEGER
	ACCESS  read-only
	STATUS  mandatory
	DESCRIPTION "CB4 Current"
		::= { bcmsplus1 4 }

bcms1-cb5-current
	OBJECT-TYPE
	SYNTAX  INTEGER
	ACCESS  read-only
	STATUS  mandatory
	DESCRIPTION "CB5 Current"
		::= { bcmsplus1 5 }

bcms1-cb6-current
	OBJECT-TYPE
	SYNTAX  INTEGER
	ACCESS  read-only
	STATUS  mandatory
	DESCRIPTION "CB6 Current"
		::= { bcmsplus1 6 }

bcms1-cb7-current
	OBJECT-TYPE
	SYNTAX  INTEGER
	ACCESS  read-only
	STATUS  mandatory
	DESCRIPTION "CB7 Current"
		::= { bcmsplus1 7 }

bcms1-cb8-current
	OBJECT-TYPE
	SYNTAX  INTEGER
	ACCESS  read-only
	STATUS  mandatory
	DESCRIPTION "CB8 Current"
		::= { bcmsplus1 8 }

bcms1-cb9-current
	OBJECT-TYPE
	SYNTAX  INTEGER
	ACCESS  read-only
	STATUS  mandatory
	DESCRIPTION "CB9 Current"
		::= { bcmsplus1 9 }

bcms1-cb10-current
	OBJECT-TYPE
	SYNTAX  INTEGER
	ACCESS  read-only
	STATUS  mandatory
	DESCRIPTION "CB10 Current"
		::= { bcmsplus1 10 }

bcms1-cb11-current
	OBJECT-TYPE
	SYNTAX  INTEGER
	ACCESS  read-only
	STATUS  mandatory
	DESCRIPTION "CB11 Current"
		::= { bcmsplus1 11 }
  
bcms1-cb12-current
	OBJECT-TYPE
	SYNTAX  INTEGER
	ACCESS  read-only
	STATUS  mandatory
	DESCRIPTION "CB12 Current"
		::= { bcmsplus1 12 }

bcms1-cb13-current
	OBJECT-TYPE
	SYNTAX  INTEGER
	ACCESS  read-only
	STATUS  mandatory
	DESCRIPTION "CB13 Current"
		::= { bcmsplus1 13 }

bcms1-cb14-current
	OBJECT-TYPE
	SYNTAX  INTEGER
	ACCESS  read-only
	STATUS  mandatory
	DESCRIPTION "CB14 Current"
		::= { bcmsplus1 14 }

bcms1-cb15-current
	OBJECT-TYPE
	SYNTAX  INTEGER
	ACCESS  read-only
	STATUS  mandatory
	DESCRIPTION "CB15 Current"
		::= { bcmsplus1 15 }

bcms1-cb16-current
	OBJECT-TYPE
	SYNTAX  INTEGER
	ACCESS  read-only
	STATUS  mandatory
	DESCRIPTION "CB16 Current"
		::= { bcmsplus1 16 }

bcms1-cb17-current
	OBJECT-TYPE
	SYNTAX  INTEGER
	ACCESS  read-only
	STATUS  mandatory
	DESCRIPTION "CB17 Current"
		::= { bcmsplus1 17 }

bcms1-cb18-current
	OBJECT-TYPE
	SYNTAX  INTEGER
	ACCESS  read-only
	STATUS  mandatory
	DESCRIPTION "CB18 Current"
		::= { bcmsplus1 18 }

bcms1-cb19-current
	OBJECT-TYPE
	SYNTAX  INTEGER
	ACCESS  read-only
	STATUS  mandatory
	DESCRIPTION "CB19 Current"
		::= { bcmsplus1 19 }

bcms1-cb20-current
	OBJECT-TYPE
	SYNTAX  INTEGER
	ACCESS  read-only
	STATUS  mandatory
	DESCRIPTION "CB20 Current"
		::= { bcmsplus1 20 }

bcms1-cb21-current
	OBJECT-TYPE
	SYNTAX  INTEGER
	ACCESS  read-only
	STATUS  mandatory
	DESCRIPTION "CB21 Current"
		::= { bcmsplus1 21 }
  
bcms1-cb22-current
	OBJECT-TYPE
	SYNTAX  INTEGER
	ACCESS  read-only
	STATUS  mandatory
	DESCRIPTION "CB22 Current"
		::= { bcmsplus1 22 }

bcms1-cb23-current
	OBJECT-TYPE
	SYNTAX  INTEGER
	ACCESS  read-only
	STATUS  mandatory
	DESCRIPTION "CB23 Current"
		::= { bcmsplus1 23 }

bcms1-cb24-current
	OBJECT-TYPE
	SYNTAX  INTEGER
	ACCESS  read-only
	STATUS  mandatory
	DESCRIPTION "CB24 Current"
		::= { bcmsplus1 24 }

bcms1-cb25-current
	OBJECT-TYPE
	SYNTAX  INTEGER
	ACCESS  read-only
	STATUS  mandatory
	DESCRIPTION "CB25 Current"
		::= { bcmsplus1 25 }

bcms1-cb26-current
	OBJECT-TYPE
	SYNTAX  INTEGER
	ACCESS  read-only
	STATUS  mandatory
	DESCRIPTION "CB26 Current"
		::= { bcmsplus1 26 }

bcms1-cb27-current
	OBJECT-TYPE
	SYNTAX  INTEGER
	ACCESS  read-only
	STATUS  mandatory
	DESCRIPTION "CB27 Current"
		::= { bcmsplus1 27 }

bcms1-cb28-current
	OBJECT-TYPE
	SYNTAX  INTEGER
	ACCESS  read-only
	STATUS  mandatory
	DESCRIPTION "CB28 Current"
		::= { bcmsplus1 28 }

bcms1-cb29-current
	OBJECT-TYPE
	SYNTAX  INTEGER
	ACCESS  read-only
	STATUS  mandatory
	DESCRIPTION "CB29 Current"
		::= { bcmsplus1 29 }

bcms1-cb30-current
	OBJECT-TYPE
	SYNTAX  INTEGER
	ACCESS  read-only
	STATUS  mandatory
	DESCRIPTION "CB30 Current"
		::= { bcmsplus1 30 }

bcms1-cb31-current
	OBJECT-TYPE
	SYNTAX  INTEGER
	ACCESS  read-only
	STATUS  mandatory
	DESCRIPTION "CB31 Current"
		::= { bcmsplus1 31 }
  
bcms1-cb32-current
	OBJECT-TYPE
	SYNTAX  INTEGER
	ACCESS  read-only
	STATUS  mandatory
	DESCRIPTION "CB32 Current"
		::= { bcmsplus1 32 }

bcms1-cb33-current
	OBJECT-TYPE
	SYNTAX  INTEGER
	ACCESS  read-only
	STATUS  mandatory
	DESCRIPTION "CB33 Current"
		::= { bcmsplus1 33 }

bcms1-cb34-current
	OBJECT-TYPE
	SYNTAX  INTEGER
	ACCESS  read-only
	STATUS  mandatory
	DESCRIPTION "CB34 Current"
		::= { bcmsplus1 34 }

bcms1-cb35-current
	OBJECT-TYPE
	SYNTAX  INTEGER
	ACCESS  read-only
	STATUS  mandatory
	DESCRIPTION "CB35 Current"
		::= { bcmsplus1 35 }

bcms1-cb36-current
	OBJECT-TYPE
	SYNTAX  INTEGER
	ACCESS  read-only
	STATUS  mandatory
	DESCRIPTION "CB36 Current"
		::= { bcmsplus1 36 }

bcms1-cb37-current
	OBJECT-TYPE
	SYNTAX  INTEGER
	ACCESS  read-only
	STATUS  mandatory
	DESCRIPTION "CB37 Current"
		::= { bcmsplus1 37 }

bcms1-cb38-current
	OBJECT-TYPE
	SYNTAX  INTEGER
	ACCESS  read-only
	STATUS  mandatory
	DESCRIPTION "CB38 Current"
		::= { bcmsplus1 38 }

bcms1-cb39-current
	OBJECT-TYPE
	SYNTAX  INTEGER
	ACCESS  read-only
	STATUS  mandatory
	DESCRIPTION "CB39 Current"
		::= { bcmsplus1 39 }

bcms1-cb40-current
	OBJECT-TYPE
	SYNTAX  INTEGER
	ACCESS  read-only
	STATUS  mandatory
	DESCRIPTION "CB40 Current"
		::= { bcmsplus1 40 }

bcms1-cb41-current
	OBJECT-TYPE
	SYNTAX  INTEGER
	ACCESS  read-only
	STATUS  mandatory
	DESCRIPTION "CB41 Current"
		::= { bcmsplus1 41 }
  
bcms1-cb42-current
	OBJECT-TYPE
	SYNTAX  INTEGER
	ACCESS  read-only
	STATUS  mandatory
	DESCRIPTION "CB42 Current"
		::= { bcmsplus1 42 }

bcms1-cb1-min
	OBJECT-TYPE
	SYNTAX  INTEGER
	ACCESS  read-only
	STATUS  mandatory
	DESCRIPTION "CB1 Min
		     Note for all minumum currents 1-42: 100 = 10.0 amps"
		::= { bcmsplus1 43 }

bcms1-cb2-min
	OBJECT-TYPE
	SYNTAX  INTEGER
	ACCESS  read-only
	STATUS  mandatory
	DESCRIPTION "CB2 Min"
		::= { bcmsplus1 44 }

bcms1-cb3-min
	OBJECT-TYPE
	SYNTAX  INTEGER
	ACCESS  read-only
	STATUS  mandatory
	DESCRIPTION "CB3 Min"
		::= { bcmsplus1 45 }

bcms1-cb4-min
	OBJECT-TYPE
	SYNTAX  INTEGER
	ACCESS  read-only
	STATUS  mandatory
	DESCRIPTION "CB4 Min"
		::= { bcmsplus1 46 }

bcms1-cb5-min
	OBJECT-TYPE
	SYNTAX  INTEGER
	ACCESS  read-only
	STATUS  mandatory
	DESCRIPTION "CB5 Min"
		::= { bcmsplus1 47 }

bcms1-cb6-min
	OBJECT-TYPE
	SYNTAX  INTEGER
	ACCESS  read-only
	STATUS  mandatory
	DESCRIPTION "CB6 Min"
		::= { bcmsplus1 48 }

bcms1-cb7-min
	OBJECT-TYPE
	SYNTAX  INTEGER
	ACCESS  read-only
	STATUS  mandatory
	DESCRIPTION "CB7 Min"
		::= { bcmsplus1 49 }

bcms1-cb8-min
	OBJECT-TYPE
	SYNTAX  INTEGER
	ACCESS  read-only
	STATUS  mandatory
	DESCRIPTION "CB8 Min"
		::= { bcmsplus1 50 }

bcms1-cb9-min
	OBJECT-TYPE
	SYNTAX  INTEGER
	ACCESS  read-only
	STATUS  mandatory
	DESCRIPTION "CB9 Min"
		::= { bcmsplus1 51 }
  
bcms1-cb10-min
	OBJECT-TYPE
	SYNTAX  INTEGER
	ACCESS  read-only
	STATUS  mandatory
	DESCRIPTION "CB10 Min"
		::= { bcmsplus1 52 }

bcms1-cb11-min
	OBJECT-TYPE
	SYNTAX  INTEGER
	ACCESS  read-only
	STATUS  mandatory
	DESCRIPTION "CB11 Min"
		::= { bcmsplus1 53 }

bcms1-cb12-min
	OBJECT-TYPE
	SYNTAX  INTEGER
	ACCESS  read-only
	STATUS  mandatory
	DESCRIPTION "CB12 Min"
		::= { bcmsplus1 54 }

bcms1-cb13-min
	OBJECT-TYPE
	SYNTAX  INTEGER
	ACCESS  read-only
	STATUS  mandatory
	DESCRIPTION "CB13 Min"
		::= { bcmsplus1 55 }

bcms1-cb14-min
	OBJECT-TYPE
	SYNTAX  INTEGER
	ACCESS  read-only
	STATUS  mandatory
	DESCRIPTION "CB14 Min"
		::= { bcmsplus1 56 }

bcms1-cb15-min
	OBJECT-TYPE
	SYNTAX  INTEGER
	ACCESS  read-only
	STATUS  mandatory
	DESCRIPTION "CB15 Min"
		::= { bcmsplus1 57 }

bcms1-cb16-min
	OBJECT-TYPE
	SYNTAX  INTEGER
	ACCESS  read-only
	STATUS  mandatory
	DESCRIPTION "CB16 Min"
		::= { bcmsplus1 58 }

bcms1-cb17-min
	OBJECT-TYPE
	SYNTAX  INTEGER
	ACCESS  read-only
	STATUS  mandatory
	DESCRIPTION "CB17 Min"
		::= { bcmsplus1 59 }


bcms1-cb18-min
	OBJECT-TYPE
	SYNTAX  INTEGER
	ACCESS  read-only
	STATUS  mandatory
	DESCRIPTION "CB18 Min"
		::= { bcmsplus1 60 }

bcms1-cb19-min
	OBJECT-TYPE
	SYNTAX  INTEGER
	ACCESS  read-only
	STATUS  mandatory
	DESCRIPTION "CB19 Min"
		::= { bcmsplus1 61 }
  
bcms1-cb20-min
	OBJECT-TYPE
	SYNTAX  INTEGER
	ACCESS  read-only
	STATUS  mandatory
	DESCRIPTION "CB20 Min"
		::= { bcmsplus1 62 }

bcms1-cb21-min
	OBJECT-TYPE
	SYNTAX  INTEGER
	ACCESS  read-only
	STATUS  mandatory
	DESCRIPTION "CB21 Min"
		::= { bcmsplus1 63 }

bcms1-cb22-min
	OBJECT-TYPE
	SYNTAX  INTEGER
	ACCESS  read-only
	STATUS  mandatory
	DESCRIPTION "CB22 Min"
		::= { bcmsplus1 64 }

bcms1-cb23-min
	OBJECT-TYPE
	SYNTAX  INTEGER
	ACCESS  read-only
	STATUS  mandatory
	DESCRIPTION "CB23 Min"
		::= { bcmsplus1 65 }

bcms1-cb24-min
	OBJECT-TYPE
	SYNTAX  INTEGER
	ACCESS  read-only
	STATUS  mandatory
	DESCRIPTION "CB24 Min"
		::= { bcmsplus1 66 }

bcms1-cb25-min
	OBJECT-TYPE
	SYNTAX  INTEGER
	ACCESS  read-only
	STATUS  mandatory
	DESCRIPTION "CB25 Min"
		::= { bcmsplus1 67 }

bcms1-cb26-min
	OBJECT-TYPE
	SYNTAX  INTEGER
	ACCESS  read-only
	STATUS  mandatory
	DESCRIPTION "CB26 Min"
		::= { bcmsplus1 68 }

bcms1-cb27-min
	OBJECT-TYPE
	SYNTAX  INTEGER
	ACCESS  read-only
	STATUS  mandatory
	DESCRIPTION "CB27 Min"
		::= { bcmsplus1 69 }

bcms1-cb28-min
	OBJECT-TYPE
	SYNTAX  INTEGER
	ACCESS  read-only
	STATUS  mandatory
	DESCRIPTION "CB28 Min"
		::= { bcmsplus1 70 }

bcms1-cb29-min
	OBJECT-TYPE
	SYNTAX  INTEGER
	ACCESS  read-only
	STATUS  mandatory
	DESCRIPTION "CB29 Min"
		::= { bcmsplus1 71 }
  
bcms1-cb30-min
	OBJECT-TYPE
	SYNTAX  INTEGER
	ACCESS  read-only
	STATUS  mandatory
	DESCRIPTION "CB30 Min"
		::= { bcmsplus1 72 }

bcms1-cb31-min
	OBJECT-TYPE
	SYNTAX  INTEGER
	ACCESS  read-only
	STATUS  mandatory
	DESCRIPTION "CB31 Min"
		::= { bcmsplus1 73 }

bcms1-cb32-min
	OBJECT-TYPE
	SYNTAX  INTEGER
	ACCESS  read-only
	STATUS  mandatory
	DESCRIPTION "CB32 Min"
		::= { bcmsplus1 74 }

bcms1-cb33-min
	OBJECT-TYPE
	SYNTAX  INTEGER
	ACCESS  read-only
	STATUS  mandatory
	DESCRIPTION "CB33 Min"
		::= { bcmsplus1 75 }

bcms1-cb34-min
	OBJECT-TYPE
	SYNTAX  INTEGER
	ACCESS  read-only
	STATUS  mandatory
	DESCRIPTION "CB34 Min"
		::= { bcmsplus1 76 }

bcms1-cb35-min
	OBJECT-TYPE
	SYNTAX  INTEGER
	ACCESS  read-only
	STATUS  mandatory
	DESCRIPTION "CB35 Min"
		::= { bcmsplus1 77 }

bcms1-cb36-min
	OBJECT-TYPE
	SYNTAX  INTEGER
	ACCESS  read-only
	STATUS  mandatory
	DESCRIPTION "CB36 Min"
		::= { bcmsplus1 78 }

bcms1-cb37-min
	OBJECT-TYPE
	SYNTAX  INTEGER
	ACCESS  read-only
	STATUS  mandatory
	DESCRIPTION "CB37 Min"
		::= { bcmsplus1 79 }

bcms1-cb38-min
	OBJECT-TYPE
	SYNTAX  INTEGER
	ACCESS  read-only
	STATUS  mandatory
	DESCRIPTION "CB38 Min"
		::= { bcmsplus1 80 }

bcms1-cb39-min
	OBJECT-TYPE
	SYNTAX  INTEGER
	ACCESS  read-only
	STATUS  mandatory
	DESCRIPTION "CB39 Min"
		::= { bcmsplus1 81 }
  
bcms1-cb40-min
	OBJECT-TYPE
	SYNTAX  INTEGER
	ACCESS  read-only
	STATUS  mandatory
	DESCRIPTION "CB40 Min"
		::= { bcmsplus1 82 }

bcms1-cb41-min
	OBJECT-TYPE
	SYNTAX  INTEGER
	ACCESS  read-only
	STATUS  mandatory
	DESCRIPTION "CB41 Min"
		::= { bcmsplus1 83 }

bcms1-cb42-min
	OBJECT-TYPE
	SYNTAX  INTEGER
	ACCESS  read-only
	STATUS  mandatory
	DESCRIPTION "CB42 Min"
		::= { bcmsplus1 84 }

bcms1-cb1-max
	OBJECT-TYPE
	SYNTAX  INTEGER
	ACCESS  read-only
	STATUS  mandatory
	DESCRIPTION "CB1 Max
		     Note for all maximum currents 1-42: 100 = 10.0 amps"
		::= { bcmsplus1 85 }

bcms1-cb2-max
	OBJECT-TYPE
	SYNTAX  INTEGER
	ACCESS  read-only
	STATUS  mandatory
	DESCRIPTION "CB2 Max"
		::= { bcmsplus1 86 }

bcms1-cb3-max
	OBJECT-TYPE
	SYNTAX  INTEGER
	ACCESS  read-only
	STATUS  mandatory
	DESCRIPTION "CB3 Max"
		::= { bcmsplus1 87 }

bcms1-cb4-max
	OBJECT-TYPE
	SYNTAX  INTEGER
	ACCESS  read-only
	STATUS  mandatory
	DESCRIPTION "CB4 Max"
		::= { bcmsplus1 88 }

bcms1-cb5-max
	OBJECT-TYPE
	SYNTAX  INTEGER
	ACCESS  read-only
	STATUS  mandatory
	DESCRIPTION "CB5 Max"
		::= { bcmsplus1 89 }

bcms1-cb6-max
	OBJECT-TYPE
	SYNTAX  INTEGER
	ACCESS  read-only
	STATUS  mandatory
	DESCRIPTION "CB6 Max"
		::= { bcmsplus1 90 }

bcms1-cb7-max
	OBJECT-TYPE
	SYNTAX  INTEGER
	ACCESS  read-only
	STATUS  mandatory
	DESCRIPTION "CB7 Max"
		::= { bcmsplus1 91 }
  
bcms1-cb8-max
	OBJECT-TYPE
	SYNTAX  INTEGER
	ACCESS  read-only
	STATUS  mandatory
	DESCRIPTION "CB8 Max"
		::= { bcmsplus1 92 }

bcms1-cb9-max
	OBJECT-TYPE
	SYNTAX  INTEGER
	ACCESS  read-only
	STATUS  mandatory
	DESCRIPTION "CB9 Max"
		::= { bcmsplus1 93 }

bcms1-cb10-max
	OBJECT-TYPE
	SYNTAX  INTEGER
	ACCESS  read-only
	STATUS  mandatory
	DESCRIPTION "CB10 Max"
		::= { bcmsplus1 94 }

bcms1-cb11-max
	OBJECT-TYPE
	SYNTAX  INTEGER
	ACCESS  read-only
	STATUS  mandatory
	DESCRIPTION "CB11 Max"
		::= { bcmsplus1 95 }

bcms1-cb12-max
	OBJECT-TYPE
	SYNTAX  INTEGER
	ACCESS  read-only
	STATUS  mandatory
	DESCRIPTION "CB12 Max"
		::= { bcmsplus1 96 }

bcms1-cb13-max
	OBJECT-TYPE
	SYNTAX  INTEGER
	ACCESS  read-only
	STATUS  mandatory
	DESCRIPTION "CB13 Max"
		::= { bcmsplus1 97 }

bcms1-cb14-max
	OBJECT-TYPE
	SYNTAX  INTEGER
	ACCESS  read-only
	STATUS  mandatory
	DESCRIPTION "CB14 Max"
		::= { bcmsplus1 98 }

bcms1-cb15-max
	OBJECT-TYPE
	SYNTAX  INTEGER
	ACCESS  read-only
	STATUS  mandatory
	DESCRIPTION "CB15 Max"
		::= { bcmsplus1 99 }


bcms1-cb16-max
	OBJECT-TYPE
	SYNTAX  INTEGER
	ACCESS  read-only
	STATUS  mandatory
	DESCRIPTION "CB16 Max"
		::= { bcmsplus1 100 }

bcms1-cb17-max
	OBJECT-TYPE
	SYNTAX  INTEGER
	ACCESS  read-only
	STATUS  mandatory
	DESCRIPTION "CB17 Max"
		::= { bcmsplus1 101 }
  
bcms1-cb18-max
	OBJECT-TYPE
	SYNTAX  INTEGER
	ACCESS  read-only
	STATUS  mandatory
	DESCRIPTION "CB18 Max"
		::= { bcmsplus1 102 }

bcms1-cb19-max
	OBJECT-TYPE
	SYNTAX  INTEGER
	ACCESS  read-only
	STATUS  mandatory
	DESCRIPTION "CB19 Max"
		::= { bcmsplus1 103 }

bcms1-cb20-max
	OBJECT-TYPE
	SYNTAX  INTEGER
	ACCESS  read-only
	STATUS  mandatory
	DESCRIPTION "CB20 Max"
		::= { bcmsplus1 104 }

bcms1-cb21-max
	OBJECT-TYPE
	SYNTAX  INTEGER
	ACCESS  read-only
	STATUS  mandatory
	DESCRIPTION "CB21 Max"
		::= { bcmsplus1 105 }

bcms1-cb22-max
	OBJECT-TYPE
	SYNTAX  INTEGER
	ACCESS  read-only
	STATUS  mandatory
	DESCRIPTION "CB22 Max"
		::= { bcmsplus1 106 }

bcms1-cb23-max
	OBJECT-TYPE
	SYNTAX  INTEGER
	ACCESS  read-only
	STATUS  mandatory
	DESCRIPTION "CB23 Max"
		::= { bcmsplus1 107 }

bcms1-cb24-max
	OBJECT-TYPE
	SYNTAX  INTEGER
	ACCESS  read-only
	STATUS  mandatory
	DESCRIPTION "CB24 Max"
		::= { bcmsplus1 108 }

bcms1-cb25-max
	OBJECT-TYPE
	SYNTAX  INTEGER
	ACCESS  read-only
	STATUS  mandatory
	DESCRIPTION "CB25 Max"
		::= { bcmsplus1 109 }

bcms1-cb26-max
	OBJECT-TYPE
	SYNTAX  INTEGER
	ACCESS  read-only
	STATUS  mandatory
	DESCRIPTION "CB26 Max"
		::= { bcmsplus1 110 }

bcms1-cb27-max
	OBJECT-TYPE
	SYNTAX  INTEGER
	ACCESS  read-only
	STATUS  mandatory
	DESCRIPTION "CB27 Max"
		::= { bcmsplus1 111 }
  
bcms1-cb28-max
	OBJECT-TYPE
	SYNTAX  INTEGER
	ACCESS  read-only
	STATUS  mandatory
	DESCRIPTION "CB28 Max"
		::= { bcmsplus1 112 }

bcms1-cb29-max
	OBJECT-TYPE
	SYNTAX  INTEGER
	ACCESS  read-only
	STATUS  mandatory
	DESCRIPTION "CB29 Max"
		::= { bcmsplus1 113 }

bcms1-cb30-max
	OBJECT-TYPE
	SYNTAX  INTEGER
	ACCESS  read-only
	STATUS  mandatory
	DESCRIPTION "CB30 Max"
		::= { bcmsplus1 114 }

bcms1-cb31-max
	OBJECT-TYPE
	SYNTAX  INTEGER
	ACCESS  read-only
	STATUS  mandatory
	DESCRIPTION "CB31 Max"
		::= { bcmsplus1 115 }

bcms1-cb32-max
	OBJECT-TYPE
	SYNTAX  INTEGER
	ACCESS  read-only
	STATUS  mandatory
	DESCRIPTION "CB32 Max"
		::= { bcmsplus1 116 }

bcms1-cb33-max
	OBJECT-TYPE
	SYNTAX  INTEGER
	ACCESS  read-only
	STATUS  mandatory
	DESCRIPTION "CB33 Max"
		::= { bcmsplus1 117 }

bcms1-cb34-max
	OBJECT-TYPE
	SYNTAX  INTEGER
	ACCESS  read-only
	STATUS  mandatory
	DESCRIPTION "CB34 Max"
		::= { bcmsplus1 118 }

bcms1-cb35-max
	OBJECT-TYPE
	SYNTAX  INTEGER
	ACCESS  read-only
	STATUS  mandatory
	DESCRIPTION "CB35 Max"
		::= { bcmsplus1 119 }

bcms1-cb36-max
	OBJECT-TYPE
	SYNTAX  INTEGER
	ACCESS  read-only
	STATUS  mandatory
	DESCRIPTION "CB36 Max"
		::= { bcmsplus1 120 }

bcms1-cb37-max
	OBJECT-TYPE
	SYNTAX  INTEGER
	ACCESS  read-only
	STATUS  mandatory
	DESCRIPTION "CB37 Max"
		::= { bcmsplus1 121 }
  
bcms1-cb38-max
	OBJECT-TYPE
	SYNTAX  INTEGER
	ACCESS  read-only
	STATUS  mandatory
	DESCRIPTION "CB38 Max"
		::= { bcmsplus1 122 }

bcms1-cb39-max
	OBJECT-TYPE
	SYNTAX  INTEGER
	ACCESS  read-only
	STATUS  mandatory
	DESCRIPTION "CB39 Max"
		::= { bcmsplus1 123 }

bcms1-cb40-max
	OBJECT-TYPE
	SYNTAX  INTEGER
	ACCESS  read-only
	STATUS  mandatory
	DESCRIPTION "CB40 Max"
		::= { bcmsplus1 124 }

bcms1-cb41-max
	OBJECT-TYPE
	SYNTAX  INTEGER
	ACCESS  read-only
	STATUS  mandatory
	DESCRIPTION "CB41 Max"
		::= { bcmsplus1 125 }

bcms1-cb42-max
	OBJECT-TYPE
	SYNTAX  INTEGER
	ACCESS  read-only
	STATUS  mandatory
	DESCRIPTION "CB42 Max"
		::= { bcmsplus1 126 }

bcms1-cb1-16-zero
	OBJECT-TYPE
	SYNTAX  INTEGER
	ACCESS  read-write
	STATUS  mandatory
	DESCRIPTION "CB1-16 Zero
		       Bit 0 = CB1
                   Bit 15 = CB16"
		::= { bcmsplus1 127 }

bcms1-cb17-32-zero
	OBJECT-TYPE
	SYNTAX  INTEGER
	ACCESS  read-write
	STATUS  mandatory
	DESCRIPTION "CB17-32 Zero
		       Bit 0 = CB17
                   Bit 15 = CB32"
		::= { bcmsplus1 128 }

bcms1-cb33-42-zero
	OBJECT-TYPE
	SYNTAX  INTEGER
	ACCESS  read-write
	STATUS  mandatory
	DESCRIPTION "CB33-42 Zero
		       Bit 0 = CB33
                   Bit 9 = CB42
                   Bits 10-25 not used"
		::= { bcmsplus1 129 }

bcms1-cb1-16-warning
	OBJECT-TYPE
	SYNTAX  INTEGER
	ACCESS  read-write
	STATUS  mandatory
	DESCRIPTION "CB1-16 Warning
		       Bit 0 = CB1
                   Bit 15 = CB16"
		::= { bcmsplus1 130 }

bcms1-cb17-32-warning
	OBJECT-TYPE
	SYNTAX  INTEGER
	ACCESS  read-write
	STATUS  mandatory
	DESCRIPTION "CB17-32 Warning
		       Bit 0 = CB17
                   Bit 15 = CB32"
		::= { bcmsplus1 131 }
  
bcms1-cb33-42-warning
	OBJECT-TYPE
	SYNTAX  INTEGER
	ACCESS  read-write
	STATUS  mandatory
	DESCRIPTION "CB33-42 Warning
		       Bit 0 = CB33
                   Bit 9 = CB42
                   Bits 10-25 not used"
		::= { bcmsplus1 132 }

bcms1-cb1-16-alarm
	OBJECT-TYPE
	SYNTAX  INTEGER
	ACCESS  read-write
	STATUS  mandatory
	DESCRIPTION "CB1-16 Alarm
		       Bit 0 = CB1
                   Bit 15 = CB16"
		::= { bcmsplus1 133 }

bcms1-cb17-32-alarm
	OBJECT-TYPE
	SYNTAX  INTEGER
	ACCESS  read-write
	STATUS  mandatory
	DESCRIPTION "CB17-32 Alarm
		       Bit 0 = CB17
                   Bit 15 = CB32"
		::= { bcmsplus1 134 }

bcms1-cb33-42-alarm
	OBJECT-TYPE
	SYNTAX  INTEGER
	ACCESS  read-write
	STATUS  mandatory
	DESCRIPTION "CB33-42 Alarm
		       Bit 0 = CB33
                   Bit 9 = CB42
                   Bits 10-25 not used"
		::= { bcmsplus1 135 }

bcms1-cb1-breaker-size
	OBJECT-TYPE
	SYNTAX  INTEGER
	ACCESS  read-write
	STATUS  mandatory
	DESCRIPTION "CB1 Breaker-Size
		     Note for all breaker sizes 1-42: 10 = 10 amps
                     Range is 10 to 100 amps"
		::= { bcmsplus1 136 }

bcms1-cb2-breaker-size
	OBJECT-TYPE
	SYNTAX  INTEGER
	ACCESS  read-write
	STATUS  mandatory
	DESCRIPTION "CB2 Breaker-Size"
		::= { bcmsplus1 137 }

bcms1-cb3-breaker-size
	OBJECT-TYPE
	SYNTAX  INTEGER
	ACCESS  read-write
	STATUS  mandatory
	DESCRIPTION "CB3 Breaker-Size"
		::= { bcmsplus1 138 }

bcms1-cb4-breaker-size
	OBJECT-TYPE
	SYNTAX  INTEGER
	ACCESS  read-write
	STATUS  mandatory
	DESCRIPTION "CB4 Breaker-Size"
		::= { bcmsplus1 139 }

bcms1-cb5-breaker-size
	OBJECT-TYPE
	SYNTAX  INTEGER
	ACCESS  read-write
	STATUS  mandatory
	DESCRIPTION "CB5 Breaker-Size"
		::= { bcmsplus1 140 }

bcms1-cb6-breaker-size
	OBJECT-TYPE
	SYNTAX  INTEGER
	ACCESS  read-write
	STATUS  mandatory
	DESCRIPTION "CB6 Breaker-Size"
		::= { bcmsplus1 141 }
  
bcms1-cb7-breaker-size
	OBJECT-TYPE
	SYNTAX  INTEGER
	ACCESS  read-write
	STATUS  mandatory
	DESCRIPTION "CB7 Breaker-Size"
		::= { bcmsplus1 142 }

bcms1-cb8-breaker-size
	OBJECT-TYPE
	SYNTAX  INTEGER
	ACCESS  read-write
	STATUS  mandatory
	DESCRIPTION "CB8 Breaker-Size"
		::= { bcmsplus1 143 }

bcms1-cb9-breaker-size
	OBJECT-TYPE
	SYNTAX  INTEGER
	ACCESS  read-write
	STATUS  mandatory
	DESCRIPTION "CB9 Breaker-Size"
		::= { bcmsplus1 144 }

bcms1-cb10-breaker-size
	OBJECT-TYPE
	SYNTAX  INTEGER
	ACCESS  read-write
	STATUS  mandatory
	DESCRIPTION "CB10 Breaker-Size"
		::= { bcmsplus1 145 }

bcms1-cb11-breaker-size
	OBJECT-TYPE
	SYNTAX  INTEGER
	ACCESS  read-write
	STATUS  mandatory
	DESCRIPTION "CB11 Breaker-Size"
		::= { bcmsplus1 146 }

bcms1-cb12-breaker-size
	OBJECT-TYPE
	SYNTAX  INTEGER
	ACCESS  read-write
	STATUS  mandatory
	DESCRIPTION "CB12 Breaker-Size"
		::= { bcmsplus1 147 }

bcms1-cb13-breaker-size
	OBJECT-TYPE
	SYNTAX  INTEGER
	ACCESS  read-write
	STATUS  mandatory
	DESCRIPTION "CB13 Breaker-Size"
		::= { bcmsplus1 148 }

bcms1-cb14-breaker-size
	OBJECT-TYPE
	SYNTAX  INTEGER
	ACCESS  read-write
	STATUS  mandatory
	DESCRIPTION "CB14 Breaker-Size"
		::= { bcmsplus1 149 }

bcms1-cb15-breaker-size
	OBJECT-TYPE
	SYNTAX  INTEGER
	ACCESS  read-write
	STATUS  mandatory
	DESCRIPTION "CB15 Breaker-Size"
		::= { bcmsplus1 150 }

bcms1-cb16-breaker-size
	OBJECT-TYPE
	SYNTAX  INTEGER
	ACCESS  read-write
	STATUS  mandatory
	DESCRIPTION "CB16 Breaker-Size"
		::= { bcmsplus1 151 }
  
bcms1-cb17-breaker-size
	OBJECT-TYPE
	SYNTAX  INTEGER
	ACCESS  read-write
	STATUS  mandatory
	DESCRIPTION "CB17 Breaker-Size"
		::= { bcmsplus1 152 }

bcms1-cb18-breaker-size
	OBJECT-TYPE
	SYNTAX  INTEGER
	ACCESS  read-write
	STATUS  mandatory
	DESCRIPTION "CB18 Breaker-Size"
		::= { bcmsplus1 153 }

bcms1-cb19-breaker-size
	OBJECT-TYPE
	SYNTAX  INTEGER
	ACCESS  read-write
	STATUS  mandatory
	DESCRIPTION "CB19 Breaker-Size"
		::= { bcmsplus1 154 }

bcms1-cb20-breaker-size
	OBJECT-TYPE
	SYNTAX  INTEGER
	ACCESS  read-write
	STATUS  mandatory
	DESCRIPTION "CB20 Breaker-Size"
		::= { bcmsplus1 155 }

bcms1-cb21-breaker-size
	OBJECT-TYPE
	SYNTAX  INTEGER
	ACCESS  read-write
	STATUS  mandatory
	DESCRIPTION "CB21 Breaker-Size"
		::= { bcmsplus1 156 }

bcms1-cb22-breaker-size
	OBJECT-TYPE
	SYNTAX  INTEGER
	ACCESS  read-write
	STATUS  mandatory
	DESCRIPTION "CB22 Breaker-Size"
		::= { bcmsplus1 157 }

bcms1-cb23-breaker-size
	OBJECT-TYPE
	SYNTAX  INTEGER
	ACCESS  read-write
	STATUS  mandatory
	DESCRIPTION "CB23 Breaker-Size"
		::= { bcmsplus1 158 }

bcms1-cb24-breaker-size
	OBJECT-TYPE
	SYNTAX  INTEGER
	ACCESS  read-write
	STATUS  mandatory
	DESCRIPTION "CB24 Breaker-Size"
		::= { bcmsplus1 159 }

bcms1-cb25-breaker-size
	OBJECT-TYPE
	SYNTAX  INTEGER
	ACCESS  read-write
	STATUS  mandatory
	DESCRIPTION "CB25 Breaker-Size"
		::= { bcmsplus1 160 }

bcms1-cb26-breaker-size
	OBJECT-TYPE
	SYNTAX  INTEGER
	ACCESS  read-write
	STATUS  mandatory
	DESCRIPTION "CB26 Breaker-Size"
		::= { bcmsplus1 161 }
  
bcms1-cb27-breaker-size
	OBJECT-TYPE
	SYNTAX  INTEGER
	ACCESS  read-write
	STATUS  mandatory
	DESCRIPTION "CB27 Breaker-Size"
		::= { bcmsplus1 162 }

bcms1-cb28-breaker-size
	OBJECT-TYPE
	SYNTAX  INTEGER
	ACCESS  read-write
	STATUS  mandatory
	DESCRIPTION "CB28 Breaker-Size"
		::= { bcmsplus1 163 }

bcms1-cb29-breaker-size
	OBJECT-TYPE
	SYNTAX  INTEGER
	ACCESS  read-write
	STATUS  mandatory
	DESCRIPTION "CB29 Breaker-Size"
		::= { bcmsplus1 164 }

bcms1-cb30-breaker-size
	OBJECT-TYPE
	SYNTAX  INTEGER
	ACCESS  read-write
	STATUS  mandatory
	DESCRIPTION "CB30 Breaker-Size"
		::= { bcmsplus1 165 }

bcms1-cb31-breaker-size
	OBJECT-TYPE
	SYNTAX  INTEGER
	ACCESS  read-write
	STATUS  mandatory
	DESCRIPTION "CB31 Breaker-Size"
		::= { bcmsplus1 166 }

bcms1-cb32-breaker-size
	OBJECT-TYPE
	SYNTAX  INTEGER
	ACCESS  read-write
	STATUS  mandatory
	DESCRIPTION "CB32 Breaker-Size"
		::= { bcmsplus1 167 }

bcms1-cb33-breaker-size
	OBJECT-TYPE
	SYNTAX  INTEGER
	ACCESS  read-write
	STATUS  mandatory
	DESCRIPTION "CB33 Breaker-Size"
		::= { bcmsplus1 168 }

bcms1-cb34-breaker-size
	OBJECT-TYPE
	SYNTAX  INTEGER
	ACCESS  read-write
	STATUS  mandatory
	DESCRIPTION "CB34 Breaker-Size"
		::= { bcmsplus1 169 }

bcms1-cb35-breaker-size
	OBJECT-TYPE
	SYNTAX  INTEGER
	ACCESS  read-write
	STATUS  mandatory
	DESCRIPTION "CB35 Breaker-Size"
		::= { bcmsplus1 170 }

bcms1-cb36-breaker-size
	OBJECT-TYPE
	SYNTAX  INTEGER
	ACCESS  read-write
	STATUS  mandatory
	DESCRIPTION "CB36 Breaker-Size"
		::= { bcmsplus1 171 }
  
bcms1-cb37-breaker-size
	OBJECT-TYPE
	SYNTAX  INTEGER
	ACCESS  read-write
	STATUS  mandatory
	DESCRIPTION "CB37 Breaker-Size"
		::= { bcmsplus1 172 }

bcms1-cb38-breaker-size
	OBJECT-TYPE
	SYNTAX  INTEGER
	ACCESS  read-write
	STATUS  mandatory
	DESCRIPTION "CB38 Breaker-Size"
		::= { bcmsplus1 173 }

bcms1-cb39-breaker-size
	OBJECT-TYPE
	SYNTAX  INTEGER
	ACCESS  read-write
	STATUS  mandatory
	DESCRIPTION "CB39 Breaker-Size"
		::= { bcmsplus1 174 }

bcms1-cb40-breaker-size
	OBJECT-TYPE
	SYNTAX  INTEGER
	ACCESS  read-write
	STATUS  mandatory
	DESCRIPTION "CB40 Breaker-Size"
		::= { bcmsplus1 175 }

bcms1-cb41-breaker-size
	OBJECT-TYPE
	SYNTAX  INTEGER
	ACCESS  read-write
	STATUS  mandatory
	DESCRIPTION "CB41 Breaker-Size"
		::= { bcmsplus1 176 }

bcms1-cb42-breaker-size
	OBJECT-TYPE
	SYNTAX  INTEGER
	ACCESS  read-write
	STATUS  mandatory
	DESCRIPTION "CB42 Breaker-Size"
		::= { bcmsplus1 177 }

bcms1-cb1-warning-threshold
	OBJECT-TYPE
	SYNTAX  INTEGER
	ACCESS  read-write
	STATUS  mandatory
	DESCRIPTION "CB1 CB1-warning-threshold
		     Note for all warning thresholds 1-42: 70 = 70% of breaker size
                     range is 0-100%"
		::= { bcmsplus1 178 }

bcms1-cb2-warning-threshold
	OBJECT-TYPE
	SYNTAX  INTEGER
	ACCESS  read-write
	STATUS  mandatory
	DESCRIPTION "CB2 Warning-Threshold"
		::= { bcmsplus1 179 }

bcms1-cb3-warning-threshold
	OBJECT-TYPE
	SYNTAX  INTEGER
	ACCESS  read-write
	STATUS  mandatory
	DESCRIPTION "CB3 Warning-Threshold"
		::= { bcmsplus1 180 }

bcms1-cb4-warning-threshold
	OBJECT-TYPE
	SYNTAX  INTEGER
	ACCESS  read-write
	STATUS  mandatory
	DESCRIPTION "CB4 Warning-Threshold"
		::= { bcmsplus1 181 }
  
bcms1-cb5-warning-threshold
	OBJECT-TYPE
	SYNTAX  INTEGER
	ACCESS  read-write
	STATUS  mandatory
	DESCRIPTION "CB5 Warning-Threshold"
		::= { bcmsplus1 182 }

bcms1-cb6-warning-threshold
	OBJECT-TYPE
	SYNTAX  INTEGER
	ACCESS  read-write
	STATUS  mandatory
	DESCRIPTION "CB6 Warning-Threshold"
		::= { bcmsplus1 183 }

bcms1-cb7-warning-threshold
	OBJECT-TYPE
	SYNTAX  INTEGER
	ACCESS  read-write
	STATUS  mandatory
	DESCRIPTION "CB7 Warning-Threshold"
		::= { bcmsplus1 184 }

bcms1-cb8-warning-threshold
	OBJECT-TYPE
	SYNTAX  INTEGER
	ACCESS  read-write
	STATUS  mandatory
	DESCRIPTION "CB8 Warning-Threshold"
		::= { bcmsplus1 185 }

bcms1-cb9-warning-threshold
	OBJECT-TYPE
	SYNTAX  INTEGER
	ACCESS  read-write
	STATUS  mandatory
	DESCRIPTION "CB9 Warning-Threshold"
		::= { bcmsplus1 186 }

bcms1-cb10-warning-threshold
	OBJECT-TYPE
	SYNTAX  INTEGER
	ACCESS  read-write
	STATUS  mandatory
	DESCRIPTION "CB10 Warning-Threshold"
		::= { bcmsplus1 187 }

bcms1-cb11-warning-threshold
	OBJECT-TYPE
	SYNTAX  INTEGER
	ACCESS  read-write
	STATUS  mandatory
	DESCRIPTION "CB11 Warning-Threshold"
		::= { bcmsplus1 188 }

bcms1-cb12-warning-threshold
	OBJECT-TYPE
	SYNTAX  INTEGER
	ACCESS  read-write
	STATUS  mandatory
	DESCRIPTION "CB12 Warning-Threshold"
		::= { bcmsplus1 189 }

bcms1-cb13-warning-threshold
	OBJECT-TYPE
	SYNTAX  INTEGER
	ACCESS  read-write
	STATUS  mandatory
	DESCRIPTION "CB13 Warning-Threshold"
		::= { bcmsplus1 190 }

bcms1-cb14-warning-threshold
	OBJECT-TYPE
	SYNTAX  INTEGER
	ACCESS  read-write
	STATUS  mandatory
	DESCRIPTION "CB14 Warning-Threshold"
		::= { bcmsplus1 191 }
  
bcms1-cb15-warning-threshold
	OBJECT-TYPE
	SYNTAX  INTEGER
	ACCESS  read-write
	STATUS  mandatory
	DESCRIPTION "CB15 Warning-Threshold"
		::= { bcmsplus1 192 }

bcms1-cb16-warning-threshold
	OBJECT-TYPE
	SYNTAX  INTEGER
	ACCESS  read-write
	STATUS  mandatory
	DESCRIPTION "CB16 Warning-Threshold"
		::= { bcmsplus1 193 }

bcms1-cb17-warning-threshold
	OBJECT-TYPE
	SYNTAX  INTEGER
	ACCESS  read-write
	STATUS  mandatory
	DESCRIPTION "CB17 Warning-Threshold"
		::= { bcmsplus1 194 }

bcms1-cb18-warning-threshold
	OBJECT-TYPE
	SYNTAX  INTEGER
	ACCESS  read-write
	STATUS  mandatory
	DESCRIPTION "CB18 Warning-Threshold"
		::= { bcmsplus1 195 }

bcms1-cb19-warning-threshold
	OBJECT-TYPE
	SYNTAX  INTEGER
	ACCESS  read-write
	STATUS  mandatory
	DESCRIPTION "CB19 Warning-Threshold"
		::= { bcmsplus1 196 }

bcms1-cb20-warning-threshold
	OBJECT-TYPE
	SYNTAX  INTEGER
	ACCESS  read-write
	STATUS  mandatory
	DESCRIPTION "CB20 Warning-Threshold"
		::= { bcmsplus1 197 }

bcms1-cb21-warning-threshold
	OBJECT-TYPE
	SYNTAX  INTEGER
	ACCESS  read-write
	STATUS  mandatory
	DESCRIPTION "CB21 Warning-Threshold"
		::= { bcmsplus1 198 }

bcms1-cb22-warning-threshold
	OBJECT-TYPE
	SYNTAX  INTEGER
	ACCESS  read-write
	STATUS  mandatory
	DESCRIPTION "CB22 Warning-Threshold"
		::= { bcmsplus1 199 }

bcms1-cb23-warning-threshold
	OBJECT-TYPE
	SYNTAX  INTEGER
	ACCESS  read-write
	STATUS  mandatory
	DESCRIPTION "CB23 Warning-Threshold"
		::= { bcmsplus1 200 }

bcms1-cb24-warning-threshold
	OBJECT-TYPE
	SYNTAX  INTEGER
	ACCESS  read-write
	STATUS  mandatory
	DESCRIPTION "CB24 Warning-Threshold"
		::= { bcmsplus1 201 }
  
bcms1-cb25-warning-threshold
	OBJECT-TYPE
	SYNTAX  INTEGER
	ACCESS  read-write
	STATUS  mandatory
	DESCRIPTION "CB25 Warning-Threshold"
		::= { bcmsplus1 202 }

bcms1-cb26-warning-threshold
	OBJECT-TYPE
	SYNTAX  INTEGER
	ACCESS  read-write
	STATUS  mandatory
	DESCRIPTION "CB26 Warning-Threshold"
		::= { bcmsplus1 203 }

bcms1-cb27-warning-threshold
	OBJECT-TYPE
	SYNTAX  INTEGER
	ACCESS  read-write
	STATUS  mandatory
	DESCRIPTION "CB27 Warning-Threshold"
		::= { bcmsplus1 204 }

bcms1-cb28-warning-threshold
	OBJECT-TYPE
	SYNTAX  INTEGER
	ACCESS  read-write
	STATUS  mandatory
	DESCRIPTION "CB28 Warning-Threshold"
		::= { bcmsplus1 205 }

bcms1-cb29-warning-threshold
	OBJECT-TYPE
	SYNTAX  INTEGER
	ACCESS  read-write
	STATUS  mandatory
	DESCRIPTION "CB29 Warning-Threshold"
		::= { bcmsplus1 206 }

bcms1-cb30-warning-threshold
	OBJECT-TYPE
	SYNTAX  INTEGER
	ACCESS  read-write
	STATUS  mandatory
	DESCRIPTION "CB30 Warning-Threshold"
		::= { bcmsplus1 207 }

bcms1-cb31-warning-threshold
	OBJECT-TYPE
	SYNTAX  INTEGER
	ACCESS  read-write
	STATUS  mandatory
	DESCRIPTION "CB31 Warning-Threshold"
		::= { bcmsplus1 208 }

bcms1-cb32-warning-threshold
	OBJECT-TYPE
	SYNTAX  INTEGER
	ACCESS  read-write
	STATUS  mandatory
	DESCRIPTION "CB32 Warning-Threshold"
		::= { bcmsplus1 209 }

bcms1-cb33-warning-threshold
	OBJECT-TYPE
	SYNTAX  INTEGER
	ACCESS  read-write
	STATUS  mandatory
	DESCRIPTION "CB33 Warning-Threshold"
		::= { bcmsplus1 210 }

bcms1-cb34-warning-threshold
	OBJECT-TYPE
	SYNTAX  INTEGER
	ACCESS  read-write
	STATUS  mandatory
	DESCRIPTION "CB34 Warning-Threshold"
		::= { bcmsplus1 211 }
  
bcms1-cb35-warning-threshold
	OBJECT-TYPE
	SYNTAX  INTEGER
	ACCESS  read-write
	STATUS  mandatory
	DESCRIPTION "CB35 Warning-Threshold"
		::= { bcmsplus1 212 }

bcms1-cb36-warning-threshold
	OBJECT-TYPE
	SYNTAX  INTEGER
	ACCESS  read-write
	STATUS  mandatory
	DESCRIPTION "CB36 Warning-Threshold"
		::= { bcmsplus1 213 }

bcms1-cb37-warning-threshold
	OBJECT-TYPE
	SYNTAX  INTEGER
	ACCESS  read-write
	STATUS  mandatory
	DESCRIPTION "CB37 Warning-Threshold"
		::= { bcmsplus1 214 }

bcms1-cb38-warning-threshold
	OBJECT-TYPE
	SYNTAX  INTEGER
	ACCESS  read-write
	STATUS  mandatory
	DESCRIPTION "CB38 Warning-Threshold"
		::= { bcmsplus1 215 }

bcms1-cb39-warning-threshold
	OBJECT-TYPE
	SYNTAX  INTEGER
	ACCESS  read-write
	STATUS  mandatory
	DESCRIPTION "CB39 Warning-Threshold"
		::= { bcmsplus1 216 }

bcms1-cb40-warning-threshold
	OBJECT-TYPE
	SYNTAX  INTEGER
	ACCESS  read-write
	STATUS  mandatory
	DESCRIPTION "CB40 Warning-Threshold"
		::= { bcmsplus1 217 }

bcms1-cb41-warning-threshold
	OBJECT-TYPE
	SYNTAX  INTEGER
	ACCESS  read-write
	STATUS  mandatory
	DESCRIPTION "CB41 Warning-Threshold"
		::= { bcmsplus1 218 }

bcms1-cb42-warning-threshold
	OBJECT-TYPE
	SYNTAX  INTEGER
	ACCESS  read-write
	STATUS  mandatory
	DESCRIPTION "CB42 Warning-Threshold"
		::= { bcmsplus1 219 }

bcms1-cb1-alarm-threshold
	OBJECT-TYPE
	SYNTAX  INTEGER
	ACCESS  read-write
	STATUS  mandatory
	DESCRIPTION "CB1 Alarm-Threshold
		     Note for all alarm thresholds 1-42: 80 = 80% of breaker size
                     range is 0-100%"
		::= { bcmsplus1 220 }


bcms1-cb2-alarm-threshold
	OBJECT-TYPE
	SYNTAX  INTEGER
	ACCESS  read-write
	STATUS  mandatory
	DESCRIPTION "CB2 Alarm-Threshold"
		::= { bcmsplus1 221 }
  
bcms1-cb3-alarm-threshold
	OBJECT-TYPE
	SYNTAX  INTEGER
	ACCESS  read-write
	STATUS  mandatory
	DESCRIPTION "CB3 Alarm-Threshold"
		::= { bcmsplus1 222 }

bcms1-cb4-alarm-threshold
	OBJECT-TYPE
	SYNTAX  INTEGER
	ACCESS  read-write
	STATUS  mandatory
	DESCRIPTION "CB4 Alarm-Threshold"
		::= { bcmsplus1 223 }

bcms1-cb5-alarm-threshold
	OBJECT-TYPE
	SYNTAX  INTEGER
	ACCESS  read-write
	STATUS  mandatory
	DESCRIPTION "CB5 Alarm-Threshold"
		::= { bcmsplus1 224 }

bcms1-cb6-alarm-threshold
	OBJECT-TYPE
	SYNTAX  INTEGER
	ACCESS  read-write
	STATUS  mandatory
	DESCRIPTION "CB6 Alarm-Threshold"
		::= { bcmsplus1 225 }

bcms1-cb7-alarm-threshold
	OBJECT-TYPE
	SYNTAX  INTEGER
	ACCESS  read-write
	STATUS  mandatory
	DESCRIPTION "CB7 Alarm-Threshold"
		::= { bcmsplus1 226 }

bcms1-cb8-alarm-threshold
	OBJECT-TYPE
	SYNTAX  INTEGER
	ACCESS  read-write
	STATUS  mandatory
	DESCRIPTION "CB8 Alarm-Threshold"
		::= { bcmsplus1 227 }

bcms1-cb9-alarm-threshold
	OBJECT-TYPE
	SYNTAX  INTEGER
	ACCESS  read-write
	STATUS  mandatory
	DESCRIPTION "CB9 Alarm-Threshold"
		::= { bcmsplus1 228 }

bcms1-cb10-alarm-threshold
	OBJECT-TYPE
	SYNTAX  INTEGER
	ACCESS  read-write
	STATUS  mandatory
	DESCRIPTION "CB10 Alarm-Threshold"
		::= { bcmsplus1 229 }

bcms1-cb11-alarm-threshold
	OBJECT-TYPE
	SYNTAX  INTEGER
	ACCESS  read-write
	STATUS  mandatory
	DESCRIPTION "CB11 Alarm-Threshold"
		::= { bcmsplus1 230 }

bcms1-cb12-alarm-threshold
	OBJECT-TYPE
	SYNTAX  INTEGER
	ACCESS  read-write
	STATUS  mandatory
	DESCRIPTION "CB12 Alarm-Threshold"
		::= { bcmsplus1 231 }
  
bcms1-cb13-alarm-threshold
	OBJECT-TYPE
	SYNTAX  INTEGER
	ACCESS  read-write
	STATUS  mandatory
	DESCRIPTION "CB13 Alarm-Threshold"
		::= { bcmsplus1 232 }

bcms1-cb14-alarm-threshold
	OBJECT-TYPE
	SYNTAX  INTEGER
	ACCESS  read-write
	STATUS  mandatory
	DESCRIPTION "CB14 Alarm-Threshold"
		::= { bcmsplus1 233 }

bcms1-cb15-alarm-threshold
	OBJECT-TYPE
	SYNTAX  INTEGER
	ACCESS  read-write
	STATUS  mandatory
	DESCRIPTION "CB15 Alarm-Threshold"
		::= { bcmsplus1 234 }

bcms1-cb16-alarm-threshold
	OBJECT-TYPE
	SYNTAX  INTEGER
	ACCESS  read-write
	STATUS  mandatory
	DESCRIPTION "CB16 Alarm-Threshold"
		::= { bcmsplus1 235 }

bcms1-cb17-alarm-threshold
	OBJECT-TYPE
	SYNTAX  INTEGER
	ACCESS  read-write
	STATUS  mandatory
	DESCRIPTION "CB17 Alarm-Threshold"
		::= { bcmsplus1 236 }

bcms1-cb18-alarm-threshold
	OBJECT-TYPE
	SYNTAX  INTEGER
	ACCESS  read-write
	STATUS  mandatory
	DESCRIPTION "CB18 Alarm-Threshold"
		::= { bcmsplus1 237 }

bcms1-cb19-alarm-threshold
	OBJECT-TYPE
	SYNTAX  INTEGER
	ACCESS  read-write
	STATUS  mandatory
	DESCRIPTION "CB19 Alarm-Threshold"
		::= { bcmsplus1 238 }

bcms1-cb20-alarm-threshold
	OBJECT-TYPE
	SYNTAX  INTEGER
	ACCESS  read-write
	STATUS  mandatory
	DESCRIPTION "CB20 Alarm-Threshold"
		::= { bcmsplus1 239 }

bcms1-cb21-alarm-threshold
	OBJECT-TYPE
	SYNTAX  INTEGER
	ACCESS  read-write
	STATUS  mandatory
	DESCRIPTION "CB21 Alarm-Threshold"
		::= { bcmsplus1 240 }

bcms1-cb22-alarm-threshold
	OBJECT-TYPE
	SYNTAX  INTEGER
	ACCESS  read-write
	STATUS  mandatory
	DESCRIPTION "CB22 Alarm-Threshold"
		::= { bcmsplus1 241 }
  
bcms1-cb23-alarm-threshold
	OBJECT-TYPE
	SYNTAX  INTEGER
	ACCESS  read-write
	STATUS  mandatory
	DESCRIPTION "CB23 Alarm-Threshold"
		::= { bcmsplus1 242 }

bcms1-cb24-alarm-threshold
	OBJECT-TYPE
	SYNTAX  INTEGER
	ACCESS  read-write
	STATUS  mandatory
	DESCRIPTION "CB24 Alarm-Threshold"
		::= { bcmsplus1 243 }

bcms1-cb25-alarm-threshold
	OBJECT-TYPE
	SYNTAX  INTEGER
	ACCESS  read-write
	STATUS  mandatory
	DESCRIPTION "CB25 Alarm-Threshold"
		::= { bcmsplus1 244 }

bcms1-cb26-alarm-threshold
	OBJECT-TYPE
	SYNTAX  INTEGER
	ACCESS  read-write
	STATUS  mandatory
	DESCRIPTION "CB26 Alarm-Threshold"
		::= { bcmsplus1 245 }

bcms1-cb27-alarm-threshold
	OBJECT-TYPE
	SYNTAX  INTEGER
	ACCESS  read-write
	STATUS  mandatory
	DESCRIPTION "CB27 Alarm-Threshold"
		::= { bcmsplus1 246 }

bcms1-cb28-alarm-threshold
	OBJECT-TYPE
	SYNTAX  INTEGER
	ACCESS  read-write
	STATUS  mandatory
	DESCRIPTION "CB28 Alarm-Threshold"
		::= { bcmsplus1 247 }

bcms1-cb29-alarm-threshold
	OBJECT-TYPE
	SYNTAX  INTEGER
	ACCESS  read-write
	STATUS  mandatory
	DESCRIPTION "CB29 Alarm-Threshold"
		::= { bcmsplus1 248 }

bcms1-cb30-alarm-threshold
	OBJECT-TYPE
	SYNTAX  INTEGER
	ACCESS  read-write
	STATUS  mandatory
	DESCRIPTION "CB30 Alarm-Threshold"
		::= { bcmsplus1 249 }

bcms1-cb31-alarm-threshold
	OBJECT-TYPE
	SYNTAX  INTEGER
	ACCESS  read-write
	STATUS  mandatory
	DESCRIPTION "CB31 Alarm-Threshold"
		::= { bcmsplus1 250 }

bcms1-cb32-alarm-threshold
	OBJECT-TYPE
	SYNTAX  INTEGER
	ACCESS  read-write
	STATUS  mandatory
	DESCRIPTION "CB32 Alarm-Threshold"
		::= { bcmsplus1 251 }
  
bcms1-cb33-alarm-threshold
	OBJECT-TYPE
	SYNTAX  INTEGER
	ACCESS  read-write
	STATUS  mandatory
	DESCRIPTION "CB33 Alarm-Threshold"
		::= { bcmsplus1 252 }

bcms1-cb34-alarm-threshold
	OBJECT-TYPE
	SYNTAX  INTEGER
	ACCESS  read-write
	STATUS  mandatory
	DESCRIPTION "CB34 Alarm-Threshold"
		::= { bcmsplus1 253 }

bcms1-cb35-alarm-threshold
	OBJECT-TYPE
	SYNTAX  INTEGER
	ACCESS  read-write
	STATUS  mandatory
	DESCRIPTION "CB35 Alarm-Threshold"
		::= { bcmsplus1 254 }

bcms1-cb36-alarm-threshold
	OBJECT-TYPE
	SYNTAX  INTEGER
	ACCESS  read-write
	STATUS  mandatory
	DESCRIPTION "CB36 Alarm-Threshold"
		::= { bcmsplus1 255 }

bcms1-cb37-alarm-threshold
	OBJECT-TYPE
	SYNTAX  INTEGER
	ACCESS  read-write
	STATUS  mandatory
	DESCRIPTION "CB37 Alarm-Threshold"
		::= { bcmsplus1 256 }

bcms1-cb38-alarm-threshold
	OBJECT-TYPE
	SYNTAX  INTEGER
	ACCESS  read-write
	STATUS  mandatory
	DESCRIPTION "CB38 Alarm-Threshold"
		::= { bcmsplus1 257 }

bcms1-cb39-alarm-threshold
	OBJECT-TYPE
	SYNTAX  INTEGER
	ACCESS  read-write
	STATUS  mandatory
	DESCRIPTION "CB39 Alarm-Threshold"
		::= { bcmsplus1 258 }

bcms1-cb40-alarm-threshold
	OBJECT-TYPE
	SYNTAX  INTEGER
	ACCESS  read-write
	STATUS  mandatory
	DESCRIPTION "CB40 Alarm-Threshold"
		::= { bcmsplus1 259 }

bcms1-cb41-alarm-threshold
	OBJECT-TYPE
	SYNTAX  INTEGER
	ACCESS  read-write
	STATUS  mandatory
	DESCRIPTION "CB41 Alarm-Threshold"
		::= { bcmsplus1 260 }

bcms1-cb42-alarm-threshold
	OBJECT-TYPE
	SYNTAX  INTEGER
	ACCESS  read-write
	STATUS  mandatory
	DESCRIPTION "CB42 Alarm-Threshold"
		::= { bcmsplus1 261 }

bcms1-cb1-warning-time-delay
	OBJECT-TYPE
	SYNTAX  INTEGER
	ACCESS  read-write
	STATUS  mandatory
	DESCRIPTION "CB1 Warning-Time-Delay
		     Note for all warning time delays 1-42: units are in seconds"                     
		::= { bcmsplus1 262 }

bcms1-cb2-warning-time-delay
	OBJECT-TYPE
	SYNTAX  INTEGER
	ACCESS  read-write
	STATUS  mandatory
	DESCRIPTION "CB2 Warning-Time-Delay"
		::= { bcmsplus1 263 }
  
bcms1-cb3-warning-time-delay
	OBJECT-TYPE
	SYNTAX  INTEGER
	ACCESS  read-write
	STATUS  mandatory
	DESCRIPTION "CB3 Warning-Time-Delay"
		::= { bcmsplus1 264 }

bcms1-cb4-warning-time-delay
	OBJECT-TYPE
	SYNTAX  INTEGER
	ACCESS  read-write
	STATUS  mandatory
	DESCRIPTION "CB4 Warning-Time-Delay"
		::= { bcmsplus1 265 }

bcms1-cb5-warning-time-delay
	OBJECT-TYPE
	SYNTAX  INTEGER
	ACCESS  read-write
	STATUS  mandatory
	DESCRIPTION "CB5 Warning-Time-Delay"
		::= { bcmsplus1 266 }

bcms1-cb6-warning-time-delay
	OBJECT-TYPE
	SYNTAX  INTEGER
	ACCESS  read-write
	STATUS  mandatory
	DESCRIPTION "CB6 Warning-Time-Delay"
		::= { bcmsplus1 267 }

bcms1-cb7-warning-time-delay
	OBJECT-TYPE
	SYNTAX  INTEGER
	ACCESS  read-write
	STATUS  mandatory
	DESCRIPTION "CB7 Warning-Time-Delay"
		::= { bcmsplus1 268 }

bcms1-cb8-warning-time-delay
	OBJECT-TYPE
	SYNTAX  INTEGER
	ACCESS  read-write
	STATUS  mandatory
	DESCRIPTION "CB8 Warning-Time-Delay"
		::= { bcmsplus1 269 }

bcms1-cb9-warning-time-delay
	OBJECT-TYPE
	SYNTAX  INTEGER
	ACCESS  read-write
	STATUS  mandatory
	DESCRIPTION "CB9 Warning-Time-Delay"
		::= { bcmsplus1 270 }

bcms1-cb10-warning-time-delay
	OBJECT-TYPE
	SYNTAX  INTEGER
	ACCESS  read-write
	STATUS  mandatory
	DESCRIPTION "CB10 Warning-Time-Delay"
		::= { bcmsplus1 271 }

bcms1-cb11-warning-time-delay
	OBJECT-TYPE
	SYNTAX  INTEGER
	ACCESS  read-write
	STATUS  mandatory
	DESCRIPTION "CB11 Warning-Time-Delay"
		::= { bcmsplus1 272 }

bcms1-cb12-warning-time-delay
	OBJECT-TYPE
	SYNTAX  INTEGER
	ACCESS  read-write
	STATUS  mandatory
	DESCRIPTION "CB12 Warning-Time-Delay"
		::= { bcmsplus1 273 }
  
bcms1-cb13-warning-time-delay
	OBJECT-TYPE
	SYNTAX  INTEGER
	ACCESS  read-write
	STATUS  mandatory
	DESCRIPTION "CB13 Warning-Time-Delay"
		::= { bcmsplus1 274 }

bcms1-cb14-warning-time-delay
	OBJECT-TYPE
	SYNTAX  INTEGER
	ACCESS  read-write
	STATUS  mandatory
	DESCRIPTION "CB14 Warning-Time-Delay"
		::= { bcmsplus1 275 }

bcms1-cb15-warning-time-delay
	OBJECT-TYPE
	SYNTAX  INTEGER
	ACCESS  read-write
	STATUS  mandatory
	DESCRIPTION "CB15 Warning-Time-Delay"
		::= { bcmsplus1 276 }

bcms1-cb16-warning-time-delay
	OBJECT-TYPE
	SYNTAX  INTEGER
	ACCESS  read-write
	STATUS  mandatory
	DESCRIPTION "CB16 Warning-Time-Delay"
		::= { bcmsplus1 277 }

bcms1-cb17-warning-time-delay
	OBJECT-TYPE
	SYNTAX  INTEGER
	ACCESS  read-write
	STATUS  mandatory
	DESCRIPTION "CB17 Warning-Time-Delay"
		::= { bcmsplus1 278 }

bcms1-cb18-warning-time-delay
	OBJECT-TYPE
	SYNTAX  INTEGER
	ACCESS  read-write
	STATUS  mandatory
	DESCRIPTION "CB18 Warning-Time-Delay"
		::= { bcmsplus1 279 }

bcms1-cb19-warning-time-delay
	OBJECT-TYPE
	SYNTAX  INTEGER
	ACCESS  read-write
	STATUS  mandatory
	DESCRIPTION "CB19 Warning-Time-Delay"
		::= { bcmsplus1 280 }

bcms1-cb20-warning-time-delay
	OBJECT-TYPE
	SYNTAX  INTEGER
	ACCESS  read-write
	STATUS  mandatory
	DESCRIPTION "CB20 Warning-Time-Delay"
		::= { bcmsplus1 281 }

bcms1-cb21-warning-time-delay
	OBJECT-TYPE
	SYNTAX  INTEGER
	ACCESS  read-write
	STATUS  mandatory
	DESCRIPTION "CB21 Warning-Time-Delay"
		::= { bcmsplus1 282 }

bcms1-cb22-warning-time-delay
	OBJECT-TYPE
	SYNTAX  INTEGER
	ACCESS  read-write
	STATUS  mandatory
	DESCRIPTION "CB22 Warning-Time-Delay"
		::= { bcmsplus1 283 }
  
bcms1-cb23-warning-time-delay
	OBJECT-TYPE
	SYNTAX  INTEGER
	ACCESS  read-write
	STATUS  mandatory
	DESCRIPTION "CB23 Warning-Time-Delay"
		::= { bcmsplus1 284 }

bcms1-cb24-warning-time-delay
	OBJECT-TYPE
	SYNTAX  INTEGER
	ACCESS  read-write
	STATUS  mandatory
	DESCRIPTION "CB24 Warning-Time-Delay"
		::= { bcmsplus1 285 }

bcms1-cb25-warning-time-delay
	OBJECT-TYPE
	SYNTAX  INTEGER
	ACCESS  read-write
	STATUS  mandatory
	DESCRIPTION "CB25 Warning-Time-Delay"
		::= { bcmsplus1 286 }

bcms1-cb26-warning-time-delay
	OBJECT-TYPE
	SYNTAX  INTEGER
	ACCESS  read-write
	STATUS  mandatory
	DESCRIPTION "CB26 Warning-Time-Delay"
		::= { bcmsplus1 287 }

bcms1-cb27-warning-time-delay
	OBJECT-TYPE
	SYNTAX  INTEGER
	ACCESS  read-write
	STATUS  mandatory
	DESCRIPTION "CB27 Warning-Time-Delay"
		::= { bcmsplus1 288 }

bcms1-cb28-warning-time-delay
	OBJECT-TYPE
	SYNTAX  INTEGER
	ACCESS  read-write
	STATUS  mandatory
	DESCRIPTION "CB28 Warning-Time-Delay"
		::= { bcmsplus1 289 }

bcms1-cb29-warning-time-delay
	OBJECT-TYPE
	SYNTAX  INTEGER
	ACCESS  read-write
	STATUS  mandatory
	DESCRIPTION "CB29 Warning-Time-Delay"
		::= { bcmsplus1 290}

bcms1-cb30-warning-time-delay
	OBJECT-TYPE
	SYNTAX  INTEGER
	ACCESS  read-write
	STATUS  mandatory
	DESCRIPTION "CB30 Warning-Time-Delay"
		::= { bcmsplus1 291 }

bcms1-cb31-warning-time-delay
	OBJECT-TYPE
	SYNTAX  INTEGER
	ACCESS  read-write
	STATUS  mandatory
	DESCRIPTION "CB31 Warning-Time-Delay"
		::= { bcmsplus1 292 }

bcms1-cb32-warning-time-delay
	OBJECT-TYPE
	SYNTAX  INTEGER
	ACCESS  read-write
	STATUS  mandatory
	DESCRIPTION "CB32 Warning-Time-Delay"
		::= { bcmsplus1 293 }
  
bcms1-cb33-warning-time-delay
	OBJECT-TYPE
	SYNTAX  INTEGER
	ACCESS  read-write
	STATUS  mandatory
	DESCRIPTION "CB33 Warning-Time-Delay"
		::= { bcmsplus1 294 }

bcms1-cb34-warning-time-delay
	OBJECT-TYPE
	SYNTAX  INTEGER
	ACCESS  read-write
	STATUS  mandatory
	DESCRIPTION "CB34 Warning-Time-Delay"
		::= { bcmsplus1 295 }

bcms1-cb35-warning-time-delay
	OBJECT-TYPE
	SYNTAX  INTEGER
	ACCESS  read-write
	STATUS  mandatory
	DESCRIPTION "CB35 Warning-Time-Delay"
		::= { bcmsplus1 296 }

bcms1-cb36-warning-time-delay
	OBJECT-TYPE
	SYNTAX  INTEGER
	ACCESS  read-write
	STATUS  mandatory
	DESCRIPTION "CB36 Warning-Time-Delay"
		::= { bcmsplus1 297 }

bcms1-cb37-warning-time-delay
	OBJECT-TYPE
	SYNTAX  INTEGER
	ACCESS  read-write
	STATUS  mandatory
	DESCRIPTION "CB37 Warning-Time-Delay"
		::= { bcmsplus1 298 }

bcms1-cb38-warning-time-delay
	OBJECT-TYPE
	SYNTAX  INTEGER
	ACCESS  read-write
	STATUS  mandatory
	DESCRIPTION "CB38 Warning-Time-Delay"
		::= { bcmsplus1 299 }

bcms1-cb39-warning-time-delay
	OBJECT-TYPE
	SYNTAX  INTEGER
	ACCESS  read-write
	STATUS  mandatory
	DESCRIPTION "CB39 Warning-Time-Delay"
		::= { bcmsplus1 300 }

bcms1-cb40-warning-time-delay
	OBJECT-TYPE
	SYNTAX  INTEGER
	ACCESS  read-write
	STATUS  mandatory
	DESCRIPTION "CB40 Warning-Time-Delay"
		::= { bcmsplus1 301 }

bcms1-cb41-warning-time-delay
	OBJECT-TYPE
	SYNTAX  INTEGER
	ACCESS  read-write
	STATUS  mandatory
	DESCRIPTION "CB41 Warning-Time-Delay"
		::= { bcmsplus1 302 }

bcms1-cb42-warning-time-delay
	OBJECT-TYPE
	SYNTAX  INTEGER
	ACCESS  read-write
	STATUS  mandatory
	DESCRIPTION "CB42 Warning-Time-Delay"
		::= { bcmsplus1 303 }

bcms1-cb1-alarm-time-delay
	OBJECT-TYPE
	SYNTAX  INTEGER
	ACCESS  read-write
	STATUS  mandatory
	DESCRIPTION "CB1 Alarm-Time-Delay
		       Note for all alarm time delays 1-42: units are in seconds"                     
		::= { bcmsplus1 304 }

bcms1-cb2-alarm-time-delay
	OBJECT-TYPE
	SYNTAX  INTEGER
	ACCESS  read-write
	STATUS  mandatory
	DESCRIPTION "CB2 Alarm-Time-Delay"
		::= { bcmsplus1 305 }
  
bcms1-cb3-alarm-time-delay
	OBJECT-TYPE
	SYNTAX  INTEGER
	ACCESS  read-write
	STATUS  mandatory
	DESCRIPTION "CB3 Alarm-Time-Delay"
		::= { bcmsplus1 306 }

bcms1-cb4-alarm-time-delay
	OBJECT-TYPE
	SYNTAX  INTEGER
	ACCESS  read-write
	STATUS  mandatory
	DESCRIPTION "CB4 Alarm-Time-Delay"
		::= { bcmsplus1 307 }

bcms1-cb5-alarm-time-delay
	OBJECT-TYPE
	SYNTAX  INTEGER
	ACCESS  read-write
	STATUS  mandatory
	DESCRIPTION "CB5 Alarm-Time-Delay"
		::= { bcmsplus1 308 }

bcms1-cb6-alarm-time-delay
	OBJECT-TYPE
	SYNTAX  INTEGER
	ACCESS  read-write
	STATUS  mandatory
	DESCRIPTION "CB6 Alarm-Time-Delay"
		::= { bcmsplus1 309 }

bcms1-cb7-alarm-time-delay
	OBJECT-TYPE
	SYNTAX  INTEGER
	ACCESS  read-write
	STATUS  mandatory
	DESCRIPTION "CB7 Alarm-Time-Delay"
		::= { bcmsplus1 310 }

bcms1-cb8-alarm-time-delay
	OBJECT-TYPE
	SYNTAX  INTEGER
	ACCESS  read-write
	STATUS  mandatory
	DESCRIPTION "CB8 Alarm-Time-Delay"
		::= { bcmsplus1 311 }

bcms1-cb9-alarm-time-delay
	OBJECT-TYPE
	SYNTAX  INTEGER
	ACCESS  read-write
	STATUS  mandatory
	DESCRIPTION "CB9 Alarm-Time-Delay"
		::= { bcmsplus1 312 }

bcms1-cb10-alarm-time-delay
	OBJECT-TYPE
	SYNTAX  INTEGER
	ACCESS  read-write
	STATUS  mandatory
	DESCRIPTION "CB10 Alarm-Time-Delay"
		::= { bcmsplus1 313 }

bcms1-cb11-alarm-time-delay
	OBJECT-TYPE
	SYNTAX  INTEGER
	ACCESS  read-write
	STATUS  mandatory
	DESCRIPTION "CB11 Alarm-Time-Delay"
		::= { bcmsplus1 314 }

bcms1-cb12-alarm-time-delay
	OBJECT-TYPE
	SYNTAX  INTEGER
	ACCESS  read-write
	STATUS  mandatory
	DESCRIPTION "CB12 Alarm-Time-Delay"
		::= { bcmsplus1 315 }
  
bcms1-cb13-alarm-time-delay
	OBJECT-TYPE
	SYNTAX  INTEGER
	ACCESS  read-write
	STATUS  mandatory
	DESCRIPTION "CB13 Alarm-Time-Delay"
		::= { bcmsplus1 316 }

bcms1-cb14-alarm-time-delay
	OBJECT-TYPE
	SYNTAX  INTEGER
	ACCESS  read-write
	STATUS  mandatory
	DESCRIPTION "CB14 Alarm-Time-Delay"
		::= { bcmsplus1 317 }

bcms1-cb15-alarm-time-delay
	OBJECT-TYPE
	SYNTAX  INTEGER
	ACCESS  read-write
	STATUS  mandatory
	DESCRIPTION "CB15 Alarm-Time-Delay"
		::= { bcmsplus1 318 }

bcms1-cb16-alarm-time-delay
	OBJECT-TYPE
	SYNTAX  INTEGER
	ACCESS  read-write
	STATUS  mandatory
	DESCRIPTION "CB16 Alarm-Time-Delay"
		::= { bcmsplus1 319 }

bcms1-cb17-alarm-time-delay
	OBJECT-TYPE
	SYNTAX  INTEGER
	ACCESS  read-write
	STATUS  mandatory
	DESCRIPTION "CB17 Alarm-Time-Delay"
		::= { bcmsplus1 320 }

bcms1-cb18-alarm-time-delay
	OBJECT-TYPE
	SYNTAX  INTEGER
	ACCESS  read-write
	STATUS  mandatory
	DESCRIPTION "CB18 Alarm-Time-Delay"
		::= { bcmsplus1 321 }

bcms1-cb19-alarm-time-delay
	OBJECT-TYPE
	SYNTAX  INTEGER
	ACCESS  read-write
	STATUS  mandatory
	DESCRIPTION "CB19 Alarm-Time-Delay"
		::= { bcmsplus1 322 }

bcms1-cb20-alarm-time-delay
	OBJECT-TYPE
	SYNTAX  INTEGER
	ACCESS  read-write
	STATUS  mandatory
	DESCRIPTION "CB20 Alarm-Time-Delay"
		::= { bcmsplus1 323 }

bcms1-cb21-alarm-time-delay
	OBJECT-TYPE
	SYNTAX  INTEGER
	ACCESS  read-write
	STATUS  mandatory
	DESCRIPTION "CB21 Alarm-Time-Delay"
		::= { bcmsplus1 324 }

bcms1-cb22-alarm-time-delay
	OBJECT-TYPE
	SYNTAX  INTEGER
	ACCESS  read-write
	STATUS  mandatory
	DESCRIPTION "CB22 Alarm-Time-Delay"
		::= { bcmsplus1 325 }
  
bcms1-cb23-alarm-time-delay
	OBJECT-TYPE
	SYNTAX  INTEGER
	ACCESS  read-write
	STATUS  mandatory
	DESCRIPTION "CB23 Alarm-Time-Delay"
		::= { bcmsplus1 326 }

bcms1-cb24-alarm-time-delay
	OBJECT-TYPE
	SYNTAX  INTEGER
	ACCESS  read-write
	STATUS  mandatory
	DESCRIPTION "CB24 Alarm-Time-Delay"
		::= { bcmsplus1 327 }

bcms1-cb25-alarm-time-delay
	OBJECT-TYPE
	SYNTAX  INTEGER
	ACCESS  read-write
	STATUS  mandatory
	DESCRIPTION "CB25 Alarm-Time-Delay"
		::= { bcmsplus1 328 }

bcms1-cb26-alarm-time-delay
	OBJECT-TYPE
	SYNTAX  INTEGER
	ACCESS  read-write
	STATUS  mandatory
	DESCRIPTION "CB26 Alarm-Time-Delay"
		::= { bcmsplus1 329 }

bcms1-cb27-alarm-time-delay
	OBJECT-TYPE
	SYNTAX  INTEGER
	ACCESS  read-write
	STATUS  mandatory
	DESCRIPTION "CB27 Alarm-Time-Delay"
		::= { bcmsplus1 330 }

bcms1-cb28-alarm-time-delay
	OBJECT-TYPE
	SYNTAX  INTEGER
	ACCESS  read-write
	STATUS  mandatory
	DESCRIPTION "CB28 Alarm-Time-Delay"
		::= { bcmsplus1 331 }

bcms1-cb29-alarm-time-delay
	OBJECT-TYPE
	SYNTAX  INTEGER
	ACCESS  read-write
	STATUS  mandatory
	DESCRIPTION "CB29 Alarm-Time-Delay"
		::= { bcmsplus1 332 }

bcms1-cb30-alarm-time-delay
	OBJECT-TYPE
	SYNTAX  INTEGER
	ACCESS  read-write
	STATUS  mandatory
	DESCRIPTION "CB30 Alarm-Time-Delay"
		::= { bcmsplus1 333 }

bcms1-cb31-alarm-time-delay
	OBJECT-TYPE
	SYNTAX  INTEGER
	ACCESS  read-write
	STATUS  mandatory
	DESCRIPTION "CB31 Alarm-Time-Delay"
		::= { bcmsplus1 334 }

bcms1-cb32-alarm-time-delay
	OBJECT-TYPE
	SYNTAX  INTEGER
	ACCESS  read-write
	STATUS  mandatory
	DESCRIPTION "CB32 Alarm-Time-Delay"
		::= { bcmsplus1 335 }
  
bcms1-cb33-alarm-time-delay
	OBJECT-TYPE
	SYNTAX  INTEGER
	ACCESS  read-write
	STATUS  mandatory
	DESCRIPTION "CB33 Alarm-Time-Delay"
		::= { bcmsplus1 336 }

bcms1-cb34-alarm-time-delay
	OBJECT-TYPE
	SYNTAX  INTEGER
	ACCESS  read-write
	STATUS  mandatory
	DESCRIPTION "CB34 Alarm-Time-Delay"
		::= { bcmsplus1 337 }

bcms1-cb35-alarm-time-delay
	OBJECT-TYPE
	SYNTAX  INTEGER
	ACCESS  read-write
	STATUS  mandatory
	DESCRIPTION "CB35 Alarm-Time-Delay"
		::= { bcmsplus1 338 }

bcms1-cb36-alarm-time-delay
	OBJECT-TYPE
	SYNTAX  INTEGER
	ACCESS  read-write
	STATUS  mandatory
	DESCRIPTION "CB36 Alarm-Time-Delay"
		::= { bcmsplus1 339 }

bcms1-cb37-alarm-time-delay
	OBJECT-TYPE
	SYNTAX  INTEGER
	ACCESS  read-write
	STATUS  mandatory
	DESCRIPTION "CB37 Alarm-Time-Delay"
		::= { bcmsplus1 340 }

bcms1-cb38-alarm-time-delay
	OBJECT-TYPE
	SYNTAX  INTEGER
	ACCESS  read-write
	STATUS  mandatory
	DESCRIPTION "CB38 Alarm-Time-Delay"
		::= { bcmsplus1 341 }

bcms1-cb39-alarm-time-delay
	OBJECT-TYPE
	SYNTAX  INTEGER
	ACCESS  read-write
	STATUS  mandatory
	DESCRIPTION "CB39 Alarm-Time-Delay"
		::= { bcmsplus1 342 }

bcms1-cb40-alarm-time-delay
	OBJECT-TYPE
	SYNTAX  INTEGER
	ACCESS  read-write
	STATUS  mandatory
	DESCRIPTION "CB40 Alarm-Time-Delay"
		::= { bcmsplus1 343 }

bcms1-cb41-alarm-time-delay
	OBJECT-TYPE
	SYNTAX  INTEGER
	ACCESS  read-write
	STATUS  mandatory
	DESCRIPTION "CB41 Alarm-Time-Delay"
		::= { bcmsplus1 344 }

bcms1-cb42-alarm-time-delay
	OBJECT-TYPE
	SYNTAX  INTEGER
	ACCESS  read-write
	STATUS  mandatory
	DESCRIPTION "CB42 Alarm-Time-Delay"
		::= { bcmsplus1 345 }

bcms1-global-breaker-size
	OBJECT-TYPE
	SYNTAX  INTEGER
	ACCESS  read-write
	STATUS  mandatory
	DESCRIPTION "Global-breaker-size
		     Note for global breaker size: 10 = 10 amps
                     Range is 10 to 100 amps"
		::= { bcmsplus1 346 }

bcms1-global-warning-threshold
	OBJECT-TYPE
	SYNTAX  INTEGER
	ACCESS  read-write
	STATUS  mandatory
	DESCRIPTION "Global-warning-threshold
		     Note for global warning threshold: 70 = 70% of breaker size
                     range is 0-100%"
		::= { bcmsplus1 347 }

bcms1-global-alarm-threshold
	OBJECT-TYPE
	SYNTAX  INTEGER
	ACCESS  read-write
	STATUS  mandatory
	DESCRIPTION "Global-alarm-threshold
		     Note for global alarm threshold: 80 = 80% of breaker size
                     range is 0-100%"
		::= { bcmsplus1 348 }

bcms1-global-warning-time-delay
	OBJECT-TYPE
	SYNTAX  INTEGER
	ACCESS  read-write
	STATUS  mandatory
	DESCRIPTION "Global-warning-time-delay
		     Note for global warning time delay: units are in seconds"                     
		::= { bcmsplus1 349 }

bcms1-global-alarm-time-delay
	OBJECT-TYPE
	SYNTAX  INTEGER
	ACCESS  read-write
	STATUS  mandatory
	DESCRIPTION "Global-alarm-time-delay
		     Note for global alarm time delay: units are in seconds"                     
		::= { bcmsplus1 350 }

bcms1-min-max-reset
	OBJECT-TYPE
	SYNTAX  INTEGER
	ACCESS  read-write
	STATUS  mandatory
	DESCRIPTION "Min-max-Reset
                     Note for Min-max Reset: writing to this register will clear minimum
		     and maximum current values"
		::= { bcmsplus1 351 }

bcms1-global-warning-alarm-register
	OBJECT-TYPE
	SYNTAX  INTEGER
	ACCESS  read-only
	STATUS  mandatory
	DESCRIPTION "Global-Warning-Alarm-Register
			bit 0:	Warning Register 1
			bit 1:	Warning Register 2
			bit 2:	Warning Register 3
			bit 3:	Alarm Register 1
			bit 4:	Alarm Register 2
			bit 5:	Alarm Register 3
			bit 6:	Zero Current Register 1
			bit 7:	Zero Current Register 2
			bit 8:	Zero Current Register 3
			bits 9 – 15: Always read as 0"
		::= { bcmsplus1 352 }

bcms1-meter-alarm-status-latching
	OBJECT-TYPE
	SYNTAX  INTEGER
	ACCESS  read-write
	STATUS  mandatory
	DESCRIPTION "Meter-Alarm-Status-Latching
			bit 0:	Over Current panelboard
			bit 1:	Under Current panelboard
			bit 2: 	Over Current both panelboards 
			bit 3: 	Under Current both panelboards
			bit 4: 	Over Voltage main
			bit 5: 	Under Voltage main
			bit 6: 	Over Voltage alternate
			bit 7: 	Under Voltage alternate
			bits 8 – 15: Not Used"
		::= { bcmsplus1 353 }

bcms1-meter-alarm-status-nonlatching
	OBJECT-TYPE
	SYNTAX  INTEGER
	ACCESS  read-only
	STATUS  mandatory
	DESCRIPTION "Meter-Alarm-Status-Nonlatching
			bit 0:	Over Current panelboard
			bit 1:	Under Current panelboard
			bit 2: 	Over Current both panelboards 
			bit 3: 	Under Current both panelboards
			bit 4: 	Over Voltage main
			bit 5: 	Under Voltage main
			bit 6: 	Over Voltage alternate
			bit 7: 	Under Voltage alternate
			bits 8 – 15: Not Used"
		::= { bcmsplus1 354 }

bcms1-digital-alarm-status
	OBJECT-TYPE
	SYNTAX  INTEGER
	ACCESS  read-only
	STATUS  mandatory
	DESCRIPTION "Digital-Alarm-Status
			bit 0:	Digital alarm 1
			bit 1:	Digital alarm 2
			bit 2: 	Digital alarm 3
			bit 3: 	Digital alarm 4
			bits 4 – 15: Not Used"
		::= { bcmsplus1 355 }

bcms1-current-option-setting
	OBJECT-TYPE
	SYNTAX  INTEGER
	ACCESS  read-only
	STATUS  mandatory
	DESCRIPTION "Current-Option-Setting
			bit 0:	option 0
			bit 1:	option 1
			bit 2: 	option 2 
			bit 3: 	neutral CTs
			bit 4:	no branch CTs
		     Option 0: no main or panelboard CTs. 	(357-359 summation of branch)
								(367-376 not used)
		     Option 1: CTs on main input feeding both panelboards. 
								(357-359 summation of branch)
		     Option 2: CTs on each panel board. 	(367-376 summation of panelboard 1 and 2) 
		     Note: Neutral current monitoring is optional."
		::= { bcmsplus1 356 }

bcms1-current-phase-a-panelboard
	OBJECT-TYPE
	SYNTAX  INTEGER
	ACCESS  read-only
	STATUS  mandatory
	DESCRIPTION "Current-Phase-A-Panelboard
                     Note for all currents: 100 = 10.0 amps"
		::= { bcmsplus1 357 }

bcms1-current-phase-b-panelboard
	OBJECT-TYPE
	SYNTAX  INTEGER
	ACCESS  read-only
	STATUS  mandatory
	DESCRIPTION "Current-Phase-B-Panelboard"
		::= { bcmsplus1 358 }

bcms1-current-phase-c-panelboard
	OBJECT-TYPE
	SYNTAX  INTEGER
	ACCESS  read-only
	STATUS  mandatory
	DESCRIPTION "Current-Phase-C-Panelboard"
		::= { bcmsplus1 359 }

bcms1-current-neutral-panelboard
	OBJECT-TYPE
	SYNTAX  INTEGER
	ACCESS  read-only
	STATUS  mandatory
	DESCRIPTION "Current-Neutral-Panelboard"
		::= { bcmsplus1 360 }


bcms1-over-current-alarm-threshhold-pnlbd
	OBJECT-TYPE
	SYNTAX  INTEGER
	ACCESS  read-write
	STATUS  mandatory
	DESCRIPTION "Over-Current-Alarm-Threshhold-Pnlbd"
		::= { bcmsplus1 361 }

bcms1-under-current-alarm-threshhold-pnlbd
	OBJECT-TYPE
	SYNTAX  INTEGER
	ACCESS  read-write
	STATUS  mandatory
	DESCRIPTION "Under-Current-Alarm-Threshhold-Pnlbd"
		::= { bcmsplus1 362 }

bcms1-over-current-set-counter-pnlbd
	OBJECT-TYPE
	SYNTAX  INTEGER
	ACCESS  read-only
	STATUS  mandatory
	DESCRIPTION "Over-Current-Set-Counter-Pnlbd
		     Note for all counters:
                     The set counter is incremented when the value goes outside the threshold limit
                     The reset counter is incremented when the value is returns to  the threshold limit"
		::= { bcmsplus1 363 }

bcms1-over-current-reset-counter-pnlbd
	OBJECT-TYPE
	SYNTAX  INTEGER
	ACCESS  read-only
	STATUS  mandatory
	DESCRIPTION "Over-Current-Reset-Counter-Pnlbd"
		::= { bcmsplus1 364 }

bcms1-under-current-set-counter-pnlbd
	OBJECT-TYPE
	SYNTAX  INTEGER
	ACCESS  read-only
	STATUS  mandatory
	DESCRIPTION "Under-Current-Set-Counter-Pnlbd"
		::= { bcmsplus1 365 }

bcms1-under-current-reset-counter-pnlbd
	OBJECT-TYPE
	SYNTAX  INTEGER
	ACCESS  read-only
	STATUS  mandatory
	DESCRIPTION "Under-Current-Reset-Counter-Pnlbd"
		::= { bcmsplus1 366 }

bcms1-current-phase-a-both-pnlbd
	OBJECT-TYPE
	SYNTAX  INTEGER
	ACCESS  read-only
	STATUS  mandatory
	DESCRIPTION "Current-Phase-A-Both-Pnlbd"
		::= { bcmsplus1 367 }

bcms1-current-phase-b-both-pnlbd
	OBJECT-TYPE
	SYNTAX  INTEGER
	ACCESS  read-only
	STATUS  mandatory
	DESCRIPTION "Current-Phase-B-Both-Pnlbd"
		::= { bcmsplus1 368 }

bcms1-current-phase-c-both-pnlbd
	OBJECT-TYPE
	SYNTAX  INTEGER
	ACCESS  read-only
	STATUS  mandatory
	DESCRIPTION "Current-Phase-C-Both-Pnlbd"
		::= { bcmsplus1 369 }

bcms1-current-neutral-both-pnlbd
	OBJECT-TYPE
	SYNTAX  INTEGER
	ACCESS  read-only
	STATUS  mandatory
	DESCRIPTION "Current-Neutral-Both-Pnlbd"
		::= { bcmsplus1 370 }


bcms1-over-current-alarm-threshhold-both-pnlbd
	OBJECT-TYPE
	SYNTAX  INTEGER
	ACCESS  read-write
	STATUS  mandatory
	DESCRIPTION "Over-Current-Alarm-Threshhold-Both-Pnlbd"
		::= { bcmsplus1 371 }

bcms1-under-current-alarm-threshhold-both-pnlbd
	OBJECT-TYPE
	SYNTAX  INTEGER
	ACCESS  read-write
	STATUS  mandatory
	DESCRIPTION "Under-Current-Alarm-Threshhold-Both-Pnlbd"
		::= { bcmsplus1 372 }

bcms1-over-current-set-counter-both-pnlbd
	OBJECT-TYPE
	SYNTAX  INTEGER
	ACCESS  read-only
	STATUS  mandatory
	DESCRIPTION "Over-Current-Set-Counter-Both-Pnlbd"
		::= { bcmsplus1 373 }

bcms1-over-current-reset-counter-both-pnlbd
	OBJECT-TYPE
	SYNTAX  INTEGER
	ACCESS  read-only
	STATUS  mandatory
	DESCRIPTION "Over-Current-Reset-Counter-Both-Pnlbd"
		::= { bcmsplus1 374 }

bcms1-under-current-set-counter-both-pnlbd
	OBJECT-TYPE
	SYNTAX  INTEGER
	ACCESS  read-only
	STATUS  mandatory
	DESCRIPTION "Under-Current-Set-Counter-Both-Pnlbd"
		::= { bcmsplus1 375 }

bcms1-under-current-reset-counter-both-pnlbd
	OBJECT-TYPE
	SYNTAX  INTEGER
	ACCESS  read-only
	STATUS  mandatory
	DESCRIPTION "Under-Current-Reset-Counter-Both-Pnlbd"
		::= { bcmsplus1 376 }

bcms1-voltage-option-setting
	OBJECT-TYPE
	SYNTAX  INTEGER
	ACCESS  read-only
	STATUS  mandatory
	DESCRIPTION "Voltage-Option-Setting
			bit 0:	option 0
			bit 1:	option 1
			bit 2: 	option 2 
			bit 3: 	option 3 
			bits 4 – 15: Not Used
                     Option 0: no voltage monitoring. (378-414 not used)
                     Option 1: One voltage feeding 1 or 2 panel boards. (390-401 not used)
                     Option 2: One voltage feeding panelboard 1 and another feeding panelboard 2. (390-401 not used)
                     Option 3: Two voltages tied together through interlocked circuit breakers feeding both panelboards. 
                               Digital input 1 and 2 are used to determine which is feeding the panelboard. A set bit 
                               indicated closed.  If both are closed, main voltage is used."
		::= { bcmsplus1 377 }

bcms1-voltage-a-b-main
	OBJECT-TYPE
	SYNTAX  INTEGER
	ACCESS  read-only
	STATUS  mandatory
	DESCRIPTION "Voltage-A-B-Main
                     Note for all voltages: 1200 = 120.0 volts"
		::= { bcmsplus1 378 }

bcms1-voltage-b-c-main
	OBJECT-TYPE
	SYNTAX  INTEGER
	ACCESS  read-only
	STATUS  mandatory
	DESCRIPTION "Voltage-B-C-Main"
		::= { bcmsplus1 379 }

bcms1-voltage-c-a-main
	OBJECT-TYPE
	SYNTAX  INTEGER
	ACCESS  read-only
	STATUS  mandatory
	DESCRIPTION "Voltage-C-A-Main"
		::= { bcmsplus1 380 }

bcms1-voltage-a-n-main
	OBJECT-TYPE
	SYNTAX  INTEGER
	ACCESS  read-only
	STATUS  mandatory
	DESCRIPTION "Voltage-A-N-Main"
		::= { bcmsplus1 381 }

bcms1-voltage-b-n-main
	OBJECT-TYPE
	SYNTAX  INTEGER
	ACCESS  read-only
	STATUS  mandatory
	DESCRIPTION "Voltage-B-N-Main"
		::= { bcmsplus1 382 }

bcms1-voltage-c-n-main
	OBJECT-TYPE
	SYNTAX  INTEGER
	ACCESS  read-only
	STATUS  mandatory
	DESCRIPTION "Voltage-C-N-Main"
		::= { bcmsplus1 383 }

bcms1-over-voltage-alarm-threshhold-main
	OBJECT-TYPE
	SYNTAX  INTEGER
	ACCESS  read-write
	STATUS  mandatory
	DESCRIPTION "Over-Voltage-Alarm-Threshhold-Main
                     Note All Over and Under Voltage is for L-L values"
		::= { bcmsplus1 384 }

bcms1-under-voltage-alarm-threshhold-main
	OBJECT-TYPE
	SYNTAX  INTEGER
	ACCESS  read-write
	STATUS  mandatory
	DESCRIPTION "Under-Voltage-Alarm-Threshhold-Main"
		::= { bcmsplus1 385 }

bcms1-over-voltage-set-counter-main
	OBJECT-TYPE
	SYNTAX  INTEGER
	ACCESS  read-only
	STATUS  mandatory
	DESCRIPTION "Over-Voltage-Set-Counter-Main"
		::= { bcmsplus1 386 }

bcms1-over-voltage-reset-counter-main
	OBJECT-TYPE
	SYNTAX  INTEGER
	ACCESS  read-only
	STATUS  mandatory
	DESCRIPTION "Over-Voltage-Reset-Counter-Main"
		::= { bcmsplus1 387 }

bcms1-under-voltage-set-counter-main
	OBJECT-TYPE
	SYNTAX  INTEGER
	ACCESS  read-only
	STATUS  mandatory
	DESCRIPTION "Under-Voltage-Set-Counter-Main"
		::= { bcmsplus1 388 }

bcms1-under-voltage-reset-counter-main
	OBJECT-TYPE
	SYNTAX  INTEGER
	ACCESS  read-only
	STATUS  mandatory
	DESCRIPTION "Under-Voltage-Reset-Counter-Main"
		::= { bcmsplus1 389 }


bcms1-voltage-frequency-main
	OBJECT-TYPE
	SYNTAX  INTEGER
	ACCESS  read-only
	STATUS  mandatory
	DESCRIPTION "Voltage-Frequency-Main
                     note for frequency: 600 = 60.0Hz
                     Range is 40-70Hz
                     Note if insufficient voltage is present frequency will read 0xFFFF"
		::= { bcmsplus1 390 }

bcms1-voltage-a-b-alternate
	OBJECT-TYPE
	SYNTAX  INTEGER
	ACCESS  read-only
	STATUS  mandatory
	DESCRIPTION "Voltage-A-B-Alternate"
		::= { bcmsplus1 391 }

bcms1-voltage-b-c-alternate
	OBJECT-TYPE
	SYNTAX  INTEGER
	ACCESS  read-only
	STATUS  mandatory
	DESCRIPTION "Voltage-B-C-Alternate"
		::= { bcmsplus1 392 }

bcms1-voltage-c-a-alternate
	OBJECT-TYPE
	SYNTAX  INTEGER
	ACCESS  read-only
	STATUS  mandatory
	DESCRIPTION "Voltage-C-A-Alternate"
		::= { bcmsplus1 393 }

bcms1-voltage-a-n-alternate
	OBJECT-TYPE
	SYNTAX  INTEGER
	ACCESS  read-only
	STATUS  mandatory
	DESCRIPTION "Voltage-A-N-Alternate"
		::= { bcmsplus1 394 }

bcms1-voltage-b-N-alternate
	OBJECT-TYPE
	SYNTAX  INTEGER
	ACCESS  read-only
	STATUS  mandatory
	DESCRIPTION "Voltage-B-N-Alternate"
		::= { bcmsplus1 395 }

bcms1-voltage-c-n-alternate
	OBJECT-TYPE
	SYNTAX  INTEGER
	ACCESS  read-only
	STATUS  mandatory
	DESCRIPTION "Voltage-C-N-Alternate"
		::= { bcmsplus1 396 }

bcms1-over-voltage-alarm-threshhold-alternate
	OBJECT-TYPE
	SYNTAX  INTEGER
	ACCESS  read-write
	STATUS  mandatory
	DESCRIPTION "Over-Voltage-Alarm-Threshhold-Alternate"
		::= { bcmsplus1 397 }

bcms1-under-voltage-alarm-threshhold-alternate
	OBJECT-TYPE
	SYNTAX  INTEGER
	ACCESS  read-write
	STATUS  mandatory
	DESCRIPTION "Under-Voltage-Alarm-Threshhold-Alternate"
		::= { bcmsplus1 398 }

bcms1-over-voltage-set-counter-alternate
	OBJECT-TYPE
	SYNTAX  INTEGER
	ACCESS  read-only
	STATUS  mandatory
	DESCRIPTION "Over-Voltage-Set-Counter-Alternate"
		::= { bcmsplus1 399 }

bcms1-over-voltage-reset-counter-alternate
	OBJECT-TYPE
	SYNTAX  INTEGER
	ACCESS  read-only
	STATUS  mandatory
	DESCRIPTION "Over-Voltage-Reset-Counter-Alternate"
		::= { bcmsplus1 400 }

bcms1-under-voltage-set-counter-alternate
	OBJECT-TYPE
	SYNTAX  INTEGER
	ACCESS  read-only
	STATUS  mandatory
	DESCRIPTION "Under-Voltage-Set-Counter-Alternate"
		::= { bcmsplus1 401 }

bcms1-under-voltage-reset-counter-alternate
	OBJECT-TYPE
	SYNTAX  INTEGER
	ACCESS  read-only
	STATUS  mandatory
	DESCRIPTION "Under-Voltage-Reset-Counter-Alternate"
		::= { bcmsplus1 402 }

bcms1-real-power-kw
	OBJECT-TYPE
	SYNTAX  INTEGER
	ACCESS  read-only
	STATUS  mandatory
	DESCRIPTION "Real-Power-KW
                     Note for all KWs: 100 = 10.0 KW"
		::= { bcmsplus1 403 }

bcms1-peal-power-phase-a
	OBJECT-TYPE
	SYNTAX  INTEGER
	ACCESS  read-only
	STATUS  mandatory
	DESCRIPTION "Real-Power-Phase-A"
		::= { bcmsplus1 404 }

bcms1-real-power-phase-b
	OBJECT-TYPE
	SYNTAX  INTEGER
	ACCESS  read-only
	STATUS  mandatory
	DESCRIPTION "Real-Power-Phase-B"
		::= { bcmsplus1 405 }

bcms1-real-power-phase-c
	OBJECT-TYPE
	SYNTAX  INTEGER
	ACCESS  read-only
	STATUS  mandatory
	DESCRIPTION "Real-Power-Phase-C"
		::= { bcmsplus1 406 }

bcms1-reactive-power-kvar
	OBJECT-TYPE
	SYNTAX  INTEGER
	ACCESS  read-only
	STATUS  mandatory
	DESCRIPTION "Reactive-Power-KVAR
                     Note for KVAR: 100 = 10.0 KVAR"
		::= { bcmsplus1 407 }

bcms1-apparent-Power-kva
	OBJECT-TYPE
	SYNTAX  INTEGER
	ACCESS  read-only
	STATUS  mandatory
	DESCRIPTION "Apparent-Power-KVA
                     Note for KVA: 100 = 10.0 KVA"
		::= { bcmsplus1 408 }

bcms1-total-power-factor
	OBJECT-TYPE
	SYNTAX  INTEGER
	ACCESS  read-only
	STATUS  mandatory
	DESCRIPTION "Total-Power-Factor
                     Note for all Power Factor: 1000 = 100.0 PF"
		::= { bcmsplus1 409 }

bcms1-power-factor-phase-a
	OBJECT-TYPE
	SYNTAX  INTEGER
	ACCESS  read-only
	STATUS  mandatory
	DESCRIPTION "Power-Factor-Phase-A"
		::= { bcmsplus1 410 }

bcms1-Power-factor-phase-b
	OBJECT-TYPE
	SYNTAX  INTEGER
	ACCESS  read-only
	STATUS  mandatory
	DESCRIPTION "Power-Factor-Phase-B"
		::= { bcmsplus1 411 }

bcms1-Power-factor-phase-c
	OBJECT-TYPE
	SYNTAX  INTEGER
	ACCESS  read-only
	STATUS  mandatory
	DESCRIPTION "Power-Factor-Phase-C"
		::= { bcmsplus1 412 }

bcms1-energy-consumption-kwh-lower-word-integer
	OBJECT-TYPE
	SYNTAX  INTEGER
	ACCESS  read-write
	STATUS  mandatory
	DESCRIPTION "Energy-Consumption-KWh-Lower-Word-Integer
		     Note for KWh: 100 = 100KWh
                     Combine lower and upper integers into a word for total KWh"
		::= { bcmsplus1 413 }

bcms1-energy-consumption-kwh-upper-word-integer
	OBJECT-TYPE
	SYNTAX  INTEGER
	ACCESS  read-write
	STATUS  mandatory
	DESCRIPTION "Energy-Consumption-KWh-Upper-Word-Integer"
		::= { bcmsplus1 414 }

bcms1-main-voltage-thd-phase-a
	OBJECT-TYPE
	SYNTAX  INTEGER
	ACCESS  read-only
	STATUS  mandatory
	DESCRIPTION "Main-Voltage-THD-Phase-A"
		::= { bcmsplus1 415 }

bcms1-main-voltage-thd-phase-b
	OBJECT-TYPE
	SYNTAX  INTEGER
	ACCESS  read-only
	STATUS  mandatory
	DESCRIPTION "Main-Voltage-THD-Phase-B"
		::= { bcmsplus1 416 }

bcms1-main-voltage-thd-phase-c
	OBJECT-TYPE
	SYNTAX  INTEGER
	ACCESS  read-only
	STATUS  mandatory
	DESCRIPTION "Main-Voltage-THD-Phase-C"
		::= { bcmsplus1 417 }

bcms1-alt-voltage-thd-phase-a
	OBJECT-TYPE
	SYNTAX  INTEGER
	ACCESS  read-only
	STATUS  mandatory
	DESCRIPTION "Alt-Voltage-THD-Phase-A"
		::= { bcmsplus1 418 }

bcms1-alt-voltage-thd-phase-b
	OBJECT-TYPE
	SYNTAX  INTEGER
	ACCESS  read-only
	STATUS  mandatory
	DESCRIPTION "Alt-Voltage-THD-Phase-B"
		::= { bcmsplus1 419 }

bcms1-alt-voltage-thd-phase-c
	OBJECT-TYPE
	SYNTAX  INTEGER
	ACCESS  read-only
	STATUS  mandatory
	DESCRIPTION "Alt-Voltage-THD-Phase-C"
		::= { bcmsplus1 420 }

bcms1-current-ground-panelboard
	OBJECT-TYPE
	SYNTAX  INTEGER
	ACCESS  read-only
	STATUS  mandatory
	DESCRIPTION "Current-Ground-Panelboard"
		::= { bcmsplus1 421 }

bcms1-percent-load-phase-a
	OBJECT-TYPE
	SYNTAX  INTEGER
	ACCESS  read-only
	STATUS  mandatory
	DESCRIPTION "Percent Load Phase A"
		::= { bcmsplus1 422 }

bcms1-percent-load-phase-b
	OBJECT-TYPE
	SYNTAX  INTEGER
	ACCESS  read-only
	STATUS  mandatory
	DESCRIPTION "Percent Load Phase B"
		::= { bcmsplus1 423 }

bcms1-percent-load-phase-c
	OBJECT-TYPE
	SYNTAX  INTEGER
	ACCESS  read-only
	STATUS  mandatory
	DESCRIPTION "Percent Load Phase C"
		::= { bcmsplus1 424 }

bcms1-full-load-current
	OBJECT-TYPE
	SYNTAX  INTEGER
	ACCESS  read-write
	STATUS  mandatory
	DESCRIPTION "Full Load Current"
		::= { bcmsplus1 425 }

--------------------------------------------------------------------------------
-- BCMSPLUS register values
--------------------------------------------------------------------------------

bcms2-cb1-current
	OBJECT-TYPE
	SYNTAX  INTEGER
	ACCESS  read-only
	STATUS  mandatory
	DESCRIPTION "CB1 Current
		     Note for all currents 1-42: 100 = 10.0 amps"
		::= { bcmsplus2 1 }
  
bcms2-cb2-current
	OBJECT-TYPE
	SYNTAX  INTEGER
	ACCESS  read-only
	STATUS  mandatory
	DESCRIPTION "CB2 Current"
		::= { bcmsplus2 2 }

bcms2-cb3-current
	OBJECT-TYPE
	SYNTAX  INTEGER
	ACCESS  read-only
	STATUS  mandatory
	DESCRIPTION "CB3 Current"
		::= { bcmsplus2 3 }

bcms2-cb4-current
	OBJECT-TYPE
	SYNTAX  INTEGER
	ACCESS  read-only
	STATUS  mandatory
	DESCRIPTION "CB4 Current"
		::= { bcmsplus2 4 }

bcms2-cb5-current
	OBJECT-TYPE
	SYNTAX  INTEGER
	ACCESS  read-only
	STATUS  mandatory
	DESCRIPTION "CB5 Current"
		::= { bcmsplus2 5 }

bcms2-cb6-current
	OBJECT-TYPE
	SYNTAX  INTEGER
	ACCESS  read-only
	STATUS  mandatory
	DESCRIPTION "CB6 Current"
		::= { bcmsplus2 6 }

bcms2-cb7-current
	OBJECT-TYPE
	SYNTAX  INTEGER
	ACCESS  read-only
	STATUS  mandatory
	DESCRIPTION "CB7 Current"
		::= { bcmsplus2 7 }

bcms2-cb8-current
	OBJECT-TYPE
	SYNTAX  INTEGER
	ACCESS  read-only
	STATUS  mandatory
	DESCRIPTION "CB8 Current"
		::= { bcmsplus2 8 }

bcms2-cb9-current
	OBJECT-TYPE
	SYNTAX  INTEGER
	ACCESS  read-only
	STATUS  mandatory
	DESCRIPTION "CB9 Current"
		::= { bcmsplus2 9 }

bcms2-cb10-current
	OBJECT-TYPE
	SYNTAX  INTEGER
	ACCESS  read-only
	STATUS  mandatory
	DESCRIPTION "CB10 Current"
		::= { bcmsplus2 10 }

bcms2-cb11-current
	OBJECT-TYPE
	SYNTAX  INTEGER
	ACCESS  read-only
	STATUS  mandatory
	DESCRIPTION "CB11 Current"
		::= { bcmsplus2 11 }
  
bcms2-cb12-current
	OBJECT-TYPE
	SYNTAX  INTEGER
	ACCESS  read-only
	STATUS  mandatory
	DESCRIPTION "CB12 Current"
		::= { bcmsplus2 12 }

bcms2-cb13-current
	OBJECT-TYPE
	SYNTAX  INTEGER
	ACCESS  read-only
	STATUS  mandatory
	DESCRIPTION "CB13 Current"
		::= { bcmsplus2 13 }

bcms2-cb14-current
	OBJECT-TYPE
	SYNTAX  INTEGER
	ACCESS  read-only
	STATUS  mandatory
	DESCRIPTION "CB14 Current"
		::= { bcmsplus2 14 }

bcms2-cb15-current
	OBJECT-TYPE
	SYNTAX  INTEGER
	ACCESS  read-only
	STATUS  mandatory
	DESCRIPTION "CB15 Current"
		::= { bcmsplus2 15 }

bcms2-cb16-current
	OBJECT-TYPE
	SYNTAX  INTEGER
	ACCESS  read-only
	STATUS  mandatory
	DESCRIPTION "CB16 Current"
		::= { bcmsplus2 16 }

bcms2-cb17-current
	OBJECT-TYPE
	SYNTAX  INTEGER
	ACCESS  read-only
	STATUS  mandatory
	DESCRIPTION "CB17 Current"
		::= { bcmsplus2 17 }

bcms2-cb18-current
	OBJECT-TYPE
	SYNTAX  INTEGER
	ACCESS  read-only
	STATUS  mandatory
	DESCRIPTION "CB18 Current"
		::= { bcmsplus2 18 }

bcms2-cb19-current
	OBJECT-TYPE
	SYNTAX  INTEGER
	ACCESS  read-only
	STATUS  mandatory
	DESCRIPTION "CB19 Current"
		::= { bcmsplus2 19 }

bcms2-cb20-current
	OBJECT-TYPE
	SYNTAX  INTEGER
	ACCESS  read-only
	STATUS  mandatory
	DESCRIPTION "CB20 Current"
		::= { bcmsplus2 20 }

bcms2-cb21-current
	OBJECT-TYPE
	SYNTAX  INTEGER
	ACCESS  read-only
	STATUS  mandatory
	DESCRIPTION "CB21 Current"
		::= { bcmsplus2 21 }
  
bcms2-cb22-current
	OBJECT-TYPE
	SYNTAX  INTEGER
	ACCESS  read-only
	STATUS  mandatory
	DESCRIPTION "CB22 Current"
		::= { bcmsplus2 22 }

bcms2-cb23-current
	OBJECT-TYPE
	SYNTAX  INTEGER
	ACCESS  read-only
	STATUS  mandatory
	DESCRIPTION "CB23 Current"
		::= { bcmsplus2 23 }

bcms2-cb24-current
	OBJECT-TYPE
	SYNTAX  INTEGER
	ACCESS  read-only
	STATUS  mandatory
	DESCRIPTION "CB24 Current"
		::= { bcmsplus2 24 }

bcms2-cb25-current
	OBJECT-TYPE
	SYNTAX  INTEGER
	ACCESS  read-only
	STATUS  mandatory
	DESCRIPTION "CB25 Current"
		::= { bcmsplus2 25 }

bcms2-cb26-current
	OBJECT-TYPE
	SYNTAX  INTEGER
	ACCESS  read-only
	STATUS  mandatory
	DESCRIPTION "CB26 Current"
		::= { bcmsplus2 26 }

bcms2-cb27-current
	OBJECT-TYPE
	SYNTAX  INTEGER
	ACCESS  read-only
	STATUS  mandatory
	DESCRIPTION "CB27 Current"
		::= { bcmsplus2 27 }

bcms2-cb28-current
	OBJECT-TYPE
	SYNTAX  INTEGER
	ACCESS  read-only
	STATUS  mandatory
	DESCRIPTION "CB28 Current"
		::= { bcmsplus2 28 }

bcms2-cb29-current
	OBJECT-TYPE
	SYNTAX  INTEGER
	ACCESS  read-only
	STATUS  mandatory
	DESCRIPTION "CB29 Current"
		::= { bcmsplus2 29 }

bcms2-cb30-current
	OBJECT-TYPE
	SYNTAX  INTEGER
	ACCESS  read-only
	STATUS  mandatory
	DESCRIPTION "CB30 Current"
		::= { bcmsplus2 30 }

bcms2-cb31-current
	OBJECT-TYPE
	SYNTAX  INTEGER
	ACCESS  read-only
	STATUS  mandatory
	DESCRIPTION "CB31 Current"
		::= { bcmsplus2 31 }
  
bcms2-cb32-current
	OBJECT-TYPE
	SYNTAX  INTEGER
	ACCESS  read-only
	STATUS  mandatory
	DESCRIPTION "CB32 Current"
		::= { bcmsplus2 32 }

bcms2-cb33-current
	OBJECT-TYPE
	SYNTAX  INTEGER
	ACCESS  read-only
	STATUS  mandatory
	DESCRIPTION "CB33 Current"
		::= { bcmsplus2 33 }

bcms2-cb34-current
	OBJECT-TYPE
	SYNTAX  INTEGER
	ACCESS  read-only
	STATUS  mandatory
	DESCRIPTION "CB34 Current"
		::= { bcmsplus2 34 }

bcms2-cb35-current
	OBJECT-TYPE
	SYNTAX  INTEGER
	ACCESS  read-only
	STATUS  mandatory
	DESCRIPTION "CB35 Current"
		::= { bcmsplus2 35 }

bcms2-cb36-current
	OBJECT-TYPE
	SYNTAX  INTEGER
	ACCESS  read-only
	STATUS  mandatory
	DESCRIPTION "CB36 Current"
		::= { bcmsplus2 36 }

bcms2-cb37-current
	OBJECT-TYPE
	SYNTAX  INTEGER
	ACCESS  read-only
	STATUS  mandatory
	DESCRIPTION "CB37 Current"
		::= { bcmsplus2 37 }

bcms2-cb38-current
	OBJECT-TYPE
	SYNTAX  INTEGER
	ACCESS  read-only
	STATUS  mandatory
	DESCRIPTION "CB38 Current"
		::= { bcmsplus2 38 }

bcms2-cb39-current
	OBJECT-TYPE
	SYNTAX  INTEGER
	ACCESS  read-only
	STATUS  mandatory
	DESCRIPTION "CB39 Current"
		::= { bcmsplus2 39 }

bcms2-cb40-current
	OBJECT-TYPE
	SYNTAX  INTEGER
	ACCESS  read-only
	STATUS  mandatory
	DESCRIPTION "CB40 Current"
		::= { bcmsplus2 40 }

bcms2-cb41-current
	OBJECT-TYPE
	SYNTAX  INTEGER
	ACCESS  read-only
	STATUS  mandatory
	DESCRIPTION "CB41 Current"
		::= { bcmsplus2 41 }
  
bcms2-cb42-current
	OBJECT-TYPE
	SYNTAX  INTEGER
	ACCESS  read-only
	STATUS  mandatory
	DESCRIPTION "CB42 Current"
		::= { bcmsplus2 42 }

bcms2-cb1-min
	OBJECT-TYPE
	SYNTAX  INTEGER
	ACCESS  read-only
	STATUS  mandatory
	DESCRIPTION "CB1 Min
		     Note for all minumum currents 1-42: 100 = 10.0 amps"
		::= { bcmsplus2 43 }

bcms2-cb2-min
	OBJECT-TYPE
	SYNTAX  INTEGER
	ACCESS  read-only
	STATUS  mandatory
	DESCRIPTION "CB2 Min"
		::= { bcmsplus2 44 }

bcms2-cb3-min
	OBJECT-TYPE
	SYNTAX  INTEGER
	ACCESS  read-only
	STATUS  mandatory
	DESCRIPTION "CB3 Min"
		::= { bcmsplus2 45 }

bcms2-cb4-min
	OBJECT-TYPE
	SYNTAX  INTEGER
	ACCESS  read-only
	STATUS  mandatory
	DESCRIPTION "CB4 Min"
		::= { bcmsplus2 46 }

bcms2-cb5-min
	OBJECT-TYPE
	SYNTAX  INTEGER
	ACCESS  read-only
	STATUS  mandatory
	DESCRIPTION "CB5 Min"
		::= { bcmsplus2 47 }

bcms2-cb6-min
	OBJECT-TYPE
	SYNTAX  INTEGER
	ACCESS  read-only
	STATUS  mandatory
	DESCRIPTION "CB6 Min"
		::= { bcmsplus2 48 }

bcms2-cb7-min
	OBJECT-TYPE
	SYNTAX  INTEGER
	ACCESS  read-only
	STATUS  mandatory
	DESCRIPTION "CB7 Min"
		::= { bcmsplus2 49 }

bcms2-cb8-min
	OBJECT-TYPE
	SYNTAX  INTEGER
	ACCESS  read-only
	STATUS  mandatory
	DESCRIPTION "CB8 Min"
		::= { bcmsplus2 50 }

bcms2-cb9-min
	OBJECT-TYPE
	SYNTAX  INTEGER
	ACCESS  read-only
	STATUS  mandatory
	DESCRIPTION "CB9 Min"
		::= { bcmsplus2 51 }
  
bcms2-cb10-min
	OBJECT-TYPE
	SYNTAX  INTEGER
	ACCESS  read-only
	STATUS  mandatory
	DESCRIPTION "CB10 Min"
		::= { bcmsplus2 52 }

bcms2-cb11-min
	OBJECT-TYPE
	SYNTAX  INTEGER
	ACCESS  read-only
	STATUS  mandatory
	DESCRIPTION "CB11 Min"
		::= { bcmsplus2 53 }

bcms2-cb12-min
	OBJECT-TYPE
	SYNTAX  INTEGER
	ACCESS  read-only
	STATUS  mandatory
	DESCRIPTION "CB12 Min"
		::= { bcmsplus2 54 }

bcms2-cb13-min
	OBJECT-TYPE
	SYNTAX  INTEGER
	ACCESS  read-only
	STATUS  mandatory
	DESCRIPTION "CB13 Min"
		::= { bcmsplus2 55 }

bcms2-cb14-min
	OBJECT-TYPE
	SYNTAX  INTEGER
	ACCESS  read-only
	STATUS  mandatory
	DESCRIPTION "CB14 Min"
		::= { bcmsplus2 56 }

bcms2-cb15-min
	OBJECT-TYPE
	SYNTAX  INTEGER
	ACCESS  read-only
	STATUS  mandatory
	DESCRIPTION "CB15 Min"
		::= { bcmsplus2 57 }

bcms2-cb16-min
	OBJECT-TYPE
	SYNTAX  INTEGER
	ACCESS  read-only
	STATUS  mandatory
	DESCRIPTION "CB16 Min"
		::= { bcmsplus2 58 }

bcms2-cb17-min
	OBJECT-TYPE
	SYNTAX  INTEGER
	ACCESS  read-only
	STATUS  mandatory
	DESCRIPTION "CB17 Min"
		::= { bcmsplus2 59 }


bcms2-cb18-min
	OBJECT-TYPE
	SYNTAX  INTEGER
	ACCESS  read-only
	STATUS  mandatory
	DESCRIPTION "CB18 Min"
		::= { bcmsplus2 60 }

bcms2-cb19-min
	OBJECT-TYPE
	SYNTAX  INTEGER
	ACCESS  read-only
	STATUS  mandatory
	DESCRIPTION "CB19 Min"
		::= { bcmsplus2 61 }
  
bcms2-cb20-min
	OBJECT-TYPE
	SYNTAX  INTEGER
	ACCESS  read-only
	STATUS  mandatory
	DESCRIPTION "CB20 Min"
		::= { bcmsplus2 62 }

bcms2-cb21-min
	OBJECT-TYPE
	SYNTAX  INTEGER
	ACCESS  read-only
	STATUS  mandatory
	DESCRIPTION "CB21 Min"
		::= { bcmsplus2 63 }

bcms2-cb22-min
	OBJECT-TYPE
	SYNTAX  INTEGER
	ACCESS  read-only
	STATUS  mandatory
	DESCRIPTION "CB22 Min"
		::= { bcmsplus2 64 }

bcms2-cb23-min
	OBJECT-TYPE
	SYNTAX  INTEGER
	ACCESS  read-only
	STATUS  mandatory
	DESCRIPTION "CB23 Min"
		::= { bcmsplus2 65 }

bcms2-cb24-min
	OBJECT-TYPE
	SYNTAX  INTEGER
	ACCESS  read-only
	STATUS  mandatory
	DESCRIPTION "CB24 Min"
		::= { bcmsplus2 66 }

bcms2-cb25-min
	OBJECT-TYPE
	SYNTAX  INTEGER
	ACCESS  read-only
	STATUS  mandatory
	DESCRIPTION "CB25 Min"
		::= { bcmsplus2 67 }

bcms2-cb26-min
	OBJECT-TYPE
	SYNTAX  INTEGER
	ACCESS  read-only
	STATUS  mandatory
	DESCRIPTION "CB26 Min"
		::= { bcmsplus2 68 }

bcms2-cb27-min
	OBJECT-TYPE
	SYNTAX  INTEGER
	ACCESS  read-only
	STATUS  mandatory
	DESCRIPTION "CB27 Min"
		::= { bcmsplus2 69 }

bcms2-cb28-min
	OBJECT-TYPE
	SYNTAX  INTEGER
	ACCESS  read-only
	STATUS  mandatory
	DESCRIPTION "CB28 Min"
		::= { bcmsplus2 70 }

bcms2-cb29-min
	OBJECT-TYPE
	SYNTAX  INTEGER
	ACCESS  read-only
	STATUS  mandatory
	DESCRIPTION "CB29 Min"
		::= { bcmsplus2 71 }
  
bcms2-cb30-min
	OBJECT-TYPE
	SYNTAX  INTEGER
	ACCESS  read-only
	STATUS  mandatory
	DESCRIPTION "CB30 Min"
		::= { bcmsplus2 72 }

bcms2-cb31-min
	OBJECT-TYPE
	SYNTAX  INTEGER
	ACCESS  read-only
	STATUS  mandatory
	DESCRIPTION "CB31 Min"
		::= { bcmsplus2 73 }

bcms2-cb32-min
	OBJECT-TYPE
	SYNTAX  INTEGER
	ACCESS  read-only
	STATUS  mandatory
	DESCRIPTION "CB32 Min"
		::= { bcmsplus2 74 }

bcms2-cb33-min
	OBJECT-TYPE
	SYNTAX  INTEGER
	ACCESS  read-only
	STATUS  mandatory
	DESCRIPTION "CB33 Min"
		::= { bcmsplus2 75 }

bcms2-cb34-min
	OBJECT-TYPE
	SYNTAX  INTEGER
	ACCESS  read-only
	STATUS  mandatory
	DESCRIPTION "CB34 Min"
		::= { bcmsplus2 76 }

bcms2-cb35-min
	OBJECT-TYPE
	SYNTAX  INTEGER
	ACCESS  read-only
	STATUS  mandatory
	DESCRIPTION "CB35 Min"
		::= { bcmsplus2 77 }

bcms2-cb36-min
	OBJECT-TYPE
	SYNTAX  INTEGER
	ACCESS  read-only
	STATUS  mandatory
	DESCRIPTION "CB36 Min"
		::= { bcmsplus2 78 }

bcms2-cb37-min
	OBJECT-TYPE
	SYNTAX  INTEGER
	ACCESS  read-only
	STATUS  mandatory
	DESCRIPTION "CB37 Min"
		::= { bcmsplus2 79 }

bcms2-cb38-min
	OBJECT-TYPE
	SYNTAX  INTEGER
	ACCESS  read-only
	STATUS  mandatory
	DESCRIPTION "CB38 Min"
		::= { bcmsplus2 80 }

bcms2-cb39-min
	OBJECT-TYPE
	SYNTAX  INTEGER
	ACCESS  read-only
	STATUS  mandatory
	DESCRIPTION "CB39 Min"
		::= { bcmsplus2 81 }
  
bcms2-cb40-min
	OBJECT-TYPE
	SYNTAX  INTEGER
	ACCESS  read-only
	STATUS  mandatory
	DESCRIPTION "CB40 Min"
		::= { bcmsplus2 82 }

bcms2-cb41-min
	OBJECT-TYPE
	SYNTAX  INTEGER
	ACCESS  read-only
	STATUS  mandatory
	DESCRIPTION "CB41 Min"
		::= { bcmsplus2 83 }

bcms2-cb42-min
	OBJECT-TYPE
	SYNTAX  INTEGER
	ACCESS  read-only
	STATUS  mandatory
	DESCRIPTION "CB42 Min"
		::= { bcmsplus2 84 }

bcms2-cb1-max
	OBJECT-TYPE
	SYNTAX  INTEGER
	ACCESS  read-only
	STATUS  mandatory
	DESCRIPTION "CB1 Max
		     Note for all maximum currents 1-42: 100 = 10.0 amps"
		::= { bcmsplus2 85 }

bcms2-cb2-max
	OBJECT-TYPE
	SYNTAX  INTEGER
	ACCESS  read-only
	STATUS  mandatory
	DESCRIPTION "CB2 Max"
		::= { bcmsplus2 86 }

bcms2-cb3-max
	OBJECT-TYPE
	SYNTAX  INTEGER
	ACCESS  read-only
	STATUS  mandatory
	DESCRIPTION "CB3 Max"
		::= { bcmsplus2 87 }

bcms2-cb4-max
	OBJECT-TYPE
	SYNTAX  INTEGER
	ACCESS  read-only
	STATUS  mandatory
	DESCRIPTION "CB4 Max"
		::= { bcmsplus2 88 }

bcms2-cb5-max
	OBJECT-TYPE
	SYNTAX  INTEGER
	ACCESS  read-only
	STATUS  mandatory
	DESCRIPTION "CB5 Max"
		::= { bcmsplus2 89 }

bcms2-cb6-max
	OBJECT-TYPE
	SYNTAX  INTEGER
	ACCESS  read-only
	STATUS  mandatory
	DESCRIPTION "CB6 Max"
		::= { bcmsplus2 90 }

bcms2-cb7-max
	OBJECT-TYPE
	SYNTAX  INTEGER
	ACCESS  read-only
	STATUS  mandatory
	DESCRIPTION "CB7 Max"
		::= { bcmsplus2 91 }
  
bcms2-cb8-max
	OBJECT-TYPE
	SYNTAX  INTEGER
	ACCESS  read-only
	STATUS  mandatory
	DESCRIPTION "CB8 Max"
		::= { bcmsplus2 92 }

bcms2-cb9-max
	OBJECT-TYPE
	SYNTAX  INTEGER
	ACCESS  read-only
	STATUS  mandatory
	DESCRIPTION "CB9 Max"
		::= { bcmsplus2 93 }

bcms2-cb10-max
	OBJECT-TYPE
	SYNTAX  INTEGER
	ACCESS  read-only
	STATUS  mandatory
	DESCRIPTION "CB10 Max"
		::= { bcmsplus2 94 }

bcms2-cb11-max
	OBJECT-TYPE
	SYNTAX  INTEGER
	ACCESS  read-only
	STATUS  mandatory
	DESCRIPTION "CB11 Max"
		::= { bcmsplus2 95 }

bcms2-cb12-max
	OBJECT-TYPE
	SYNTAX  INTEGER
	ACCESS  read-only
	STATUS  mandatory
	DESCRIPTION "CB12 Max"
		::= { bcmsplus2 96 }

bcms2-cb13-max
	OBJECT-TYPE
	SYNTAX  INTEGER
	ACCESS  read-only
	STATUS  mandatory
	DESCRIPTION "CB13 Max"
		::= { bcmsplus2 97 }

bcms2-cb14-max
	OBJECT-TYPE
	SYNTAX  INTEGER
	ACCESS  read-only
	STATUS  mandatory
	DESCRIPTION "CB14 Max"
		::= { bcmsplus2 98 }

bcms2-cb15-max
	OBJECT-TYPE
	SYNTAX  INTEGER
	ACCESS  read-only
	STATUS  mandatory
	DESCRIPTION "CB15 Max"
		::= { bcmsplus2 99 }


bcms2-cb16-max
	OBJECT-TYPE
	SYNTAX  INTEGER
	ACCESS  read-only
	STATUS  mandatory
	DESCRIPTION "CB16 Max"
		::= { bcmsplus2 100 }

bcms2-cb17-max
	OBJECT-TYPE
	SYNTAX  INTEGER
	ACCESS  read-only
	STATUS  mandatory
	DESCRIPTION "CB17 Max"
		::= { bcmsplus2 101 }
  
bcms2-cb18-max
	OBJECT-TYPE
	SYNTAX  INTEGER
	ACCESS  read-only
	STATUS  mandatory
	DESCRIPTION "CB18 Max"
		::= { bcmsplus2 102 }

bcms2-cb19-max
	OBJECT-TYPE
	SYNTAX  INTEGER
	ACCESS  read-only
	STATUS  mandatory
	DESCRIPTION "CB19 Max"
		::= { bcmsplus2 103 }

bcms2-cb20-max
	OBJECT-TYPE
	SYNTAX  INTEGER
	ACCESS  read-only
	STATUS  mandatory
	DESCRIPTION "CB20 Max"
		::= { bcmsplus2 104 }

bcms2-cb21-max
	OBJECT-TYPE
	SYNTAX  INTEGER
	ACCESS  read-only
	STATUS  mandatory
	DESCRIPTION "CB21 Max"
		::= { bcmsplus2 105 }

bcms2-cb22-max
	OBJECT-TYPE
	SYNTAX  INTEGER
	ACCESS  read-only
	STATUS  mandatory
	DESCRIPTION "CB22 Max"
		::= { bcmsplus2 106 }

bcms2-cb23-max
	OBJECT-TYPE
	SYNTAX  INTEGER
	ACCESS  read-only
	STATUS  mandatory
	DESCRIPTION "CB23 Max"
		::= { bcmsplus2 107 }

bcms2-cb24-max
	OBJECT-TYPE
	SYNTAX  INTEGER
	ACCESS  read-only
	STATUS  mandatory
	DESCRIPTION "CB24 Max"
		::= { bcmsplus2 108 }

bcms2-cb25-max
	OBJECT-TYPE
	SYNTAX  INTEGER
	ACCESS  read-only
	STATUS  mandatory
	DESCRIPTION "CB25 Max"
		::= { bcmsplus2 109 }

bcms2-cb26-max
	OBJECT-TYPE
	SYNTAX  INTEGER
	ACCESS  read-only
	STATUS  mandatory
	DESCRIPTION "CB26 Max"
		::= { bcmsplus2 110 }

bcms2-cb27-max
	OBJECT-TYPE
	SYNTAX  INTEGER
	ACCESS  read-only
	STATUS  mandatory
	DESCRIPTION "CB27 Max"
		::= { bcmsplus2 111 }
  
bcms2-cb28-max
	OBJECT-TYPE
	SYNTAX  INTEGER
	ACCESS  read-only
	STATUS  mandatory
	DESCRIPTION "CB28 Max"
		::= { bcmsplus2 112 }

bcms2-cb29-max
	OBJECT-TYPE
	SYNTAX  INTEGER
	ACCESS  read-only
	STATUS  mandatory
	DESCRIPTION "CB29 Max"
		::= { bcmsplus2 113 }

bcms2-cb30-max
	OBJECT-TYPE
	SYNTAX  INTEGER
	ACCESS  read-only
	STATUS  mandatory
	DESCRIPTION "CB30 Max"
		::= { bcmsplus2 114 }

bcms2-cb31-max
	OBJECT-TYPE
	SYNTAX  INTEGER
	ACCESS  read-only
	STATUS  mandatory
	DESCRIPTION "CB31 Max"
		::= { bcmsplus2 115 }

bcms2-cb32-max
	OBJECT-TYPE
	SYNTAX  INTEGER
	ACCESS  read-only
	STATUS  mandatory
	DESCRIPTION "CB32 Max"
		::= { bcmsplus2 116 }

bcms2-cb33-max
	OBJECT-TYPE
	SYNTAX  INTEGER
	ACCESS  read-only
	STATUS  mandatory
	DESCRIPTION "CB33 Max"
		::= { bcmsplus2 117 }

bcms2-cb34-max
	OBJECT-TYPE
	SYNTAX  INTEGER
	ACCESS  read-only
	STATUS  mandatory
	DESCRIPTION "CB34 Max"
		::= { bcmsplus2 118 }

bcms2-cb35-max
	OBJECT-TYPE
	SYNTAX  INTEGER
	ACCESS  read-only
	STATUS  mandatory
	DESCRIPTION "CB35 Max"
		::= { bcmsplus2 119 }

bcms2-cb36-max
	OBJECT-TYPE
	SYNTAX  INTEGER
	ACCESS  read-only
	STATUS  mandatory
	DESCRIPTION "CB36 Max"
		::= { bcmsplus2 120 }

bcms2-cb37-max
	OBJECT-TYPE
	SYNTAX  INTEGER
	ACCESS  read-only
	STATUS  mandatory
	DESCRIPTION "CB37 Max"
		::= { bcmsplus2 121 }
  
bcms2-cb38-max
	OBJECT-TYPE
	SYNTAX  INTEGER
	ACCESS  read-only
	STATUS  mandatory
	DESCRIPTION "CB38 Max"
		::= { bcmsplus2 122 }

bcms2-cb39-max
	OBJECT-TYPE
	SYNTAX  INTEGER
	ACCESS  read-only
	STATUS  mandatory
	DESCRIPTION "CB39 Max"
		::= { bcmsplus2 123 }

bcms2-cb40-max
	OBJECT-TYPE
	SYNTAX  INTEGER
	ACCESS  read-only
	STATUS  mandatory
	DESCRIPTION "CB40 Max"
		::= { bcmsplus2 124 }

bcms2-cb41-max
	OBJECT-TYPE
	SYNTAX  INTEGER
	ACCESS  read-only
	STATUS  mandatory
	DESCRIPTION "CB41 Max"
		::= { bcmsplus2 125 }

bcms2-cb42-max
	OBJECT-TYPE
	SYNTAX  INTEGER
	ACCESS  read-only
	STATUS  mandatory
	DESCRIPTION "CB42 Max"
		::= { bcmsplus2 126 }

bcms2-cb1-16-zero
	OBJECT-TYPE
	SYNTAX  INTEGER
	ACCESS  read-write
	STATUS  mandatory
	DESCRIPTION "CB1-16 Zero
		       Bit 0 = CB1
                   Bit 15 = CB16"
		::= { bcmsplus2 127 }

bcms2-cb17-32-zero
	OBJECT-TYPE
	SYNTAX  INTEGER
	ACCESS  read-write
	STATUS  mandatory
	DESCRIPTION "CB17-32 Zero
		       Bit 0 = CB17
                   Bit 15 = CB32"
		::= { bcmsplus2 128 }

bcms2-cb33-42-zero
	OBJECT-TYPE
	SYNTAX  INTEGER
	ACCESS  read-write
	STATUS  mandatory
	DESCRIPTION "CB33-42 Zero
		       Bit 0 = CB33
                   Bit 9 = CB42
                   Bits 10-25 not used"
		::= { bcmsplus2 129 }

bcms2-cb1-16-warning
	OBJECT-TYPE
	SYNTAX  INTEGER
	ACCESS  read-write
	STATUS  mandatory
	DESCRIPTION "CB1-16 Warning
		       Bit 0 = CB1
                   Bit 15 = CB16"
		::= { bcmsplus2 130 }

bcms2-cb17-32-warning
	OBJECT-TYPE
	SYNTAX  INTEGER
	ACCESS  read-write
	STATUS  mandatory
	DESCRIPTION "CB17-32 Warning
		       Bit 0 = CB17
                   Bit 15 = CB32"
		::= { bcmsplus2 131 }
  
bcms2-cb33-42-warning
	OBJECT-TYPE
	SYNTAX  INTEGER
	ACCESS  read-write
	STATUS  mandatory
	DESCRIPTION "CB33-42 Warning
		       Bit 0 = CB33
                   Bit 9 = CB42
                   Bits 10-25 not used"
		::= { bcmsplus2 132 }

bcms2-cb1-16-alarm
	OBJECT-TYPE
	SYNTAX  INTEGER
	ACCESS  read-write
	STATUS  mandatory
	DESCRIPTION "CB1-16 Alarm
		       Bit 0 = CB1
                   Bit 15 = CB16"
		::= { bcmsplus2 133 }

bcms2-cb17-32-alarm
	OBJECT-TYPE
	SYNTAX  INTEGER
	ACCESS  read-write
	STATUS  mandatory
	DESCRIPTION "CB17-32 Alarm
		       Bit 0 = CB17
                   Bit 15 = CB32"
		::= { bcmsplus2 134 }

bcms2-cb33-42-alarm
	OBJECT-TYPE
	SYNTAX  INTEGER
	ACCESS  read-write
	STATUS  mandatory
	DESCRIPTION "CB33-42 Alarm
		       Bit 0 = CB33
                   Bit 9 = CB42
                   Bits 10-25 not used"
		::= { bcmsplus2 135 }

bcms2-cb1-breaker-size
	OBJECT-TYPE
	SYNTAX  INTEGER
	ACCESS  read-write
	STATUS  mandatory
	DESCRIPTION "CB1 Breaker-Size
		     Note for all breaker sizes 1-42: 10 = 10 amps
                     Range is 10 to 100 amps"
		::= { bcmsplus2 136 }

bcms2-cb2-breaker-size
	OBJECT-TYPE
	SYNTAX  INTEGER
	ACCESS  read-write
	STATUS  mandatory
	DESCRIPTION "CB2 Breaker-Size"
		::= { bcmsplus2 137 }

bcms2-cb3-breaker-size
	OBJECT-TYPE
	SYNTAX  INTEGER
	ACCESS  read-write
	STATUS  mandatory
	DESCRIPTION "CB3 Breaker-Size"
		::= { bcmsplus2 138 }

bcms2-cb4-breaker-size
	OBJECT-TYPE
	SYNTAX  INTEGER
	ACCESS  read-write
	STATUS  mandatory
	DESCRIPTION "CB4 Breaker-Size"
		::= { bcmsplus2 139 }

bcms2-cb5-breaker-size
	OBJECT-TYPE
	SYNTAX  INTEGER
	ACCESS  read-write
	STATUS  mandatory
	DESCRIPTION "CB5 Breaker-Size"
		::= { bcmsplus2 140 }

bcms2-cb6-breaker-size
	OBJECT-TYPE
	SYNTAX  INTEGER
	ACCESS  read-write
	STATUS  mandatory
	DESCRIPTION "CB6 Breaker-Size"
		::= { bcmsplus2 141 }
  
bcms2-cb7-breaker-size
	OBJECT-TYPE
	SYNTAX  INTEGER
	ACCESS  read-write
	STATUS  mandatory
	DESCRIPTION "CB7 Breaker-Size"
		::= { bcmsplus2 142 }

bcms2-cb8-breaker-size
	OBJECT-TYPE
	SYNTAX  INTEGER
	ACCESS  read-write
	STATUS  mandatory
	DESCRIPTION "CB8 Breaker-Size"
		::= { bcmsplus2 143 }

bcms2-cb9-breaker-size
	OBJECT-TYPE
	SYNTAX  INTEGER
	ACCESS  read-write
	STATUS  mandatory
	DESCRIPTION "CB9 Breaker-Size"
		::= { bcmsplus2 144 }

bcms2-cb10-breaker-size
	OBJECT-TYPE
	SYNTAX  INTEGER
	ACCESS  read-write
	STATUS  mandatory
	DESCRIPTION "CB10 Breaker-Size"
		::= { bcmsplus2 145 }

bcms2-cb11-breaker-size
	OBJECT-TYPE
	SYNTAX  INTEGER
	ACCESS  read-write
	STATUS  mandatory
	DESCRIPTION "CB11 Breaker-Size"
		::= { bcmsplus2 146 }

bcms2-cb12-breaker-size
	OBJECT-TYPE
	SYNTAX  INTEGER
	ACCESS  read-write
	STATUS  mandatory
	DESCRIPTION "CB12 Breaker-Size"
		::= { bcmsplus2 147 }

bcms2-cb13-breaker-size
	OBJECT-TYPE
	SYNTAX  INTEGER
	ACCESS  read-write
	STATUS  mandatory
	DESCRIPTION "CB13 Breaker-Size"
		::= { bcmsplus2 148 }

bcms2-cb14-breaker-size
	OBJECT-TYPE
	SYNTAX  INTEGER
	ACCESS  read-write
	STATUS  mandatory
	DESCRIPTION "CB14 Breaker-Size"
		::= { bcmsplus2 149 }

bcms2-cb15-breaker-size
	OBJECT-TYPE
	SYNTAX  INTEGER
	ACCESS  read-write
	STATUS  mandatory
	DESCRIPTION "CB15 Breaker-Size"
		::= { bcmsplus2 150 }

bcms2-cb16-breaker-size
	OBJECT-TYPE
	SYNTAX  INTEGER
	ACCESS  read-write
	STATUS  mandatory
	DESCRIPTION "CB16 Breaker-Size"
		::= { bcmsplus2 151 }
  
bcms2-cb17-breaker-size
	OBJECT-TYPE
	SYNTAX  INTEGER
	ACCESS  read-write
	STATUS  mandatory
	DESCRIPTION "CB17 Breaker-Size"
		::= { bcmsplus2 152 }

bcms2-cb18-breaker-size
	OBJECT-TYPE
	SYNTAX  INTEGER
	ACCESS  read-write
	STATUS  mandatory
	DESCRIPTION "CB18 Breaker-Size"
		::= { bcmsplus2 153 }

bcms2-cb19-breaker-size
	OBJECT-TYPE
	SYNTAX  INTEGER
	ACCESS  read-write
	STATUS  mandatory
	DESCRIPTION "CB19 Breaker-Size"
		::= { bcmsplus2 154 }

bcms2-cb20-breaker-size
	OBJECT-TYPE
	SYNTAX  INTEGER
	ACCESS  read-write
	STATUS  mandatory
	DESCRIPTION "CB20 Breaker-Size"
		::= { bcmsplus2 155 }

bcms2-cb21-breaker-size
	OBJECT-TYPE
	SYNTAX  INTEGER
	ACCESS  read-write
	STATUS  mandatory
	DESCRIPTION "CB21 Breaker-Size"
		::= { bcmsplus2 156 }

bcms2-cb22-breaker-size
	OBJECT-TYPE
	SYNTAX  INTEGER
	ACCESS  read-write
	STATUS  mandatory
	DESCRIPTION "CB22 Breaker-Size"
		::= { bcmsplus2 157 }

bcms2-cb23-breaker-size
	OBJECT-TYPE
	SYNTAX  INTEGER
	ACCESS  read-write
	STATUS  mandatory
	DESCRIPTION "CB23 Breaker-Size"
		::= { bcmsplus2 158 }

bcms2-cb24-breaker-size
	OBJECT-TYPE
	SYNTAX  INTEGER
	ACCESS  read-write
	STATUS  mandatory
	DESCRIPTION "CB24 Breaker-Size"
		::= { bcmsplus2 159 }

bcms2-cb25-breaker-size
	OBJECT-TYPE
	SYNTAX  INTEGER
	ACCESS  read-write
	STATUS  mandatory
	DESCRIPTION "CB25 Breaker-Size"
		::= { bcmsplus2 160 }

bcms2-cb26-breaker-size
	OBJECT-TYPE
	SYNTAX  INTEGER
	ACCESS  read-write
	STATUS  mandatory
	DESCRIPTION "CB26 Breaker-Size"
		::= { bcmsplus2 161 }
  
bcms2-cb27-breaker-size
	OBJECT-TYPE
	SYNTAX  INTEGER
	ACCESS  read-write
	STATUS  mandatory
	DESCRIPTION "CB27 Breaker-Size"
		::= { bcmsplus2 162 }

bcms2-cb28-breaker-size
	OBJECT-TYPE
	SYNTAX  INTEGER
	ACCESS  read-write
	STATUS  mandatory
	DESCRIPTION "CB28 Breaker-Size"
		::= { bcmsplus2 163 }

bcms2-cb29-breaker-size
	OBJECT-TYPE
	SYNTAX  INTEGER
	ACCESS  read-write
	STATUS  mandatory
	DESCRIPTION "CB29 Breaker-Size"
		::= { bcmsplus2 164 }

bcms2-cb30-breaker-size
	OBJECT-TYPE
	SYNTAX  INTEGER
	ACCESS  read-write
	STATUS  mandatory
	DESCRIPTION "CB30 Breaker-Size"
		::= { bcmsplus2 165 }

bcms2-cb31-breaker-size
	OBJECT-TYPE
	SYNTAX  INTEGER
	ACCESS  read-write
	STATUS  mandatory
	DESCRIPTION "CB31 Breaker-Size"
		::= { bcmsplus2 166 }

bcms2-cb32-breaker-size
	OBJECT-TYPE
	SYNTAX  INTEGER
	ACCESS  read-write
	STATUS  mandatory
	DESCRIPTION "CB32 Breaker-Size"
		::= { bcmsplus2 167 }

bcms2-cb33-breaker-size
	OBJECT-TYPE
	SYNTAX  INTEGER
	ACCESS  read-write
	STATUS  mandatory
	DESCRIPTION "CB33 Breaker-Size"
		::= { bcmsplus2 168 }

bcms2-cb34-breaker-size
	OBJECT-TYPE
	SYNTAX  INTEGER
	ACCESS  read-write
	STATUS  mandatory
	DESCRIPTION "CB34 Breaker-Size"
		::= { bcmsplus2 169 }

bcms2-cb35-breaker-size
	OBJECT-TYPE
	SYNTAX  INTEGER
	ACCESS  read-write
	STATUS  mandatory
	DESCRIPTION "CB35 Breaker-Size"
		::= { bcmsplus2 170 }

bcms2-cb36-breaker-size
	OBJECT-TYPE
	SYNTAX  INTEGER
	ACCESS  read-write
	STATUS  mandatory
	DESCRIPTION "CB36 Breaker-Size"
		::= { bcmsplus2 171 }
  
bcms2-cb37-breaker-size
	OBJECT-TYPE
	SYNTAX  INTEGER
	ACCESS  read-write
	STATUS  mandatory
	DESCRIPTION "CB37 Breaker-Size"
		::= { bcmsplus2 172 }

bcms2-cb38-breaker-size
	OBJECT-TYPE
	SYNTAX  INTEGER
	ACCESS  read-write
	STATUS  mandatory
	DESCRIPTION "CB38 Breaker-Size"
		::= { bcmsplus2 173 }

bcms2-cb39-breaker-size
	OBJECT-TYPE
	SYNTAX  INTEGER
	ACCESS  read-write
	STATUS  mandatory
	DESCRIPTION "CB39 Breaker-Size"
		::= { bcmsplus2 174 }

bcms2-cb40-breaker-size
	OBJECT-TYPE
	SYNTAX  INTEGER
	ACCESS  read-write
	STATUS  mandatory
	DESCRIPTION "CB40 Breaker-Size"
		::= { bcmsplus2 175 }

bcms2-cb41-breaker-size
	OBJECT-TYPE
	SYNTAX  INTEGER
	ACCESS  read-write
	STATUS  mandatory
	DESCRIPTION "CB41 Breaker-Size"
		::= { bcmsplus2 176 }

bcms2-cb42-breaker-size
	OBJECT-TYPE
	SYNTAX  INTEGER
	ACCESS  read-write
	STATUS  mandatory
	DESCRIPTION "CB42 Breaker-Size"
		::= { bcmsplus2 177 }

bcms2-cb1-warning-threshold
	OBJECT-TYPE
	SYNTAX  INTEGER
	ACCESS  read-write
	STATUS  mandatory
	DESCRIPTION "CB1 CB1-warning-threshold
		     Note for all warning thresholds 1-42: 70 = 70% of breaker size
                     range is 0-100%"
		::= { bcmsplus2 178 }

bcms2-cb2-warning-threshold
	OBJECT-TYPE
	SYNTAX  INTEGER
	ACCESS  read-write
	STATUS  mandatory
	DESCRIPTION "CB2 Warning-Threshold"
		::= { bcmsplus2 179 }

bcms2-cb3-warning-threshold
	OBJECT-TYPE
	SYNTAX  INTEGER
	ACCESS  read-write
	STATUS  mandatory
	DESCRIPTION "CB3 Warning-Threshold"
		::= { bcmsplus2 180 }

bcms2-cb4-warning-threshold
	OBJECT-TYPE
	SYNTAX  INTEGER
	ACCESS  read-write
	STATUS  mandatory
	DESCRIPTION "CB4 Warning-Threshold"
		::= { bcmsplus2 181 }
  
bcms2-cb5-warning-threshold
	OBJECT-TYPE
	SYNTAX  INTEGER
	ACCESS  read-write
	STATUS  mandatory
	DESCRIPTION "CB5 Warning-Threshold"
		::= { bcmsplus2 182 }

bcms2-cb6-warning-threshold
	OBJECT-TYPE
	SYNTAX  INTEGER
	ACCESS  read-write
	STATUS  mandatory
	DESCRIPTION "CB6 Warning-Threshold"
		::= { bcmsplus2 183 }

bcms2-cb7-warning-threshold
	OBJECT-TYPE
	SYNTAX  INTEGER
	ACCESS  read-write
	STATUS  mandatory
	DESCRIPTION "CB7 Warning-Threshold"
		::= { bcmsplus2 184 }

bcms2-cb8-warning-threshold
	OBJECT-TYPE
	SYNTAX  INTEGER
	ACCESS  read-write
	STATUS  mandatory
	DESCRIPTION "CB8 Warning-Threshold"
		::= { bcmsplus2 185 }

bcms2-cb9-warning-threshold
	OBJECT-TYPE
	SYNTAX  INTEGER
	ACCESS  read-write
	STATUS  mandatory
	DESCRIPTION "CB9 Warning-Threshold"
		::= { bcmsplus2 186 }

bcms2-cb10-warning-threshold
	OBJECT-TYPE
	SYNTAX  INTEGER
	ACCESS  read-write
	STATUS  mandatory
	DESCRIPTION "CB10 Warning-Threshold"
		::= { bcmsplus2 187 }

bcms2-cb11-warning-threshold
	OBJECT-TYPE
	SYNTAX  INTEGER
	ACCESS  read-write
	STATUS  mandatory
	DESCRIPTION "CB11 Warning-Threshold"
		::= { bcmsplus2 188 }

bcms2-cb12-warning-threshold
	OBJECT-TYPE
	SYNTAX  INTEGER
	ACCESS  read-write
	STATUS  mandatory
	DESCRIPTION "CB12 Warning-Threshold"
		::= { bcmsplus2 189 }

bcms2-cb13-warning-threshold
	OBJECT-TYPE
	SYNTAX  INTEGER
	ACCESS  read-write
	STATUS  mandatory
	DESCRIPTION "CB13 Warning-Threshold"
		::= { bcmsplus2 190 }

bcms2-cb14-warning-threshold
	OBJECT-TYPE
	SYNTAX  INTEGER
	ACCESS  read-write
	STATUS  mandatory
	DESCRIPTION "CB14 Warning-Threshold"
		::= { bcmsplus2 191 }
  
bcms2-cb15-warning-threshold
	OBJECT-TYPE
	SYNTAX  INTEGER
	ACCESS  read-write
	STATUS  mandatory
	DESCRIPTION "CB15 Warning-Threshold"
		::= { bcmsplus2 192 }

bcms2-cb16-warning-threshold
	OBJECT-TYPE
	SYNTAX  INTEGER
	ACCESS  read-write
	STATUS  mandatory
	DESCRIPTION "CB16 Warning-Threshold"
		::= { bcmsplus2 193 }

bcms2-cb17-warning-threshold
	OBJECT-TYPE
	SYNTAX  INTEGER
	ACCESS  read-write
	STATUS  mandatory
	DESCRIPTION "CB17 Warning-Threshold"
		::= { bcmsplus2 194 }

bcms2-cb18-warning-threshold
	OBJECT-TYPE
	SYNTAX  INTEGER
	ACCESS  read-write
	STATUS  mandatory
	DESCRIPTION "CB18 Warning-Threshold"
		::= { bcmsplus2 195 }

bcms2-cb19-warning-threshold
	OBJECT-TYPE
	SYNTAX  INTEGER
	ACCESS  read-write
	STATUS  mandatory
	DESCRIPTION "CB19 Warning-Threshold"
		::= { bcmsplus2 196 }

bcms2-cb20-warning-threshold
	OBJECT-TYPE
	SYNTAX  INTEGER
	ACCESS  read-write
	STATUS  mandatory
	DESCRIPTION "CB20 Warning-Threshold"
		::= { bcmsplus2 197 }

bcms2-cb21-warning-threshold
	OBJECT-TYPE
	SYNTAX  INTEGER
	ACCESS  read-write
	STATUS  mandatory
	DESCRIPTION "CB21 Warning-Threshold"
		::= { bcmsplus2 198 }

bcms2-cb22-warning-threshold
	OBJECT-TYPE
	SYNTAX  INTEGER
	ACCESS  read-write
	STATUS  mandatory
	DESCRIPTION "CB22 Warning-Threshold"
		::= { bcmsplus2 199 }

bcms2-cb23-warning-threshold
	OBJECT-TYPE
	SYNTAX  INTEGER
	ACCESS  read-write
	STATUS  mandatory
	DESCRIPTION "CB23 Warning-Threshold"
		::= { bcmsplus2 200 }

bcms2-cb24-warning-threshold
	OBJECT-TYPE
	SYNTAX  INTEGER
	ACCESS  read-write
	STATUS  mandatory
	DESCRIPTION "CB24 Warning-Threshold"
		::= { bcmsplus2 201 }
  
bcms2-cb25-warning-threshold
	OBJECT-TYPE
	SYNTAX  INTEGER
	ACCESS  read-write
	STATUS  mandatory
	DESCRIPTION "CB25 Warning-Threshold"
		::= { bcmsplus2 202 }

bcms2-cb26-warning-threshold
	OBJECT-TYPE
	SYNTAX  INTEGER
	ACCESS  read-write
	STATUS  mandatory
	DESCRIPTION "CB26 Warning-Threshold"
		::= { bcmsplus2 203 }

bcms2-cb27-warning-threshold
	OBJECT-TYPE
	SYNTAX  INTEGER
	ACCESS  read-write
	STATUS  mandatory
	DESCRIPTION "CB27 Warning-Threshold"
		::= { bcmsplus2 204 }

bcms2-cb28-warning-threshold
	OBJECT-TYPE
	SYNTAX  INTEGER
	ACCESS  read-write
	STATUS  mandatory
	DESCRIPTION "CB28 Warning-Threshold"
		::= { bcmsplus2 205 }

bcms2-cb29-warning-threshold
	OBJECT-TYPE
	SYNTAX  INTEGER
	ACCESS  read-write
	STATUS  mandatory
	DESCRIPTION "CB29 Warning-Threshold"
		::= { bcmsplus2 206 }

bcms2-cb30-warning-threshold
	OBJECT-TYPE
	SYNTAX  INTEGER
	ACCESS  read-write
	STATUS  mandatory
	DESCRIPTION "CB30 Warning-Threshold"
		::= { bcmsplus2 207 }

bcms2-cb31-warning-threshold
	OBJECT-TYPE
	SYNTAX  INTEGER
	ACCESS  read-write
	STATUS  mandatory
	DESCRIPTION "CB31 Warning-Threshold"
		::= { bcmsplus2 208 }

bcms2-cb32-warning-threshold
	OBJECT-TYPE
	SYNTAX  INTEGER
	ACCESS  read-write
	STATUS  mandatory
	DESCRIPTION "CB32 Warning-Threshold"
		::= { bcmsplus2 209 }

bcms2-cb33-warning-threshold
	OBJECT-TYPE
	SYNTAX  INTEGER
	ACCESS  read-write
	STATUS  mandatory
	DESCRIPTION "CB33 Warning-Threshold"
		::= { bcmsplus2 210 }

bcms2-cb34-warning-threshold
	OBJECT-TYPE
	SYNTAX  INTEGER
	ACCESS  read-write
	STATUS  mandatory
	DESCRIPTION "CB34 Warning-Threshold"
		::= { bcmsplus2 211 }
  
bcms2-cb35-warning-threshold
	OBJECT-TYPE
	SYNTAX  INTEGER
	ACCESS  read-write
	STATUS  mandatory
	DESCRIPTION "CB35 Warning-Threshold"
		::= { bcmsplus2 212 }

bcms2-cb36-warning-threshold
	OBJECT-TYPE
	SYNTAX  INTEGER
	ACCESS  read-write
	STATUS  mandatory
	DESCRIPTION "CB36 Warning-Threshold"
		::= { bcmsplus2 213 }

bcms2-cb37-warning-threshold
	OBJECT-TYPE
	SYNTAX  INTEGER
	ACCESS  read-write
	STATUS  mandatory
	DESCRIPTION "CB37 Warning-Threshold"
		::= { bcmsplus2 214 }

bcms2-cb38-warning-threshold
	OBJECT-TYPE
	SYNTAX  INTEGER
	ACCESS  read-write
	STATUS  mandatory
	DESCRIPTION "CB38 Warning-Threshold"
		::= { bcmsplus2 215 }

bcms2-cb39-warning-threshold
	OBJECT-TYPE
	SYNTAX  INTEGER
	ACCESS  read-write
	STATUS  mandatory
	DESCRIPTION "CB39 Warning-Threshold"
		::= { bcmsplus2 216 }

bcms2-cb40-warning-threshold
	OBJECT-TYPE
	SYNTAX  INTEGER
	ACCESS  read-write
	STATUS  mandatory
	DESCRIPTION "CB40 Warning-Threshold"
		::= { bcmsplus2 217 }

bcms2-cb41-warning-threshold
	OBJECT-TYPE
	SYNTAX  INTEGER
	ACCESS  read-write
	STATUS  mandatory
	DESCRIPTION "CB41 Warning-Threshold"
		::= { bcmsplus2 218 }

bcms2-cb42-warning-threshold
	OBJECT-TYPE
	SYNTAX  INTEGER
	ACCESS  read-write
	STATUS  mandatory
	DESCRIPTION "CB42 Warning-Threshold"
		::= { bcmsplus2 219 }

bcms2-cb1-alarm-threshold
	OBJECT-TYPE
	SYNTAX  INTEGER
	ACCESS  read-write
	STATUS  mandatory
	DESCRIPTION "CB1 Alarm-Threshold
		     Note for all alarm thresholds 1-42: 80 = 80% of breaker size
                     range is 0-100%"
		::= { bcmsplus2 220 }


bcms2-cb2-alarm-threshold
	OBJECT-TYPE
	SYNTAX  INTEGER
	ACCESS  read-write
	STATUS  mandatory
	DESCRIPTION "CB2 Alarm-Threshold"
		::= { bcmsplus2 221 }
  
bcms2-cb3-alarm-threshold
	OBJECT-TYPE
	SYNTAX  INTEGER
	ACCESS  read-write
	STATUS  mandatory
	DESCRIPTION "CB3 Alarm-Threshold"
		::= { bcmsplus2 222 }

bcms2-cb4-alarm-threshold
	OBJECT-TYPE
	SYNTAX  INTEGER
	ACCESS  read-write
	STATUS  mandatory
	DESCRIPTION "CB4 Alarm-Threshold"
		::= { bcmsplus2 223 }

bcms2-cb5-alarm-threshold
	OBJECT-TYPE
	SYNTAX  INTEGER
	ACCESS  read-write
	STATUS  mandatory
	DESCRIPTION "CB5 Alarm-Threshold"
		::= { bcmsplus2 224 }

bcms2-cb6-alarm-threshold
	OBJECT-TYPE
	SYNTAX  INTEGER
	ACCESS  read-write
	STATUS  mandatory
	DESCRIPTION "CB6 Alarm-Threshold"
		::= { bcmsplus2 225 }

bcms2-cb7-alarm-threshold
	OBJECT-TYPE
	SYNTAX  INTEGER
	ACCESS  read-write
	STATUS  mandatory
	DESCRIPTION "CB7 Alarm-Threshold"
		::= { bcmsplus2 226 }

bcms2-cb8-alarm-threshold
	OBJECT-TYPE
	SYNTAX  INTEGER
	ACCESS  read-write
	STATUS  mandatory
	DESCRIPTION "CB8 Alarm-Threshold"
		::= { bcmsplus2 227 }

bcms2-cb9-alarm-threshold
	OBJECT-TYPE
	SYNTAX  INTEGER
	ACCESS  read-write
	STATUS  mandatory
	DESCRIPTION "CB9 Alarm-Threshold"
		::= { bcmsplus2 228 }

bcms2-cb10-alarm-threshold
	OBJECT-TYPE
	SYNTAX  INTEGER
	ACCESS  read-write
	STATUS  mandatory
	DESCRIPTION "CB10 Alarm-Threshold"
		::= { bcmsplus2 229 }

bcms2-cb11-alarm-threshold
	OBJECT-TYPE
	SYNTAX  INTEGER
	ACCESS  read-write
	STATUS  mandatory
	DESCRIPTION "CB11 Alarm-Threshold"
		::= { bcmsplus2 230 }

bcms2-cb12-alarm-threshold
	OBJECT-TYPE
	SYNTAX  INTEGER
	ACCESS  read-write
	STATUS  mandatory
	DESCRIPTION "CB12 Alarm-Threshold"
		::= { bcmsplus2 231 }
  
bcms2-cb13-alarm-threshold
	OBJECT-TYPE
	SYNTAX  INTEGER
	ACCESS  read-write
	STATUS  mandatory
	DESCRIPTION "CB13 Alarm-Threshold"
		::= { bcmsplus2 232 }

bcms2-cb14-alarm-threshold
	OBJECT-TYPE
	SYNTAX  INTEGER
	ACCESS  read-write
	STATUS  mandatory
	DESCRIPTION "CB14 Alarm-Threshold"
		::= { bcmsplus2 233 }

bcms2-cb15-alarm-threshold
	OBJECT-TYPE
	SYNTAX  INTEGER
	ACCESS  read-write
	STATUS  mandatory
	DESCRIPTION "CB15 Alarm-Threshold"
		::= { bcmsplus2 234 }

bcms2-cb16-alarm-threshold
	OBJECT-TYPE
	SYNTAX  INTEGER
	ACCESS  read-write
	STATUS  mandatory
	DESCRIPTION "CB16 Alarm-Threshold"
		::= { bcmsplus2 235 }

bcms2-cb17-alarm-threshold
	OBJECT-TYPE
	SYNTAX  INTEGER
	ACCESS  read-write
	STATUS  mandatory
	DESCRIPTION "CB17 Alarm-Threshold"
		::= { bcmsplus2 236 }

bcms2-cb18-alarm-threshold
	OBJECT-TYPE
	SYNTAX  INTEGER
	ACCESS  read-write
	STATUS  mandatory
	DESCRIPTION "CB18 Alarm-Threshold"
		::= { bcmsplus2 237 }

bcms2-cb19-alarm-threshold
	OBJECT-TYPE
	SYNTAX  INTEGER
	ACCESS  read-write
	STATUS  mandatory
	DESCRIPTION "CB19 Alarm-Threshold"
		::= { bcmsplus2 238 }

bcms2-cb20-alarm-threshold
	OBJECT-TYPE
	SYNTAX  INTEGER
	ACCESS  read-write
	STATUS  mandatory
	DESCRIPTION "CB20 Alarm-Threshold"
		::= { bcmsplus2 239 }

bcms2-cb21-alarm-threshold
	OBJECT-TYPE
	SYNTAX  INTEGER
	ACCESS  read-write
	STATUS  mandatory
	DESCRIPTION "CB21 Alarm-Threshold"
		::= { bcmsplus2 240 }

bcms2-cb22-alarm-threshold
	OBJECT-TYPE
	SYNTAX  INTEGER
	ACCESS  read-write
	STATUS  mandatory
	DESCRIPTION "CB22 Alarm-Threshold"
		::= { bcmsplus2 241 }
  
bcms2-cb23-alarm-threshold
	OBJECT-TYPE
	SYNTAX  INTEGER
	ACCESS  read-write
	STATUS  mandatory
	DESCRIPTION "CB23 Alarm-Threshold"
		::= { bcmsplus2 242 }

bcms2-cb24-alarm-threshold
	OBJECT-TYPE
	SYNTAX  INTEGER
	ACCESS  read-write
	STATUS  mandatory
	DESCRIPTION "CB24 Alarm-Threshold"
		::= { bcmsplus2 243 }

bcms2-cb25-alarm-threshold
	OBJECT-TYPE
	SYNTAX  INTEGER
	ACCESS  read-write
	STATUS  mandatory
	DESCRIPTION "CB25 Alarm-Threshold"
		::= { bcmsplus2 244 }

bcms2-cb26-alarm-threshold
	OBJECT-TYPE
	SYNTAX  INTEGER
	ACCESS  read-write
	STATUS  mandatory
	DESCRIPTION "CB26 Alarm-Threshold"
		::= { bcmsplus2 245 }

bcms2-cb27-alarm-threshold
	OBJECT-TYPE
	SYNTAX  INTEGER
	ACCESS  read-write
	STATUS  mandatory
	DESCRIPTION "CB27 Alarm-Threshold"
		::= { bcmsplus2 246 }

bcms2-cb28-alarm-threshold
	OBJECT-TYPE
	SYNTAX  INTEGER
	ACCESS  read-write
	STATUS  mandatory
	DESCRIPTION "CB28 Alarm-Threshold"
		::= { bcmsplus2 247 }

bcms2-cb29-alarm-threshold
	OBJECT-TYPE
	SYNTAX  INTEGER
	ACCESS  read-write
	STATUS  mandatory
	DESCRIPTION "CB29 Alarm-Threshold"
		::= { bcmsplus2 248 }

bcms2-cb30-alarm-threshold
	OBJECT-TYPE
	SYNTAX  INTEGER
	ACCESS  read-write
	STATUS  mandatory
	DESCRIPTION "CB30 Alarm-Threshold"
		::= { bcmsplus2 249 }

bcms2-cb31-alarm-threshold
	OBJECT-TYPE
	SYNTAX  INTEGER
	ACCESS  read-write
	STATUS  mandatory
	DESCRIPTION "CB31 Alarm-Threshold"
		::= { bcmsplus2 250 }

bcms2-cb32-alarm-threshold
	OBJECT-TYPE
	SYNTAX  INTEGER
	ACCESS  read-write
	STATUS  mandatory
	DESCRIPTION "CB32 Alarm-Threshold"
		::= { bcmsplus2 251 }
  
bcms2-cb33-alarm-threshold
	OBJECT-TYPE
	SYNTAX  INTEGER
	ACCESS  read-write
	STATUS  mandatory
	DESCRIPTION "CB33 Alarm-Threshold"
		::= { bcmsplus2 252 }

bcms2-cb34-alarm-threshold
	OBJECT-TYPE
	SYNTAX  INTEGER
	ACCESS  read-write
	STATUS  mandatory
	DESCRIPTION "CB34 Alarm-Threshold"
		::= { bcmsplus2 253 }

bcms2-cb35-alarm-threshold
	OBJECT-TYPE
	SYNTAX  INTEGER
	ACCESS  read-write
	STATUS  mandatory
	DESCRIPTION "CB35 Alarm-Threshold"
		::= { bcmsplus2 254 }

bcms2-cb36-alarm-threshold
	OBJECT-TYPE
	SYNTAX  INTEGER
	ACCESS  read-write
	STATUS  mandatory
	DESCRIPTION "CB36 Alarm-Threshold"
		::= { bcmsplus2 255 }

bcms2-cb37-alarm-threshold
	OBJECT-TYPE
	SYNTAX  INTEGER
	ACCESS  read-write
	STATUS  mandatory
	DESCRIPTION "CB37 Alarm-Threshold"
		::= { bcmsplus2 256 }

bcms2-cb38-alarm-threshold
	OBJECT-TYPE
	SYNTAX  INTEGER
	ACCESS  read-write
	STATUS  mandatory
	DESCRIPTION "CB38 Alarm-Threshold"
		::= { bcmsplus2 257 }

bcms2-cb39-alarm-threshold
	OBJECT-TYPE
	SYNTAX  INTEGER
	ACCESS  read-write
	STATUS  mandatory
	DESCRIPTION "CB39 Alarm-Threshold"
		::= { bcmsplus2 258 }

bcms2-cb40-alarm-threshold
	OBJECT-TYPE
	SYNTAX  INTEGER
	ACCESS  read-write
	STATUS  mandatory
	DESCRIPTION "CB40 Alarm-Threshold"
		::= { bcmsplus2 259 }

bcms2-cb41-alarm-threshold
	OBJECT-TYPE
	SYNTAX  INTEGER
	ACCESS  read-write
	STATUS  mandatory
	DESCRIPTION "CB41 Alarm-Threshold"
		::= { bcmsplus2 260 }

bcms2-cb42-alarm-threshold
	OBJECT-TYPE
	SYNTAX  INTEGER
	ACCESS  read-write
	STATUS  mandatory
	DESCRIPTION "CB42 Alarm-Threshold"
		::= { bcmsplus2 261 }

bcms2-cb1-warning-time-delay
	OBJECT-TYPE
	SYNTAX  INTEGER
	ACCESS  read-write
	STATUS  mandatory
	DESCRIPTION "CB1 Warning-Time-Delay
		     Note for all warning time delays 1-42: units are in seconds"                     
		::= { bcmsplus2 262 }

bcms2-cb2-warning-time-delay
	OBJECT-TYPE
	SYNTAX  INTEGER
	ACCESS  read-write
	STATUS  mandatory
	DESCRIPTION "CB2 Warning-Time-Delay"
		::= { bcmsplus2 263 }
  
bcms2-cb3-warning-time-delay
	OBJECT-TYPE
	SYNTAX  INTEGER
	ACCESS  read-write
	STATUS  mandatory
	DESCRIPTION "CB3 Warning-Time-Delay"
		::= { bcmsplus2 264 }

bcms2-cb4-warning-time-delay
	OBJECT-TYPE
	SYNTAX  INTEGER
	ACCESS  read-write
	STATUS  mandatory
	DESCRIPTION "CB4 Warning-Time-Delay"
		::= { bcmsplus2 265 }

bcms2-cb5-warning-time-delay
	OBJECT-TYPE
	SYNTAX  INTEGER
	ACCESS  read-write
	STATUS  mandatory
	DESCRIPTION "CB5 Warning-Time-Delay"
		::= { bcmsplus2 266 }

bcms2-cb6-warning-time-delay
	OBJECT-TYPE
	SYNTAX  INTEGER
	ACCESS  read-write
	STATUS  mandatory
	DESCRIPTION "CB6 Warning-Time-Delay"
		::= { bcmsplus2 267 }

bcms2-cb7-warning-time-delay
	OBJECT-TYPE
	SYNTAX  INTEGER
	ACCESS  read-write
	STATUS  mandatory
	DESCRIPTION "CB7 Warning-Time-Delay"
		::= { bcmsplus2 268 }

bcms2-cb8-warning-time-delay
	OBJECT-TYPE
	SYNTAX  INTEGER
	ACCESS  read-write
	STATUS  mandatory
	DESCRIPTION "CB8 Warning-Time-Delay"
		::= { bcmsplus2 269 }

bcms2-cb9-warning-time-delay
	OBJECT-TYPE
	SYNTAX  INTEGER
	ACCESS  read-write
	STATUS  mandatory
	DESCRIPTION "CB9 Warning-Time-Delay"
		::= { bcmsplus2 270 }

bcms2-cb10-warning-time-delay
	OBJECT-TYPE
	SYNTAX  INTEGER
	ACCESS  read-write
	STATUS  mandatory
	DESCRIPTION "CB10 Warning-Time-Delay"
		::= { bcmsplus2 271 }

bcms2-cb11-warning-time-delay
	OBJECT-TYPE
	SYNTAX  INTEGER
	ACCESS  read-write
	STATUS  mandatory
	DESCRIPTION "CB11 Warning-Time-Delay"
		::= { bcmsplus2 272 }

bcms2-cb12-warning-time-delay
	OBJECT-TYPE
	SYNTAX  INTEGER
	ACCESS  read-write
	STATUS  mandatory
	DESCRIPTION "CB12 Warning-Time-Delay"
		::= { bcmsplus2 273 }
  
bcms2-cb13-warning-time-delay
	OBJECT-TYPE
	SYNTAX  INTEGER
	ACCESS  read-write
	STATUS  mandatory
	DESCRIPTION "CB13 Warning-Time-Delay"
		::= { bcmsplus2 274 }

bcms2-cb14-warning-time-delay
	OBJECT-TYPE
	SYNTAX  INTEGER
	ACCESS  read-write
	STATUS  mandatory
	DESCRIPTION "CB14 Warning-Time-Delay"
		::= { bcmsplus2 275 }

bcms2-cb15-warning-time-delay
	OBJECT-TYPE
	SYNTAX  INTEGER
	ACCESS  read-write
	STATUS  mandatory
	DESCRIPTION "CB15 Warning-Time-Delay"
		::= { bcmsplus2 276 }

bcms2-cb16-warning-time-delay
	OBJECT-TYPE
	SYNTAX  INTEGER
	ACCESS  read-write
	STATUS  mandatory
	DESCRIPTION "CB16 Warning-Time-Delay"
		::= { bcmsplus2 277 }

bcms2-cb17-warning-time-delay
	OBJECT-TYPE
	SYNTAX  INTEGER
	ACCESS  read-write
	STATUS  mandatory
	DESCRIPTION "CB17 Warning-Time-Delay"
		::= { bcmsplus2 278 }

bcms2-cb18-warning-time-delay
	OBJECT-TYPE
	SYNTAX  INTEGER
	ACCESS  read-write
	STATUS  mandatory
	DESCRIPTION "CB18 Warning-Time-Delay"
		::= { bcmsplus2 279 }

bcms2-cb19-warning-time-delay
	OBJECT-TYPE
	SYNTAX  INTEGER
	ACCESS  read-write
	STATUS  mandatory
	DESCRIPTION "CB19 Warning-Time-Delay"
		::= { bcmsplus2 280 }

bcms2-cb20-warning-time-delay
	OBJECT-TYPE
	SYNTAX  INTEGER
	ACCESS  read-write
	STATUS  mandatory
	DESCRIPTION "CB20 Warning-Time-Delay"
		::= { bcmsplus2 281 }

bcms2-cb21-warning-time-delay
	OBJECT-TYPE
	SYNTAX  INTEGER
	ACCESS  read-write
	STATUS  mandatory
	DESCRIPTION "CB21 Warning-Time-Delay"
		::= { bcmsplus2 282 }

bcms2-cb22-warning-time-delay
	OBJECT-TYPE
	SYNTAX  INTEGER
	ACCESS  read-write
	STATUS  mandatory
	DESCRIPTION "CB22 Warning-Time-Delay"
		::= { bcmsplus2 283 }
  
bcms2-cb23-warning-time-delay
	OBJECT-TYPE
	SYNTAX  INTEGER
	ACCESS  read-write
	STATUS  mandatory
	DESCRIPTION "CB23 Warning-Time-Delay"
		::= { bcmsplus2 284 }

bcms2-cb24-warning-time-delay
	OBJECT-TYPE
	SYNTAX  INTEGER
	ACCESS  read-write
	STATUS  mandatory
	DESCRIPTION "CB24 Warning-Time-Delay"
		::= { bcmsplus2 285 }

bcms2-cb25-warning-time-delay
	OBJECT-TYPE
	SYNTAX  INTEGER
	ACCESS  read-write
	STATUS  mandatory
	DESCRIPTION "CB25 Warning-Time-Delay"
		::= { bcmsplus2 286 }

bcms2-cb26-warning-time-delay
	OBJECT-TYPE
	SYNTAX  INTEGER
	ACCESS  read-write
	STATUS  mandatory
	DESCRIPTION "CB26 Warning-Time-Delay"
		::= { bcmsplus2 287 }

bcms2-cb27-warning-time-delay
	OBJECT-TYPE
	SYNTAX  INTEGER
	ACCESS  read-write
	STATUS  mandatory
	DESCRIPTION "CB27 Warning-Time-Delay"
		::= { bcmsplus2 288 }

bcms2-cb28-warning-time-delay
	OBJECT-TYPE
	SYNTAX  INTEGER
	ACCESS  read-write
	STATUS  mandatory
	DESCRIPTION "CB28 Warning-Time-Delay"
		::= { bcmsplus2 289 }

bcms2-cb29-warning-time-delay
	OBJECT-TYPE
	SYNTAX  INTEGER
	ACCESS  read-write
	STATUS  mandatory
	DESCRIPTION "CB29 Warning-Time-Delay"
		::= { bcmsplus2 290}

bcms2-cb30-warning-time-delay
	OBJECT-TYPE
	SYNTAX  INTEGER
	ACCESS  read-write
	STATUS  mandatory
	DESCRIPTION "CB30 Warning-Time-Delay"
		::= { bcmsplus2 291 }

bcms2-cb31-warning-time-delay
	OBJECT-TYPE
	SYNTAX  INTEGER
	ACCESS  read-write
	STATUS  mandatory
	DESCRIPTION "CB31 Warning-Time-Delay"
		::= { bcmsplus2 292 }

bcms2-cb32-warning-time-delay
	OBJECT-TYPE
	SYNTAX  INTEGER
	ACCESS  read-write
	STATUS  mandatory
	DESCRIPTION "CB32 Warning-Time-Delay"
		::= { bcmsplus2 293 }
  
bcms2-cb33-warning-time-delay
	OBJECT-TYPE
	SYNTAX  INTEGER
	ACCESS  read-write
	STATUS  mandatory
	DESCRIPTION "CB33 Warning-Time-Delay"
		::= { bcmsplus2 294 }

bcms2-cb34-warning-time-delay
	OBJECT-TYPE
	SYNTAX  INTEGER
	ACCESS  read-write
	STATUS  mandatory
	DESCRIPTION "CB34 Warning-Time-Delay"
		::= { bcmsplus2 295 }

bcms2-cb35-warning-time-delay
	OBJECT-TYPE
	SYNTAX  INTEGER
	ACCESS  read-write
	STATUS  mandatory
	DESCRIPTION "CB35 Warning-Time-Delay"
		::= { bcmsplus2 296 }

bcms2-cb36-warning-time-delay
	OBJECT-TYPE
	SYNTAX  INTEGER
	ACCESS  read-write
	STATUS  mandatory
	DESCRIPTION "CB36 Warning-Time-Delay"
		::= { bcmsplus2 297 }

bcms2-cb37-warning-time-delay
	OBJECT-TYPE
	SYNTAX  INTEGER
	ACCESS  read-write
	STATUS  mandatory
	DESCRIPTION "CB37 Warning-Time-Delay"
		::= { bcmsplus2 298 }

bcms2-cb38-warning-time-delay
	OBJECT-TYPE
	SYNTAX  INTEGER
	ACCESS  read-write
	STATUS  mandatory
	DESCRIPTION "CB38 Warning-Time-Delay"
		::= { bcmsplus2 299 }

bcms2-cb39-warning-time-delay
	OBJECT-TYPE
	SYNTAX  INTEGER
	ACCESS  read-write
	STATUS  mandatory
	DESCRIPTION "CB39 Warning-Time-Delay"
		::= { bcmsplus2 300 }

bcms2-cb40-warning-time-delay
	OBJECT-TYPE
	SYNTAX  INTEGER
	ACCESS  read-write
	STATUS  mandatory
	DESCRIPTION "CB40 Warning-Time-Delay"
		::= { bcmsplus2 301 }

bcms2-cb41-warning-time-delay
	OBJECT-TYPE
	SYNTAX  INTEGER
	ACCESS  read-write
	STATUS  mandatory
	DESCRIPTION "CB41 Warning-Time-Delay"
		::= { bcmsplus2 302 }

bcms2-cb42-warning-time-delay
	OBJECT-TYPE
	SYNTAX  INTEGER
	ACCESS  read-write
	STATUS  mandatory
	DESCRIPTION "CB42 Warning-Time-Delay"
		::= { bcmsplus2 303 }

bcms2-cb1-alarm-time-delay
	OBJECT-TYPE
	SYNTAX  INTEGER
	ACCESS  read-write
	STATUS  mandatory
	DESCRIPTION "CB1 Alarm-Time-Delay
		       Note for all alarm time delays 1-42: units are in seconds"                     
		::= { bcmsplus2 304 }

bcms2-cb2-alarm-time-delay
	OBJECT-TYPE
	SYNTAX  INTEGER
	ACCESS  read-write
	STATUS  mandatory
	DESCRIPTION "CB2 Alarm-Time-Delay"
		::= { bcmsplus2 305 }
  
bcms2-cb3-alarm-time-delay
	OBJECT-TYPE
	SYNTAX  INTEGER
	ACCESS  read-write
	STATUS  mandatory
	DESCRIPTION "CB3 Alarm-Time-Delay"
		::= { bcmsplus2 306 }

bcms2-cb4-alarm-time-delay
	OBJECT-TYPE
	SYNTAX  INTEGER
	ACCESS  read-write
	STATUS  mandatory
	DESCRIPTION "CB4 Alarm-Time-Delay"
		::= { bcmsplus2 307 }

bcms2-cb5-alarm-time-delay
	OBJECT-TYPE
	SYNTAX  INTEGER
	ACCESS  read-write
	STATUS  mandatory
	DESCRIPTION "CB5 Alarm-Time-Delay"
		::= { bcmsplus2 308 }

bcms2-cb6-alarm-time-delay
	OBJECT-TYPE
	SYNTAX  INTEGER
	ACCESS  read-write
	STATUS  mandatory
	DESCRIPTION "CB6 Alarm-Time-Delay"
		::= { bcmsplus2 309 }

bcms2-cb7-alarm-time-delay
	OBJECT-TYPE
	SYNTAX  INTEGER
	ACCESS  read-write
	STATUS  mandatory
	DESCRIPTION "CB7 Alarm-Time-Delay"
		::= { bcmsplus2 310 }

bcms2-cb8-alarm-time-delay
	OBJECT-TYPE
	SYNTAX  INTEGER
	ACCESS  read-write
	STATUS  mandatory
	DESCRIPTION "CB8 Alarm-Time-Delay"
		::= { bcmsplus2 311 }

bcms2-cb9-alarm-time-delay
	OBJECT-TYPE
	SYNTAX  INTEGER
	ACCESS  read-write
	STATUS  mandatory
	DESCRIPTION "CB9 Alarm-Time-Delay"
		::= { bcmsplus2 312 }

bcms2-cb10-alarm-time-delay
	OBJECT-TYPE
	SYNTAX  INTEGER
	ACCESS  read-write
	STATUS  mandatory
	DESCRIPTION "CB10 Alarm-Time-Delay"
		::= { bcmsplus2 313 }

bcms2-cb11-alarm-time-delay
	OBJECT-TYPE
	SYNTAX  INTEGER
	ACCESS  read-write
	STATUS  mandatory
	DESCRIPTION "CB11 Alarm-Time-Delay"
		::= { bcmsplus2 314 }

bcms2-cb12-alarm-time-delay
	OBJECT-TYPE
	SYNTAX  INTEGER
	ACCESS  read-write
	STATUS  mandatory
	DESCRIPTION "CB12 Alarm-Time-Delay"
		::= { bcmsplus2 315 }
  
bcms2-cb13-alarm-time-delay
	OBJECT-TYPE
	SYNTAX  INTEGER
	ACCESS  read-write
	STATUS  mandatory
	DESCRIPTION "CB13 Alarm-Time-Delay"
		::= { bcmsplus2 316 }

bcms2-cb14-alarm-time-delay
	OBJECT-TYPE
	SYNTAX  INTEGER
	ACCESS  read-write
	STATUS  mandatory
	DESCRIPTION "CB14 Alarm-Time-Delay"
		::= { bcmsplus2 317 }

bcms2-cb15-alarm-time-delay
	OBJECT-TYPE
	SYNTAX  INTEGER
	ACCESS  read-write
	STATUS  mandatory
	DESCRIPTION "CB15 Alarm-Time-Delay"
		::= { bcmsplus2 318 }

bcms2-cb16-alarm-time-delay
	OBJECT-TYPE
	SYNTAX  INTEGER
	ACCESS  read-write
	STATUS  mandatory
	DESCRIPTION "CB16 Alarm-Time-Delay"
		::= { bcmsplus2 319 }

bcms2-cb17-alarm-time-delay
	OBJECT-TYPE
	SYNTAX  INTEGER
	ACCESS  read-write
	STATUS  mandatory
	DESCRIPTION "CB17 Alarm-Time-Delay"
		::= { bcmsplus2 320 }

bcms2-cb18-alarm-time-delay
	OBJECT-TYPE
	SYNTAX  INTEGER
	ACCESS  read-write
	STATUS  mandatory
	DESCRIPTION "CB18 Alarm-Time-Delay"
		::= { bcmsplus2 321 }

bcms2-cb19-alarm-time-delay
	OBJECT-TYPE
	SYNTAX  INTEGER
	ACCESS  read-write
	STATUS  mandatory
	DESCRIPTION "CB19 Alarm-Time-Delay"
		::= { bcmsplus2 322 }

bcms2-cb20-alarm-time-delay
	OBJECT-TYPE
	SYNTAX  INTEGER
	ACCESS  read-write
	STATUS  mandatory
	DESCRIPTION "CB20 Alarm-Time-Delay"
		::= { bcmsplus2 323 }

bcms2-cb21-alarm-time-delay
	OBJECT-TYPE
	SYNTAX  INTEGER
	ACCESS  read-write
	STATUS  mandatory
	DESCRIPTION "CB21 Alarm-Time-Delay"
		::= { bcmsplus2 324 }

bcms2-cb22-alarm-time-delay
	OBJECT-TYPE
	SYNTAX  INTEGER
	ACCESS  read-write
	STATUS  mandatory
	DESCRIPTION "CB22 Alarm-Time-Delay"
		::= { bcmsplus2 325 }
  
bcms2-cb23-alarm-time-delay
	OBJECT-TYPE
	SYNTAX  INTEGER
	ACCESS  read-write
	STATUS  mandatory
	DESCRIPTION "CB23 Alarm-Time-Delay"
		::= { bcmsplus2 326 }

bcms2-cb24-alarm-time-delay
	OBJECT-TYPE
	SYNTAX  INTEGER
	ACCESS  read-write
	STATUS  mandatory
	DESCRIPTION "CB24 Alarm-Time-Delay"
		::= { bcmsplus2 327 }

bcms2-cb25-alarm-time-delay
	OBJECT-TYPE
	SYNTAX  INTEGER
	ACCESS  read-write
	STATUS  mandatory
	DESCRIPTION "CB25 Alarm-Time-Delay"
		::= { bcmsplus2 328 }

bcms2-cb26-alarm-time-delay
	OBJECT-TYPE
	SYNTAX  INTEGER
	ACCESS  read-write
	STATUS  mandatory
	DESCRIPTION "CB26 Alarm-Time-Delay"
		::= { bcmsplus2 329 }

bcms2-cb27-alarm-time-delay
	OBJECT-TYPE
	SYNTAX  INTEGER
	ACCESS  read-write
	STATUS  mandatory
	DESCRIPTION "CB27 Alarm-Time-Delay"
		::= { bcmsplus2 330 }

bcms2-cb28-alarm-time-delay
	OBJECT-TYPE
	SYNTAX  INTEGER
	ACCESS  read-write
	STATUS  mandatory
	DESCRIPTION "CB28 Alarm-Time-Delay"
		::= { bcmsplus2 331 }

bcms2-cb29-alarm-time-delay
	OBJECT-TYPE
	SYNTAX  INTEGER
	ACCESS  read-write
	STATUS  mandatory
	DESCRIPTION "CB29 Alarm-Time-Delay"
		::= { bcmsplus2 332 }

bcms2-cb30-alarm-time-delay
	OBJECT-TYPE
	SYNTAX  INTEGER
	ACCESS  read-write
	STATUS  mandatory
	DESCRIPTION "CB30 Alarm-Time-Delay"
		::= { bcmsplus2 333 }

bcms2-cb31-alarm-time-delay
	OBJECT-TYPE
	SYNTAX  INTEGER
	ACCESS  read-write
	STATUS  mandatory
	DESCRIPTION "CB31 Alarm-Time-Delay"
		::= { bcmsplus2 334 }

bcms2-cb32-alarm-time-delay
	OBJECT-TYPE
	SYNTAX  INTEGER
	ACCESS  read-write
	STATUS  mandatory
	DESCRIPTION "CB32 Alarm-Time-Delay"
		::= { bcmsplus2 335 }
  
bcms2-cb33-alarm-time-delay
	OBJECT-TYPE
	SYNTAX  INTEGER
	ACCESS  read-write
	STATUS  mandatory
	DESCRIPTION "CB33 Alarm-Time-Delay"
		::= { bcmsplus2 336 }

bcms2-cb34-alarm-time-delay
	OBJECT-TYPE
	SYNTAX  INTEGER
	ACCESS  read-write
	STATUS  mandatory
	DESCRIPTION "CB34 Alarm-Time-Delay"
		::= { bcmsplus2 337 }

bcms2-cb35-alarm-time-delay
	OBJECT-TYPE
	SYNTAX  INTEGER
	ACCESS  read-write
	STATUS  mandatory
	DESCRIPTION "CB35 Alarm-Time-Delay"
		::= { bcmsplus2 338 }

bcms2-cb36-alarm-time-delay
	OBJECT-TYPE
	SYNTAX  INTEGER
	ACCESS  read-write
	STATUS  mandatory
	DESCRIPTION "CB36 Alarm-Time-Delay"
		::= { bcmsplus2 339 }

bcms2-cb37-alarm-time-delay
	OBJECT-TYPE
	SYNTAX  INTEGER
	ACCESS  read-write
	STATUS  mandatory
	DESCRIPTION "CB37 Alarm-Time-Delay"
		::= { bcmsplus2 340 }

bcms2-cb38-alarm-time-delay
	OBJECT-TYPE
	SYNTAX  INTEGER
	ACCESS  read-write
	STATUS  mandatory
	DESCRIPTION "CB38 Alarm-Time-Delay"
		::= { bcmsplus2 341 }

bcms2-cb39-alarm-time-delay
	OBJECT-TYPE
	SYNTAX  INTEGER
	ACCESS  read-write
	STATUS  mandatory
	DESCRIPTION "CB39 Alarm-Time-Delay"
		::= { bcmsplus2 342 }

bcms2-cb40-alarm-time-delay
	OBJECT-TYPE
	SYNTAX  INTEGER
	ACCESS  read-write
	STATUS  mandatory
	DESCRIPTION "CB40 Alarm-Time-Delay"
		::= { bcmsplus2 343 }

bcms2-cb41-alarm-time-delay
	OBJECT-TYPE
	SYNTAX  INTEGER
	ACCESS  read-write
	STATUS  mandatory
	DESCRIPTION "CB41 Alarm-Time-Delay"
		::= { bcmsplus2 344 }

bcms2-cb42-alarm-time-delay
	OBJECT-TYPE
	SYNTAX  INTEGER
	ACCESS  read-write
	STATUS  mandatory
	DESCRIPTION "CB42 Alarm-Time-Delay"
		::= { bcmsplus2 345 }

bcms2-global-breaker-size
	OBJECT-TYPE
	SYNTAX  INTEGER
	ACCESS  read-write
	STATUS  mandatory
	DESCRIPTION "Global-breaker-size
		     Note for global breaker size: 10 = 10 amps
                     Range is 10 to 100 amps"
		::= { bcmsplus2 346 }

bcms2-global-warning-threshold
	OBJECT-TYPE
	SYNTAX  INTEGER
	ACCESS  read-write
	STATUS  mandatory
	DESCRIPTION "Global-warning-threshold
		     Note for global warning threshold: 70 = 70% of breaker size
                     range is 0-100%"
		::= { bcmsplus2 347 }

bcms2-global-alarm-threshold
	OBJECT-TYPE
	SYNTAX  INTEGER
	ACCESS  read-write
	STATUS  mandatory
	DESCRIPTION "Global-alarm-threshold
		     Note for global alarm threshold: 80 = 80% of breaker size
                     range is 0-100%"
		::= { bcmsplus2 348 }

bcms2-global-warning-time-delay
	OBJECT-TYPE
	SYNTAX  INTEGER
	ACCESS  read-write
	STATUS  mandatory
	DESCRIPTION "Global-warning-time-delay
		     Note for global warning time delay: units are in seconds"                     
		::= { bcmsplus2 349 }

bcms2-global-alarm-time-delay
	OBJECT-TYPE
	SYNTAX  INTEGER
	ACCESS  read-write
	STATUS  mandatory
	DESCRIPTION "Global-alarm-time-delay
		     Note for global alarm time delay: units are in seconds"                     
		::= { bcmsplus2 350 }

bcms2-min-max-reset
	OBJECT-TYPE
	SYNTAX  INTEGER
	ACCESS  read-write
	STATUS  mandatory
	DESCRIPTION "Min-max-Reset
                     Note for Min-max Reset: writing to this register will clear minimum
		     and maximum current values"
		::= { bcmsplus2 351 }

bcms2-global-warning-alarm-register
	OBJECT-TYPE
	SYNTAX  INTEGER
	ACCESS  read-only
	STATUS  mandatory
	DESCRIPTION "Global-Warning-Alarm-Register
			bit 0:	Warning Register 1
			bit 1:	Warning Register 2
			bit 2:	Warning Register 3
			bit 3:	Alarm Register 1
			bit 4:	Alarm Register 2
			bit 5:	Alarm Register 3
			bit 6:	Zero Current Register 1
			bit 7:	Zero Current Register 2
			bit 8:	Zero Current Register 3
			bits 9 – 15: Always read as 0"
		::= { bcmsplus2 352 }

bcms2-meter-alarm-status-latching
	OBJECT-TYPE
	SYNTAX  INTEGER
	ACCESS  read-write
	STATUS  mandatory
	DESCRIPTION "Meter-Alarm-Status-Latching
			bit 0:	Over Current panelboard
			bit 1:	Under Current panelboard
			bit 2: 	Over Current both panelboards 
			bit 3: 	Under Current both panelboards
			bit 4: 	Over Voltage main
			bit 5: 	Under Voltage main
			bit 6: 	Over Voltage alternate
			bit 7: 	Under Voltage alternate
			bits 8 – 15: Not Used"
		::= { bcmsplus2 353 }

bcms2-meter-alarm-status-nonlatching
	OBJECT-TYPE
	SYNTAX  INTEGER
	ACCESS  read-only
	STATUS  mandatory
	DESCRIPTION "Meter-Alarm-Status-Nonlatching
			bit 0:	Over Current panelboard
			bit 1:	Under Current panelboard
			bit 2: 	Over Current both panelboards 
			bit 3: 	Under Current both panelboards
			bit 4: 	Over Voltage main
			bit 5: 	Under Voltage main
			bit 6: 	Over Voltage alternate
			bit 7: 	Under Voltage alternate
			bits 8 – 15: Not Used"
		::= { bcmsplus2 354 }

bcms2-digital-alarm-status
	OBJECT-TYPE
	SYNTAX  INTEGER
	ACCESS  read-only
	STATUS  mandatory
	DESCRIPTION "Digital-Alarm-Status
			bit 0:	Digital alarm 1
			bit 1:	Digital alarm 2
			bit 2: 	Digital alarm 3
			bit 3: 	Digital alarm 4
			bits 4 – 15: Not Used"
		::= { bcmsplus2 355 }

bcms2-current-option-setting
	OBJECT-TYPE
	SYNTAX  INTEGER
	ACCESS  read-only
	STATUS  mandatory
	DESCRIPTION "Current-Option-Setting
			bit 0:	option 0
			bit 1:	option 1
			bit 2: 	option 2 
			bit 3: 	neutral CTs
			bit 4:	no branch CTs
		     Option 0: no main or panelboard CTs. 	(357-359 summation of branch)
								(367-376 not used)
		     Option 1: CTs on main input feeding both panelboards. 
								(357-359 summation of branch)
		     Option 2: CTs on each panel board. 	(367-376 summation of panelboard 1 and 2) 
		     Note: Neutral current monitoring is optional."
		::= { bcmsplus2 356 }

bcms2-current-phase-a-panelboard
	OBJECT-TYPE
	SYNTAX  INTEGER
	ACCESS  read-only
	STATUS  mandatory
	DESCRIPTION "Current-Phase-A-Panelboard
                     Note for all currents: 100 = 10.0 amps"
		::= { bcmsplus2 357 }

bcms2-current-phase-b-panelboard
	OBJECT-TYPE
	SYNTAX  INTEGER
	ACCESS  read-only
	STATUS  mandatory
	DESCRIPTION "Current-Phase-B-Panelboard"
		::= { bcmsplus2 358 }

bcms2-current-phase-c-panelboard
	OBJECT-TYPE
	SYNTAX  INTEGER
	ACCESS  read-only
	STATUS  mandatory
	DESCRIPTION "Current-Phase-C-Panelboard"
		::= { bcmsplus2 359 }

bcms2-current-neutral-panelboard
	OBJECT-TYPE
	SYNTAX  INTEGER
	ACCESS  read-only
	STATUS  mandatory
	DESCRIPTION "Current-Neutral-Panelboard"
		::= { bcmsplus2 360 }


bcms2-over-current-alarm-threshhold-pnlbd
	OBJECT-TYPE
	SYNTAX  INTEGER
	ACCESS  read-write
	STATUS  mandatory
	DESCRIPTION "Over-Current-Alarm-Threshhold-Pnlbd"
		::= { bcmsplus2 361 }

bcms2-under-current-alarm-threshhold-pnlbd
	OBJECT-TYPE
	SYNTAX  INTEGER
	ACCESS  read-write
	STATUS  mandatory
	DESCRIPTION "Under-Current-Alarm-Threshhold-Pnlbd"
		::= { bcmsplus2 362 }

bcms2-over-current-set-counter-pnlbd
	OBJECT-TYPE
	SYNTAX  INTEGER
	ACCESS  read-only
	STATUS  mandatory
	DESCRIPTION "Over-Current-Set-Counter-Pnlbd
		     Note for all counters:
                     The set counter is incremented when the value goes outside the threshold limit
                     The reset counter is incremented when the value is returns to  the threshold limit"
		::= { bcmsplus2 363 }

bcms2-over-current-reset-counter-pnlbd
	OBJECT-TYPE
	SYNTAX  INTEGER
	ACCESS  read-only
	STATUS  mandatory
	DESCRIPTION "Over-Current-Reset-Counter-Pnlbd"
		::= { bcmsplus2 364 }

bcms2-under-current-set-counter-pnlbd
	OBJECT-TYPE
	SYNTAX  INTEGER
	ACCESS  read-only
	STATUS  mandatory
	DESCRIPTION "Under-Current-Set-Counter-Pnlbd"
		::= { bcmsplus2 365 }

bcms2-under-current-reset-counter-pnlbd
	OBJECT-TYPE
	SYNTAX  INTEGER
	ACCESS  read-only
	STATUS  mandatory
	DESCRIPTION "Under-Current-Reset-Counter-Pnlbd"
		::= { bcmsplus2 366 }

bcms2-current-phase-a-both-pnlbd
	OBJECT-TYPE
	SYNTAX  INTEGER
	ACCESS  read-only
	STATUS  mandatory
	DESCRIPTION "Current-Phase-A-Both-Pnlbd"
		::= { bcmsplus2 367 }

bcms2-current-phase-b-both-pnlbd
	OBJECT-TYPE
	SYNTAX  INTEGER
	ACCESS  read-only
	STATUS  mandatory
	DESCRIPTION "Current-Phase-B-Both-Pnlbd"
		::= { bcmsplus2 368 }

bcms2-current-phase-c-both-pnlbd
	OBJECT-TYPE
	SYNTAX  INTEGER
	ACCESS  read-only
	STATUS  mandatory
	DESCRIPTION "Current-Phase-C-Both-Pnlbd"
		::= { bcmsplus2 369 }

bcms2-current-neutral-both-pnlbd
	OBJECT-TYPE
	SYNTAX  INTEGER
	ACCESS  read-only
	STATUS  mandatory
	DESCRIPTION "Current-Neutral-Both-Pnlbd"
		::= { bcmsplus2 370 }


bcms2-over-current-alarm-threshhold-both-pnlbd
	OBJECT-TYPE
	SYNTAX  INTEGER
	ACCESS  read-write
	STATUS  mandatory
	DESCRIPTION "Over-Current-Alarm-Threshhold-Both-Pnlbd"
		::= { bcmsplus2 371 }

bcms2-under-current-alarm-threshhold-both-pnlbd
	OBJECT-TYPE
	SYNTAX  INTEGER
	ACCESS  read-write
	STATUS  mandatory
	DESCRIPTION "Under-Current-Alarm-Threshhold-Both-Pnlbd"
		::= { bcmsplus2 372 }

bcms2-over-current-set-counter-both-pnlbd
	OBJECT-TYPE
	SYNTAX  INTEGER
	ACCESS  read-only
	STATUS  mandatory
	DESCRIPTION "Over-Current-Set-Counter-Both-Pnlbd"
		::= { bcmsplus2 373 }

bcms2-over-current-reset-counter-both-pnlbd
	OBJECT-TYPE
	SYNTAX  INTEGER
	ACCESS  read-only
	STATUS  mandatory
	DESCRIPTION "Over-Current-Reset-Counter-Both-Pnlbd"
		::= { bcmsplus2 374 }

bcms2-under-current-set-counter-both-pnlbd
	OBJECT-TYPE
	SYNTAX  INTEGER
	ACCESS  read-only
	STATUS  mandatory
	DESCRIPTION "Under-Current-Set-Counter-Both-Pnlbd"
		::= { bcmsplus2 375 }

bcms2-under-current-reset-counter-both-pnlbd
	OBJECT-TYPE
	SYNTAX  INTEGER
	ACCESS  read-only
	STATUS  mandatory
	DESCRIPTION "Under-Current-Reset-Counter-Both-Pnlbd"
		::= { bcmsplus2 376 }

bcms2-voltage-option-setting
	OBJECT-TYPE
	SYNTAX  INTEGER
	ACCESS  read-only
	STATUS  mandatory
	DESCRIPTION "Voltage-Option-Setting
			bit 0:	option 0
			bit 1:	option 1
			bit 2: 	option 2 
			bit 3: 	option 3 
			bits 4 – 15: Not Used
                     Option 0: no voltage monitoring. (378-414 not used)
                     Option 1: One voltage feeding 1 or 2 panel boards. (390-401 not used)
                     Option 2: One voltage feeding panelboard 1 and another feeding panelboard 2. (390-401 not used)
                     Option 3: Two voltages tied together through interlocked circuit breakers feeding both panelboards. 
                               Digital input 1 and 2 are used to determine which is feeding the panelboard. A set bit 
                               indicated closed.  If both are closed, main voltage is used."
		::= { bcmsplus2 377 }

bcms2-voltage-a-b-main
	OBJECT-TYPE
	SYNTAX  INTEGER
	ACCESS  read-only
	STATUS  mandatory
	DESCRIPTION "Voltage-A-B-Main
                     Note for all voltages: 1200 = 120.0 volts"
		::= { bcmsplus2 378 }

bcms2-voltage-b-c-main
	OBJECT-TYPE
	SYNTAX  INTEGER
	ACCESS  read-only
	STATUS  mandatory
	DESCRIPTION "Voltage-B-C-Main"
		::= { bcmsplus2 379 }

bcms2-voltage-c-a-main
	OBJECT-TYPE
	SYNTAX  INTEGER
	ACCESS  read-only
	STATUS  mandatory
	DESCRIPTION "Voltage-C-A-Main"
		::= { bcmsplus2 380 }

bcms2-voltage-a-n-main
	OBJECT-TYPE
	SYNTAX  INTEGER
	ACCESS  read-only
	STATUS  mandatory
	DESCRIPTION "Voltage-A-N-Main"
		::= { bcmsplus2 381 }

bcms2-voltage-b-n-main
	OBJECT-TYPE
	SYNTAX  INTEGER
	ACCESS  read-only
	STATUS  mandatory
	DESCRIPTION "Voltage-B-N-Main"
		::= { bcmsplus2 382 }

bcms2-voltage-c-n-main
	OBJECT-TYPE
	SYNTAX  INTEGER
	ACCESS  read-only
	STATUS  mandatory
	DESCRIPTION "Voltage-C-N-Main"
		::= { bcmsplus2 383 }

bcms2-over-voltage-alarm-threshhold-main
	OBJECT-TYPE
	SYNTAX  INTEGER
	ACCESS  read-write
	STATUS  mandatory
	DESCRIPTION "Over-Voltage-Alarm-Threshhold-Main
                     Note All Over and Under Voltage is for L-L values"
		::= { bcmsplus2 384 }

bcms2-under-voltage-alarm-threshhold-main
	OBJECT-TYPE
	SYNTAX  INTEGER
	ACCESS  read-write
	STATUS  mandatory
	DESCRIPTION "Under-Voltage-Alarm-Threshhold-Main"
		::= { bcmsplus2 385 }

bcms2-over-voltage-set-counter-main
	OBJECT-TYPE
	SYNTAX  INTEGER
	ACCESS  read-only
	STATUS  mandatory
	DESCRIPTION "Over-Voltage-Set-Counter-Main"
		::= { bcmsplus2 386 }

bcms2-over-voltage-reset-counter-main
	OBJECT-TYPE
	SYNTAX  INTEGER
	ACCESS  read-only
	STATUS  mandatory
	DESCRIPTION "Over-Voltage-Reset-Counter-Main"
		::= { bcmsplus2 387 }

bcms2-under-voltage-set-counter-main
	OBJECT-TYPE
	SYNTAX  INTEGER
	ACCESS  read-only
	STATUS  mandatory
	DESCRIPTION "Under-Voltage-Set-Counter-Main"
		::= { bcmsplus2 388 }

bcms2-under-voltage-reset-counter-main
	OBJECT-TYPE
	SYNTAX  INTEGER
	ACCESS  read-only
	STATUS  mandatory
	DESCRIPTION "Under-Voltage-Reset-Counter-Main"
		::= { bcmsplus2 389 }


bcms2-voltage-frequency-main
	OBJECT-TYPE
	SYNTAX  INTEGER
	ACCESS  read-only
	STATUS  mandatory
	DESCRIPTION "Voltage-Frequency-Main
                     note for frequency: 600 = 60.0Hz
                     Range is 40-70Hz
                     Note if insufficient voltage is present frequency will read 0xFFFF"
		::= { bcmsplus2 390 }

bcms2-voltage-a-b-alternate
	OBJECT-TYPE
	SYNTAX  INTEGER
	ACCESS  read-only
	STATUS  mandatory
	DESCRIPTION "Voltage-A-B-Alternate"
		::= { bcmsplus2 391 }

bcms2-voltage-b-c-alternate
	OBJECT-TYPE
	SYNTAX  INTEGER
	ACCESS  read-only
	STATUS  mandatory
	DESCRIPTION "Voltage-B-C-Alternate"
		::= { bcmsplus2 392 }

bcms2-voltage-c-a-alternate
	OBJECT-TYPE
	SYNTAX  INTEGER
	ACCESS  read-only
	STATUS  mandatory
	DESCRIPTION "Voltage-C-A-Alternate"
		::= { bcmsplus2 393 }

bcms2-voltage-a-n-alternate
	OBJECT-TYPE
	SYNTAX  INTEGER
	ACCESS  read-only
	STATUS  mandatory
	DESCRIPTION "Voltage-A-N-Alternate"
		::= { bcmsplus2 394 }

bcms2-voltage-b-N-alternate
	OBJECT-TYPE
	SYNTAX  INTEGER
	ACCESS  read-only
	STATUS  mandatory
	DESCRIPTION "Voltage-B-N-Alternate"
		::= { bcmsplus2 395 }

bcms2-voltage-c-n-alternate
	OBJECT-TYPE
	SYNTAX  INTEGER
	ACCESS  read-only
	STATUS  mandatory
	DESCRIPTION "Voltage-C-N-Alternate"
		::= { bcmsplus2 396 }

bcms2-over-voltage-alarm-threshhold-alternate
	OBJECT-TYPE
	SYNTAX  INTEGER
	ACCESS  read-write
	STATUS  mandatory
	DESCRIPTION "Over-Voltage-Alarm-Threshhold-Alternate"
		::= { bcmsplus2 397 }

bcms2-under-voltage-alarm-threshhold-alternate
	OBJECT-TYPE
	SYNTAX  INTEGER
	ACCESS  read-write
	STATUS  mandatory
	DESCRIPTION "Under-Voltage-Alarm-Threshhold-Alternate"
		::= { bcmsplus2 398 }

bcms2-over-voltage-set-counter-alternate
	OBJECT-TYPE
	SYNTAX  INTEGER
	ACCESS  read-only
	STATUS  mandatory
	DESCRIPTION "Over-Voltage-Set-Counter-Alternate"
		::= { bcmsplus2 399 }

bcms2-over-voltage-reset-counter-alternate
	OBJECT-TYPE
	SYNTAX  INTEGER
	ACCESS  read-only
	STATUS  mandatory
	DESCRIPTION "Over-Voltage-Reset-Counter-Alternate"
		::= { bcmsplus2 400 }

bcms2-under-voltage-set-counter-alternate
	OBJECT-TYPE
	SYNTAX  INTEGER
	ACCESS  read-only
	STATUS  mandatory
	DESCRIPTION "Under-Voltage-Set-Counter-Alternate"
		::= { bcmsplus2 401 }

bcms2-under-voltage-reset-counter-alternate
	OBJECT-TYPE
	SYNTAX  INTEGER
	ACCESS  read-only
	STATUS  mandatory
	DESCRIPTION "Under-Voltage-Reset-Counter-Alternate"
		::= { bcmsplus2 402 }

bcms2-real-power-kw
	OBJECT-TYPE
	SYNTAX  INTEGER
	ACCESS  read-only
	STATUS  mandatory
	DESCRIPTION "Real-Power-KW
                     Note for all KWs: 100 = 10.0 KW"
		::= { bcmsplus2 403 }

bcms2-peal-power-phase-a
	OBJECT-TYPE
	SYNTAX  INTEGER
	ACCESS  read-only
	STATUS  mandatory
	DESCRIPTION "Real-Power-Phase-A"
		::= { bcmsplus2 404 }

bcms2-real-power-phase-b
	OBJECT-TYPE
	SYNTAX  INTEGER
	ACCESS  read-only
	STATUS  mandatory
	DESCRIPTION "Real-Power-Phase-B"
		::= { bcmsplus2 405 }

bcms2-real-power-phase-c
	OBJECT-TYPE
	SYNTAX  INTEGER
	ACCESS  read-only
	STATUS  mandatory
	DESCRIPTION "Real-Power-Phase-C"
		::= { bcmsplus2 406 }

bcms2-reactive-power-kvar
	OBJECT-TYPE
	SYNTAX  INTEGER
	ACCESS  read-only
	STATUS  mandatory
	DESCRIPTION "Reactive-Power-KVAR
                     Note for KVAR: 100 = 10.0 KVAR"
		::= { bcmsplus2 407 }

bcms2-apparent-Power-kva
	OBJECT-TYPE
	SYNTAX  INTEGER
	ACCESS  read-only
	STATUS  mandatory
	DESCRIPTION "Apparent-Power-KVA
                     Note for KVA: 100 = 10.0 KVA"
		::= { bcmsplus2 408 }

bcms2-total-power-factor
	OBJECT-TYPE
	SYNTAX  INTEGER
	ACCESS  read-only
	STATUS  mandatory
	DESCRIPTION "Total-Power-Factor
                     Note for all Power Factor: 1000 = 100.0 PF"
		::= { bcmsplus2 409 }

bcms2-power-factor-phase-a
	OBJECT-TYPE
	SYNTAX  INTEGER
	ACCESS  read-only
	STATUS  mandatory
	DESCRIPTION "Power-Factor-Phase-A"
		::= { bcmsplus2 410 }

bcms2-Power-factor-phase-b
	OBJECT-TYPE
	SYNTAX  INTEGER
	ACCESS  read-only
	STATUS  mandatory
	DESCRIPTION "Power-Factor-Phase-B"
		::= { bcmsplus2 411 }

bcms2-Power-factor-phase-c
	OBJECT-TYPE
	SYNTAX  INTEGER
	ACCESS  read-only
	STATUS  mandatory
	DESCRIPTION "Power-Factor-Phase-C"
		::= { bcmsplus2 412 }

bcms2-energy-consumption-kwh-lower-word-integer
	OBJECT-TYPE
	SYNTAX  INTEGER
	ACCESS  read-write
	STATUS  mandatory
	DESCRIPTION "Energy-Consumption-KWh-Lower-Word-Integer
		     Note for KWh: 100 = 100KWh
                     Combine lower and upper integers into a word for total KWh"
		::= { bcmsplus2 413 }

bcms2-energy-consumption-kwh-upper-word-integer
	OBJECT-TYPE
	SYNTAX  INTEGER
	ACCESS  read-write
	STATUS  mandatory
	DESCRIPTION "Energy-Consumption-KWh-Upper-Word-Integer"
		::= { bcmsplus2 414 }

bcms2-main-voltage-thd-phase-a
	OBJECT-TYPE
	SYNTAX  INTEGER
	ACCESS  read-only
	STATUS  mandatory
	DESCRIPTION "Main-Voltage-THD-Phase-A"
		::= { bcmsplus2 415 }

bcms2-main-voltage-thd-phase-b
	OBJECT-TYPE
	SYNTAX  INTEGER
	ACCESS  read-only
	STATUS  mandatory
	DESCRIPTION "Main-Voltage-THD-Phase-B"
		::= { bcmsplus2 416 }

bcms2-main-voltage-thd-phase-c
	OBJECT-TYPE
	SYNTAX  INTEGER
	ACCESS  read-only
	STATUS  mandatory
	DESCRIPTION "Main-Voltage-THD-Phase-C"
		::= { bcmsplus2 417 }

bcms2-alt-voltage-thd-phase-a
	OBJECT-TYPE
	SYNTAX  INTEGER
	ACCESS  read-only
	STATUS  mandatory
	DESCRIPTION "Alt-Voltage-THD-Phase-A"
		::= { bcmsplus2 418 }

bcms2-alt-voltage-thd-phase-b
	OBJECT-TYPE
	SYNTAX  INTEGER
	ACCESS  read-only
	STATUS  mandatory
	DESCRIPTION "Alt-Voltage-THD-Phase-B"
		::= { bcmsplus2 419 }

bcms2-alt-voltage-thd-phase-c
	OBJECT-TYPE
	SYNTAX  INTEGER
	ACCESS  read-only
	STATUS  mandatory
	DESCRIPTION "Alt-Voltage-THD-Phase-C"
		::= { bcmsplus2 420 }

bcms2-current-ground-panelboard
	OBJECT-TYPE
	SYNTAX  INTEGER
	ACCESS  read-only
	STATUS  mandatory
	DESCRIPTION "Current-Ground-Panelboard"
		::= { bcmsplus2 421 }

bcms2-percent-load-phase-a
	OBJECT-TYPE
	SYNTAX  INTEGER
	ACCESS  read-only
	STATUS  mandatory
	DESCRIPTION "Percent Load Phase A"
		::= { bcmsplus2 422 }

bcms2-percent-load-phase-b
	OBJECT-TYPE
	SYNTAX  INTEGER
	ACCESS  read-only
	STATUS  mandatory
	DESCRIPTION "Percent Load Phase B"
		::= { bcmsplus2 423 }

bcms2-percent-load-phase-c
	OBJECT-TYPE
	SYNTAX  INTEGER
	ACCESS  read-only
	STATUS  mandatory
	DESCRIPTION "Percent Load Phase C"
		::= { bcmsplus2 424 }

bcms2-full-load-current
	OBJECT-TYPE
	SYNTAX  INTEGER
	ACCESS  read-write
	STATUS  mandatory
	DESCRIPTION "Full Load Current"
		::= { bcmsplus2 425 }

--------------------------------------------------------------------------------
-- BCMSPLUS register values
--------------------------------------------------------------------------------

bcms3-cb1-current
	OBJECT-TYPE
	SYNTAX  INTEGER
	ACCESS  read-only
	STATUS  mandatory
	DESCRIPTION "CB1 Current
		     Note for all currents 1-42: 100 = 10.0 amps"
		::= { bcmsplus3 1 }
  
bcms3-cb2-current
	OBJECT-TYPE
	SYNTAX  INTEGER
	ACCESS  read-only
	STATUS  mandatory
	DESCRIPTION "CB2 Current"
		::= { bcmsplus3 2 }

bcms3-cb3-current
	OBJECT-TYPE
	SYNTAX  INTEGER
	ACCESS  read-only
	STATUS  mandatory
	DESCRIPTION "CB3 Current"
		::= { bcmsplus3 3 }

bcms3-cb4-current
	OBJECT-TYPE
	SYNTAX  INTEGER
	ACCESS  read-only
	STATUS  mandatory
	DESCRIPTION "CB4 Current"
		::= { bcmsplus3 4 }

bcms3-cb5-current
	OBJECT-TYPE
	SYNTAX  INTEGER
	ACCESS  read-only
	STATUS  mandatory
	DESCRIPTION "CB5 Current"
		::= { bcmsplus3 5 }

bcms3-cb6-current
	OBJECT-TYPE
	SYNTAX  INTEGER
	ACCESS  read-only
	STATUS  mandatory
	DESCRIPTION "CB6 Current"
		::= { bcmsplus3 6 }

bcms3-cb7-current
	OBJECT-TYPE
	SYNTAX  INTEGER
	ACCESS  read-only
	STATUS  mandatory
	DESCRIPTION "CB7 Current"
		::= { bcmsplus3 7 }

bcms3-cb8-current
	OBJECT-TYPE
	SYNTAX  INTEGER
	ACCESS  read-only
	STATUS  mandatory
	DESCRIPTION "CB8 Current"
		::= { bcmsplus3 8 }

bcms3-cb9-current
	OBJECT-TYPE
	SYNTAX  INTEGER
	ACCESS  read-only
	STATUS  mandatory
	DESCRIPTION "CB9 Current"
		::= { bcmsplus3 9 }

bcms3-cb10-current
	OBJECT-TYPE
	SYNTAX  INTEGER
	ACCESS  read-only
	STATUS  mandatory
	DESCRIPTION "CB10 Current"
		::= { bcmsplus3 10 }

bcms3-cb11-current
	OBJECT-TYPE
	SYNTAX  INTEGER
	ACCESS  read-only
	STATUS  mandatory
	DESCRIPTION "CB11 Current"
		::= { bcmsplus3 11 }
  
bcms3-cb12-current
	OBJECT-TYPE
	SYNTAX  INTEGER
	ACCESS  read-only
	STATUS  mandatory
	DESCRIPTION "CB12 Current"
		::= { bcmsplus3 12 }

bcms3-cb13-current
	OBJECT-TYPE
	SYNTAX  INTEGER
	ACCESS  read-only
	STATUS  mandatory
	DESCRIPTION "CB13 Current"
		::= { bcmsplus3 13 }

bcms3-cb14-current
	OBJECT-TYPE
	SYNTAX  INTEGER
	ACCESS  read-only
	STATUS  mandatory
	DESCRIPTION "CB14 Current"
		::= { bcmsplus3 14 }

bcms3-cb15-current
	OBJECT-TYPE
	SYNTAX  INTEGER
	ACCESS  read-only
	STATUS  mandatory
	DESCRIPTION "CB15 Current"
		::= { bcmsplus3 15 }

bcms3-cb16-current
	OBJECT-TYPE
	SYNTAX  INTEGER
	ACCESS  read-only
	STATUS  mandatory
	DESCRIPTION "CB16 Current"
		::= { bcmsplus3 16 }

bcms3-cb17-current
	OBJECT-TYPE
	SYNTAX  INTEGER
	ACCESS  read-only
	STATUS  mandatory
	DESCRIPTION "CB17 Current"
		::= { bcmsplus3 17 }

bcms3-cb18-current
	OBJECT-TYPE
	SYNTAX  INTEGER
	ACCESS  read-only
	STATUS  mandatory
	DESCRIPTION "CB18 Current"
		::= { bcmsplus3 18 }

bcms3-cb19-current
	OBJECT-TYPE
	SYNTAX  INTEGER
	ACCESS  read-only
	STATUS  mandatory
	DESCRIPTION "CB19 Current"
		::= { bcmsplus3 19 }

bcms3-cb20-current
	OBJECT-TYPE
	SYNTAX  INTEGER
	ACCESS  read-only
	STATUS  mandatory
	DESCRIPTION "CB20 Current"
		::= { bcmsplus3 20 }

bcms3-cb21-current
	OBJECT-TYPE
	SYNTAX  INTEGER
	ACCESS  read-only
	STATUS  mandatory
	DESCRIPTION "CB21 Current"
		::= { bcmsplus3 21 }
  
bcms3-cb22-current
	OBJECT-TYPE
	SYNTAX  INTEGER
	ACCESS  read-only
	STATUS  mandatory
	DESCRIPTION "CB22 Current"
		::= { bcmsplus3 22 }

bcms3-cb23-current
	OBJECT-TYPE
	SYNTAX  INTEGER
	ACCESS  read-only
	STATUS  mandatory
	DESCRIPTION "CB23 Current"
		::= { bcmsplus3 23 }

bcms3-cb24-current
	OBJECT-TYPE
	SYNTAX  INTEGER
	ACCESS  read-only
	STATUS  mandatory
	DESCRIPTION "CB24 Current"
		::= { bcmsplus3 24 }

bcms3-cb25-current
	OBJECT-TYPE
	SYNTAX  INTEGER
	ACCESS  read-only
	STATUS  mandatory
	DESCRIPTION "CB25 Current"
		::= { bcmsplus3 25 }

bcms3-cb26-current
	OBJECT-TYPE
	SYNTAX  INTEGER
	ACCESS  read-only
	STATUS  mandatory
	DESCRIPTION "CB26 Current"
		::= { bcmsplus3 26 }

bcms3-cb27-current
	OBJECT-TYPE
	SYNTAX  INTEGER
	ACCESS  read-only
	STATUS  mandatory
	DESCRIPTION "CB27 Current"
		::= { bcmsplus3 27 }

bcms3-cb28-current
	OBJECT-TYPE
	SYNTAX  INTEGER
	ACCESS  read-only
	STATUS  mandatory
	DESCRIPTION "CB28 Current"
		::= { bcmsplus3 28 }

bcms3-cb29-current
	OBJECT-TYPE
	SYNTAX  INTEGER
	ACCESS  read-only
	STATUS  mandatory
	DESCRIPTION "CB29 Current"
		::= { bcmsplus3 29 }

bcms3-cb30-current
	OBJECT-TYPE
	SYNTAX  INTEGER
	ACCESS  read-only
	STATUS  mandatory
	DESCRIPTION "CB30 Current"
		::= { bcmsplus3 30 }

bcms3-cb31-current
	OBJECT-TYPE
	SYNTAX  INTEGER
	ACCESS  read-only
	STATUS  mandatory
	DESCRIPTION "CB31 Current"
		::= { bcmsplus3 31 }
  
bcms3-cb32-current
	OBJECT-TYPE
	SYNTAX  INTEGER
	ACCESS  read-only
	STATUS  mandatory
	DESCRIPTION "CB32 Current"
		::= { bcmsplus3 32 }

bcms3-cb33-current
	OBJECT-TYPE
	SYNTAX  INTEGER
	ACCESS  read-only
	STATUS  mandatory
	DESCRIPTION "CB33 Current"
		::= { bcmsplus3 33 }

bcms3-cb34-current
	OBJECT-TYPE
	SYNTAX  INTEGER
	ACCESS  read-only
	STATUS  mandatory
	DESCRIPTION "CB34 Current"
		::= { bcmsplus3 34 }

bcms3-cb35-current
	OBJECT-TYPE
	SYNTAX  INTEGER
	ACCESS  read-only
	STATUS  mandatory
	DESCRIPTION "CB35 Current"
		::= { bcmsplus3 35 }

bcms3-cb36-current
	OBJECT-TYPE
	SYNTAX  INTEGER
	ACCESS  read-only
	STATUS  mandatory
	DESCRIPTION "CB36 Current"
		::= { bcmsplus3 36 }

bcms3-cb37-current
	OBJECT-TYPE
	SYNTAX  INTEGER
	ACCESS  read-only
	STATUS  mandatory
	DESCRIPTION "CB37 Current"
		::= { bcmsplus3 37 }

bcms3-cb38-current
	OBJECT-TYPE
	SYNTAX  INTEGER
	ACCESS  read-only
	STATUS  mandatory
	DESCRIPTION "CB38 Current"
		::= { bcmsplus3 38 }

bcms3-cb39-current
	OBJECT-TYPE
	SYNTAX  INTEGER
	ACCESS  read-only
	STATUS  mandatory
	DESCRIPTION "CB39 Current"
		::= { bcmsplus3 39 }

bcms3-cb40-current
	OBJECT-TYPE
	SYNTAX  INTEGER
	ACCESS  read-only
	STATUS  mandatory
	DESCRIPTION "CB40 Current"
		::= { bcmsplus3 40 }

bcms3-cb41-current
	OBJECT-TYPE
	SYNTAX  INTEGER
	ACCESS  read-only
	STATUS  mandatory
	DESCRIPTION "CB41 Current"
		::= { bcmsplus3 41 }
  
bcms3-cb42-current
	OBJECT-TYPE
	SYNTAX  INTEGER
	ACCESS  read-only
	STATUS  mandatory
	DESCRIPTION "CB42 Current"
		::= { bcmsplus3 42 }

bcms3-cb1-min
	OBJECT-TYPE
	SYNTAX  INTEGER
	ACCESS  read-only
	STATUS  mandatory
	DESCRIPTION "CB1 Min
		     Note for all minumum currents 1-42: 100 = 10.0 amps"
		::= { bcmsplus3 43 }

bcms3-cb2-min
	OBJECT-TYPE
	SYNTAX  INTEGER
	ACCESS  read-only
	STATUS  mandatory
	DESCRIPTION "CB2 Min"
		::= { bcmsplus3 44 }

bcms3-cb3-min
	OBJECT-TYPE
	SYNTAX  INTEGER
	ACCESS  read-only
	STATUS  mandatory
	DESCRIPTION "CB3 Min"
		::= { bcmsplus3 45 }

bcms3-cb4-min
	OBJECT-TYPE
	SYNTAX  INTEGER
	ACCESS  read-only
	STATUS  mandatory
	DESCRIPTION "CB4 Min"
		::= { bcmsplus3 46 }

bcms3-cb5-min
	OBJECT-TYPE
	SYNTAX  INTEGER
	ACCESS  read-only
	STATUS  mandatory
	DESCRIPTION "CB5 Min"
		::= { bcmsplus3 47 }

bcms3-cb6-min
	OBJECT-TYPE
	SYNTAX  INTEGER
	ACCESS  read-only
	STATUS  mandatory
	DESCRIPTION "CB6 Min"
		::= { bcmsplus3 48 }

bcms3-cb7-min
	OBJECT-TYPE
	SYNTAX  INTEGER
	ACCESS  read-only
	STATUS  mandatory
	DESCRIPTION "CB7 Min"
		::= { bcmsplus3 49 }

bcms3-cb8-min
	OBJECT-TYPE
	SYNTAX  INTEGER
	ACCESS  read-only
	STATUS  mandatory
	DESCRIPTION "CB8 Min"
		::= { bcmsplus3 50 }

bcms3-cb9-min
	OBJECT-TYPE
	SYNTAX  INTEGER
	ACCESS  read-only
	STATUS  mandatory
	DESCRIPTION "CB9 Min"
		::= { bcmsplus3 51 }
  
bcms3-cb10-min
	OBJECT-TYPE
	SYNTAX  INTEGER
	ACCESS  read-only
	STATUS  mandatory
	DESCRIPTION "CB10 Min"
		::= { bcmsplus3 52 }

bcms3-cb11-min
	OBJECT-TYPE
	SYNTAX  INTEGER
	ACCESS  read-only
	STATUS  mandatory
	DESCRIPTION "CB11 Min"
		::= { bcmsplus3 53 }

bcms3-cb12-min
	OBJECT-TYPE
	SYNTAX  INTEGER
	ACCESS  read-only
	STATUS  mandatory
	DESCRIPTION "CB12 Min"
		::= { bcmsplus3 54 }

bcms3-cb13-min
	OBJECT-TYPE
	SYNTAX  INTEGER
	ACCESS  read-only
	STATUS  mandatory
	DESCRIPTION "CB13 Min"
		::= { bcmsplus3 55 }

bcms3-cb14-min
	OBJECT-TYPE
	SYNTAX  INTEGER
	ACCESS  read-only
	STATUS  mandatory
	DESCRIPTION "CB14 Min"
		::= { bcmsplus3 56 }

bcms3-cb15-min
	OBJECT-TYPE
	SYNTAX  INTEGER
	ACCESS  read-only
	STATUS  mandatory
	DESCRIPTION "CB15 Min"
		::= { bcmsplus3 57 }

bcms3-cb16-min
	OBJECT-TYPE
	SYNTAX  INTEGER
	ACCESS  read-only
	STATUS  mandatory
	DESCRIPTION "CB16 Min"
		::= { bcmsplus3 58 }

bcms3-cb17-min
	OBJECT-TYPE
	SYNTAX  INTEGER
	ACCESS  read-only
	STATUS  mandatory
	DESCRIPTION "CB17 Min"
		::= { bcmsplus3 59 }


bcms3-cb18-min
	OBJECT-TYPE
	SYNTAX  INTEGER
	ACCESS  read-only
	STATUS  mandatory
	DESCRIPTION "CB18 Min"
		::= { bcmsplus3 60 }

bcms3-cb19-min
	OBJECT-TYPE
	SYNTAX  INTEGER
	ACCESS  read-only
	STATUS  mandatory
	DESCRIPTION "CB19 Min"
		::= { bcmsplus3 61 }
  
bcms3-cb20-min
	OBJECT-TYPE
	SYNTAX  INTEGER
	ACCESS  read-only
	STATUS  mandatory
	DESCRIPTION "CB20 Min"
		::= { bcmsplus3 62 }

bcms3-cb21-min
	OBJECT-TYPE
	SYNTAX  INTEGER
	ACCESS  read-only
	STATUS  mandatory
	DESCRIPTION "CB21 Min"
		::= { bcmsplus3 63 }

bcms3-cb22-min
	OBJECT-TYPE
	SYNTAX  INTEGER
	ACCESS  read-only
	STATUS  mandatory
	DESCRIPTION "CB22 Min"
		::= { bcmsplus3 64 }

bcms3-cb23-min
	OBJECT-TYPE
	SYNTAX  INTEGER
	ACCESS  read-only
	STATUS  mandatory
	DESCRIPTION "CB23 Min"
		::= { bcmsplus3 65 }

bcms3-cb24-min
	OBJECT-TYPE
	SYNTAX  INTEGER
	ACCESS  read-only
	STATUS  mandatory
	DESCRIPTION "CB24 Min"
		::= { bcmsplus3 66 }

bcms3-cb25-min
	OBJECT-TYPE
	SYNTAX  INTEGER
	ACCESS  read-only
	STATUS  mandatory
	DESCRIPTION "CB25 Min"
		::= { bcmsplus3 67 }

bcms3-cb26-min
	OBJECT-TYPE
	SYNTAX  INTEGER
	ACCESS  read-only
	STATUS  mandatory
	DESCRIPTION "CB26 Min"
		::= { bcmsplus3 68 }

bcms3-cb27-min
	OBJECT-TYPE
	SYNTAX  INTEGER
	ACCESS  read-only
	STATUS  mandatory
	DESCRIPTION "CB27 Min"
		::= { bcmsplus3 69 }

bcms3-cb28-min
	OBJECT-TYPE
	SYNTAX  INTEGER
	ACCESS  read-only
	STATUS  mandatory
	DESCRIPTION "CB28 Min"
		::= { bcmsplus3 70 }

bcms3-cb29-min
	OBJECT-TYPE
	SYNTAX  INTEGER
	ACCESS  read-only
	STATUS  mandatory
	DESCRIPTION "CB29 Min"
		::= { bcmsplus3 71 }
  
bcms3-cb30-min
	OBJECT-TYPE
	SYNTAX  INTEGER
	ACCESS  read-only
	STATUS  mandatory
	DESCRIPTION "CB30 Min"
		::= { bcmsplus3 72 }

bcms3-cb31-min
	OBJECT-TYPE
	SYNTAX  INTEGER
	ACCESS  read-only
	STATUS  mandatory
	DESCRIPTION "CB31 Min"
		::= { bcmsplus3 73 }

bcms3-cb32-min
	OBJECT-TYPE
	SYNTAX  INTEGER
	ACCESS  read-only
	STATUS  mandatory
	DESCRIPTION "CB32 Min"
		::= { bcmsplus3 74 }

bcms3-cb33-min
	OBJECT-TYPE
	SYNTAX  INTEGER
	ACCESS  read-only
	STATUS  mandatory
	DESCRIPTION "CB33 Min"
		::= { bcmsplus3 75 }

bcms3-cb34-min
	OBJECT-TYPE
	SYNTAX  INTEGER
	ACCESS  read-only
	STATUS  mandatory
	DESCRIPTION "CB34 Min"
		::= { bcmsplus3 76 }

bcms3-cb35-min
	OBJECT-TYPE
	SYNTAX  INTEGER
	ACCESS  read-only
	STATUS  mandatory
	DESCRIPTION "CB35 Min"
		::= { bcmsplus3 77 }

bcms3-cb36-min
	OBJECT-TYPE
	SYNTAX  INTEGER
	ACCESS  read-only
	STATUS  mandatory
	DESCRIPTION "CB36 Min"
		::= { bcmsplus3 78 }

bcms3-cb37-min
	OBJECT-TYPE
	SYNTAX  INTEGER
	ACCESS  read-only
	STATUS  mandatory
	DESCRIPTION "CB37 Min"
		::= { bcmsplus3 79 }

bcms3-cb38-min
	OBJECT-TYPE
	SYNTAX  INTEGER
	ACCESS  read-only
	STATUS  mandatory
	DESCRIPTION "CB38 Min"
		::= { bcmsplus3 80 }

bcms3-cb39-min
	OBJECT-TYPE
	SYNTAX  INTEGER
	ACCESS  read-only
	STATUS  mandatory
	DESCRIPTION "CB39 Min"
		::= { bcmsplus3 81 }
  
bcms3-cb40-min
	OBJECT-TYPE
	SYNTAX  INTEGER
	ACCESS  read-only
	STATUS  mandatory
	DESCRIPTION "CB40 Min"
		::= { bcmsplus3 82 }

bcms3-cb41-min
	OBJECT-TYPE
	SYNTAX  INTEGER
	ACCESS  read-only
	STATUS  mandatory
	DESCRIPTION "CB41 Min"
		::= { bcmsplus3 83 }

bcms3-cb42-min
	OBJECT-TYPE
	SYNTAX  INTEGER
	ACCESS  read-only
	STATUS  mandatory
	DESCRIPTION "CB42 Min"
		::= { bcmsplus3 84 }

bcms3-cb1-max
	OBJECT-TYPE
	SYNTAX  INTEGER
	ACCESS  read-only
	STATUS  mandatory
	DESCRIPTION "CB1 Max
		     Note for all maximum currents 1-42: 100 = 10.0 amps"
		::= { bcmsplus3 85 }

bcms3-cb2-max
	OBJECT-TYPE
	SYNTAX  INTEGER
	ACCESS  read-only
	STATUS  mandatory
	DESCRIPTION "CB2 Max"
		::= { bcmsplus3 86 }

bcms3-cb3-max
	OBJECT-TYPE
	SYNTAX  INTEGER
	ACCESS  read-only
	STATUS  mandatory
	DESCRIPTION "CB3 Max"
		::= { bcmsplus3 87 }

bcms3-cb4-max
	OBJECT-TYPE
	SYNTAX  INTEGER
	ACCESS  read-only
	STATUS  mandatory
	DESCRIPTION "CB4 Max"
		::= { bcmsplus3 88 }

bcms3-cb5-max
	OBJECT-TYPE
	SYNTAX  INTEGER
	ACCESS  read-only
	STATUS  mandatory
	DESCRIPTION "CB5 Max"
		::= { bcmsplus3 89 }

bcms3-cb6-max
	OBJECT-TYPE
	SYNTAX  INTEGER
	ACCESS  read-only
	STATUS  mandatory
	DESCRIPTION "CB6 Max"
		::= { bcmsplus3 90 }

bcms3-cb7-max
	OBJECT-TYPE
	SYNTAX  INTEGER
	ACCESS  read-only
	STATUS  mandatory
	DESCRIPTION "CB7 Max"
		::= { bcmsplus3 91 }
  
bcms3-cb8-max
	OBJECT-TYPE
	SYNTAX  INTEGER
	ACCESS  read-only
	STATUS  mandatory
	DESCRIPTION "CB8 Max"
		::= { bcmsplus3 92 }

bcms3-cb9-max
	OBJECT-TYPE
	SYNTAX  INTEGER
	ACCESS  read-only
	STATUS  mandatory
	DESCRIPTION "CB9 Max"
		::= { bcmsplus3 93 }

bcms3-cb10-max
	OBJECT-TYPE
	SYNTAX  INTEGER
	ACCESS  read-only
	STATUS  mandatory
	DESCRIPTION "CB10 Max"
		::= { bcmsplus3 94 }

bcms3-cb11-max
	OBJECT-TYPE
	SYNTAX  INTEGER
	ACCESS  read-only
	STATUS  mandatory
	DESCRIPTION "CB11 Max"
		::= { bcmsplus3 95 }

bcms3-cb12-max
	OBJECT-TYPE
	SYNTAX  INTEGER
	ACCESS  read-only
	STATUS  mandatory
	DESCRIPTION "CB12 Max"
		::= { bcmsplus3 96 }

bcms3-cb13-max
	OBJECT-TYPE
	SYNTAX  INTEGER
	ACCESS  read-only
	STATUS  mandatory
	DESCRIPTION "CB13 Max"
		::= { bcmsplus3 97 }

bcms3-cb14-max
	OBJECT-TYPE
	SYNTAX  INTEGER
	ACCESS  read-only
	STATUS  mandatory
	DESCRIPTION "CB14 Max"
		::= { bcmsplus3 98 }

bcms3-cb15-max
	OBJECT-TYPE
	SYNTAX  INTEGER
	ACCESS  read-only
	STATUS  mandatory
	DESCRIPTION "CB15 Max"
		::= { bcmsplus3 99 }


bcms3-cb16-max
	OBJECT-TYPE
	SYNTAX  INTEGER
	ACCESS  read-only
	STATUS  mandatory
	DESCRIPTION "CB16 Max"
		::= { bcmsplus3 100 }

bcms3-cb17-max
	OBJECT-TYPE
	SYNTAX  INTEGER
	ACCESS  read-only
	STATUS  mandatory
	DESCRIPTION "CB17 Max"
		::= { bcmsplus3 101 }
  
bcms3-cb18-max
	OBJECT-TYPE
	SYNTAX  INTEGER
	ACCESS  read-only
	STATUS  mandatory
	DESCRIPTION "CB18 Max"
		::= { bcmsplus3 102 }

bcms3-cb19-max
	OBJECT-TYPE
	SYNTAX  INTEGER
	ACCESS  read-only
	STATUS  mandatory
	DESCRIPTION "CB19 Max"
		::= { bcmsplus3 103 }

bcms3-cb20-max
	OBJECT-TYPE
	SYNTAX  INTEGER
	ACCESS  read-only
	STATUS  mandatory
	DESCRIPTION "CB20 Max"
		::= { bcmsplus3 104 }

bcms3-cb21-max
	OBJECT-TYPE
	SYNTAX  INTEGER
	ACCESS  read-only
	STATUS  mandatory
	DESCRIPTION "CB21 Max"
		::= { bcmsplus3 105 }

bcms3-cb22-max
	OBJECT-TYPE
	SYNTAX  INTEGER
	ACCESS  read-only
	STATUS  mandatory
	DESCRIPTION "CB22 Max"
		::= { bcmsplus3 106 }

bcms3-cb23-max
	OBJECT-TYPE
	SYNTAX  INTEGER
	ACCESS  read-only
	STATUS  mandatory
	DESCRIPTION "CB23 Max"
		::= { bcmsplus3 107 }

bcms3-cb24-max
	OBJECT-TYPE
	SYNTAX  INTEGER
	ACCESS  read-only
	STATUS  mandatory
	DESCRIPTION "CB24 Max"
		::= { bcmsplus3 108 }

bcms3-cb25-max
	OBJECT-TYPE
	SYNTAX  INTEGER
	ACCESS  read-only
	STATUS  mandatory
	DESCRIPTION "CB25 Max"
		::= { bcmsplus3 109 }

bcms3-cb26-max
	OBJECT-TYPE
	SYNTAX  INTEGER
	ACCESS  read-only
	STATUS  mandatory
	DESCRIPTION "CB26 Max"
		::= { bcmsplus3 110 }

bcms3-cb27-max
	OBJECT-TYPE
	SYNTAX  INTEGER
	ACCESS  read-only
	STATUS  mandatory
	DESCRIPTION "CB27 Max"
		::= { bcmsplus3 111 }
  
bcms3-cb28-max
	OBJECT-TYPE
	SYNTAX  INTEGER
	ACCESS  read-only
	STATUS  mandatory
	DESCRIPTION "CB28 Max"
		::= { bcmsplus3 112 }

bcms3-cb29-max
	OBJECT-TYPE
	SYNTAX  INTEGER
	ACCESS  read-only
	STATUS  mandatory
	DESCRIPTION "CB29 Max"
		::= { bcmsplus3 113 }

bcms3-cb30-max
	OBJECT-TYPE
	SYNTAX  INTEGER
	ACCESS  read-only
	STATUS  mandatory
	DESCRIPTION "CB30 Max"
		::= { bcmsplus3 114 }

bcms3-cb31-max
	OBJECT-TYPE
	SYNTAX  INTEGER
	ACCESS  read-only
	STATUS  mandatory
	DESCRIPTION "CB31 Max"
		::= { bcmsplus3 115 }

bcms3-cb32-max
	OBJECT-TYPE
	SYNTAX  INTEGER
	ACCESS  read-only
	STATUS  mandatory
	DESCRIPTION "CB32 Max"
		::= { bcmsplus3 116 }

bcms3-cb33-max
	OBJECT-TYPE
	SYNTAX  INTEGER
	ACCESS  read-only
	STATUS  mandatory
	DESCRIPTION "CB33 Max"
		::= { bcmsplus3 117 }

bcms3-cb34-max
	OBJECT-TYPE
	SYNTAX  INTEGER
	ACCESS  read-only
	STATUS  mandatory
	DESCRIPTION "CB34 Max"
		::= { bcmsplus3 118 }

bcms3-cb35-max
	OBJECT-TYPE
	SYNTAX  INTEGER
	ACCESS  read-only
	STATUS  mandatory
	DESCRIPTION "CB35 Max"
		::= { bcmsplus3 119 }

bcms3-cb36-max
	OBJECT-TYPE
	SYNTAX  INTEGER
	ACCESS  read-only
	STATUS  mandatory
	DESCRIPTION "CB36 Max"
		::= { bcmsplus3 120 }

bcms3-cb37-max
	OBJECT-TYPE
	SYNTAX  INTEGER
	ACCESS  read-only
	STATUS  mandatory
	DESCRIPTION "CB37 Max"
		::= { bcmsplus3 121 }
  
bcms3-cb38-max
	OBJECT-TYPE
	SYNTAX  INTEGER
	ACCESS  read-only
	STATUS  mandatory
	DESCRIPTION "CB38 Max"
		::= { bcmsplus3 122 }

bcms3-cb39-max
	OBJECT-TYPE
	SYNTAX  INTEGER
	ACCESS  read-only
	STATUS  mandatory
	DESCRIPTION "CB39 Max"
		::= { bcmsplus3 123 }

bcms3-cb40-max
	OBJECT-TYPE
	SYNTAX  INTEGER
	ACCESS  read-only
	STATUS  mandatory
	DESCRIPTION "CB40 Max"
		::= { bcmsplus3 124 }

bcms3-cb41-max
	OBJECT-TYPE
	SYNTAX  INTEGER
	ACCESS  read-only
	STATUS  mandatory
	DESCRIPTION "CB41 Max"
		::= { bcmsplus3 125 }

bcms3-cb42-max
	OBJECT-TYPE
	SYNTAX  INTEGER
	ACCESS  read-only
	STATUS  mandatory
	DESCRIPTION "CB42 Max"
		::= { bcmsplus3 126 }

bcms3-cb1-16-zero
	OBJECT-TYPE
	SYNTAX  INTEGER
	ACCESS  read-write
	STATUS  mandatory
	DESCRIPTION "CB1-16 Zero
		       Bit 0 = CB1
                   Bit 15 = CB16"
		::= { bcmsplus3 127 }

bcms3-cb17-32-zero
	OBJECT-TYPE
	SYNTAX  INTEGER
	ACCESS  read-write
	STATUS  mandatory
	DESCRIPTION "CB17-32 Zero
		       Bit 0 = CB17
                   Bit 15 = CB32"
		::= { bcmsplus3 128 }

bcms3-cb33-42-zero
	OBJECT-TYPE
	SYNTAX  INTEGER
	ACCESS  read-write
	STATUS  mandatory
	DESCRIPTION "CB33-42 Zero
		       Bit 0 = CB33
                   Bit 9 = CB42
                   Bits 10-25 not used"
		::= { bcmsplus3 129 }

bcms3-cb1-16-warning
	OBJECT-TYPE
	SYNTAX  INTEGER
	ACCESS  read-write
	STATUS  mandatory
	DESCRIPTION "CB1-16 Warning
		       Bit 0 = CB1
                   Bit 15 = CB16"
		::= { bcmsplus3 130 }

bcms3-cb17-32-warning
	OBJECT-TYPE
	SYNTAX  INTEGER
	ACCESS  read-write
	STATUS  mandatory
	DESCRIPTION "CB17-32 Warning
		       Bit 0 = CB17
                   Bit 15 = CB32"
		::= { bcmsplus3 131 }
  
bcms3-cb33-42-warning
	OBJECT-TYPE
	SYNTAX  INTEGER
	ACCESS  read-write
	STATUS  mandatory
	DESCRIPTION "CB33-42 Warning
		       Bit 0 = CB33
                   Bit 9 = CB42
                   Bits 10-25 not used"
		::= { bcmsplus3 132 }

bcms3-cb1-16-alarm
	OBJECT-TYPE
	SYNTAX  INTEGER
	ACCESS  read-write
	STATUS  mandatory
	DESCRIPTION "CB1-16 Alarm
		       Bit 0 = CB1
                   Bit 15 = CB16"
		::= { bcmsplus3 133 }

bcms3-cb17-32-alarm
	OBJECT-TYPE
	SYNTAX  INTEGER
	ACCESS  read-write
	STATUS  mandatory
	DESCRIPTION "CB17-32 Alarm
		       Bit 0 = CB17
                   Bit 15 = CB32"
		::= { bcmsplus3 134 }

bcms3-cb33-42-alarm
	OBJECT-TYPE
	SYNTAX  INTEGER
	ACCESS  read-write
	STATUS  mandatory
	DESCRIPTION "CB33-42 Alarm
		       Bit 0 = CB33
                   Bit 9 = CB42
                   Bits 10-25 not used"
		::= { bcmsplus3 135 }

bcms3-cb1-breaker-size
	OBJECT-TYPE
	SYNTAX  INTEGER
	ACCESS  read-write
	STATUS  mandatory
	DESCRIPTION "CB1 Breaker-Size
		     Note for all breaker sizes 1-42: 10 = 10 amps
                     Range is 10 to 100 amps"
		::= { bcmsplus3 136 }

bcms3-cb2-breaker-size
	OBJECT-TYPE
	SYNTAX  INTEGER
	ACCESS  read-write
	STATUS  mandatory
	DESCRIPTION "CB2 Breaker-Size"
		::= { bcmsplus3 137 }

bcms3-cb3-breaker-size
	OBJECT-TYPE
	SYNTAX  INTEGER
	ACCESS  read-write
	STATUS  mandatory
	DESCRIPTION "CB3 Breaker-Size"
		::= { bcmsplus3 138 }

bcms3-cb4-breaker-size
	OBJECT-TYPE
	SYNTAX  INTEGER
	ACCESS  read-write
	STATUS  mandatory
	DESCRIPTION "CB4 Breaker-Size"
		::= { bcmsplus3 139 }

bcms3-cb5-breaker-size
	OBJECT-TYPE
	SYNTAX  INTEGER
	ACCESS  read-write
	STATUS  mandatory
	DESCRIPTION "CB5 Breaker-Size"
		::= { bcmsplus3 140 }

bcms3-cb6-breaker-size
	OBJECT-TYPE
	SYNTAX  INTEGER
	ACCESS  read-write
	STATUS  mandatory
	DESCRIPTION "CB6 Breaker-Size"
		::= { bcmsplus3 141 }
  
bcms3-cb7-breaker-size
	OBJECT-TYPE
	SYNTAX  INTEGER
	ACCESS  read-write
	STATUS  mandatory
	DESCRIPTION "CB7 Breaker-Size"
		::= { bcmsplus3 142 }

bcms3-cb8-breaker-size
	OBJECT-TYPE
	SYNTAX  INTEGER
	ACCESS  read-write
	STATUS  mandatory
	DESCRIPTION "CB8 Breaker-Size"
		::= { bcmsplus3 143 }

bcms3-cb9-breaker-size
	OBJECT-TYPE
	SYNTAX  INTEGER
	ACCESS  read-write
	STATUS  mandatory
	DESCRIPTION "CB9 Breaker-Size"
		::= { bcmsplus3 144 }

bcms3-cb10-breaker-size
	OBJECT-TYPE
	SYNTAX  INTEGER
	ACCESS  read-write
	STATUS  mandatory
	DESCRIPTION "CB10 Breaker-Size"
		::= { bcmsplus3 145 }

bcms3-cb11-breaker-size
	OBJECT-TYPE
	SYNTAX  INTEGER
	ACCESS  read-write
	STATUS  mandatory
	DESCRIPTION "CB11 Breaker-Size"
		::= { bcmsplus3 146 }

bcms3-cb12-breaker-size
	OBJECT-TYPE
	SYNTAX  INTEGER
	ACCESS  read-write
	STATUS  mandatory
	DESCRIPTION "CB12 Breaker-Size"
		::= { bcmsplus3 147 }

bcms3-cb13-breaker-size
	OBJECT-TYPE
	SYNTAX  INTEGER
	ACCESS  read-write
	STATUS  mandatory
	DESCRIPTION "CB13 Breaker-Size"
		::= { bcmsplus3 148 }

bcms3-cb14-breaker-size
	OBJECT-TYPE
	SYNTAX  INTEGER
	ACCESS  read-write
	STATUS  mandatory
	DESCRIPTION "CB14 Breaker-Size"
		::= { bcmsplus3 149 }

bcms3-cb15-breaker-size
	OBJECT-TYPE
	SYNTAX  INTEGER
	ACCESS  read-write
	STATUS  mandatory
	DESCRIPTION "CB15 Breaker-Size"
		::= { bcmsplus3 150 }

bcms3-cb16-breaker-size
	OBJECT-TYPE
	SYNTAX  INTEGER
	ACCESS  read-write
	STATUS  mandatory
	DESCRIPTION "CB16 Breaker-Size"
		::= { bcmsplus3 151 }
  
bcms3-cb17-breaker-size
	OBJECT-TYPE
	SYNTAX  INTEGER
	ACCESS  read-write
	STATUS  mandatory
	DESCRIPTION "CB17 Breaker-Size"
		::= { bcmsplus3 152 }

bcms3-cb18-breaker-size
	OBJECT-TYPE
	SYNTAX  INTEGER
	ACCESS  read-write
	STATUS  mandatory
	DESCRIPTION "CB18 Breaker-Size"
		::= { bcmsplus3 153 }

bcms3-cb19-breaker-size
	OBJECT-TYPE
	SYNTAX  INTEGER
	ACCESS  read-write
	STATUS  mandatory
	DESCRIPTION "CB19 Breaker-Size"
		::= { bcmsplus3 154 }

bcms3-cb20-breaker-size
	OBJECT-TYPE
	SYNTAX  INTEGER
	ACCESS  read-write
	STATUS  mandatory
	DESCRIPTION "CB20 Breaker-Size"
		::= { bcmsplus3 155 }

bcms3-cb21-breaker-size
	OBJECT-TYPE
	SYNTAX  INTEGER
	ACCESS  read-write
	STATUS  mandatory
	DESCRIPTION "CB21 Breaker-Size"
		::= { bcmsplus3 156 }

bcms3-cb22-breaker-size
	OBJECT-TYPE
	SYNTAX  INTEGER
	ACCESS  read-write
	STATUS  mandatory
	DESCRIPTION "CB22 Breaker-Size"
		::= { bcmsplus3 157 }

bcms3-cb23-breaker-size
	OBJECT-TYPE
	SYNTAX  INTEGER
	ACCESS  read-write
	STATUS  mandatory
	DESCRIPTION "CB23 Breaker-Size"
		::= { bcmsplus3 158 }

bcms3-cb24-breaker-size
	OBJECT-TYPE
	SYNTAX  INTEGER
	ACCESS  read-write
	STATUS  mandatory
	DESCRIPTION "CB24 Breaker-Size"
		::= { bcmsplus3 159 }

bcms3-cb25-breaker-size
	OBJECT-TYPE
	SYNTAX  INTEGER
	ACCESS  read-write
	STATUS  mandatory
	DESCRIPTION "CB25 Breaker-Size"
		::= { bcmsplus3 160 }

bcms3-cb26-breaker-size
	OBJECT-TYPE
	SYNTAX  INTEGER
	ACCESS  read-write
	STATUS  mandatory
	DESCRIPTION "CB26 Breaker-Size"
		::= { bcmsplus3 161 }
  
bcms3-cb27-breaker-size
	OBJECT-TYPE
	SYNTAX  INTEGER
	ACCESS  read-write
	STATUS  mandatory
	DESCRIPTION "CB27 Breaker-Size"
		::= { bcmsplus3 162 }

bcms3-cb28-breaker-size
	OBJECT-TYPE
	SYNTAX  INTEGER
	ACCESS  read-write
	STATUS  mandatory
	DESCRIPTION "CB28 Breaker-Size"
		::= { bcmsplus3 163 }

bcms3-cb29-breaker-size
	OBJECT-TYPE
	SYNTAX  INTEGER
	ACCESS  read-write
	STATUS  mandatory
	DESCRIPTION "CB29 Breaker-Size"
		::= { bcmsplus3 164 }

bcms3-cb30-breaker-size
	OBJECT-TYPE
	SYNTAX  INTEGER
	ACCESS  read-write
	STATUS  mandatory
	DESCRIPTION "CB30 Breaker-Size"
		::= { bcmsplus3 165 }

bcms3-cb31-breaker-size
	OBJECT-TYPE
	SYNTAX  INTEGER
	ACCESS  read-write
	STATUS  mandatory
	DESCRIPTION "CB31 Breaker-Size"
		::= { bcmsplus3 166 }

bcms3-cb32-breaker-size
	OBJECT-TYPE
	SYNTAX  INTEGER
	ACCESS  read-write
	STATUS  mandatory
	DESCRIPTION "CB32 Breaker-Size"
		::= { bcmsplus3 167 }

bcms3-cb33-breaker-size
	OBJECT-TYPE
	SYNTAX  INTEGER
	ACCESS  read-write
	STATUS  mandatory
	DESCRIPTION "CB33 Breaker-Size"
		::= { bcmsplus3 168 }

bcms3-cb34-breaker-size
	OBJECT-TYPE
	SYNTAX  INTEGER
	ACCESS  read-write
	STATUS  mandatory
	DESCRIPTION "CB34 Breaker-Size"
		::= { bcmsplus3 169 }

bcms3-cb35-breaker-size
	OBJECT-TYPE
	SYNTAX  INTEGER
	ACCESS  read-write
	STATUS  mandatory
	DESCRIPTION "CB35 Breaker-Size"
		::= { bcmsplus3 170 }

bcms3-cb36-breaker-size
	OBJECT-TYPE
	SYNTAX  INTEGER
	ACCESS  read-write
	STATUS  mandatory
	DESCRIPTION "CB36 Breaker-Size"
		::= { bcmsplus3 171 }
  
bcms3-cb37-breaker-size
	OBJECT-TYPE
	SYNTAX  INTEGER
	ACCESS  read-write
	STATUS  mandatory
	DESCRIPTION "CB37 Breaker-Size"
		::= { bcmsplus3 172 }

bcms3-cb38-breaker-size
	OBJECT-TYPE
	SYNTAX  INTEGER
	ACCESS  read-write
	STATUS  mandatory
	DESCRIPTION "CB38 Breaker-Size"
		::= { bcmsplus3 173 }

bcms3-cb39-breaker-size
	OBJECT-TYPE
	SYNTAX  INTEGER
	ACCESS  read-write
	STATUS  mandatory
	DESCRIPTION "CB39 Breaker-Size"
		::= { bcmsplus3 174 }

bcms3-cb40-breaker-size
	OBJECT-TYPE
	SYNTAX  INTEGER
	ACCESS  read-write
	STATUS  mandatory
	DESCRIPTION "CB40 Breaker-Size"
		::= { bcmsplus3 175 }

bcms3-cb41-breaker-size
	OBJECT-TYPE
	SYNTAX  INTEGER
	ACCESS  read-write
	STATUS  mandatory
	DESCRIPTION "CB41 Breaker-Size"
		::= { bcmsplus3 176 }

bcms3-cb42-breaker-size
	OBJECT-TYPE
	SYNTAX  INTEGER
	ACCESS  read-write
	STATUS  mandatory
	DESCRIPTION "CB42 Breaker-Size"
		::= { bcmsplus3 177 }

bcms3-cb1-warning-threshold
	OBJECT-TYPE
	SYNTAX  INTEGER
	ACCESS  read-write
	STATUS  mandatory
	DESCRIPTION "CB1 CB1-warning-threshold
		     Note for all warning thresholds 1-42: 70 = 70% of breaker size
                     range is 0-100%"
		::= { bcmsplus3 178 }

bcms3-cb2-warning-threshold
	OBJECT-TYPE
	SYNTAX  INTEGER
	ACCESS  read-write
	STATUS  mandatory
	DESCRIPTION "CB2 Warning-Threshold"
		::= { bcmsplus3 179 }

bcms3-cb3-warning-threshold
	OBJECT-TYPE
	SYNTAX  INTEGER
	ACCESS  read-write
	STATUS  mandatory
	DESCRIPTION "CB3 Warning-Threshold"
		::= { bcmsplus3 180 }

bcms3-cb4-warning-threshold
	OBJECT-TYPE
	SYNTAX  INTEGER
	ACCESS  read-write
	STATUS  mandatory
	DESCRIPTION "CB4 Warning-Threshold"
		::= { bcmsplus3 181 }
  
bcms3-cb5-warning-threshold
	OBJECT-TYPE
	SYNTAX  INTEGER
	ACCESS  read-write
	STATUS  mandatory
	DESCRIPTION "CB5 Warning-Threshold"
		::= { bcmsplus3 182 }

bcms3-cb6-warning-threshold
	OBJECT-TYPE
	SYNTAX  INTEGER
	ACCESS  read-write
	STATUS  mandatory
	DESCRIPTION "CB6 Warning-Threshold"
		::= { bcmsplus3 183 }

bcms3-cb7-warning-threshold
	OBJECT-TYPE
	SYNTAX  INTEGER
	ACCESS  read-write
	STATUS  mandatory
	DESCRIPTION "CB7 Warning-Threshold"
		::= { bcmsplus3 184 }

bcms3-cb8-warning-threshold
	OBJECT-TYPE
	SYNTAX  INTEGER
	ACCESS  read-write
	STATUS  mandatory
	DESCRIPTION "CB8 Warning-Threshold"
		::= { bcmsplus3 185 }

bcms3-cb9-warning-threshold
	OBJECT-TYPE
	SYNTAX  INTEGER
	ACCESS  read-write
	STATUS  mandatory
	DESCRIPTION "CB9 Warning-Threshold"
		::= { bcmsplus3 186 }

bcms3-cb10-warning-threshold
	OBJECT-TYPE
	SYNTAX  INTEGER
	ACCESS  read-write
	STATUS  mandatory
	DESCRIPTION "CB10 Warning-Threshold"
		::= { bcmsplus3 187 }

bcms3-cb11-warning-threshold
	OBJECT-TYPE
	SYNTAX  INTEGER
	ACCESS  read-write
	STATUS  mandatory
	DESCRIPTION "CB11 Warning-Threshold"
		::= { bcmsplus3 188 }

bcms3-cb12-warning-threshold
	OBJECT-TYPE
	SYNTAX  INTEGER
	ACCESS  read-write
	STATUS  mandatory
	DESCRIPTION "CB12 Warning-Threshold"
		::= { bcmsplus3 189 }

bcms3-cb13-warning-threshold
	OBJECT-TYPE
	SYNTAX  INTEGER
	ACCESS  read-write
	STATUS  mandatory
	DESCRIPTION "CB13 Warning-Threshold"
		::= { bcmsplus3 190 }

bcms3-cb14-warning-threshold
	OBJECT-TYPE
	SYNTAX  INTEGER
	ACCESS  read-write
	STATUS  mandatory
	DESCRIPTION "CB14 Warning-Threshold"
		::= { bcmsplus3 191 }
  
bcms3-cb15-warning-threshold
	OBJECT-TYPE
	SYNTAX  INTEGER
	ACCESS  read-write
	STATUS  mandatory
	DESCRIPTION "CB15 Warning-Threshold"
		::= { bcmsplus3 192 }

bcms3-cb16-warning-threshold
	OBJECT-TYPE
	SYNTAX  INTEGER
	ACCESS  read-write
	STATUS  mandatory
	DESCRIPTION "CB16 Warning-Threshold"
		::= { bcmsplus3 193 }

bcms3-cb17-warning-threshold
	OBJECT-TYPE
	SYNTAX  INTEGER
	ACCESS  read-write
	STATUS  mandatory
	DESCRIPTION "CB17 Warning-Threshold"
		::= { bcmsplus3 194 }

bcms3-cb18-warning-threshold
	OBJECT-TYPE
	SYNTAX  INTEGER
	ACCESS  read-write
	STATUS  mandatory
	DESCRIPTION "CB18 Warning-Threshold"
		::= { bcmsplus3 195 }

bcms3-cb19-warning-threshold
	OBJECT-TYPE
	SYNTAX  INTEGER
	ACCESS  read-write
	STATUS  mandatory
	DESCRIPTION "CB19 Warning-Threshold"
		::= { bcmsplus3 196 }

bcms3-cb20-warning-threshold
	OBJECT-TYPE
	SYNTAX  INTEGER
	ACCESS  read-write
	STATUS  mandatory
	DESCRIPTION "CB20 Warning-Threshold"
		::= { bcmsplus3 197 }

bcms3-cb21-warning-threshold
	OBJECT-TYPE
	SYNTAX  INTEGER
	ACCESS  read-write
	STATUS  mandatory
	DESCRIPTION "CB21 Warning-Threshold"
		::= { bcmsplus3 198 }

bcms3-cb22-warning-threshold
	OBJECT-TYPE
	SYNTAX  INTEGER
	ACCESS  read-write
	STATUS  mandatory
	DESCRIPTION "CB22 Warning-Threshold"
		::= { bcmsplus3 199 }

bcms3-cb23-warning-threshold
	OBJECT-TYPE
	SYNTAX  INTEGER
	ACCESS  read-write
	STATUS  mandatory
	DESCRIPTION "CB23 Warning-Threshold"
		::= { bcmsplus3 200 }

bcms3-cb24-warning-threshold
	OBJECT-TYPE
	SYNTAX  INTEGER
	ACCESS  read-write
	STATUS  mandatory
	DESCRIPTION "CB24 Warning-Threshold"
		::= { bcmsplus3 201 }
  
bcms3-cb25-warning-threshold
	OBJECT-TYPE
	SYNTAX  INTEGER
	ACCESS  read-write
	STATUS  mandatory
	DESCRIPTION "CB25 Warning-Threshold"
		::= { bcmsplus3 202 }

bcms3-cb26-warning-threshold
	OBJECT-TYPE
	SYNTAX  INTEGER
	ACCESS  read-write
	STATUS  mandatory
	DESCRIPTION "CB26 Warning-Threshold"
		::= { bcmsplus3 203 }

bcms3-cb27-warning-threshold
	OBJECT-TYPE
	SYNTAX  INTEGER
	ACCESS  read-write
	STATUS  mandatory
	DESCRIPTION "CB27 Warning-Threshold"
		::= { bcmsplus3 204 }

bcms3-cb28-warning-threshold
	OBJECT-TYPE
	SYNTAX  INTEGER
	ACCESS  read-write
	STATUS  mandatory
	DESCRIPTION "CB28 Warning-Threshold"
		::= { bcmsplus3 205 }

bcms3-cb29-warning-threshold
	OBJECT-TYPE
	SYNTAX  INTEGER
	ACCESS  read-write
	STATUS  mandatory
	DESCRIPTION "CB29 Warning-Threshold"
		::= { bcmsplus3 206 }

bcms3-cb30-warning-threshold
	OBJECT-TYPE
	SYNTAX  INTEGER
	ACCESS  read-write
	STATUS  mandatory
	DESCRIPTION "CB30 Warning-Threshold"
		::= { bcmsplus3 207 }

bcms3-cb31-warning-threshold
	OBJECT-TYPE
	SYNTAX  INTEGER
	ACCESS  read-write
	STATUS  mandatory
	DESCRIPTION "CB31 Warning-Threshold"
		::= { bcmsplus3 208 }

bcms3-cb32-warning-threshold
	OBJECT-TYPE
	SYNTAX  INTEGER
	ACCESS  read-write
	STATUS  mandatory
	DESCRIPTION "CB32 Warning-Threshold"
		::= { bcmsplus3 209 }

bcms3-cb33-warning-threshold
	OBJECT-TYPE
	SYNTAX  INTEGER
	ACCESS  read-write
	STATUS  mandatory
	DESCRIPTION "CB33 Warning-Threshold"
		::= { bcmsplus3 210 }

bcms3-cb34-warning-threshold
	OBJECT-TYPE
	SYNTAX  INTEGER
	ACCESS  read-write
	STATUS  mandatory
	DESCRIPTION "CB34 Warning-Threshold"
		::= { bcmsplus3 211 }
  
bcms3-cb35-warning-threshold
	OBJECT-TYPE
	SYNTAX  INTEGER
	ACCESS  read-write
	STATUS  mandatory
	DESCRIPTION "CB35 Warning-Threshold"
		::= { bcmsplus3 212 }

bcms3-cb36-warning-threshold
	OBJECT-TYPE
	SYNTAX  INTEGER
	ACCESS  read-write
	STATUS  mandatory
	DESCRIPTION "CB36 Warning-Threshold"
		::= { bcmsplus3 213 }

bcms3-cb37-warning-threshold
	OBJECT-TYPE
	SYNTAX  INTEGER
	ACCESS  read-write
	STATUS  mandatory
	DESCRIPTION "CB37 Warning-Threshold"
		::= { bcmsplus3 214 }

bcms3-cb38-warning-threshold
	OBJECT-TYPE
	SYNTAX  INTEGER
	ACCESS  read-write
	STATUS  mandatory
	DESCRIPTION "CB38 Warning-Threshold"
		::= { bcmsplus3 215 }

bcms3-cb39-warning-threshold
	OBJECT-TYPE
	SYNTAX  INTEGER
	ACCESS  read-write
	STATUS  mandatory
	DESCRIPTION "CB39 Warning-Threshold"
		::= { bcmsplus3 216 }

bcms3-cb40-warning-threshold
	OBJECT-TYPE
	SYNTAX  INTEGER
	ACCESS  read-write
	STATUS  mandatory
	DESCRIPTION "CB40 Warning-Threshold"
		::= { bcmsplus3 217 }

bcms3-cb41-warning-threshold
	OBJECT-TYPE
	SYNTAX  INTEGER
	ACCESS  read-write
	STATUS  mandatory
	DESCRIPTION "CB41 Warning-Threshold"
		::= { bcmsplus3 218 }

bcms3-cb42-warning-threshold
	OBJECT-TYPE
	SYNTAX  INTEGER
	ACCESS  read-write
	STATUS  mandatory
	DESCRIPTION "CB42 Warning-Threshold"
		::= { bcmsplus3 219 }

bcms3-cb1-alarm-threshold
	OBJECT-TYPE
	SYNTAX  INTEGER
	ACCESS  read-write
	STATUS  mandatory
	DESCRIPTION "CB1 Alarm-Threshold
		     Note for all alarm thresholds 1-42: 80 = 80% of breaker size
                     range is 0-100%"
		::= { bcmsplus3 220 }


bcms3-cb2-alarm-threshold
	OBJECT-TYPE
	SYNTAX  INTEGER
	ACCESS  read-write
	STATUS  mandatory
	DESCRIPTION "CB2 Alarm-Threshold"
		::= { bcmsplus3 221 }
  
bcms3-cb3-alarm-threshold
	OBJECT-TYPE
	SYNTAX  INTEGER
	ACCESS  read-write
	STATUS  mandatory
	DESCRIPTION "CB3 Alarm-Threshold"
		::= { bcmsplus3 222 }

bcms3-cb4-alarm-threshold
	OBJECT-TYPE
	SYNTAX  INTEGER
	ACCESS  read-write
	STATUS  mandatory
	DESCRIPTION "CB4 Alarm-Threshold"
		::= { bcmsplus3 223 }

bcms3-cb5-alarm-threshold
	OBJECT-TYPE
	SYNTAX  INTEGER
	ACCESS  read-write
	STATUS  mandatory
	DESCRIPTION "CB5 Alarm-Threshold"
		::= { bcmsplus3 224 }

bcms3-cb6-alarm-threshold
	OBJECT-TYPE
	SYNTAX  INTEGER
	ACCESS  read-write
	STATUS  mandatory
	DESCRIPTION "CB6 Alarm-Threshold"
		::= { bcmsplus3 225 }

bcms3-cb7-alarm-threshold
	OBJECT-TYPE
	SYNTAX  INTEGER
	ACCESS  read-write
	STATUS  mandatory
	DESCRIPTION "CB7 Alarm-Threshold"
		::= { bcmsplus3 226 }

bcms3-cb8-alarm-threshold
	OBJECT-TYPE
	SYNTAX  INTEGER
	ACCESS  read-write
	STATUS  mandatory
	DESCRIPTION "CB8 Alarm-Threshold"
		::= { bcmsplus3 227 }

bcms3-cb9-alarm-threshold
	OBJECT-TYPE
	SYNTAX  INTEGER
	ACCESS  read-write
	STATUS  mandatory
	DESCRIPTION "CB9 Alarm-Threshold"
		::= { bcmsplus3 228 }

bcms3-cb10-alarm-threshold
	OBJECT-TYPE
	SYNTAX  INTEGER
	ACCESS  read-write
	STATUS  mandatory
	DESCRIPTION "CB10 Alarm-Threshold"
		::= { bcmsplus3 229 }

bcms3-cb11-alarm-threshold
	OBJECT-TYPE
	SYNTAX  INTEGER
	ACCESS  read-write
	STATUS  mandatory
	DESCRIPTION "CB11 Alarm-Threshold"
		::= { bcmsplus3 230 }

bcms3-cb12-alarm-threshold
	OBJECT-TYPE
	SYNTAX  INTEGER
	ACCESS  read-write
	STATUS  mandatory
	DESCRIPTION "CB12 Alarm-Threshold"
		::= { bcmsplus3 231 }
  
bcms3-cb13-alarm-threshold
	OBJECT-TYPE
	SYNTAX  INTEGER
	ACCESS  read-write
	STATUS  mandatory
	DESCRIPTION "CB13 Alarm-Threshold"
		::= { bcmsplus3 232 }

bcms3-cb14-alarm-threshold
	OBJECT-TYPE
	SYNTAX  INTEGER
	ACCESS  read-write
	STATUS  mandatory
	DESCRIPTION "CB14 Alarm-Threshold"
		::= { bcmsplus3 233 }

bcms3-cb15-alarm-threshold
	OBJECT-TYPE
	SYNTAX  INTEGER
	ACCESS  read-write
	STATUS  mandatory
	DESCRIPTION "CB15 Alarm-Threshold"
		::= { bcmsplus3 234 }

bcms3-cb16-alarm-threshold
	OBJECT-TYPE
	SYNTAX  INTEGER
	ACCESS  read-write
	STATUS  mandatory
	DESCRIPTION "CB16 Alarm-Threshold"
		::= { bcmsplus3 235 }

bcms3-cb17-alarm-threshold
	OBJECT-TYPE
	SYNTAX  INTEGER
	ACCESS  read-write
	STATUS  mandatory
	DESCRIPTION "CB17 Alarm-Threshold"
		::= { bcmsplus3 236 }

bcms3-cb18-alarm-threshold
	OBJECT-TYPE
	SYNTAX  INTEGER
	ACCESS  read-write
	STATUS  mandatory
	DESCRIPTION "CB18 Alarm-Threshold"
		::= { bcmsplus3 237 }

bcms3-cb19-alarm-threshold
	OBJECT-TYPE
	SYNTAX  INTEGER
	ACCESS  read-write
	STATUS  mandatory
	DESCRIPTION "CB19 Alarm-Threshold"
		::= { bcmsplus3 238 }

bcms3-cb20-alarm-threshold
	OBJECT-TYPE
	SYNTAX  INTEGER
	ACCESS  read-write
	STATUS  mandatory
	DESCRIPTION "CB20 Alarm-Threshold"
		::= { bcmsplus3 239 }

bcms3-cb21-alarm-threshold
	OBJECT-TYPE
	SYNTAX  INTEGER
	ACCESS  read-write
	STATUS  mandatory
	DESCRIPTION "CB21 Alarm-Threshold"
		::= { bcmsplus3 240 }

bcms3-cb22-alarm-threshold
	OBJECT-TYPE
	SYNTAX  INTEGER
	ACCESS  read-write
	STATUS  mandatory
	DESCRIPTION "CB22 Alarm-Threshold"
		::= { bcmsplus3 241 }
  
bcms3-cb23-alarm-threshold
	OBJECT-TYPE
	SYNTAX  INTEGER
	ACCESS  read-write
	STATUS  mandatory
	DESCRIPTION "CB23 Alarm-Threshold"
		::= { bcmsplus3 242 }

bcms3-cb24-alarm-threshold
	OBJECT-TYPE
	SYNTAX  INTEGER
	ACCESS  read-write
	STATUS  mandatory
	DESCRIPTION "CB24 Alarm-Threshold"
		::= { bcmsplus3 243 }

bcms3-cb25-alarm-threshold
	OBJECT-TYPE
	SYNTAX  INTEGER
	ACCESS  read-write
	STATUS  mandatory
	DESCRIPTION "CB25 Alarm-Threshold"
		::= { bcmsplus3 244 }

bcms3-cb26-alarm-threshold
	OBJECT-TYPE
	SYNTAX  INTEGER
	ACCESS  read-write
	STATUS  mandatory
	DESCRIPTION "CB26 Alarm-Threshold"
		::= { bcmsplus3 245 }

bcms3-cb27-alarm-threshold
	OBJECT-TYPE
	SYNTAX  INTEGER
	ACCESS  read-write
	STATUS  mandatory
	DESCRIPTION "CB27 Alarm-Threshold"
		::= { bcmsplus3 246 }

bcms3-cb28-alarm-threshold
	OBJECT-TYPE
	SYNTAX  INTEGER
	ACCESS  read-write
	STATUS  mandatory
	DESCRIPTION "CB28 Alarm-Threshold"
		::= { bcmsplus3 247 }

bcms3-cb29-alarm-threshold
	OBJECT-TYPE
	SYNTAX  INTEGER
	ACCESS  read-write
	STATUS  mandatory
	DESCRIPTION "CB29 Alarm-Threshold"
		::= { bcmsplus3 248 }

bcms3-cb30-alarm-threshold
	OBJECT-TYPE
	SYNTAX  INTEGER
	ACCESS  read-write
	STATUS  mandatory
	DESCRIPTION "CB30 Alarm-Threshold"
		::= { bcmsplus3 249 }

bcms3-cb31-alarm-threshold
	OBJECT-TYPE
	SYNTAX  INTEGER
	ACCESS  read-write
	STATUS  mandatory
	DESCRIPTION "CB31 Alarm-Threshold"
		::= { bcmsplus3 250 }

bcms3-cb32-alarm-threshold
	OBJECT-TYPE
	SYNTAX  INTEGER
	ACCESS  read-write
	STATUS  mandatory
	DESCRIPTION "CB32 Alarm-Threshold"
		::= { bcmsplus3 251 }
  
bcms3-cb33-alarm-threshold
	OBJECT-TYPE
	SYNTAX  INTEGER
	ACCESS  read-write
	STATUS  mandatory
	DESCRIPTION "CB33 Alarm-Threshold"
		::= { bcmsplus3 252 }

bcms3-cb34-alarm-threshold
	OBJECT-TYPE
	SYNTAX  INTEGER
	ACCESS  read-write
	STATUS  mandatory
	DESCRIPTION "CB34 Alarm-Threshold"
		::= { bcmsplus3 253 }

bcms3-cb35-alarm-threshold
	OBJECT-TYPE
	SYNTAX  INTEGER
	ACCESS  read-write
	STATUS  mandatory
	DESCRIPTION "CB35 Alarm-Threshold"
		::= { bcmsplus3 254 }

bcms3-cb36-alarm-threshold
	OBJECT-TYPE
	SYNTAX  INTEGER
	ACCESS  read-write
	STATUS  mandatory
	DESCRIPTION "CB36 Alarm-Threshold"
		::= { bcmsplus3 255 }

bcms3-cb37-alarm-threshold
	OBJECT-TYPE
	SYNTAX  INTEGER
	ACCESS  read-write
	STATUS  mandatory
	DESCRIPTION "CB37 Alarm-Threshold"
		::= { bcmsplus3 256 }

bcms3-cb38-alarm-threshold
	OBJECT-TYPE
	SYNTAX  INTEGER
	ACCESS  read-write
	STATUS  mandatory
	DESCRIPTION "CB38 Alarm-Threshold"
		::= { bcmsplus3 257 }

bcms3-cb39-alarm-threshold
	OBJECT-TYPE
	SYNTAX  INTEGER
	ACCESS  read-write
	STATUS  mandatory
	DESCRIPTION "CB39 Alarm-Threshold"
		::= { bcmsplus3 258 }

bcms3-cb40-alarm-threshold
	OBJECT-TYPE
	SYNTAX  INTEGER
	ACCESS  read-write
	STATUS  mandatory
	DESCRIPTION "CB40 Alarm-Threshold"
		::= { bcmsplus3 259 }

bcms3-cb41-alarm-threshold
	OBJECT-TYPE
	SYNTAX  INTEGER
	ACCESS  read-write
	STATUS  mandatory
	DESCRIPTION "CB41 Alarm-Threshold"
		::= { bcmsplus3 260 }

bcms3-cb42-alarm-threshold
	OBJECT-TYPE
	SYNTAX  INTEGER
	ACCESS  read-write
	STATUS  mandatory
	DESCRIPTION "CB42 Alarm-Threshold"
		::= { bcmsplus3 261 }

bcms3-cb1-warning-time-delay
	OBJECT-TYPE
	SYNTAX  INTEGER
	ACCESS  read-write
	STATUS  mandatory
	DESCRIPTION "CB1 Warning-Time-Delay
		     Note for all warning time delays 1-42: units are in seconds"                     
		::= { bcmsplus3 262 }

bcms3-cb2-warning-time-delay
	OBJECT-TYPE
	SYNTAX  INTEGER
	ACCESS  read-write
	STATUS  mandatory
	DESCRIPTION "CB2 Warning-Time-Delay"
		::= { bcmsplus3 263 }
  
bcms3-cb3-warning-time-delay
	OBJECT-TYPE
	SYNTAX  INTEGER
	ACCESS  read-write
	STATUS  mandatory
	DESCRIPTION "CB3 Warning-Time-Delay"
		::= { bcmsplus3 264 }

bcms3-cb4-warning-time-delay
	OBJECT-TYPE
	SYNTAX  INTEGER
	ACCESS  read-write
	STATUS  mandatory
	DESCRIPTION "CB4 Warning-Time-Delay"
		::= { bcmsplus3 265 }

bcms3-cb5-warning-time-delay
	OBJECT-TYPE
	SYNTAX  INTEGER
	ACCESS  read-write
	STATUS  mandatory
	DESCRIPTION "CB5 Warning-Time-Delay"
		::= { bcmsplus3 266 }

bcms3-cb6-warning-time-delay
	OBJECT-TYPE
	SYNTAX  INTEGER
	ACCESS  read-write
	STATUS  mandatory
	DESCRIPTION "CB6 Warning-Time-Delay"
		::= { bcmsplus3 267 }

bcms3-cb7-warning-time-delay
	OBJECT-TYPE
	SYNTAX  INTEGER
	ACCESS  read-write
	STATUS  mandatory
	DESCRIPTION "CB7 Warning-Time-Delay"
		::= { bcmsplus3 268 }

bcms3-cb8-warning-time-delay
	OBJECT-TYPE
	SYNTAX  INTEGER
	ACCESS  read-write
	STATUS  mandatory
	DESCRIPTION "CB8 Warning-Time-Delay"
		::= { bcmsplus3 269 }

bcms3-cb9-warning-time-delay
	OBJECT-TYPE
	SYNTAX  INTEGER
	ACCESS  read-write
	STATUS  mandatory
	DESCRIPTION "CB9 Warning-Time-Delay"
		::= { bcmsplus3 270 }

bcms3-cb10-warning-time-delay
	OBJECT-TYPE
	SYNTAX  INTEGER
	ACCESS  read-write
	STATUS  mandatory
	DESCRIPTION "CB10 Warning-Time-Delay"
		::= { bcmsplus3 271 }

bcms3-cb11-warning-time-delay
	OBJECT-TYPE
	SYNTAX  INTEGER
	ACCESS  read-write
	STATUS  mandatory
	DESCRIPTION "CB11 Warning-Time-Delay"
		::= { bcmsplus3 272 }

bcms3-cb12-warning-time-delay
	OBJECT-TYPE
	SYNTAX  INTEGER
	ACCESS  read-write
	STATUS  mandatory
	DESCRIPTION "CB12 Warning-Time-Delay"
		::= { bcmsplus3 273 }
  
bcms3-cb13-warning-time-delay
	OBJECT-TYPE
	SYNTAX  INTEGER
	ACCESS  read-write
	STATUS  mandatory
	DESCRIPTION "CB13 Warning-Time-Delay"
		::= { bcmsplus3 274 }

bcms3-cb14-warning-time-delay
	OBJECT-TYPE
	SYNTAX  INTEGER
	ACCESS  read-write
	STATUS  mandatory
	DESCRIPTION "CB14 Warning-Time-Delay"
		::= { bcmsplus3 275 }

bcms3-cb15-warning-time-delay
	OBJECT-TYPE
	SYNTAX  INTEGER
	ACCESS  read-write
	STATUS  mandatory
	DESCRIPTION "CB15 Warning-Time-Delay"
		::= { bcmsplus3 276 }

bcms3-cb16-warning-time-delay
	OBJECT-TYPE
	SYNTAX  INTEGER
	ACCESS  read-write
	STATUS  mandatory
	DESCRIPTION "CB16 Warning-Time-Delay"
		::= { bcmsplus3 277 }

bcms3-cb17-warning-time-delay
	OBJECT-TYPE
	SYNTAX  INTEGER
	ACCESS  read-write
	STATUS  mandatory
	DESCRIPTION "CB17 Warning-Time-Delay"
		::= { bcmsplus3 278 }

bcms3-cb18-warning-time-delay
	OBJECT-TYPE
	SYNTAX  INTEGER
	ACCESS  read-write
	STATUS  mandatory
	DESCRIPTION "CB18 Warning-Time-Delay"
		::= { bcmsplus3 279 }

bcms3-cb19-warning-time-delay
	OBJECT-TYPE
	SYNTAX  INTEGER
	ACCESS  read-write
	STATUS  mandatory
	DESCRIPTION "CB19 Warning-Time-Delay"
		::= { bcmsplus3 280 }

bcms3-cb20-warning-time-delay
	OBJECT-TYPE
	SYNTAX  INTEGER
	ACCESS  read-write
	STATUS  mandatory
	DESCRIPTION "CB20 Warning-Time-Delay"
		::= { bcmsplus3 281 }

bcms3-cb21-warning-time-delay
	OBJECT-TYPE
	SYNTAX  INTEGER
	ACCESS  read-write
	STATUS  mandatory
	DESCRIPTION "CB21 Warning-Time-Delay"
		::= { bcmsplus3 282 }

bcms3-cb22-warning-time-delay
	OBJECT-TYPE
	SYNTAX  INTEGER
	ACCESS  read-write
	STATUS  mandatory
	DESCRIPTION "CB22 Warning-Time-Delay"
		::= { bcmsplus3 283 }
  
bcms3-cb23-warning-time-delay
	OBJECT-TYPE
	SYNTAX  INTEGER
	ACCESS  read-write
	STATUS  mandatory
	DESCRIPTION "CB23 Warning-Time-Delay"
		::= { bcmsplus3 284 }

bcms3-cb24-warning-time-delay
	OBJECT-TYPE
	SYNTAX  INTEGER
	ACCESS  read-write
	STATUS  mandatory
	DESCRIPTION "CB24 Warning-Time-Delay"
		::= { bcmsplus3 285 }

bcms3-cb25-warning-time-delay
	OBJECT-TYPE
	SYNTAX  INTEGER
	ACCESS  read-write
	STATUS  mandatory
	DESCRIPTION "CB25 Warning-Time-Delay"
		::= { bcmsplus3 286 }

bcms3-cb26-warning-time-delay
	OBJECT-TYPE
	SYNTAX  INTEGER
	ACCESS  read-write
	STATUS  mandatory
	DESCRIPTION "CB26 Warning-Time-Delay"
		::= { bcmsplus3 287 }

bcms3-cb27-warning-time-delay
	OBJECT-TYPE
	SYNTAX  INTEGER
	ACCESS  read-write
	STATUS  mandatory
	DESCRIPTION "CB27 Warning-Time-Delay"
		::= { bcmsplus3 288 }

bcms3-cb28-warning-time-delay
	OBJECT-TYPE
	SYNTAX  INTEGER
	ACCESS  read-write
	STATUS  mandatory
	DESCRIPTION "CB28 Warning-Time-Delay"
		::= { bcmsplus3 289 }

bcms3-cb29-warning-time-delay
	OBJECT-TYPE
	SYNTAX  INTEGER
	ACCESS  read-write
	STATUS  mandatory
	DESCRIPTION "CB29 Warning-Time-Delay"
		::= { bcmsplus3 290}

bcms3-cb30-warning-time-delay
	OBJECT-TYPE
	SYNTAX  INTEGER
	ACCESS  read-write
	STATUS  mandatory
	DESCRIPTION "CB30 Warning-Time-Delay"
		::= { bcmsplus3 291 }

bcms3-cb31-warning-time-delay
	OBJECT-TYPE
	SYNTAX  INTEGER
	ACCESS  read-write
	STATUS  mandatory
	DESCRIPTION "CB31 Warning-Time-Delay"
		::= { bcmsplus3 292 }

bcms3-cb32-warning-time-delay
	OBJECT-TYPE
	SYNTAX  INTEGER
	ACCESS  read-write
	STATUS  mandatory
	DESCRIPTION "CB32 Warning-Time-Delay"
		::= { bcmsplus3 293 }
  
bcms3-cb33-warning-time-delay
	OBJECT-TYPE
	SYNTAX  INTEGER
	ACCESS  read-write
	STATUS  mandatory
	DESCRIPTION "CB33 Warning-Time-Delay"
		::= { bcmsplus3 294 }

bcms3-cb34-warning-time-delay
	OBJECT-TYPE
	SYNTAX  INTEGER
	ACCESS  read-write
	STATUS  mandatory
	DESCRIPTION "CB34 Warning-Time-Delay"
		::= { bcmsplus3 295 }

bcms3-cb35-warning-time-delay
	OBJECT-TYPE
	SYNTAX  INTEGER
	ACCESS  read-write
	STATUS  mandatory
	DESCRIPTION "CB35 Warning-Time-Delay"
		::= { bcmsplus3 296 }

bcms3-cb36-warning-time-delay
	OBJECT-TYPE
	SYNTAX  INTEGER
	ACCESS  read-write
	STATUS  mandatory
	DESCRIPTION "CB36 Warning-Time-Delay"
		::= { bcmsplus3 297 }

bcms3-cb37-warning-time-delay
	OBJECT-TYPE
	SYNTAX  INTEGER
	ACCESS  read-write
	STATUS  mandatory
	DESCRIPTION "CB37 Warning-Time-Delay"
		::= { bcmsplus3 298 }

bcms3-cb38-warning-time-delay
	OBJECT-TYPE
	SYNTAX  INTEGER
	ACCESS  read-write
	STATUS  mandatory
	DESCRIPTION "CB38 Warning-Time-Delay"
		::= { bcmsplus3 299 }

bcms3-cb39-warning-time-delay
	OBJECT-TYPE
	SYNTAX  INTEGER
	ACCESS  read-write
	STATUS  mandatory
	DESCRIPTION "CB39 Warning-Time-Delay"
		::= { bcmsplus3 300 }

bcms3-cb40-warning-time-delay
	OBJECT-TYPE
	SYNTAX  INTEGER
	ACCESS  read-write
	STATUS  mandatory
	DESCRIPTION "CB40 Warning-Time-Delay"
		::= { bcmsplus3 301 }

bcms3-cb41-warning-time-delay
	OBJECT-TYPE
	SYNTAX  INTEGER
	ACCESS  read-write
	STATUS  mandatory
	DESCRIPTION "CB41 Warning-Time-Delay"
		::= { bcmsplus3 302 }

bcms3-cb42-warning-time-delay
	OBJECT-TYPE
	SYNTAX  INTEGER
	ACCESS  read-write
	STATUS  mandatory
	DESCRIPTION "CB42 Warning-Time-Delay"
		::= { bcmsplus3 303 }

bcms3-cb1-alarm-time-delay
	OBJECT-TYPE
	SYNTAX  INTEGER
	ACCESS  read-write
	STATUS  mandatory
	DESCRIPTION "CB1 Alarm-Time-Delay
		       Note for all alarm time delays 1-42: units are in seconds"                     
		::= { bcmsplus3 304 }

bcms3-cb2-alarm-time-delay
	OBJECT-TYPE
	SYNTAX  INTEGER
	ACCESS  read-write
	STATUS  mandatory
	DESCRIPTION "CB2 Alarm-Time-Delay"
		::= { bcmsplus3 305 }
  
bcms3-cb3-alarm-time-delay
	OBJECT-TYPE
	SYNTAX  INTEGER
	ACCESS  read-write
	STATUS  mandatory
	DESCRIPTION "CB3 Alarm-Time-Delay"
		::= { bcmsplus3 306 }

bcms3-cb4-alarm-time-delay
	OBJECT-TYPE
	SYNTAX  INTEGER
	ACCESS  read-write
	STATUS  mandatory
	DESCRIPTION "CB4 Alarm-Time-Delay"
		::= { bcmsplus3 307 }

bcms3-cb5-alarm-time-delay
	OBJECT-TYPE
	SYNTAX  INTEGER
	ACCESS  read-write
	STATUS  mandatory
	DESCRIPTION "CB5 Alarm-Time-Delay"
		::= { bcmsplus3 308 }

bcms3-cb6-alarm-time-delay
	OBJECT-TYPE
	SYNTAX  INTEGER
	ACCESS  read-write
	STATUS  mandatory
	DESCRIPTION "CB6 Alarm-Time-Delay"
		::= { bcmsplus3 309 }

bcms3-cb7-alarm-time-delay
	OBJECT-TYPE
	SYNTAX  INTEGER
	ACCESS  read-write
	STATUS  mandatory
	DESCRIPTION "CB7 Alarm-Time-Delay"
		::= { bcmsplus3 310 }

bcms3-cb8-alarm-time-delay
	OBJECT-TYPE
	SYNTAX  INTEGER
	ACCESS  read-write
	STATUS  mandatory
	DESCRIPTION "CB8 Alarm-Time-Delay"
		::= { bcmsplus3 311 }

bcms3-cb9-alarm-time-delay
	OBJECT-TYPE
	SYNTAX  INTEGER
	ACCESS  read-write
	STATUS  mandatory
	DESCRIPTION "CB9 Alarm-Time-Delay"
		::= { bcmsplus3 312 }

bcms3-cb10-alarm-time-delay
	OBJECT-TYPE
	SYNTAX  INTEGER
	ACCESS  read-write
	STATUS  mandatory
	DESCRIPTION "CB10 Alarm-Time-Delay"
		::= { bcmsplus3 313 }

bcms3-cb11-alarm-time-delay
	OBJECT-TYPE
	SYNTAX  INTEGER
	ACCESS  read-write
	STATUS  mandatory
	DESCRIPTION "CB11 Alarm-Time-Delay"
		::= { bcmsplus3 314 }

bcms3-cb12-alarm-time-delay
	OBJECT-TYPE
	SYNTAX  INTEGER
	ACCESS  read-write
	STATUS  mandatory
	DESCRIPTION "CB12 Alarm-Time-Delay"
		::= { bcmsplus3 315 }
  
bcms3-cb13-alarm-time-delay
	OBJECT-TYPE
	SYNTAX  INTEGER
	ACCESS  read-write
	STATUS  mandatory
	DESCRIPTION "CB13 Alarm-Time-Delay"
		::= { bcmsplus3 316 }

bcms3-cb14-alarm-time-delay
	OBJECT-TYPE
	SYNTAX  INTEGER
	ACCESS  read-write
	STATUS  mandatory
	DESCRIPTION "CB14 Alarm-Time-Delay"
		::= { bcmsplus3 317 }

bcms3-cb15-alarm-time-delay
	OBJECT-TYPE
	SYNTAX  INTEGER
	ACCESS  read-write
	STATUS  mandatory
	DESCRIPTION "CB15 Alarm-Time-Delay"
		::= { bcmsplus3 318 }

bcms3-cb16-alarm-time-delay
	OBJECT-TYPE
	SYNTAX  INTEGER
	ACCESS  read-write
	STATUS  mandatory
	DESCRIPTION "CB16 Alarm-Time-Delay"
		::= { bcmsplus3 319 }

bcms3-cb17-alarm-time-delay
	OBJECT-TYPE
	SYNTAX  INTEGER
	ACCESS  read-write
	STATUS  mandatory
	DESCRIPTION "CB17 Alarm-Time-Delay"
		::= { bcmsplus3 320 }

bcms3-cb18-alarm-time-delay
	OBJECT-TYPE
	SYNTAX  INTEGER
	ACCESS  read-write
	STATUS  mandatory
	DESCRIPTION "CB18 Alarm-Time-Delay"
		::= { bcmsplus3 321 }

bcms3-cb19-alarm-time-delay
	OBJECT-TYPE
	SYNTAX  INTEGER
	ACCESS  read-write
	STATUS  mandatory
	DESCRIPTION "CB19 Alarm-Time-Delay"
		::= { bcmsplus3 322 }

bcms3-cb20-alarm-time-delay
	OBJECT-TYPE
	SYNTAX  INTEGER
	ACCESS  read-write
	STATUS  mandatory
	DESCRIPTION "CB20 Alarm-Time-Delay"
		::= { bcmsplus3 323 }

bcms3-cb21-alarm-time-delay
	OBJECT-TYPE
	SYNTAX  INTEGER
	ACCESS  read-write
	STATUS  mandatory
	DESCRIPTION "CB21 Alarm-Time-Delay"
		::= { bcmsplus3 324 }

bcms3-cb22-alarm-time-delay
	OBJECT-TYPE
	SYNTAX  INTEGER
	ACCESS  read-write
	STATUS  mandatory
	DESCRIPTION "CB22 Alarm-Time-Delay"
		::= { bcmsplus3 325 }
  
bcms3-cb23-alarm-time-delay
	OBJECT-TYPE
	SYNTAX  INTEGER
	ACCESS  read-write
	STATUS  mandatory
	DESCRIPTION "CB23 Alarm-Time-Delay"
		::= { bcmsplus3 326 }

bcms3-cb24-alarm-time-delay
	OBJECT-TYPE
	SYNTAX  INTEGER
	ACCESS  read-write
	STATUS  mandatory
	DESCRIPTION "CB24 Alarm-Time-Delay"
		::= { bcmsplus3 327 }

bcms3-cb25-alarm-time-delay
	OBJECT-TYPE
	SYNTAX  INTEGER
	ACCESS  read-write
	STATUS  mandatory
	DESCRIPTION "CB25 Alarm-Time-Delay"
		::= { bcmsplus3 328 }

bcms3-cb26-alarm-time-delay
	OBJECT-TYPE
	SYNTAX  INTEGER
	ACCESS  read-write
	STATUS  mandatory
	DESCRIPTION "CB26 Alarm-Time-Delay"
		::= { bcmsplus3 329 }

bcms3-cb27-alarm-time-delay
	OBJECT-TYPE
	SYNTAX  INTEGER
	ACCESS  read-write
	STATUS  mandatory
	DESCRIPTION "CB27 Alarm-Time-Delay"
		::= { bcmsplus3 330 }

bcms3-cb28-alarm-time-delay
	OBJECT-TYPE
	SYNTAX  INTEGER
	ACCESS  read-write
	STATUS  mandatory
	DESCRIPTION "CB28 Alarm-Time-Delay"
		::= { bcmsplus3 331 }

bcms3-cb29-alarm-time-delay
	OBJECT-TYPE
	SYNTAX  INTEGER
	ACCESS  read-write
	STATUS  mandatory
	DESCRIPTION "CB29 Alarm-Time-Delay"
		::= { bcmsplus3 332 }

bcms3-cb30-alarm-time-delay
	OBJECT-TYPE
	SYNTAX  INTEGER
	ACCESS  read-write
	STATUS  mandatory
	DESCRIPTION "CB30 Alarm-Time-Delay"
		::= { bcmsplus3 333 }

bcms3-cb31-alarm-time-delay
	OBJECT-TYPE
	SYNTAX  INTEGER
	ACCESS  read-write
	STATUS  mandatory
	DESCRIPTION "CB31 Alarm-Time-Delay"
		::= { bcmsplus3 334 }

bcms3-cb32-alarm-time-delay
	OBJECT-TYPE
	SYNTAX  INTEGER
	ACCESS  read-write
	STATUS  mandatory
	DESCRIPTION "CB32 Alarm-Time-Delay"
		::= { bcmsplus3 335 }
  
bcms3-cb33-alarm-time-delay
	OBJECT-TYPE
	SYNTAX  INTEGER
	ACCESS  read-write
	STATUS  mandatory
	DESCRIPTION "CB33 Alarm-Time-Delay"
		::= { bcmsplus3 336 }

bcms3-cb34-alarm-time-delay
	OBJECT-TYPE
	SYNTAX  INTEGER
	ACCESS  read-write
	STATUS  mandatory
	DESCRIPTION "CB34 Alarm-Time-Delay"
		::= { bcmsplus3 337 }

bcms3-cb35-alarm-time-delay
	OBJECT-TYPE
	SYNTAX  INTEGER
	ACCESS  read-write
	STATUS  mandatory
	DESCRIPTION "CB35 Alarm-Time-Delay"
		::= { bcmsplus3 338 }

bcms3-cb36-alarm-time-delay
	OBJECT-TYPE
	SYNTAX  INTEGER
	ACCESS  read-write
	STATUS  mandatory
	DESCRIPTION "CB36 Alarm-Time-Delay"
		::= { bcmsplus3 339 }

bcms3-cb37-alarm-time-delay
	OBJECT-TYPE
	SYNTAX  INTEGER
	ACCESS  read-write
	STATUS  mandatory
	DESCRIPTION "CB37 Alarm-Time-Delay"
		::= { bcmsplus3 340 }

bcms3-cb38-alarm-time-delay
	OBJECT-TYPE
	SYNTAX  INTEGER
	ACCESS  read-write
	STATUS  mandatory
	DESCRIPTION "CB38 Alarm-Time-Delay"
		::= { bcmsplus3 341 }

bcms3-cb39-alarm-time-delay
	OBJECT-TYPE
	SYNTAX  INTEGER
	ACCESS  read-write
	STATUS  mandatory
	DESCRIPTION "CB39 Alarm-Time-Delay"
		::= { bcmsplus3 342 }

bcms3-cb40-alarm-time-delay
	OBJECT-TYPE
	SYNTAX  INTEGER
	ACCESS  read-write
	STATUS  mandatory
	DESCRIPTION "CB40 Alarm-Time-Delay"
		::= { bcmsplus3 343 }

bcms3-cb41-alarm-time-delay
	OBJECT-TYPE
	SYNTAX  INTEGER
	ACCESS  read-write
	STATUS  mandatory
	DESCRIPTION "CB41 Alarm-Time-Delay"
		::= { bcmsplus3 344 }

bcms3-cb42-alarm-time-delay
	OBJECT-TYPE
	SYNTAX  INTEGER
	ACCESS  read-write
	STATUS  mandatory
	DESCRIPTION "CB42 Alarm-Time-Delay"
		::= { bcmsplus3 345 }

bcms3-global-breaker-size
	OBJECT-TYPE
	SYNTAX  INTEGER
	ACCESS  read-write
	STATUS  mandatory
	DESCRIPTION "Global-breaker-size
		     Note for global breaker size: 10 = 10 amps
                     Range is 10 to 100 amps"
		::= { bcmsplus3 346 }

bcms3-global-warning-threshold
	OBJECT-TYPE
	SYNTAX  INTEGER
	ACCESS  read-write
	STATUS  mandatory
	DESCRIPTION "Global-warning-threshold
		     Note for global warning threshold: 70 = 70% of breaker size
                     range is 0-100%"
		::= { bcmsplus3 347 }

bcms3-global-alarm-threshold
	OBJECT-TYPE
	SYNTAX  INTEGER
	ACCESS  read-write
	STATUS  mandatory
	DESCRIPTION "Global-alarm-threshold
		     Note for global alarm threshold: 80 = 80% of breaker size
                     range is 0-100%"
		::= { bcmsplus3 348 }

bcms3-global-warning-time-delay
	OBJECT-TYPE
	SYNTAX  INTEGER
	ACCESS  read-write
	STATUS  mandatory
	DESCRIPTION "Global-warning-time-delay
		     Note for global warning time delay: units are in seconds"                     
		::= { bcmsplus3 349 }

bcms3-global-alarm-time-delay
	OBJECT-TYPE
	SYNTAX  INTEGER
	ACCESS  read-write
	STATUS  mandatory
	DESCRIPTION "Global-alarm-time-delay
		     Note for global alarm time delay: units are in seconds"                     
		::= { bcmsplus3 350 }

bcms3-min-max-reset
	OBJECT-TYPE
	SYNTAX  INTEGER
	ACCESS  read-write
	STATUS  mandatory
	DESCRIPTION "Min-max-Reset
                     Note for Min-max Reset: writing to this register will clear minimum
		     and maximum current values"
		::= { bcmsplus3 351 }

bcms3-global-warning-alarm-register
	OBJECT-TYPE
	SYNTAX  INTEGER
	ACCESS  read-only
	STATUS  mandatory
	DESCRIPTION "Global-Warning-Alarm-Register
			bit 0:	Warning Register 1
			bit 1:	Warning Register 2
			bit 2:	Warning Register 3
			bit 3:	Alarm Register 1
			bit 4:	Alarm Register 2
			bit 5:	Alarm Register 3
			bit 6:	Zero Current Register 1
			bit 7:	Zero Current Register 2
			bit 8:	Zero Current Register 3
			bits 9 – 15: Always read as 0"
		::= { bcmsplus3 352 }

bcms3-meter-alarm-status-latching
	OBJECT-TYPE
	SYNTAX  INTEGER
	ACCESS  read-write
	STATUS  mandatory
	DESCRIPTION "Meter-Alarm-Status-Latching
			bit 0:	Over Current panelboard
			bit 1:	Under Current panelboard
			bit 2: 	Over Current both panelboards 
			bit 3: 	Under Current both panelboards
			bit 4: 	Over Voltage main
			bit 5: 	Under Voltage main
			bit 6: 	Over Voltage alternate
			bit 7: 	Under Voltage alternate
			bits 8 – 15: Not Used"
		::= { bcmsplus3 353 }

bcms3-meter-alarm-status-nonlatching
	OBJECT-TYPE
	SYNTAX  INTEGER
	ACCESS  read-only
	STATUS  mandatory
	DESCRIPTION "Meter-Alarm-Status-Nonlatching
			bit 0:	Over Current panelboard
			bit 1:	Under Current panelboard
			bit 2: 	Over Current both panelboards 
			bit 3: 	Under Current both panelboards
			bit 4: 	Over Voltage main
			bit 5: 	Under Voltage main
			bit 6: 	Over Voltage alternate
			bit 7: 	Under Voltage alternate
			bits 8 – 15: Not Used"
		::= { bcmsplus3 354 }

bcms3-digital-alarm-status
	OBJECT-TYPE
	SYNTAX  INTEGER
	ACCESS  read-only
	STATUS  mandatory
	DESCRIPTION "Digital-Alarm-Status
			bit 0:	Digital alarm 1
			bit 1:	Digital alarm 2
			bit 2: 	Digital alarm 3
			bit 3: 	Digital alarm 4
			bits 4 – 15: Not Used"
		::= { bcmsplus3 355 }

bcms3-current-option-setting
	OBJECT-TYPE
	SYNTAX  INTEGER
	ACCESS  read-only
	STATUS  mandatory
	DESCRIPTION "Current-Option-Setting
			bit 0:	option 0
			bit 1:	option 1
			bit 2: 	option 2 
			bit 3: 	neutral CTs
			bit 4:	no branch CTs
		     Option 0: no main or panelboard CTs. 	(357-359 summation of branch)
								(367-376 not used)
		     Option 1: CTs on main input feeding both panelboards. 
								(357-359 summation of branch)
		     Option 2: CTs on each panel board. 	(367-376 summation of panelboard 1 and 2) 
		     Note: Neutral current monitoring is optional."
		::= { bcmsplus3 356 }

bcms3-current-phase-a-panelboard
	OBJECT-TYPE
	SYNTAX  INTEGER
	ACCESS  read-only
	STATUS  mandatory
	DESCRIPTION "Current-Phase-A-Panelboard
                     Note for all currents: 100 = 10.0 amps"
		::= { bcmsplus3 357 }

bcms3-current-phase-b-panelboard
	OBJECT-TYPE
	SYNTAX  INTEGER
	ACCESS  read-only
	STATUS  mandatory
	DESCRIPTION "Current-Phase-B-Panelboard"
		::= { bcmsplus3 358 }

bcms3-current-phase-c-panelboard
	OBJECT-TYPE
	SYNTAX  INTEGER
	ACCESS  read-only
	STATUS  mandatory
	DESCRIPTION "Current-Phase-C-Panelboard"
		::= { bcmsplus3 359 }

bcms3-current-neutral-panelboard
	OBJECT-TYPE
	SYNTAX  INTEGER
	ACCESS  read-only
	STATUS  mandatory
	DESCRIPTION "Current-Neutral-Panelboard"
		::= { bcmsplus3 360 }


bcms3-over-current-alarm-threshhold-pnlbd
	OBJECT-TYPE
	SYNTAX  INTEGER
	ACCESS  read-write
	STATUS  mandatory
	DESCRIPTION "Over-Current-Alarm-Threshhold-Pnlbd"
		::= { bcmsplus3 361 }

bcms3-under-current-alarm-threshhold-pnlbd
	OBJECT-TYPE
	SYNTAX  INTEGER
	ACCESS  read-write
	STATUS  mandatory
	DESCRIPTION "Under-Current-Alarm-Threshhold-Pnlbd"
		::= { bcmsplus3 362 }

bcms3-over-current-set-counter-pnlbd
	OBJECT-TYPE
	SYNTAX  INTEGER
	ACCESS  read-only
	STATUS  mandatory
	DESCRIPTION "Over-Current-Set-Counter-Pnlbd
		     Note for all counters:
                     The set counter is incremented when the value goes outside the threshold limit
                     The reset counter is incremented when the value is returns to  the threshold limit"
		::= { bcmsplus3 363 }

bcms3-over-current-reset-counter-pnlbd
	OBJECT-TYPE
	SYNTAX  INTEGER
	ACCESS  read-only
	STATUS  mandatory
	DESCRIPTION "Over-Current-Reset-Counter-Pnlbd"
		::= { bcmsplus3 364 }

bcms3-under-current-set-counter-pnlbd
	OBJECT-TYPE
	SYNTAX  INTEGER
	ACCESS  read-only
	STATUS  mandatory
	DESCRIPTION "Under-Current-Set-Counter-Pnlbd"
		::= { bcmsplus3 365 }

bcms3-under-current-reset-counter-pnlbd
	OBJECT-TYPE
	SYNTAX  INTEGER
	ACCESS  read-only
	STATUS  mandatory
	DESCRIPTION "Under-Current-Reset-Counter-Pnlbd"
		::= { bcmsplus3 366 }

bcms3-current-phase-a-both-pnlbd
	OBJECT-TYPE
	SYNTAX  INTEGER
	ACCESS  read-only
	STATUS  mandatory
	DESCRIPTION "Current-Phase-A-Both-Pnlbd"
		::= { bcmsplus3 367 }

bcms3-current-phase-b-both-pnlbd
	OBJECT-TYPE
	SYNTAX  INTEGER
	ACCESS  read-only
	STATUS  mandatory
	DESCRIPTION "Current-Phase-B-Both-Pnlbd"
		::= { bcmsplus3 368 }

bcms3-current-phase-c-both-pnlbd
	OBJECT-TYPE
	SYNTAX  INTEGER
	ACCESS  read-only
	STATUS  mandatory
	DESCRIPTION "Current-Phase-C-Both-Pnlbd"
		::= { bcmsplus3 369 }

bcms3-current-neutral-both-pnlbd
	OBJECT-TYPE
	SYNTAX  INTEGER
	ACCESS  read-only
	STATUS  mandatory
	DESCRIPTION "Current-Neutral-Both-Pnlbd"
		::= { bcmsplus3 370 }


bcms3-over-current-alarm-threshhold-both-pnlbd
	OBJECT-TYPE
	SYNTAX  INTEGER
	ACCESS  read-write
	STATUS  mandatory
	DESCRIPTION "Over-Current-Alarm-Threshhold-Both-Pnlbd"
		::= { bcmsplus3 371 }

bcms3-under-current-alarm-threshhold-both-pnlbd
	OBJECT-TYPE
	SYNTAX  INTEGER
	ACCESS  read-write
	STATUS  mandatory
	DESCRIPTION "Under-Current-Alarm-Threshhold-Both-Pnlbd"
		::= { bcmsplus3 372 }

bcms3-over-current-set-counter-both-pnlbd
	OBJECT-TYPE
	SYNTAX  INTEGER
	ACCESS  read-only
	STATUS  mandatory
	DESCRIPTION "Over-Current-Set-Counter-Both-Pnlbd"
		::= { bcmsplus3 373 }

bcms3-over-current-reset-counter-both-pnlbd
	OBJECT-TYPE
	SYNTAX  INTEGER
	ACCESS  read-only
	STATUS  mandatory
	DESCRIPTION "Over-Current-Reset-Counter-Both-Pnlbd"
		::= { bcmsplus3 374 }

bcms3-under-current-set-counter-both-pnlbd
	OBJECT-TYPE
	SYNTAX  INTEGER
	ACCESS  read-only
	STATUS  mandatory
	DESCRIPTION "Under-Current-Set-Counter-Both-Pnlbd"
		::= { bcmsplus3 375 }

bcms3-under-current-reset-counter-both-pnlbd
	OBJECT-TYPE
	SYNTAX  INTEGER
	ACCESS  read-only
	STATUS  mandatory
	DESCRIPTION "Under-Current-Reset-Counter-Both-Pnlbd"
		::= { bcmsplus3 376 }

bcms3-voltage-option-setting
	OBJECT-TYPE
	SYNTAX  INTEGER
	ACCESS  read-only
	STATUS  mandatory
	DESCRIPTION "Voltage-Option-Setting
			bit 0:	option 0
			bit 1:	option 1
			bit 2: 	option 2 
			bit 3: 	option 3 
			bits 4 – 15: Not Used
                     Option 0: no voltage monitoring. (378-414 not used)
                     Option 1: One voltage feeding 1 or 2 panel boards. (390-401 not used)
                     Option 2: One voltage feeding panelboard 1 and another feeding panelboard 2. (390-401 not used)
                     Option 3: Two voltages tied together through interlocked circuit breakers feeding both panelboards. 
                               Digital input 1 and 2 are used to determine which is feeding the panelboard. A set bit 
                               indicated closed.  If both are closed, main voltage is used."
		::= { bcmsplus3 377 }

bcms3-voltage-a-b-main
	OBJECT-TYPE
	SYNTAX  INTEGER
	ACCESS  read-only
	STATUS  mandatory
	DESCRIPTION "Voltage-A-B-Main
                     Note for all voltages: 1200 = 120.0 volts"
		::= { bcmsplus3 378 }

bcms3-voltage-b-c-main
	OBJECT-TYPE
	SYNTAX  INTEGER
	ACCESS  read-only
	STATUS  mandatory
	DESCRIPTION "Voltage-B-C-Main"
		::= { bcmsplus3 379 }

bcms3-voltage-c-a-main
	OBJECT-TYPE
	SYNTAX  INTEGER
	ACCESS  read-only
	STATUS  mandatory
	DESCRIPTION "Voltage-C-A-Main"
		::= { bcmsplus3 380 }

bcms3-voltage-a-n-main
	OBJECT-TYPE
	SYNTAX  INTEGER
	ACCESS  read-only
	STATUS  mandatory
	DESCRIPTION "Voltage-A-N-Main"
		::= { bcmsplus3 381 }

bcms3-voltage-b-n-main
	OBJECT-TYPE
	SYNTAX  INTEGER
	ACCESS  read-only
	STATUS  mandatory
	DESCRIPTION "Voltage-B-N-Main"
		::= { bcmsplus3 382 }

bcms3-voltage-c-n-main
	OBJECT-TYPE
	SYNTAX  INTEGER
	ACCESS  read-only
	STATUS  mandatory
	DESCRIPTION "Voltage-C-N-Main"
		::= { bcmsplus3 383 }

bcms3-over-voltage-alarm-threshhold-main
	OBJECT-TYPE
	SYNTAX  INTEGER
	ACCESS  read-write
	STATUS  mandatory
	DESCRIPTION "Over-Voltage-Alarm-Threshhold-Main
                     Note All Over and Under Voltage is for L-L values"
		::= { bcmsplus3 384 }

bcms3-under-voltage-alarm-threshhold-main
	OBJECT-TYPE
	SYNTAX  INTEGER
	ACCESS  read-write
	STATUS  mandatory
	DESCRIPTION "Under-Voltage-Alarm-Threshhold-Main"
		::= { bcmsplus3 385 }

bcms3-over-voltage-set-counter-main
	OBJECT-TYPE
	SYNTAX  INTEGER
	ACCESS  read-only
	STATUS  mandatory
	DESCRIPTION "Over-Voltage-Set-Counter-Main"
		::= { bcmsplus3 386 }

bcms3-over-voltage-reset-counter-main
	OBJECT-TYPE
	SYNTAX  INTEGER
	ACCESS  read-only
	STATUS  mandatory
	DESCRIPTION "Over-Voltage-Reset-Counter-Main"
		::= { bcmsplus3 387 }

bcms3-under-voltage-set-counter-main
	OBJECT-TYPE
	SYNTAX  INTEGER
	ACCESS  read-only
	STATUS  mandatory
	DESCRIPTION "Under-Voltage-Set-Counter-Main"
		::= { bcmsplus3 388 }

bcms3-under-voltage-reset-counter-main
	OBJECT-TYPE
	SYNTAX  INTEGER
	ACCESS  read-only
	STATUS  mandatory
	DESCRIPTION "Under-Voltage-Reset-Counter-Main"
		::= { bcmsplus3 389 }


bcms3-voltage-frequency-main
	OBJECT-TYPE
	SYNTAX  INTEGER
	ACCESS  read-only
	STATUS  mandatory
	DESCRIPTION "Voltage-Frequency-Main
                     note for frequency: 600 = 60.0Hz
                     Range is 40-70Hz
                     Note if insufficient voltage is present frequency will read 0xFFFF"
		::= { bcmsplus3 390 }

bcms3-voltage-a-b-alternate
	OBJECT-TYPE
	SYNTAX  INTEGER
	ACCESS  read-only
	STATUS  mandatory
	DESCRIPTION "Voltage-A-B-Alternate"
		::= { bcmsplus3 391 }

bcms3-voltage-b-c-alternate
	OBJECT-TYPE
	SYNTAX  INTEGER
	ACCESS  read-only
	STATUS  mandatory
	DESCRIPTION "Voltage-B-C-Alternate"
		::= { bcmsplus3 392 }

bcms3-voltage-c-a-alternate
	OBJECT-TYPE
	SYNTAX  INTEGER
	ACCESS  read-only
	STATUS  mandatory
	DESCRIPTION "Voltage-C-A-Alternate"
		::= { bcmsplus3 393 }

bcms3-voltage-a-n-alternate
	OBJECT-TYPE
	SYNTAX  INTEGER
	ACCESS  read-only
	STATUS  mandatory
	DESCRIPTION "Voltage-A-N-Alternate"
		::= { bcmsplus3 394 }

bcms3-voltage-b-N-alternate
	OBJECT-TYPE
	SYNTAX  INTEGER
	ACCESS  read-only
	STATUS  mandatory
	DESCRIPTION "Voltage-B-N-Alternate"
		::= { bcmsplus3 395 }

bcms3-voltage-c-n-alternate
	OBJECT-TYPE
	SYNTAX  INTEGER
	ACCESS  read-only
	STATUS  mandatory
	DESCRIPTION "Voltage-C-N-Alternate"
		::= { bcmsplus3 396 }

bcms3-over-voltage-alarm-threshhold-alternate
	OBJECT-TYPE
	SYNTAX  INTEGER
	ACCESS  read-write
	STATUS  mandatory
	DESCRIPTION "Over-Voltage-Alarm-Threshhold-Alternate"
		::= { bcmsplus3 397 }

bcms3-under-voltage-alarm-threshhold-alternate
	OBJECT-TYPE
	SYNTAX  INTEGER
	ACCESS  read-write
	STATUS  mandatory
	DESCRIPTION "Under-Voltage-Alarm-Threshhold-Alternate"
		::= { bcmsplus3 398 }

bcms3-over-voltage-set-counter-alternate
	OBJECT-TYPE
	SYNTAX  INTEGER
	ACCESS  read-only
	STATUS  mandatory
	DESCRIPTION "Over-Voltage-Set-Counter-Alternate"
		::= { bcmsplus3 399 }

bcms3-over-voltage-reset-counter-alternate
	OBJECT-TYPE
	SYNTAX  INTEGER
	ACCESS  read-only
	STATUS  mandatory
	DESCRIPTION "Over-Voltage-Reset-Counter-Alternate"
		::= { bcmsplus3 400 }

bcms3-under-voltage-set-counter-alternate
	OBJECT-TYPE
	SYNTAX  INTEGER
	ACCESS  read-only
	STATUS  mandatory
	DESCRIPTION "Under-Voltage-Set-Counter-Alternate"
		::= { bcmsplus3 401 }

bcms3-under-voltage-reset-counter-alternate
	OBJECT-TYPE
	SYNTAX  INTEGER
	ACCESS  read-only
	STATUS  mandatory
	DESCRIPTION "Under-Voltage-Reset-Counter-Alternate"
		::= { bcmsplus3 402 }

bcms3-real-power-kw
	OBJECT-TYPE
	SYNTAX  INTEGER
	ACCESS  read-only
	STATUS  mandatory
	DESCRIPTION "Real-Power-KW
                     Note for all KWs: 100 = 10.0 KW"
		::= { bcmsplus3 403 }

bcms3-peal-power-phase-a
	OBJECT-TYPE
	SYNTAX  INTEGER
	ACCESS  read-only
	STATUS  mandatory
	DESCRIPTION "Real-Power-Phase-A"
		::= { bcmsplus3 404 }

bcms3-real-power-phase-b
	OBJECT-TYPE
	SYNTAX  INTEGER
	ACCESS  read-only
	STATUS  mandatory
	DESCRIPTION "Real-Power-Phase-B"
		::= { bcmsplus3 405 }

bcms3-real-power-phase-c
	OBJECT-TYPE
	SYNTAX  INTEGER
	ACCESS  read-only
	STATUS  mandatory
	DESCRIPTION "Real-Power-Phase-C"
		::= { bcmsplus3 406 }

bcms3-reactive-power-kvar
	OBJECT-TYPE
	SYNTAX  INTEGER
	ACCESS  read-only
	STATUS  mandatory
	DESCRIPTION "Reactive-Power-KVAR
                     Note for KVAR: 100 = 10.0 KVAR"
		::= { bcmsplus3 407 }

bcms3-apparent-Power-kva
	OBJECT-TYPE
	SYNTAX  INTEGER
	ACCESS  read-only
	STATUS  mandatory
	DESCRIPTION "Apparent-Power-KVA
                     Note for KVA: 100 = 10.0 KVA"
		::= { bcmsplus3 408 }

bcms3-total-power-factor
	OBJECT-TYPE
	SYNTAX  INTEGER
	ACCESS  read-only
	STATUS  mandatory
	DESCRIPTION "Total-Power-Factor
                     Note for all Power Factor: 1000 = 100.0 PF"
		::= { bcmsplus3 409 }

bcms3-power-factor-phase-a
	OBJECT-TYPE
	SYNTAX  INTEGER
	ACCESS  read-only
	STATUS  mandatory
	DESCRIPTION "Power-Factor-Phase-A"
		::= { bcmsplus3 410 }

bcms3-Power-factor-phase-b
	OBJECT-TYPE
	SYNTAX  INTEGER
	ACCESS  read-only
	STATUS  mandatory
	DESCRIPTION "Power-Factor-Phase-B"
		::= { bcmsplus3 411 }

bcms3-Power-factor-phase-c
	OBJECT-TYPE
	SYNTAX  INTEGER
	ACCESS  read-only
	STATUS  mandatory
	DESCRIPTION "Power-Factor-Phase-C"
		::= { bcmsplus3 412 }

bcms3-energy-consumption-kwh-lower-word-integer
	OBJECT-TYPE
	SYNTAX  INTEGER
	ACCESS  read-write
	STATUS  mandatory
	DESCRIPTION "Energy-Consumption-KWh-Lower-Word-Integer
		     Note for KWh: 100 = 100KWh
                     Combine lower and upper integers into a word for total KWh"
		::= { bcmsplus3 413 }

bcms3-energy-consumption-kwh-upper-word-integer
	OBJECT-TYPE
	SYNTAX  INTEGER
	ACCESS  read-write
	STATUS  mandatory
	DESCRIPTION "Energy-Consumption-KWh-Upper-Word-Integer"
		::= { bcmsplus3 414 }

bcms3-main-voltage-thd-phase-a
	OBJECT-TYPE
	SYNTAX  INTEGER
	ACCESS  read-only
	STATUS  mandatory
	DESCRIPTION "Main-Voltage-THD-Phase-A"
		::= { bcmsplus3 415 }

bcms3-main-voltage-thd-phase-b
	OBJECT-TYPE
	SYNTAX  INTEGER
	ACCESS  read-only
	STATUS  mandatory
	DESCRIPTION "Main-Voltage-THD-Phase-B"
		::= { bcmsplus3 416 }

bcms3-main-voltage-thd-phase-c
	OBJECT-TYPE
	SYNTAX  INTEGER
	ACCESS  read-only
	STATUS  mandatory
	DESCRIPTION "Main-Voltage-THD-Phase-C"
		::= { bcmsplus3 417 }

bcms3-alt-voltage-thd-phase-a
	OBJECT-TYPE
	SYNTAX  INTEGER
	ACCESS  read-only
	STATUS  mandatory
	DESCRIPTION "Alt-Voltage-THD-Phase-A"
		::= { bcmsplus3 418 }

bcms3-alt-voltage-thd-phase-b
	OBJECT-TYPE
	SYNTAX  INTEGER
	ACCESS  read-only
	STATUS  mandatory
	DESCRIPTION "Alt-Voltage-THD-Phase-B"
		::= { bcmsplus3 419 }

bcms3-alt-voltage-thd-phase-c
	OBJECT-TYPE
	SYNTAX  INTEGER
	ACCESS  read-only
	STATUS  mandatory
	DESCRIPTION "Alt-Voltage-THD-Phase-C"
		::= { bcmsplus3 420 }

bcms3-current-ground-panelboard
	OBJECT-TYPE
	SYNTAX  INTEGER
	ACCESS  read-only
	STATUS  mandatory
	DESCRIPTION "Current-Ground-Panelboard"
		::= { bcmsplus3 421 }

bcms3-percent-load-phase-a
	OBJECT-TYPE
	SYNTAX  INTEGER
	ACCESS  read-only
	STATUS  mandatory
	DESCRIPTION "Percent Load Phase A"
		::= { bcmsplus3 422 }

bcms3-percent-load-phase-b
	OBJECT-TYPE
	SYNTAX  INTEGER
	ACCESS  read-only
	STATUS  mandatory
	DESCRIPTION "Percent Load Phase B"
		::= { bcmsplus3 423 }

bcms3-percent-load-phase-c
	OBJECT-TYPE
	SYNTAX  INTEGER
	ACCESS  read-only
	STATUS  mandatory
	DESCRIPTION "Percent Load Phase C"
		::= { bcmsplus3 424 }

bcms3-full-load-current
	OBJECT-TYPE
	SYNTAX  INTEGER
	ACCESS  read-write
	STATUS  mandatory
	DESCRIPTION "Full Load Current"
		::= { bcmsplus3 425 }

--------------------------------------------------------------------------------
-- BCMSPLUS register values
--------------------------------------------------------------------------------

bcms4-cb1-current
	OBJECT-TYPE
	SYNTAX  INTEGER
	ACCESS  read-only
	STATUS  mandatory
	DESCRIPTION "CB1 Current
		     Note for all currents 1-42: 100 = 10.0 amps"
		::= { bcmsplus4 1 }
  
bcms4-cb2-current
	OBJECT-TYPE
	SYNTAX  INTEGER
	ACCESS  read-only
	STATUS  mandatory
	DESCRIPTION "CB2 Current"
		::= { bcmsplus4 2 }

bcms4-cb3-current
	OBJECT-TYPE
	SYNTAX  INTEGER
	ACCESS  read-only
	STATUS  mandatory
	DESCRIPTION "CB3 Current"
		::= { bcmsplus4 3 }

bcms4-cb4-current
	OBJECT-TYPE
	SYNTAX  INTEGER
	ACCESS  read-only
	STATUS  mandatory
	DESCRIPTION "CB4 Current"
		::= { bcmsplus4 4 }

bcms4-cb5-current
	OBJECT-TYPE
	SYNTAX  INTEGER
	ACCESS  read-only
	STATUS  mandatory
	DESCRIPTION "CB5 Current"
		::= { bcmsplus4 5 }

bcms4-cb6-current
	OBJECT-TYPE
	SYNTAX  INTEGER
	ACCESS  read-only
	STATUS  mandatory
	DESCRIPTION "CB6 Current"
		::= { bcmsplus4 6 }

bcms4-cb7-current
	OBJECT-TYPE
	SYNTAX  INTEGER
	ACCESS  read-only
	STATUS  mandatory
	DESCRIPTION "CB7 Current"
		::= { bcmsplus4 7 }

bcms4-cb8-current
	OBJECT-TYPE
	SYNTAX  INTEGER
	ACCESS  read-only
	STATUS  mandatory
	DESCRIPTION "CB8 Current"
		::= { bcmsplus4 8 }

bcms4-cb9-current
	OBJECT-TYPE
	SYNTAX  INTEGER
	ACCESS  read-only
	STATUS  mandatory
	DESCRIPTION "CB9 Current"
		::= { bcmsplus4 9 }

bcms4-cb10-current
	OBJECT-TYPE
	SYNTAX  INTEGER
	ACCESS  read-only
	STATUS  mandatory
	DESCRIPTION "CB10 Current"
		::= { bcmsplus4 10 }

bcms4-cb11-current
	OBJECT-TYPE
	SYNTAX  INTEGER
	ACCESS  read-only
	STATUS  mandatory
	DESCRIPTION "CB11 Current"
		::= { bcmsplus4 11 }
  
bcms4-cb12-current
	OBJECT-TYPE
	SYNTAX  INTEGER
	ACCESS  read-only
	STATUS  mandatory
	DESCRIPTION "CB12 Current"
		::= { bcmsplus4 12 }

bcms4-cb13-current
	OBJECT-TYPE
	SYNTAX  INTEGER
	ACCESS  read-only
	STATUS  mandatory
	DESCRIPTION "CB13 Current"
		::= { bcmsplus4 13 }

bcms4-cb14-current
	OBJECT-TYPE
	SYNTAX  INTEGER
	ACCESS  read-only
	STATUS  mandatory
	DESCRIPTION "CB14 Current"
		::= { bcmsplus4 14 }

bcms4-cb15-current
	OBJECT-TYPE
	SYNTAX  INTEGER
	ACCESS  read-only
	STATUS  mandatory
	DESCRIPTION "CB15 Current"
		::= { bcmsplus4 15 }

bcms4-cb16-current
	OBJECT-TYPE
	SYNTAX  INTEGER
	ACCESS  read-only
	STATUS  mandatory
	DESCRIPTION "CB16 Current"
		::= { bcmsplus4 16 }

bcms4-cb17-current
	OBJECT-TYPE
	SYNTAX  INTEGER
	ACCESS  read-only
	STATUS  mandatory
	DESCRIPTION "CB17 Current"
		::= { bcmsplus4 17 }

bcms4-cb18-current
	OBJECT-TYPE
	SYNTAX  INTEGER
	ACCESS  read-only
	STATUS  mandatory
	DESCRIPTION "CB18 Current"
		::= { bcmsplus4 18 }

bcms4-cb19-current
	OBJECT-TYPE
	SYNTAX  INTEGER
	ACCESS  read-only
	STATUS  mandatory
	DESCRIPTION "CB19 Current"
		::= { bcmsplus4 19 }

bcms4-cb20-current
	OBJECT-TYPE
	SYNTAX  INTEGER
	ACCESS  read-only
	STATUS  mandatory
	DESCRIPTION "CB20 Current"
		::= { bcmsplus4 20 }

bcms4-cb21-current
	OBJECT-TYPE
	SYNTAX  INTEGER
	ACCESS  read-only
	STATUS  mandatory
	DESCRIPTION "CB21 Current"
		::= { bcmsplus4 21 }
  
bcms4-cb22-current
	OBJECT-TYPE
	SYNTAX  INTEGER
	ACCESS  read-only
	STATUS  mandatory
	DESCRIPTION "CB22 Current"
		::= { bcmsplus4 22 }

bcms4-cb23-current
	OBJECT-TYPE
	SYNTAX  INTEGER
	ACCESS  read-only
	STATUS  mandatory
	DESCRIPTION "CB23 Current"
		::= { bcmsplus4 23 }

bcms4-cb24-current
	OBJECT-TYPE
	SYNTAX  INTEGER
	ACCESS  read-only
	STATUS  mandatory
	DESCRIPTION "CB24 Current"
		::= { bcmsplus4 24 }

bcms4-cb25-current
	OBJECT-TYPE
	SYNTAX  INTEGER
	ACCESS  read-only
	STATUS  mandatory
	DESCRIPTION "CB25 Current"
		::= { bcmsplus4 25 }

bcms4-cb26-current
	OBJECT-TYPE
	SYNTAX  INTEGER
	ACCESS  read-only
	STATUS  mandatory
	DESCRIPTION "CB26 Current"
		::= { bcmsplus4 26 }

bcms4-cb27-current
	OBJECT-TYPE
	SYNTAX  INTEGER
	ACCESS  read-only
	STATUS  mandatory
	DESCRIPTION "CB27 Current"
		::= { bcmsplus4 27 }

bcms4-cb28-current
	OBJECT-TYPE
	SYNTAX  INTEGER
	ACCESS  read-only
	STATUS  mandatory
	DESCRIPTION "CB28 Current"
		::= { bcmsplus4 28 }

bcms4-cb29-current
	OBJECT-TYPE
	SYNTAX  INTEGER
	ACCESS  read-only
	STATUS  mandatory
	DESCRIPTION "CB29 Current"
		::= { bcmsplus4 29 }

bcms4-cb30-current
	OBJECT-TYPE
	SYNTAX  INTEGER
	ACCESS  read-only
	STATUS  mandatory
	DESCRIPTION "CB30 Current"
		::= { bcmsplus4 30 }

bcms4-cb31-current
	OBJECT-TYPE
	SYNTAX  INTEGER
	ACCESS  read-only
	STATUS  mandatory
	DESCRIPTION "CB31 Current"
		::= { bcmsplus4 31 }
  
bcms4-cb32-current
	OBJECT-TYPE
	SYNTAX  INTEGER
	ACCESS  read-only
	STATUS  mandatory
	DESCRIPTION "CB32 Current"
		::= { bcmsplus4 32 }

bcms4-cb33-current
	OBJECT-TYPE
	SYNTAX  INTEGER
	ACCESS  read-only
	STATUS  mandatory
	DESCRIPTION "CB33 Current"
		::= { bcmsplus4 33 }

bcms4-cb34-current
	OBJECT-TYPE
	SYNTAX  INTEGER
	ACCESS  read-only
	STATUS  mandatory
	DESCRIPTION "CB34 Current"
		::= { bcmsplus4 34 }

bcms4-cb35-current
	OBJECT-TYPE
	SYNTAX  INTEGER
	ACCESS  read-only
	STATUS  mandatory
	DESCRIPTION "CB35 Current"
		::= { bcmsplus4 35 }

bcms4-cb36-current
	OBJECT-TYPE
	SYNTAX  INTEGER
	ACCESS  read-only
	STATUS  mandatory
	DESCRIPTION "CB36 Current"
		::= { bcmsplus4 36 }

bcms4-cb37-current
	OBJECT-TYPE
	SYNTAX  INTEGER
	ACCESS  read-only
	STATUS  mandatory
	DESCRIPTION "CB37 Current"
		::= { bcmsplus4 37 }

bcms4-cb38-current
	OBJECT-TYPE
	SYNTAX  INTEGER
	ACCESS  read-only
	STATUS  mandatory
	DESCRIPTION "CB38 Current"
		::= { bcmsplus4 38 }

bcms4-cb39-current
	OBJECT-TYPE
	SYNTAX  INTEGER
	ACCESS  read-only
	STATUS  mandatory
	DESCRIPTION "CB39 Current"
		::= { bcmsplus4 39 }

bcms4-cb40-current
	OBJECT-TYPE
	SYNTAX  INTEGER
	ACCESS  read-only
	STATUS  mandatory
	DESCRIPTION "CB40 Current"
		::= { bcmsplus4 40 }

bcms4-cb41-current
	OBJECT-TYPE
	SYNTAX  INTEGER
	ACCESS  read-only
	STATUS  mandatory
	DESCRIPTION "CB41 Current"
		::= { bcmsplus4 41 }
  
bcms4-cb42-current
	OBJECT-TYPE
	SYNTAX  INTEGER
	ACCESS  read-only
	STATUS  mandatory
	DESCRIPTION "CB42 Current"
		::= { bcmsplus4 42 }

bcms4-cb1-min
	OBJECT-TYPE
	SYNTAX  INTEGER
	ACCESS  read-only
	STATUS  mandatory
	DESCRIPTION "CB1 Min
		     Note for all minumum currents 1-42: 100 = 10.0 amps"
		::= { bcmsplus4 43 }

bcms4-cb2-min
	OBJECT-TYPE
	SYNTAX  INTEGER
	ACCESS  read-only
	STATUS  mandatory
	DESCRIPTION "CB2 Min"
		::= { bcmsplus4 44 }

bcms4-cb3-min
	OBJECT-TYPE
	SYNTAX  INTEGER
	ACCESS  read-only
	STATUS  mandatory
	DESCRIPTION "CB3 Min"
		::= { bcmsplus4 45 }

bcms4-cb4-min
	OBJECT-TYPE
	SYNTAX  INTEGER
	ACCESS  read-only
	STATUS  mandatory
	DESCRIPTION "CB4 Min"
		::= { bcmsplus4 46 }

bcms4-cb5-min
	OBJECT-TYPE
	SYNTAX  INTEGER
	ACCESS  read-only
	STATUS  mandatory
	DESCRIPTION "CB5 Min"
		::= { bcmsplus4 47 }

bcms4-cb6-min
	OBJECT-TYPE
	SYNTAX  INTEGER
	ACCESS  read-only
	STATUS  mandatory
	DESCRIPTION "CB6 Min"
		::= { bcmsplus4 48 }

bcms4-cb7-min
	OBJECT-TYPE
	SYNTAX  INTEGER
	ACCESS  read-only
	STATUS  mandatory
	DESCRIPTION "CB7 Min"
		::= { bcmsplus4 49 }

bcms4-cb8-min
	OBJECT-TYPE
	SYNTAX  INTEGER
	ACCESS  read-only
	STATUS  mandatory
	DESCRIPTION "CB8 Min"
		::= { bcmsplus4 50 }

bcms4-cb9-min
	OBJECT-TYPE
	SYNTAX  INTEGER
	ACCESS  read-only
	STATUS  mandatory
	DESCRIPTION "CB9 Min"
		::= { bcmsplus4 51 }
  
bcms4-cb10-min
	OBJECT-TYPE
	SYNTAX  INTEGER
	ACCESS  read-only
	STATUS  mandatory
	DESCRIPTION "CB10 Min"
		::= { bcmsplus4 52 }

bcms4-cb11-min
	OBJECT-TYPE
	SYNTAX  INTEGER
	ACCESS  read-only
	STATUS  mandatory
	DESCRIPTION "CB11 Min"
		::= { bcmsplus4 53 }

bcms4-cb12-min
	OBJECT-TYPE
	SYNTAX  INTEGER
	ACCESS  read-only
	STATUS  mandatory
	DESCRIPTION "CB12 Min"
		::= { bcmsplus4 54 }

bcms4-cb13-min
	OBJECT-TYPE
	SYNTAX  INTEGER
	ACCESS  read-only
	STATUS  mandatory
	DESCRIPTION "CB13 Min"
		::= { bcmsplus4 55 }

bcms4-cb14-min
	OBJECT-TYPE
	SYNTAX  INTEGER
	ACCESS  read-only
	STATUS  mandatory
	DESCRIPTION "CB14 Min"
		::= { bcmsplus4 56 }

bcms4-cb15-min
	OBJECT-TYPE
	SYNTAX  INTEGER
	ACCESS  read-only
	STATUS  mandatory
	DESCRIPTION "CB15 Min"
		::= { bcmsplus4 57 }

bcms4-cb16-min
	OBJECT-TYPE
	SYNTAX  INTEGER
	ACCESS  read-only
	STATUS  mandatory
	DESCRIPTION "CB16 Min"
		::= { bcmsplus4 58 }

bcms4-cb17-min
	OBJECT-TYPE
	SYNTAX  INTEGER
	ACCESS  read-only
	STATUS  mandatory
	DESCRIPTION "CB17 Min"
		::= { bcmsplus4 59 }


bcms4-cb18-min
	OBJECT-TYPE
	SYNTAX  INTEGER
	ACCESS  read-only
	STATUS  mandatory
	DESCRIPTION "CB18 Min"
		::= { bcmsplus4 60 }

bcms4-cb19-min
	OBJECT-TYPE
	SYNTAX  INTEGER
	ACCESS  read-only
	STATUS  mandatory
	DESCRIPTION "CB19 Min"
		::= { bcmsplus4 61 }
  
bcms4-cb20-min
	OBJECT-TYPE
	SYNTAX  INTEGER
	ACCESS  read-only
	STATUS  mandatory
	DESCRIPTION "CB20 Min"
		::= { bcmsplus4 62 }

bcms4-cb21-min
	OBJECT-TYPE
	SYNTAX  INTEGER
	ACCESS  read-only
	STATUS  mandatory
	DESCRIPTION "CB21 Min"
		::= { bcmsplus4 63 }

bcms4-cb22-min
	OBJECT-TYPE
	SYNTAX  INTEGER
	ACCESS  read-only
	STATUS  mandatory
	DESCRIPTION "CB22 Min"
		::= { bcmsplus4 64 }

bcms4-cb23-min
	OBJECT-TYPE
	SYNTAX  INTEGER
	ACCESS  read-only
	STATUS  mandatory
	DESCRIPTION "CB23 Min"
		::= { bcmsplus4 65 }

bcms4-cb24-min
	OBJECT-TYPE
	SYNTAX  INTEGER
	ACCESS  read-only
	STATUS  mandatory
	DESCRIPTION "CB24 Min"
		::= { bcmsplus4 66 }

bcms4-cb25-min
	OBJECT-TYPE
	SYNTAX  INTEGER
	ACCESS  read-only
	STATUS  mandatory
	DESCRIPTION "CB25 Min"
		::= { bcmsplus4 67 }

bcms4-cb26-min
	OBJECT-TYPE
	SYNTAX  INTEGER
	ACCESS  read-only
	STATUS  mandatory
	DESCRIPTION "CB26 Min"
		::= { bcmsplus4 68 }

bcms4-cb27-min
	OBJECT-TYPE
	SYNTAX  INTEGER
	ACCESS  read-only
	STATUS  mandatory
	DESCRIPTION "CB27 Min"
		::= { bcmsplus4 69 }

bcms4-cb28-min
	OBJECT-TYPE
	SYNTAX  INTEGER
	ACCESS  read-only
	STATUS  mandatory
	DESCRIPTION "CB28 Min"
		::= { bcmsplus4 70 }

bcms4-cb29-min
	OBJECT-TYPE
	SYNTAX  INTEGER
	ACCESS  read-only
	STATUS  mandatory
	DESCRIPTION "CB29 Min"
		::= { bcmsplus4 71 }
  
bcms4-cb30-min
	OBJECT-TYPE
	SYNTAX  INTEGER
	ACCESS  read-only
	STATUS  mandatory
	DESCRIPTION "CB30 Min"
		::= { bcmsplus4 72 }

bcms4-cb31-min
	OBJECT-TYPE
	SYNTAX  INTEGER
	ACCESS  read-only
	STATUS  mandatory
	DESCRIPTION "CB31 Min"
		::= { bcmsplus4 73 }

bcms4-cb32-min
	OBJECT-TYPE
	SYNTAX  INTEGER
	ACCESS  read-only
	STATUS  mandatory
	DESCRIPTION "CB32 Min"
		::= { bcmsplus4 74 }

bcms4-cb33-min
	OBJECT-TYPE
	SYNTAX  INTEGER
	ACCESS  read-only
	STATUS  mandatory
	DESCRIPTION "CB33 Min"
		::= { bcmsplus4 75 }

bcms4-cb34-min
	OBJECT-TYPE
	SYNTAX  INTEGER
	ACCESS  read-only
	STATUS  mandatory
	DESCRIPTION "CB34 Min"
		::= { bcmsplus4 76 }

bcms4-cb35-min
	OBJECT-TYPE
	SYNTAX  INTEGER
	ACCESS  read-only
	STATUS  mandatory
	DESCRIPTION "CB35 Min"
		::= { bcmsplus4 77 }

bcms4-cb36-min
	OBJECT-TYPE
	SYNTAX  INTEGER
	ACCESS  read-only
	STATUS  mandatory
	DESCRIPTION "CB36 Min"
		::= { bcmsplus4 78 }

bcms4-cb37-min
	OBJECT-TYPE
	SYNTAX  INTEGER
	ACCESS  read-only
	STATUS  mandatory
	DESCRIPTION "CB37 Min"
		::= { bcmsplus4 79 }

bcms4-cb38-min
	OBJECT-TYPE
	SYNTAX  INTEGER
	ACCESS  read-only
	STATUS  mandatory
	DESCRIPTION "CB38 Min"
		::= { bcmsplus4 80 }

bcms4-cb39-min
	OBJECT-TYPE
	SYNTAX  INTEGER
	ACCESS  read-only
	STATUS  mandatory
	DESCRIPTION "CB39 Min"
		::= { bcmsplus4 81 }
  
bcms4-cb40-min
	OBJECT-TYPE
	SYNTAX  INTEGER
	ACCESS  read-only
	STATUS  mandatory
	DESCRIPTION "CB40 Min"
		::= { bcmsplus4 82 }

bcms4-cb41-min
	OBJECT-TYPE
	SYNTAX  INTEGER
	ACCESS  read-only
	STATUS  mandatory
	DESCRIPTION "CB41 Min"
		::= { bcmsplus4 83 }

bcms4-cb42-min
	OBJECT-TYPE
	SYNTAX  INTEGER
	ACCESS  read-only
	STATUS  mandatory
	DESCRIPTION "CB42 Min"
		::= { bcmsplus4 84 }

bcms4-cb1-max
	OBJECT-TYPE
	SYNTAX  INTEGER
	ACCESS  read-only
	STATUS  mandatory
	DESCRIPTION "CB1 Max
		     Note for all maximum currents 1-42: 100 = 10.0 amps"
		::= { bcmsplus4 85 }

bcms4-cb2-max
	OBJECT-TYPE
	SYNTAX  INTEGER
	ACCESS  read-only
	STATUS  mandatory
	DESCRIPTION "CB2 Max"
		::= { bcmsplus4 86 }

bcms4-cb3-max
	OBJECT-TYPE
	SYNTAX  INTEGER
	ACCESS  read-only
	STATUS  mandatory
	DESCRIPTION "CB3 Max"
		::= { bcmsplus4 87 }

bcms4-cb4-max
	OBJECT-TYPE
	SYNTAX  INTEGER
	ACCESS  read-only
	STATUS  mandatory
	DESCRIPTION "CB4 Max"
		::= { bcmsplus4 88 }

bcms4-cb5-max
	OBJECT-TYPE
	SYNTAX  INTEGER
	ACCESS  read-only
	STATUS  mandatory
	DESCRIPTION "CB5 Max"
		::= { bcmsplus4 89 }

bcms4-cb6-max
	OBJECT-TYPE
	SYNTAX  INTEGER
	ACCESS  read-only
	STATUS  mandatory
	DESCRIPTION "CB6 Max"
		::= { bcmsplus4 90 }

bcms4-cb7-max
	OBJECT-TYPE
	SYNTAX  INTEGER
	ACCESS  read-only
	STATUS  mandatory
	DESCRIPTION "CB7 Max"
		::= { bcmsplus4 91 }
  
bcms4-cb8-max
	OBJECT-TYPE
	SYNTAX  INTEGER
	ACCESS  read-only
	STATUS  mandatory
	DESCRIPTION "CB8 Max"
		::= { bcmsplus4 92 }

bcms4-cb9-max
	OBJECT-TYPE
	SYNTAX  INTEGER
	ACCESS  read-only
	STATUS  mandatory
	DESCRIPTION "CB9 Max"
		::= { bcmsplus4 93 }

bcms4-cb10-max
	OBJECT-TYPE
	SYNTAX  INTEGER
	ACCESS  read-only
	STATUS  mandatory
	DESCRIPTION "CB10 Max"
		::= { bcmsplus4 94 }

bcms4-cb11-max
	OBJECT-TYPE
	SYNTAX  INTEGER
	ACCESS  read-only
	STATUS  mandatory
	DESCRIPTION "CB11 Max"
		::= { bcmsplus4 95 }

bcms4-cb12-max
	OBJECT-TYPE
	SYNTAX  INTEGER
	ACCESS  read-only
	STATUS  mandatory
	DESCRIPTION "CB12 Max"
		::= { bcmsplus4 96 }

bcms4-cb13-max
	OBJECT-TYPE
	SYNTAX  INTEGER
	ACCESS  read-only
	STATUS  mandatory
	DESCRIPTION "CB13 Max"
		::= { bcmsplus4 97 }

bcms4-cb14-max
	OBJECT-TYPE
	SYNTAX  INTEGER
	ACCESS  read-only
	STATUS  mandatory
	DESCRIPTION "CB14 Max"
		::= { bcmsplus4 98 }

bcms4-cb15-max
	OBJECT-TYPE
	SYNTAX  INTEGER
	ACCESS  read-only
	STATUS  mandatory
	DESCRIPTION "CB15 Max"
		::= { bcmsplus4 99 }


bcms4-cb16-max
	OBJECT-TYPE
	SYNTAX  INTEGER
	ACCESS  read-only
	STATUS  mandatory
	DESCRIPTION "CB16 Max"
		::= { bcmsplus4 100 }

bcms4-cb17-max
	OBJECT-TYPE
	SYNTAX  INTEGER
	ACCESS  read-only
	STATUS  mandatory
	DESCRIPTION "CB17 Max"
		::= { bcmsplus4 101 }
  
bcms4-cb18-max
	OBJECT-TYPE
	SYNTAX  INTEGER
	ACCESS  read-only
	STATUS  mandatory
	DESCRIPTION "CB18 Max"
		::= { bcmsplus4 102 }

bcms4-cb19-max
	OBJECT-TYPE
	SYNTAX  INTEGER
	ACCESS  read-only
	STATUS  mandatory
	DESCRIPTION "CB19 Max"
		::= { bcmsplus4 103 }

bcms4-cb20-max
	OBJECT-TYPE
	SYNTAX  INTEGER
	ACCESS  read-only
	STATUS  mandatory
	DESCRIPTION "CB20 Max"
		::= { bcmsplus4 104 }

bcms4-cb21-max
	OBJECT-TYPE
	SYNTAX  INTEGER
	ACCESS  read-only
	STATUS  mandatory
	DESCRIPTION "CB21 Max"
		::= { bcmsplus4 105 }

bcms4-cb22-max
	OBJECT-TYPE
	SYNTAX  INTEGER
	ACCESS  read-only
	STATUS  mandatory
	DESCRIPTION "CB22 Max"
		::= { bcmsplus4 106 }

bcms4-cb23-max
	OBJECT-TYPE
	SYNTAX  INTEGER
	ACCESS  read-only
	STATUS  mandatory
	DESCRIPTION "CB23 Max"
		::= { bcmsplus4 107 }

bcms4-cb24-max
	OBJECT-TYPE
	SYNTAX  INTEGER
	ACCESS  read-only
	STATUS  mandatory
	DESCRIPTION "CB24 Max"
		::= { bcmsplus4 108 }

bcms4-cb25-max
	OBJECT-TYPE
	SYNTAX  INTEGER
	ACCESS  read-only
	STATUS  mandatory
	DESCRIPTION "CB25 Max"
		::= { bcmsplus4 109 }

bcms4-cb26-max
	OBJECT-TYPE
	SYNTAX  INTEGER
	ACCESS  read-only
	STATUS  mandatory
	DESCRIPTION "CB26 Max"
		::= { bcmsplus4 110 }

bcms4-cb27-max
	OBJECT-TYPE
	SYNTAX  INTEGER
	ACCESS  read-only
	STATUS  mandatory
	DESCRIPTION "CB27 Max"
		::= { bcmsplus4 111 }
  
bcms4-cb28-max
	OBJECT-TYPE
	SYNTAX  INTEGER
	ACCESS  read-only
	STATUS  mandatory
	DESCRIPTION "CB28 Max"
		::= { bcmsplus4 112 }

bcms4-cb29-max
	OBJECT-TYPE
	SYNTAX  INTEGER
	ACCESS  read-only
	STATUS  mandatory
	DESCRIPTION "CB29 Max"
		::= { bcmsplus4 113 }

bcms4-cb30-max
	OBJECT-TYPE
	SYNTAX  INTEGER
	ACCESS  read-only
	STATUS  mandatory
	DESCRIPTION "CB30 Max"
		::= { bcmsplus4 114 }

bcms4-cb31-max
	OBJECT-TYPE
	SYNTAX  INTEGER
	ACCESS  read-only
	STATUS  mandatory
	DESCRIPTION "CB31 Max"
		::= { bcmsplus4 115 }

bcms4-cb32-max
	OBJECT-TYPE
	SYNTAX  INTEGER
	ACCESS  read-only
	STATUS  mandatory
	DESCRIPTION "CB32 Max"
		::= { bcmsplus4 116 }

bcms4-cb33-max
	OBJECT-TYPE
	SYNTAX  INTEGER
	ACCESS  read-only
	STATUS  mandatory
	DESCRIPTION "CB33 Max"
		::= { bcmsplus4 117 }

bcms4-cb34-max
	OBJECT-TYPE
	SYNTAX  INTEGER
	ACCESS  read-only
	STATUS  mandatory
	DESCRIPTION "CB34 Max"
		::= { bcmsplus4 118 }

bcms4-cb35-max
	OBJECT-TYPE
	SYNTAX  INTEGER
	ACCESS  read-only
	STATUS  mandatory
	DESCRIPTION "CB35 Max"
		::= { bcmsplus4 119 }

bcms4-cb36-max
	OBJECT-TYPE
	SYNTAX  INTEGER
	ACCESS  read-only
	STATUS  mandatory
	DESCRIPTION "CB36 Max"
		::= { bcmsplus4 120 }

bcms4-cb37-max
	OBJECT-TYPE
	SYNTAX  INTEGER
	ACCESS  read-only
	STATUS  mandatory
	DESCRIPTION "CB37 Max"
		::= { bcmsplus4 121 }
  
bcms4-cb38-max
	OBJECT-TYPE
	SYNTAX  INTEGER
	ACCESS  read-only
	STATUS  mandatory
	DESCRIPTION "CB38 Max"
		::= { bcmsplus4 122 }

bcms4-cb39-max
	OBJECT-TYPE
	SYNTAX  INTEGER
	ACCESS  read-only
	STATUS  mandatory
	DESCRIPTION "CB39 Max"
		::= { bcmsplus4 123 }

bcms4-cb40-max
	OBJECT-TYPE
	SYNTAX  INTEGER
	ACCESS  read-only
	STATUS  mandatory
	DESCRIPTION "CB40 Max"
		::= { bcmsplus4 124 }

bcms4-cb41-max
	OBJECT-TYPE
	SYNTAX  INTEGER
	ACCESS  read-only
	STATUS  mandatory
	DESCRIPTION "CB41 Max"
		::= { bcmsplus4 125 }

bcms4-cb42-max
	OBJECT-TYPE
	SYNTAX  INTEGER
	ACCESS  read-only
	STATUS  mandatory
	DESCRIPTION "CB42 Max"
		::= { bcmsplus4 126 }

bcms4-cb1-16-zero
	OBJECT-TYPE
	SYNTAX  INTEGER
	ACCESS  read-write
	STATUS  mandatory
	DESCRIPTION "CB1-16 Zero
		       Bit 0 = CB1
                   Bit 15 = CB16"
		::= { bcmsplus4 127 }

bcms4-cb17-32-zero
	OBJECT-TYPE
	SYNTAX  INTEGER
	ACCESS  read-write
	STATUS  mandatory
	DESCRIPTION "CB17-32 Zero
		       Bit 0 = CB17
                   Bit 15 = CB32"
		::= { bcmsplus4 128 }

bcms4-cb33-42-zero
	OBJECT-TYPE
	SYNTAX  INTEGER
	ACCESS  read-write
	STATUS  mandatory
	DESCRIPTION "CB33-42 Zero
		       Bit 0 = CB33
                   Bit 9 = CB42
                   Bits 10-25 not used"
		::= { bcmsplus4 129 }

bcms4-cb1-16-warning
	OBJECT-TYPE
	SYNTAX  INTEGER
	ACCESS  read-write
	STATUS  mandatory
	DESCRIPTION "CB1-16 Warning
		       Bit 0 = CB1
                   Bit 15 = CB16"
		::= { bcmsplus4 130 }

bcms4-cb17-32-warning
	OBJECT-TYPE
	SYNTAX  INTEGER
	ACCESS  read-write
	STATUS  mandatory
	DESCRIPTION "CB17-32 Warning
		       Bit 0 = CB17
                   Bit 15 = CB32"
		::= { bcmsplus4 131 }
  
bcms4-cb33-42-warning
	OBJECT-TYPE
	SYNTAX  INTEGER
	ACCESS  read-write
	STATUS  mandatory
	DESCRIPTION "CB33-42 Warning
		       Bit 0 = CB33
                   Bit 9 = CB42
                   Bits 10-25 not used"
		::= { bcmsplus4 132 }

bcms4-cb1-16-alarm
	OBJECT-TYPE
	SYNTAX  INTEGER
	ACCESS  read-write
	STATUS  mandatory
	DESCRIPTION "CB1-16 Alarm
		       Bit 0 = CB1
                   Bit 15 = CB16"
		::= { bcmsplus4 133 }

bcms4-cb17-32-alarm
	OBJECT-TYPE
	SYNTAX  INTEGER
	ACCESS  read-write
	STATUS  mandatory
	DESCRIPTION "CB17-32 Alarm
		       Bit 0 = CB17
                   Bit 15 = CB32"
		::= { bcmsplus4 134 }

bcms4-cb33-42-alarm
	OBJECT-TYPE
	SYNTAX  INTEGER
	ACCESS  read-write
	STATUS  mandatory
	DESCRIPTION "CB33-42 Alarm
		       Bit 0 = CB33
                   Bit 9 = CB42
                   Bits 10-25 not used"
		::= { bcmsplus4 135 }

bcms4-cb1-breaker-size
	OBJECT-TYPE
	SYNTAX  INTEGER
	ACCESS  read-write
	STATUS  mandatory
	DESCRIPTION "CB1 Breaker-Size
		     Note for all breaker sizes 1-42: 10 = 10 amps
                     Range is 10 to 100 amps"
		::= { bcmsplus4 136 }

bcms4-cb2-breaker-size
	OBJECT-TYPE
	SYNTAX  INTEGER
	ACCESS  read-write
	STATUS  mandatory
	DESCRIPTION "CB2 Breaker-Size"
		::= { bcmsplus4 137 }

bcms4-cb3-breaker-size
	OBJECT-TYPE
	SYNTAX  INTEGER
	ACCESS  read-write
	STATUS  mandatory
	DESCRIPTION "CB3 Breaker-Size"
		::= { bcmsplus4 138 }

bcms4-cb4-breaker-size
	OBJECT-TYPE
	SYNTAX  INTEGER
	ACCESS  read-write
	STATUS  mandatory
	DESCRIPTION "CB4 Breaker-Size"
		::= { bcmsplus4 139 }

bcms4-cb5-breaker-size
	OBJECT-TYPE
	SYNTAX  INTEGER
	ACCESS  read-write
	STATUS  mandatory
	DESCRIPTION "CB5 Breaker-Size"
		::= { bcmsplus4 140 }

bcms4-cb6-breaker-size
	OBJECT-TYPE
	SYNTAX  INTEGER
	ACCESS  read-write
	STATUS  mandatory
	DESCRIPTION "CB6 Breaker-Size"
		::= { bcmsplus4 141 }
  
bcms4-cb7-breaker-size
	OBJECT-TYPE
	SYNTAX  INTEGER
	ACCESS  read-write
	STATUS  mandatory
	DESCRIPTION "CB7 Breaker-Size"
		::= { bcmsplus4 142 }

bcms4-cb8-breaker-size
	OBJECT-TYPE
	SYNTAX  INTEGER
	ACCESS  read-write
	STATUS  mandatory
	DESCRIPTION "CB8 Breaker-Size"
		::= { bcmsplus4 143 }

bcms4-cb9-breaker-size
	OBJECT-TYPE
	SYNTAX  INTEGER
	ACCESS  read-write
	STATUS  mandatory
	DESCRIPTION "CB9 Breaker-Size"
		::= { bcmsplus4 144 }

bcms4-cb10-breaker-size
	OBJECT-TYPE
	SYNTAX  INTEGER
	ACCESS  read-write
	STATUS  mandatory
	DESCRIPTION "CB10 Breaker-Size"
		::= { bcmsplus4 145 }

bcms4-cb11-breaker-size
	OBJECT-TYPE
	SYNTAX  INTEGER
	ACCESS  read-write
	STATUS  mandatory
	DESCRIPTION "CB11 Breaker-Size"
		::= { bcmsplus4 146 }

bcms4-cb12-breaker-size
	OBJECT-TYPE
	SYNTAX  INTEGER
	ACCESS  read-write
	STATUS  mandatory
	DESCRIPTION "CB12 Breaker-Size"
		::= { bcmsplus4 147 }

bcms4-cb13-breaker-size
	OBJECT-TYPE
	SYNTAX  INTEGER
	ACCESS  read-write
	STATUS  mandatory
	DESCRIPTION "CB13 Breaker-Size"
		::= { bcmsplus4 148 }

bcms4-cb14-breaker-size
	OBJECT-TYPE
	SYNTAX  INTEGER
	ACCESS  read-write
	STATUS  mandatory
	DESCRIPTION "CB14 Breaker-Size"
		::= { bcmsplus4 149 }

bcms4-cb15-breaker-size
	OBJECT-TYPE
	SYNTAX  INTEGER
	ACCESS  read-write
	STATUS  mandatory
	DESCRIPTION "CB15 Breaker-Size"
		::= { bcmsplus4 150 }

bcms4-cb16-breaker-size
	OBJECT-TYPE
	SYNTAX  INTEGER
	ACCESS  read-write
	STATUS  mandatory
	DESCRIPTION "CB16 Breaker-Size"
		::= { bcmsplus4 151 }
  
bcms4-cb17-breaker-size
	OBJECT-TYPE
	SYNTAX  INTEGER
	ACCESS  read-write
	STATUS  mandatory
	DESCRIPTION "CB17 Breaker-Size"
		::= { bcmsplus4 152 }

bcms4-cb18-breaker-size
	OBJECT-TYPE
	SYNTAX  INTEGER
	ACCESS  read-write
	STATUS  mandatory
	DESCRIPTION "CB18 Breaker-Size"
		::= { bcmsplus4 153 }

bcms4-cb19-breaker-size
	OBJECT-TYPE
	SYNTAX  INTEGER
	ACCESS  read-write
	STATUS  mandatory
	DESCRIPTION "CB19 Breaker-Size"
		::= { bcmsplus4 154 }

bcms4-cb20-breaker-size
	OBJECT-TYPE
	SYNTAX  INTEGER
	ACCESS  read-write
	STATUS  mandatory
	DESCRIPTION "CB20 Breaker-Size"
		::= { bcmsplus4 155 }

bcms4-cb21-breaker-size
	OBJECT-TYPE
	SYNTAX  INTEGER
	ACCESS  read-write
	STATUS  mandatory
	DESCRIPTION "CB21 Breaker-Size"
		::= { bcmsplus4 156 }

bcms4-cb22-breaker-size
	OBJECT-TYPE
	SYNTAX  INTEGER
	ACCESS  read-write
	STATUS  mandatory
	DESCRIPTION "CB22 Breaker-Size"
		::= { bcmsplus4 157 }

bcms4-cb23-breaker-size
	OBJECT-TYPE
	SYNTAX  INTEGER
	ACCESS  read-write
	STATUS  mandatory
	DESCRIPTION "CB23 Breaker-Size"
		::= { bcmsplus4 158 }

bcms4-cb24-breaker-size
	OBJECT-TYPE
	SYNTAX  INTEGER
	ACCESS  read-write
	STATUS  mandatory
	DESCRIPTION "CB24 Breaker-Size"
		::= { bcmsplus4 159 }

bcms4-cb25-breaker-size
	OBJECT-TYPE
	SYNTAX  INTEGER
	ACCESS  read-write
	STATUS  mandatory
	DESCRIPTION "CB25 Breaker-Size"
		::= { bcmsplus4 160 }

bcms4-cb26-breaker-size
	OBJECT-TYPE
	SYNTAX  INTEGER
	ACCESS  read-write
	STATUS  mandatory
	DESCRIPTION "CB26 Breaker-Size"
		::= { bcmsplus4 161 }
  
bcms4-cb27-breaker-size
	OBJECT-TYPE
	SYNTAX  INTEGER
	ACCESS  read-write
	STATUS  mandatory
	DESCRIPTION "CB27 Breaker-Size"
		::= { bcmsplus4 162 }

bcms4-cb28-breaker-size
	OBJECT-TYPE
	SYNTAX  INTEGER
	ACCESS  read-write
	STATUS  mandatory
	DESCRIPTION "CB28 Breaker-Size"
		::= { bcmsplus4 163 }

bcms4-cb29-breaker-size
	OBJECT-TYPE
	SYNTAX  INTEGER
	ACCESS  read-write
	STATUS  mandatory
	DESCRIPTION "CB29 Breaker-Size"
		::= { bcmsplus4 164 }

bcms4-cb30-breaker-size
	OBJECT-TYPE
	SYNTAX  INTEGER
	ACCESS  read-write
	STATUS  mandatory
	DESCRIPTION "CB30 Breaker-Size"
		::= { bcmsplus4 165 }

bcms4-cb31-breaker-size
	OBJECT-TYPE
	SYNTAX  INTEGER
	ACCESS  read-write
	STATUS  mandatory
	DESCRIPTION "CB31 Breaker-Size"
		::= { bcmsplus4 166 }

bcms4-cb32-breaker-size
	OBJECT-TYPE
	SYNTAX  INTEGER
	ACCESS  read-write
	STATUS  mandatory
	DESCRIPTION "CB32 Breaker-Size"
		::= { bcmsplus4 167 }

bcms4-cb33-breaker-size
	OBJECT-TYPE
	SYNTAX  INTEGER
	ACCESS  read-write
	STATUS  mandatory
	DESCRIPTION "CB33 Breaker-Size"
		::= { bcmsplus4 168 }

bcms4-cb34-breaker-size
	OBJECT-TYPE
	SYNTAX  INTEGER
	ACCESS  read-write
	STATUS  mandatory
	DESCRIPTION "CB34 Breaker-Size"
		::= { bcmsplus4 169 }

bcms4-cb35-breaker-size
	OBJECT-TYPE
	SYNTAX  INTEGER
	ACCESS  read-write
	STATUS  mandatory
	DESCRIPTION "CB35 Breaker-Size"
		::= { bcmsplus4 170 }

bcms4-cb36-breaker-size
	OBJECT-TYPE
	SYNTAX  INTEGER
	ACCESS  read-write
	STATUS  mandatory
	DESCRIPTION "CB36 Breaker-Size"
		::= { bcmsplus4 171 }
  
bcms4-cb37-breaker-size
	OBJECT-TYPE
	SYNTAX  INTEGER
	ACCESS  read-write
	STATUS  mandatory
	DESCRIPTION "CB37 Breaker-Size"
		::= { bcmsplus4 172 }

bcms4-cb38-breaker-size
	OBJECT-TYPE
	SYNTAX  INTEGER
	ACCESS  read-write
	STATUS  mandatory
	DESCRIPTION "CB38 Breaker-Size"
		::= { bcmsplus4 173 }

bcms4-cb39-breaker-size
	OBJECT-TYPE
	SYNTAX  INTEGER
	ACCESS  read-write
	STATUS  mandatory
	DESCRIPTION "CB39 Breaker-Size"
		::= { bcmsplus4 174 }

bcms4-cb40-breaker-size
	OBJECT-TYPE
	SYNTAX  INTEGER
	ACCESS  read-write
	STATUS  mandatory
	DESCRIPTION "CB40 Breaker-Size"
		::= { bcmsplus4 175 }

bcms4-cb41-breaker-size
	OBJECT-TYPE
	SYNTAX  INTEGER
	ACCESS  read-write
	STATUS  mandatory
	DESCRIPTION "CB41 Breaker-Size"
		::= { bcmsplus4 176 }

bcms4-cb42-breaker-size
	OBJECT-TYPE
	SYNTAX  INTEGER
	ACCESS  read-write
	STATUS  mandatory
	DESCRIPTION "CB42 Breaker-Size"
		::= { bcmsplus4 177 }

bcms4-cb1-warning-threshold
	OBJECT-TYPE
	SYNTAX  INTEGER
	ACCESS  read-write
	STATUS  mandatory
	DESCRIPTION "CB1 CB1-warning-threshold
		     Note for all warning thresholds 1-42: 70 = 70% of breaker size
                     range is 0-100%"
		::= { bcmsplus4 178 }

bcms4-cb2-warning-threshold
	OBJECT-TYPE
	SYNTAX  INTEGER
	ACCESS  read-write
	STATUS  mandatory
	DESCRIPTION "CB2 Warning-Threshold"
		::= { bcmsplus4 179 }

bcms4-cb3-warning-threshold
	OBJECT-TYPE
	SYNTAX  INTEGER
	ACCESS  read-write
	STATUS  mandatory
	DESCRIPTION "CB3 Warning-Threshold"
		::= { bcmsplus4 180 }

bcms4-cb4-warning-threshold
	OBJECT-TYPE
	SYNTAX  INTEGER
	ACCESS  read-write
	STATUS  mandatory
	DESCRIPTION "CB4 Warning-Threshold"
		::= { bcmsplus4 181 }
  
bcms4-cb5-warning-threshold
	OBJECT-TYPE
	SYNTAX  INTEGER
	ACCESS  read-write
	STATUS  mandatory
	DESCRIPTION "CB5 Warning-Threshold"
		::= { bcmsplus4 182 }

bcms4-cb6-warning-threshold
	OBJECT-TYPE
	SYNTAX  INTEGER
	ACCESS  read-write
	STATUS  mandatory
	DESCRIPTION "CB6 Warning-Threshold"
		::= { bcmsplus4 183 }

bcms4-cb7-warning-threshold
	OBJECT-TYPE
	SYNTAX  INTEGER
	ACCESS  read-write
	STATUS  mandatory
	DESCRIPTION "CB7 Warning-Threshold"
		::= { bcmsplus4 184 }

bcms4-cb8-warning-threshold
	OBJECT-TYPE
	SYNTAX  INTEGER
	ACCESS  read-write
	STATUS  mandatory
	DESCRIPTION "CB8 Warning-Threshold"
		::= { bcmsplus4 185 }

bcms4-cb9-warning-threshold
	OBJECT-TYPE
	SYNTAX  INTEGER
	ACCESS  read-write
	STATUS  mandatory
	DESCRIPTION "CB9 Warning-Threshold"
		::= { bcmsplus4 186 }

bcms4-cb10-warning-threshold
	OBJECT-TYPE
	SYNTAX  INTEGER
	ACCESS  read-write
	STATUS  mandatory
	DESCRIPTION "CB10 Warning-Threshold"
		::= { bcmsplus4 187 }

bcms4-cb11-warning-threshold
	OBJECT-TYPE
	SYNTAX  INTEGER
	ACCESS  read-write
	STATUS  mandatory
	DESCRIPTION "CB11 Warning-Threshold"
		::= { bcmsplus4 188 }

bcms4-cb12-warning-threshold
	OBJECT-TYPE
	SYNTAX  INTEGER
	ACCESS  read-write
	STATUS  mandatory
	DESCRIPTION "CB12 Warning-Threshold"
		::= { bcmsplus4 189 }

bcms4-cb13-warning-threshold
	OBJECT-TYPE
	SYNTAX  INTEGER
	ACCESS  read-write
	STATUS  mandatory
	DESCRIPTION "CB13 Warning-Threshold"
		::= { bcmsplus4 190 }

bcms4-cb14-warning-threshold
	OBJECT-TYPE
	SYNTAX  INTEGER
	ACCESS  read-write
	STATUS  mandatory
	DESCRIPTION "CB14 Warning-Threshold"
		::= { bcmsplus4 191 }
  
bcms4-cb15-warning-threshold
	OBJECT-TYPE
	SYNTAX  INTEGER
	ACCESS  read-write
	STATUS  mandatory
	DESCRIPTION "CB15 Warning-Threshold"
		::= { bcmsplus4 192 }

bcms4-cb16-warning-threshold
	OBJECT-TYPE
	SYNTAX  INTEGER
	ACCESS  read-write
	STATUS  mandatory
	DESCRIPTION "CB16 Warning-Threshold"
		::= { bcmsplus4 193 }

bcms4-cb17-warning-threshold
	OBJECT-TYPE
	SYNTAX  INTEGER
	ACCESS  read-write
	STATUS  mandatory
	DESCRIPTION "CB17 Warning-Threshold"
		::= { bcmsplus4 194 }

bcms4-cb18-warning-threshold
	OBJECT-TYPE
	SYNTAX  INTEGER
	ACCESS  read-write
	STATUS  mandatory
	DESCRIPTION "CB18 Warning-Threshold"
		::= { bcmsplus4 195 }

bcms4-cb19-warning-threshold
	OBJECT-TYPE
	SYNTAX  INTEGER
	ACCESS  read-write
	STATUS  mandatory
	DESCRIPTION "CB19 Warning-Threshold"
		::= { bcmsplus4 196 }

bcms4-cb20-warning-threshold
	OBJECT-TYPE
	SYNTAX  INTEGER
	ACCESS  read-write
	STATUS  mandatory
	DESCRIPTION "CB20 Warning-Threshold"
		::= { bcmsplus4 197 }

bcms4-cb21-warning-threshold
	OBJECT-TYPE
	SYNTAX  INTEGER
	ACCESS  read-write
	STATUS  mandatory
	DESCRIPTION "CB21 Warning-Threshold"
		::= { bcmsplus4 198 }

bcms4-cb22-warning-threshold
	OBJECT-TYPE
	SYNTAX  INTEGER
	ACCESS  read-write
	STATUS  mandatory
	DESCRIPTION "CB22 Warning-Threshold"
		::= { bcmsplus4 199 }

bcms4-cb23-warning-threshold
	OBJECT-TYPE
	SYNTAX  INTEGER
	ACCESS  read-write
	STATUS  mandatory
	DESCRIPTION "CB23 Warning-Threshold"
		::= { bcmsplus4 200 }

bcms4-cb24-warning-threshold
	OBJECT-TYPE
	SYNTAX  INTEGER
	ACCESS  read-write
	STATUS  mandatory
	DESCRIPTION "CB24 Warning-Threshold"
		::= { bcmsplus4 201 }
  
bcms4-cb25-warning-threshold
	OBJECT-TYPE
	SYNTAX  INTEGER
	ACCESS  read-write
	STATUS  mandatory
	DESCRIPTION "CB25 Warning-Threshold"
		::= { bcmsplus4 202 }

bcms4-cb26-warning-threshold
	OBJECT-TYPE
	SYNTAX  INTEGER
	ACCESS  read-write
	STATUS  mandatory
	DESCRIPTION "CB26 Warning-Threshold"
		::= { bcmsplus4 203 }

bcms4-cb27-warning-threshold
	OBJECT-TYPE
	SYNTAX  INTEGER
	ACCESS  read-write
	STATUS  mandatory
	DESCRIPTION "CB27 Warning-Threshold"
		::= { bcmsplus4 204 }

bcms4-cb28-warning-threshold
	OBJECT-TYPE
	SYNTAX  INTEGER
	ACCESS  read-write
	STATUS  mandatory
	DESCRIPTION "CB28 Warning-Threshold"
		::= { bcmsplus4 205 }

bcms4-cb29-warning-threshold
	OBJECT-TYPE
	SYNTAX  INTEGER
	ACCESS  read-write
	STATUS  mandatory
	DESCRIPTION "CB29 Warning-Threshold"
		::= { bcmsplus4 206 }

bcms4-cb30-warning-threshold
	OBJECT-TYPE
	SYNTAX  INTEGER
	ACCESS  read-write
	STATUS  mandatory
	DESCRIPTION "CB30 Warning-Threshold"
		::= { bcmsplus4 207 }

bcms4-cb31-warning-threshold
	OBJECT-TYPE
	SYNTAX  INTEGER
	ACCESS  read-write
	STATUS  mandatory
	DESCRIPTION "CB31 Warning-Threshold"
		::= { bcmsplus4 208 }

bcms4-cb32-warning-threshold
	OBJECT-TYPE
	SYNTAX  INTEGER
	ACCESS  read-write
	STATUS  mandatory
	DESCRIPTION "CB32 Warning-Threshold"
		::= { bcmsplus4 209 }

bcms4-cb33-warning-threshold
	OBJECT-TYPE
	SYNTAX  INTEGER
	ACCESS  read-write
	STATUS  mandatory
	DESCRIPTION "CB33 Warning-Threshold"
		::= { bcmsplus4 210 }

bcms4-cb34-warning-threshold
	OBJECT-TYPE
	SYNTAX  INTEGER
	ACCESS  read-write
	STATUS  mandatory
	DESCRIPTION "CB34 Warning-Threshold"
		::= { bcmsplus4 211 }
  
bcms4-cb35-warning-threshold
	OBJECT-TYPE
	SYNTAX  INTEGER
	ACCESS  read-write
	STATUS  mandatory
	DESCRIPTION "CB35 Warning-Threshold"
		::= { bcmsplus4 212 }

bcms4-cb36-warning-threshold
	OBJECT-TYPE
	SYNTAX  INTEGER
	ACCESS  read-write
	STATUS  mandatory
	DESCRIPTION "CB36 Warning-Threshold"
		::= { bcmsplus4 213 }

bcms4-cb37-warning-threshold
	OBJECT-TYPE
	SYNTAX  INTEGER
	ACCESS  read-write
	STATUS  mandatory
	DESCRIPTION "CB37 Warning-Threshold"
		::= { bcmsplus4 214 }

bcms4-cb38-warning-threshold
	OBJECT-TYPE
	SYNTAX  INTEGER
	ACCESS  read-write
	STATUS  mandatory
	DESCRIPTION "CB38 Warning-Threshold"
		::= { bcmsplus4 215 }

bcms4-cb39-warning-threshold
	OBJECT-TYPE
	SYNTAX  INTEGER
	ACCESS  read-write
	STATUS  mandatory
	DESCRIPTION "CB39 Warning-Threshold"
		::= { bcmsplus4 216 }

bcms4-cb40-warning-threshold
	OBJECT-TYPE
	SYNTAX  INTEGER
	ACCESS  read-write
	STATUS  mandatory
	DESCRIPTION "CB40 Warning-Threshold"
		::= { bcmsplus4 217 }

bcms4-cb41-warning-threshold
	OBJECT-TYPE
	SYNTAX  INTEGER
	ACCESS  read-write
	STATUS  mandatory
	DESCRIPTION "CB41 Warning-Threshold"
		::= { bcmsplus4 218 }

bcms4-cb42-warning-threshold
	OBJECT-TYPE
	SYNTAX  INTEGER
	ACCESS  read-write
	STATUS  mandatory
	DESCRIPTION "CB42 Warning-Threshold"
		::= { bcmsplus4 219 }

bcms4-cb1-alarm-threshold
	OBJECT-TYPE
	SYNTAX  INTEGER
	ACCESS  read-write
	STATUS  mandatory
	DESCRIPTION "CB1 Alarm-Threshold
		     Note for all alarm thresholds 1-42: 80 = 80% of breaker size
                     range is 0-100%"
		::= { bcmsplus4 220 }


bcms4-cb2-alarm-threshold
	OBJECT-TYPE
	SYNTAX  INTEGER
	ACCESS  read-write
	STATUS  mandatory
	DESCRIPTION "CB2 Alarm-Threshold"
		::= { bcmsplus4 221 }
  
bcms4-cb3-alarm-threshold
	OBJECT-TYPE
	SYNTAX  INTEGER
	ACCESS  read-write
	STATUS  mandatory
	DESCRIPTION "CB3 Alarm-Threshold"
		::= { bcmsplus4 222 }

bcms4-cb4-alarm-threshold
	OBJECT-TYPE
	SYNTAX  INTEGER
	ACCESS  read-write
	STATUS  mandatory
	DESCRIPTION "CB4 Alarm-Threshold"
		::= { bcmsplus4 223 }

bcms4-cb5-alarm-threshold
	OBJECT-TYPE
	SYNTAX  INTEGER
	ACCESS  read-write
	STATUS  mandatory
	DESCRIPTION "CB5 Alarm-Threshold"
		::= { bcmsplus4 224 }

bcms4-cb6-alarm-threshold
	OBJECT-TYPE
	SYNTAX  INTEGER
	ACCESS  read-write
	STATUS  mandatory
	DESCRIPTION "CB6 Alarm-Threshold"
		::= { bcmsplus4 225 }

bcms4-cb7-alarm-threshold
	OBJECT-TYPE
	SYNTAX  INTEGER
	ACCESS  read-write
	STATUS  mandatory
	DESCRIPTION "CB7 Alarm-Threshold"
		::= { bcmsplus4 226 }

bcms4-cb8-alarm-threshold
	OBJECT-TYPE
	SYNTAX  INTEGER
	ACCESS  read-write
	STATUS  mandatory
	DESCRIPTION "CB8 Alarm-Threshold"
		::= { bcmsplus4 227 }

bcms4-cb9-alarm-threshold
	OBJECT-TYPE
	SYNTAX  INTEGER
	ACCESS  read-write
	STATUS  mandatory
	DESCRIPTION "CB9 Alarm-Threshold"
		::= { bcmsplus4 228 }

bcms4-cb10-alarm-threshold
	OBJECT-TYPE
	SYNTAX  INTEGER
	ACCESS  read-write
	STATUS  mandatory
	DESCRIPTION "CB10 Alarm-Threshold"
		::= { bcmsplus4 229 }

bcms4-cb11-alarm-threshold
	OBJECT-TYPE
	SYNTAX  INTEGER
	ACCESS  read-write
	STATUS  mandatory
	DESCRIPTION "CB11 Alarm-Threshold"
		::= { bcmsplus4 230 }

bcms4-cb12-alarm-threshold
	OBJECT-TYPE
	SYNTAX  INTEGER
	ACCESS  read-write
	STATUS  mandatory
	DESCRIPTION "CB12 Alarm-Threshold"
		::= { bcmsplus4 231 }
  
bcms4-cb13-alarm-threshold
	OBJECT-TYPE
	SYNTAX  INTEGER
	ACCESS  read-write
	STATUS  mandatory
	DESCRIPTION "CB13 Alarm-Threshold"
		::= { bcmsplus4 232 }

bcms4-cb14-alarm-threshold
	OBJECT-TYPE
	SYNTAX  INTEGER
	ACCESS  read-write
	STATUS  mandatory
	DESCRIPTION "CB14 Alarm-Threshold"
		::= { bcmsplus4 233 }

bcms4-cb15-alarm-threshold
	OBJECT-TYPE
	SYNTAX  INTEGER
	ACCESS  read-write
	STATUS  mandatory
	DESCRIPTION "CB15 Alarm-Threshold"
		::= { bcmsplus4 234 }

bcms4-cb16-alarm-threshold
	OBJECT-TYPE
	SYNTAX  INTEGER
	ACCESS  read-write
	STATUS  mandatory
	DESCRIPTION "CB16 Alarm-Threshold"
		::= { bcmsplus4 235 }

bcms4-cb17-alarm-threshold
	OBJECT-TYPE
	SYNTAX  INTEGER
	ACCESS  read-write
	STATUS  mandatory
	DESCRIPTION "CB17 Alarm-Threshold"
		::= { bcmsplus4 236 }

bcms4-cb18-alarm-threshold
	OBJECT-TYPE
	SYNTAX  INTEGER
	ACCESS  read-write
	STATUS  mandatory
	DESCRIPTION "CB18 Alarm-Threshold"
		::= { bcmsplus4 237 }

bcms4-cb19-alarm-threshold
	OBJECT-TYPE
	SYNTAX  INTEGER
	ACCESS  read-write
	STATUS  mandatory
	DESCRIPTION "CB19 Alarm-Threshold"
		::= { bcmsplus4 238 }

bcms4-cb20-alarm-threshold
	OBJECT-TYPE
	SYNTAX  INTEGER
	ACCESS  read-write
	STATUS  mandatory
	DESCRIPTION "CB20 Alarm-Threshold"
		::= { bcmsplus4 239 }

bcms4-cb21-alarm-threshold
	OBJECT-TYPE
	SYNTAX  INTEGER
	ACCESS  read-write
	STATUS  mandatory
	DESCRIPTION "CB21 Alarm-Threshold"
		::= { bcmsplus4 240 }

bcms4-cb22-alarm-threshold
	OBJECT-TYPE
	SYNTAX  INTEGER
	ACCESS  read-write
	STATUS  mandatory
	DESCRIPTION "CB22 Alarm-Threshold"
		::= { bcmsplus4 241 }
  
bcms4-cb23-alarm-threshold
	OBJECT-TYPE
	SYNTAX  INTEGER
	ACCESS  read-write
	STATUS  mandatory
	DESCRIPTION "CB23 Alarm-Threshold"
		::= { bcmsplus4 242 }

bcms4-cb24-alarm-threshold
	OBJECT-TYPE
	SYNTAX  INTEGER
	ACCESS  read-write
	STATUS  mandatory
	DESCRIPTION "CB24 Alarm-Threshold"
		::= { bcmsplus4 243 }

bcms4-cb25-alarm-threshold
	OBJECT-TYPE
	SYNTAX  INTEGER
	ACCESS  read-write
	STATUS  mandatory
	DESCRIPTION "CB25 Alarm-Threshold"
		::= { bcmsplus4 244 }

bcms4-cb26-alarm-threshold
	OBJECT-TYPE
	SYNTAX  INTEGER
	ACCESS  read-write
	STATUS  mandatory
	DESCRIPTION "CB26 Alarm-Threshold"
		::= { bcmsplus4 245 }

bcms4-cb27-alarm-threshold
	OBJECT-TYPE
	SYNTAX  INTEGER
	ACCESS  read-write
	STATUS  mandatory
	DESCRIPTION "CB27 Alarm-Threshold"
		::= { bcmsplus4 246 }

bcms4-cb28-alarm-threshold
	OBJECT-TYPE
	SYNTAX  INTEGER
	ACCESS  read-write
	STATUS  mandatory
	DESCRIPTION "CB28 Alarm-Threshold"
		::= { bcmsplus4 247 }

bcms4-cb29-alarm-threshold
	OBJECT-TYPE
	SYNTAX  INTEGER
	ACCESS  read-write
	STATUS  mandatory
	DESCRIPTION "CB29 Alarm-Threshold"
		::= { bcmsplus4 248 }

bcms4-cb30-alarm-threshold
	OBJECT-TYPE
	SYNTAX  INTEGER
	ACCESS  read-write
	STATUS  mandatory
	DESCRIPTION "CB30 Alarm-Threshold"
		::= { bcmsplus4 249 }

bcms4-cb31-alarm-threshold
	OBJECT-TYPE
	SYNTAX  INTEGER
	ACCESS  read-write
	STATUS  mandatory
	DESCRIPTION "CB31 Alarm-Threshold"
		::= { bcmsplus4 250 }

bcms4-cb32-alarm-threshold
	OBJECT-TYPE
	SYNTAX  INTEGER
	ACCESS  read-write
	STATUS  mandatory
	DESCRIPTION "CB32 Alarm-Threshold"
		::= { bcmsplus4 251 }
  
bcms4-cb33-alarm-threshold
	OBJECT-TYPE
	SYNTAX  INTEGER
	ACCESS  read-write
	STATUS  mandatory
	DESCRIPTION "CB33 Alarm-Threshold"
		::= { bcmsplus4 252 }

bcms4-cb34-alarm-threshold
	OBJECT-TYPE
	SYNTAX  INTEGER
	ACCESS  read-write
	STATUS  mandatory
	DESCRIPTION "CB34 Alarm-Threshold"
		::= { bcmsplus4 253 }

bcms4-cb35-alarm-threshold
	OBJECT-TYPE
	SYNTAX  INTEGER
	ACCESS  read-write
	STATUS  mandatory
	DESCRIPTION "CB35 Alarm-Threshold"
		::= { bcmsplus4 254 }

bcms4-cb36-alarm-threshold
	OBJECT-TYPE
	SYNTAX  INTEGER
	ACCESS  read-write
	STATUS  mandatory
	DESCRIPTION "CB36 Alarm-Threshold"
		::= { bcmsplus4 255 }

bcms4-cb37-alarm-threshold
	OBJECT-TYPE
	SYNTAX  INTEGER
	ACCESS  read-write
	STATUS  mandatory
	DESCRIPTION "CB37 Alarm-Threshold"
		::= { bcmsplus4 256 }

bcms4-cb38-alarm-threshold
	OBJECT-TYPE
	SYNTAX  INTEGER
	ACCESS  read-write
	STATUS  mandatory
	DESCRIPTION "CB38 Alarm-Threshold"
		::= { bcmsplus4 257 }

bcms4-cb39-alarm-threshold
	OBJECT-TYPE
	SYNTAX  INTEGER
	ACCESS  read-write
	STATUS  mandatory
	DESCRIPTION "CB39 Alarm-Threshold"
		::= { bcmsplus4 258 }

bcms4-cb40-alarm-threshold
	OBJECT-TYPE
	SYNTAX  INTEGER
	ACCESS  read-write
	STATUS  mandatory
	DESCRIPTION "CB40 Alarm-Threshold"
		::= { bcmsplus4 259 }

bcms4-cb41-alarm-threshold
	OBJECT-TYPE
	SYNTAX  INTEGER
	ACCESS  read-write
	STATUS  mandatory
	DESCRIPTION "CB41 Alarm-Threshold"
		::= { bcmsplus4 260 }

bcms4-cb42-alarm-threshold
	OBJECT-TYPE
	SYNTAX  INTEGER
	ACCESS  read-write
	STATUS  mandatory
	DESCRIPTION "CB42 Alarm-Threshold"
		::= { bcmsplus4 261 }

bcms4-cb1-warning-time-delay
	OBJECT-TYPE
	SYNTAX  INTEGER
	ACCESS  read-write
	STATUS  mandatory
	DESCRIPTION "CB1 Warning-Time-Delay
		     Note for all warning time delays 1-42: units are in seconds"                     
		::= { bcmsplus4 262 }

bcms4-cb2-warning-time-delay
	OBJECT-TYPE
	SYNTAX  INTEGER
	ACCESS  read-write
	STATUS  mandatory
	DESCRIPTION "CB2 Warning-Time-Delay"
		::= { bcmsplus4 263 }
  
bcms4-cb3-warning-time-delay
	OBJECT-TYPE
	SYNTAX  INTEGER
	ACCESS  read-write
	STATUS  mandatory
	DESCRIPTION "CB3 Warning-Time-Delay"
		::= { bcmsplus4 264 }

bcms4-cb4-warning-time-delay
	OBJECT-TYPE
	SYNTAX  INTEGER
	ACCESS  read-write
	STATUS  mandatory
	DESCRIPTION "CB4 Warning-Time-Delay"
		::= { bcmsplus4 265 }

bcms4-cb5-warning-time-delay
	OBJECT-TYPE
	SYNTAX  INTEGER
	ACCESS  read-write
	STATUS  mandatory
	DESCRIPTION "CB5 Warning-Time-Delay"
		::= { bcmsplus4 266 }

bcms4-cb6-warning-time-delay
	OBJECT-TYPE
	SYNTAX  INTEGER
	ACCESS  read-write
	STATUS  mandatory
	DESCRIPTION "CB6 Warning-Time-Delay"
		::= { bcmsplus4 267 }

bcms4-cb7-warning-time-delay
	OBJECT-TYPE
	SYNTAX  INTEGER
	ACCESS  read-write
	STATUS  mandatory
	DESCRIPTION "CB7 Warning-Time-Delay"
		::= { bcmsplus4 268 }

bcms4-cb8-warning-time-delay
	OBJECT-TYPE
	SYNTAX  INTEGER
	ACCESS  read-write
	STATUS  mandatory
	DESCRIPTION "CB8 Warning-Time-Delay"
		::= { bcmsplus4 269 }

bcms4-cb9-warning-time-delay
	OBJECT-TYPE
	SYNTAX  INTEGER
	ACCESS  read-write
	STATUS  mandatory
	DESCRIPTION "CB9 Warning-Time-Delay"
		::= { bcmsplus4 270 }

bcms4-cb10-warning-time-delay
	OBJECT-TYPE
	SYNTAX  INTEGER
	ACCESS  read-write
	STATUS  mandatory
	DESCRIPTION "CB10 Warning-Time-Delay"
		::= { bcmsplus4 271 }

bcms4-cb11-warning-time-delay
	OBJECT-TYPE
	SYNTAX  INTEGER
	ACCESS  read-write
	STATUS  mandatory
	DESCRIPTION "CB11 Warning-Time-Delay"
		::= { bcmsplus4 272 }

bcms4-cb12-warning-time-delay
	OBJECT-TYPE
	SYNTAX  INTEGER
	ACCESS  read-write
	STATUS  mandatory
	DESCRIPTION "CB12 Warning-Time-Delay"
		::= { bcmsplus4 273 }
  
bcms4-cb13-warning-time-delay
	OBJECT-TYPE
	SYNTAX  INTEGER
	ACCESS  read-write
	STATUS  mandatory
	DESCRIPTION "CB13 Warning-Time-Delay"
		::= { bcmsplus4 274 }

bcms4-cb14-warning-time-delay
	OBJECT-TYPE
	SYNTAX  INTEGER
	ACCESS  read-write
	STATUS  mandatory
	DESCRIPTION "CB14 Warning-Time-Delay"
		::= { bcmsplus4 275 }

bcms4-cb15-warning-time-delay
	OBJECT-TYPE
	SYNTAX  INTEGER
	ACCESS  read-write
	STATUS  mandatory
	DESCRIPTION "CB15 Warning-Time-Delay"
		::= { bcmsplus4 276 }

bcms4-cb16-warning-time-delay
	OBJECT-TYPE
	SYNTAX  INTEGER
	ACCESS  read-write
	STATUS  mandatory
	DESCRIPTION "CB16 Warning-Time-Delay"
		::= { bcmsplus4 277 }

bcms4-cb17-warning-time-delay
	OBJECT-TYPE
	SYNTAX  INTEGER
	ACCESS  read-write
	STATUS  mandatory
	DESCRIPTION "CB17 Warning-Time-Delay"
		::= { bcmsplus4 278 }

bcms4-cb18-warning-time-delay
	OBJECT-TYPE
	SYNTAX  INTEGER
	ACCESS  read-write
	STATUS  mandatory
	DESCRIPTION "CB18 Warning-Time-Delay"
		::= { bcmsplus4 279 }

bcms4-cb19-warning-time-delay
	OBJECT-TYPE
	SYNTAX  INTEGER
	ACCESS  read-write
	STATUS  mandatory
	DESCRIPTION "CB19 Warning-Time-Delay"
		::= { bcmsplus4 280 }

bcms4-cb20-warning-time-delay
	OBJECT-TYPE
	SYNTAX  INTEGER
	ACCESS  read-write
	STATUS  mandatory
	DESCRIPTION "CB20 Warning-Time-Delay"
		::= { bcmsplus4 281 }

bcms4-cb21-warning-time-delay
	OBJECT-TYPE
	SYNTAX  INTEGER
	ACCESS  read-write
	STATUS  mandatory
	DESCRIPTION "CB21 Warning-Time-Delay"
		::= { bcmsplus4 282 }

bcms4-cb22-warning-time-delay
	OBJECT-TYPE
	SYNTAX  INTEGER
	ACCESS  read-write
	STATUS  mandatory
	DESCRIPTION "CB22 Warning-Time-Delay"
		::= { bcmsplus4 283 }
  
bcms4-cb23-warning-time-delay
	OBJECT-TYPE
	SYNTAX  INTEGER
	ACCESS  read-write
	STATUS  mandatory
	DESCRIPTION "CB23 Warning-Time-Delay"
		::= { bcmsplus4 284 }

bcms4-cb24-warning-time-delay
	OBJECT-TYPE
	SYNTAX  INTEGER
	ACCESS  read-write
	STATUS  mandatory
	DESCRIPTION "CB24 Warning-Time-Delay"
		::= { bcmsplus4 285 }

bcms4-cb25-warning-time-delay
	OBJECT-TYPE
	SYNTAX  INTEGER
	ACCESS  read-write
	STATUS  mandatory
	DESCRIPTION "CB25 Warning-Time-Delay"
		::= { bcmsplus4 286 }

bcms4-cb26-warning-time-delay
	OBJECT-TYPE
	SYNTAX  INTEGER
	ACCESS  read-write
	STATUS  mandatory
	DESCRIPTION "CB26 Warning-Time-Delay"
		::= { bcmsplus4 287 }

bcms4-cb27-warning-time-delay
	OBJECT-TYPE
	SYNTAX  INTEGER
	ACCESS  read-write
	STATUS  mandatory
	DESCRIPTION "CB27 Warning-Time-Delay"
		::= { bcmsplus4 288 }

bcms4-cb28-warning-time-delay
	OBJECT-TYPE
	SYNTAX  INTEGER
	ACCESS  read-write
	STATUS  mandatory
	DESCRIPTION "CB28 Warning-Time-Delay"
		::= { bcmsplus4 289 }

bcms4-cb29-warning-time-delay
	OBJECT-TYPE
	SYNTAX  INTEGER
	ACCESS  read-write
	STATUS  mandatory
	DESCRIPTION "CB29 Warning-Time-Delay"
		::= { bcmsplus4 290}

bcms4-cb30-warning-time-delay
	OBJECT-TYPE
	SYNTAX  INTEGER
	ACCESS  read-write
	STATUS  mandatory
	DESCRIPTION "CB30 Warning-Time-Delay"
		::= { bcmsplus4 291 }

bcms4-cb31-warning-time-delay
	OBJECT-TYPE
	SYNTAX  INTEGER
	ACCESS  read-write
	STATUS  mandatory
	DESCRIPTION "CB31 Warning-Time-Delay"
		::= { bcmsplus4 292 }

bcms4-cb32-warning-time-delay
	OBJECT-TYPE
	SYNTAX  INTEGER
	ACCESS  read-write
	STATUS  mandatory
	DESCRIPTION "CB32 Warning-Time-Delay"
		::= { bcmsplus4 293 }
  
bcms4-cb33-warning-time-delay
	OBJECT-TYPE
	SYNTAX  INTEGER
	ACCESS  read-write
	STATUS  mandatory
	DESCRIPTION "CB33 Warning-Time-Delay"
		::= { bcmsplus4 294 }

bcms4-cb34-warning-time-delay
	OBJECT-TYPE
	SYNTAX  INTEGER
	ACCESS  read-write
	STATUS  mandatory
	DESCRIPTION "CB34 Warning-Time-Delay"
		::= { bcmsplus4 295 }

bcms4-cb35-warning-time-delay
	OBJECT-TYPE
	SYNTAX  INTEGER
	ACCESS  read-write
	STATUS  mandatory
	DESCRIPTION "CB35 Warning-Time-Delay"
		::= { bcmsplus4 296 }

bcms4-cb36-warning-time-delay
	OBJECT-TYPE
	SYNTAX  INTEGER
	ACCESS  read-write
	STATUS  mandatory
	DESCRIPTION "CB36 Warning-Time-Delay"
		::= { bcmsplus4 297 }

bcms4-cb37-warning-time-delay
	OBJECT-TYPE
	SYNTAX  INTEGER
	ACCESS  read-write
	STATUS  mandatory
	DESCRIPTION "CB37 Warning-Time-Delay"
		::= { bcmsplus4 298 }

bcms4-cb38-warning-time-delay
	OBJECT-TYPE
	SYNTAX  INTEGER
	ACCESS  read-write
	STATUS  mandatory
	DESCRIPTION "CB38 Warning-Time-Delay"
		::= { bcmsplus4 299 }

bcms4-cb39-warning-time-delay
	OBJECT-TYPE
	SYNTAX  INTEGER
	ACCESS  read-write
	STATUS  mandatory
	DESCRIPTION "CB39 Warning-Time-Delay"
		::= { bcmsplus4 300 }

bcms4-cb40-warning-time-delay
	OBJECT-TYPE
	SYNTAX  INTEGER
	ACCESS  read-write
	STATUS  mandatory
	DESCRIPTION "CB40 Warning-Time-Delay"
		::= { bcmsplus4 301 }

bcms4-cb41-warning-time-delay
	OBJECT-TYPE
	SYNTAX  INTEGER
	ACCESS  read-write
	STATUS  mandatory
	DESCRIPTION "CB41 Warning-Time-Delay"
		::= { bcmsplus4 302 }

bcms4-cb42-warning-time-delay
	OBJECT-TYPE
	SYNTAX  INTEGER
	ACCESS  read-write
	STATUS  mandatory
	DESCRIPTION "CB42 Warning-Time-Delay"
		::= { bcmsplus4 303 }

bcms4-cb1-alarm-time-delay
	OBJECT-TYPE
	SYNTAX  INTEGER
	ACCESS  read-write
	STATUS  mandatory
	DESCRIPTION "CB1 Alarm-Time-Delay
		       Note for all alarm time delays 1-42: units are in seconds"                     
		::= { bcmsplus4 304 }

bcms4-cb2-alarm-time-delay
	OBJECT-TYPE
	SYNTAX  INTEGER
	ACCESS  read-write
	STATUS  mandatory
	DESCRIPTION "CB2 Alarm-Time-Delay"
		::= { bcmsplus4 305 }
  
bcms4-cb3-alarm-time-delay
	OBJECT-TYPE
	SYNTAX  INTEGER
	ACCESS  read-write
	STATUS  mandatory
	DESCRIPTION "CB3 Alarm-Time-Delay"
		::= { bcmsplus4 306 }

bcms4-cb4-alarm-time-delay
	OBJECT-TYPE
	SYNTAX  INTEGER
	ACCESS  read-write
	STATUS  mandatory
	DESCRIPTION "CB4 Alarm-Time-Delay"
		::= { bcmsplus4 307 }

bcms4-cb5-alarm-time-delay
	OBJECT-TYPE
	SYNTAX  INTEGER
	ACCESS  read-write
	STATUS  mandatory
	DESCRIPTION "CB5 Alarm-Time-Delay"
		::= { bcmsplus4 308 }

bcms4-cb6-alarm-time-delay
	OBJECT-TYPE
	SYNTAX  INTEGER
	ACCESS  read-write
	STATUS  mandatory
	DESCRIPTION "CB6 Alarm-Time-Delay"
		::= { bcmsplus4 309 }

bcms4-cb7-alarm-time-delay
	OBJECT-TYPE
	SYNTAX  INTEGER
	ACCESS  read-write
	STATUS  mandatory
	DESCRIPTION "CB7 Alarm-Time-Delay"
		::= { bcmsplus4 310 }

bcms4-cb8-alarm-time-delay
	OBJECT-TYPE
	SYNTAX  INTEGER
	ACCESS  read-write
	STATUS  mandatory
	DESCRIPTION "CB8 Alarm-Time-Delay"
		::= { bcmsplus4 311 }

bcms4-cb9-alarm-time-delay
	OBJECT-TYPE
	SYNTAX  INTEGER
	ACCESS  read-write
	STATUS  mandatory
	DESCRIPTION "CB9 Alarm-Time-Delay"
		::= { bcmsplus4 312 }

bcms4-cb10-alarm-time-delay
	OBJECT-TYPE
	SYNTAX  INTEGER
	ACCESS  read-write
	STATUS  mandatory
	DESCRIPTION "CB10 Alarm-Time-Delay"
		::= { bcmsplus4 313 }

bcms4-cb11-alarm-time-delay
	OBJECT-TYPE
	SYNTAX  INTEGER
	ACCESS  read-write
	STATUS  mandatory
	DESCRIPTION "CB11 Alarm-Time-Delay"
		::= { bcmsplus4 314 }

bcms4-cb12-alarm-time-delay
	OBJECT-TYPE
	SYNTAX  INTEGER
	ACCESS  read-write
	STATUS  mandatory
	DESCRIPTION "CB12 Alarm-Time-Delay"
		::= { bcmsplus4 315 }
  
bcms4-cb13-alarm-time-delay
	OBJECT-TYPE
	SYNTAX  INTEGER
	ACCESS  read-write
	STATUS  mandatory
	DESCRIPTION "CB13 Alarm-Time-Delay"
		::= { bcmsplus4 316 }

bcms4-cb14-alarm-time-delay
	OBJECT-TYPE
	SYNTAX  INTEGER
	ACCESS  read-write
	STATUS  mandatory
	DESCRIPTION "CB14 Alarm-Time-Delay"
		::= { bcmsplus4 317 }

bcms4-cb15-alarm-time-delay
	OBJECT-TYPE
	SYNTAX  INTEGER
	ACCESS  read-write
	STATUS  mandatory
	DESCRIPTION "CB15 Alarm-Time-Delay"
		::= { bcmsplus4 318 }

bcms4-cb16-alarm-time-delay
	OBJECT-TYPE
	SYNTAX  INTEGER
	ACCESS  read-write
	STATUS  mandatory
	DESCRIPTION "CB16 Alarm-Time-Delay"
		::= { bcmsplus4 319 }

bcms4-cb17-alarm-time-delay
	OBJECT-TYPE
	SYNTAX  INTEGER
	ACCESS  read-write
	STATUS  mandatory
	DESCRIPTION "CB17 Alarm-Time-Delay"
		::= { bcmsplus4 320 }

bcms4-cb18-alarm-time-delay
	OBJECT-TYPE
	SYNTAX  INTEGER
	ACCESS  read-write
	STATUS  mandatory
	DESCRIPTION "CB18 Alarm-Time-Delay"
		::= { bcmsplus4 321 }

bcms4-cb19-alarm-time-delay
	OBJECT-TYPE
	SYNTAX  INTEGER
	ACCESS  read-write
	STATUS  mandatory
	DESCRIPTION "CB19 Alarm-Time-Delay"
		::= { bcmsplus4 322 }

bcms4-cb20-alarm-time-delay
	OBJECT-TYPE
	SYNTAX  INTEGER
	ACCESS  read-write
	STATUS  mandatory
	DESCRIPTION "CB20 Alarm-Time-Delay"
		::= { bcmsplus4 323 }

bcms4-cb21-alarm-time-delay
	OBJECT-TYPE
	SYNTAX  INTEGER
	ACCESS  read-write
	STATUS  mandatory
	DESCRIPTION "CB21 Alarm-Time-Delay"
		::= { bcmsplus4 324 }

bcms4-cb22-alarm-time-delay
	OBJECT-TYPE
	SYNTAX  INTEGER
	ACCESS  read-write
	STATUS  mandatory
	DESCRIPTION "CB22 Alarm-Time-Delay"
		::= { bcmsplus4 325 }
  
bcms4-cb23-alarm-time-delay
	OBJECT-TYPE
	SYNTAX  INTEGER
	ACCESS  read-write
	STATUS  mandatory
	DESCRIPTION "CB23 Alarm-Time-Delay"
		::= { bcmsplus4 326 }

bcms4-cb24-alarm-time-delay
	OBJECT-TYPE
	SYNTAX  INTEGER
	ACCESS  read-write
	STATUS  mandatory
	DESCRIPTION "CB24 Alarm-Time-Delay"
		::= { bcmsplus4 327 }

bcms4-cb25-alarm-time-delay
	OBJECT-TYPE
	SYNTAX  INTEGER
	ACCESS  read-write
	STATUS  mandatory
	DESCRIPTION "CB25 Alarm-Time-Delay"
		::= { bcmsplus4 328 }

bcms4-cb26-alarm-time-delay
	OBJECT-TYPE
	SYNTAX  INTEGER
	ACCESS  read-write
	STATUS  mandatory
	DESCRIPTION "CB26 Alarm-Time-Delay"
		::= { bcmsplus4 329 }

bcms4-cb27-alarm-time-delay
	OBJECT-TYPE
	SYNTAX  INTEGER
	ACCESS  read-write
	STATUS  mandatory
	DESCRIPTION "CB27 Alarm-Time-Delay"
		::= { bcmsplus4 330 }

bcms4-cb28-alarm-time-delay
	OBJECT-TYPE
	SYNTAX  INTEGER
	ACCESS  read-write
	STATUS  mandatory
	DESCRIPTION "CB28 Alarm-Time-Delay"
		::= { bcmsplus4 331 }

bcms4-cb29-alarm-time-delay
	OBJECT-TYPE
	SYNTAX  INTEGER
	ACCESS  read-write
	STATUS  mandatory
	DESCRIPTION "CB29 Alarm-Time-Delay"
		::= { bcmsplus4 332 }

bcms4-cb30-alarm-time-delay
	OBJECT-TYPE
	SYNTAX  INTEGER
	ACCESS  read-write
	STATUS  mandatory
	DESCRIPTION "CB30 Alarm-Time-Delay"
		::= { bcmsplus4 333 }

bcms4-cb31-alarm-time-delay
	OBJECT-TYPE
	SYNTAX  INTEGER
	ACCESS  read-write
	STATUS  mandatory
	DESCRIPTION "CB31 Alarm-Time-Delay"
		::= { bcmsplus4 334 }

bcms4-cb32-alarm-time-delay
	OBJECT-TYPE
	SYNTAX  INTEGER
	ACCESS  read-write
	STATUS  mandatory
	DESCRIPTION "CB32 Alarm-Time-Delay"
		::= { bcmsplus4 335 }
  
bcms4-cb33-alarm-time-delay
	OBJECT-TYPE
	SYNTAX  INTEGER
	ACCESS  read-write
	STATUS  mandatory
	DESCRIPTION "CB33 Alarm-Time-Delay"
		::= { bcmsplus4 336 }

bcms4-cb34-alarm-time-delay
	OBJECT-TYPE
	SYNTAX  INTEGER
	ACCESS  read-write
	STATUS  mandatory
	DESCRIPTION "CB34 Alarm-Time-Delay"
		::= { bcmsplus4 337 }

bcms4-cb35-alarm-time-delay
	OBJECT-TYPE
	SYNTAX  INTEGER
	ACCESS  read-write
	STATUS  mandatory
	DESCRIPTION "CB35 Alarm-Time-Delay"
		::= { bcmsplus4 338 }

bcms4-cb36-alarm-time-delay
	OBJECT-TYPE
	SYNTAX  INTEGER
	ACCESS  read-write
	STATUS  mandatory
	DESCRIPTION "CB36 Alarm-Time-Delay"
		::= { bcmsplus4 339 }

bcms4-cb37-alarm-time-delay
	OBJECT-TYPE
	SYNTAX  INTEGER
	ACCESS  read-write
	STATUS  mandatory
	DESCRIPTION "CB37 Alarm-Time-Delay"
		::= { bcmsplus4 340 }

bcms4-cb38-alarm-time-delay
	OBJECT-TYPE
	SYNTAX  INTEGER
	ACCESS  read-write
	STATUS  mandatory
	DESCRIPTION "CB38 Alarm-Time-Delay"
		::= { bcmsplus4 341 }

bcms4-cb39-alarm-time-delay
	OBJECT-TYPE
	SYNTAX  INTEGER
	ACCESS  read-write
	STATUS  mandatory
	DESCRIPTION "CB39 Alarm-Time-Delay"
		::= { bcmsplus4 342 }

bcms4-cb40-alarm-time-delay
	OBJECT-TYPE
	SYNTAX  INTEGER
	ACCESS  read-write
	STATUS  mandatory
	DESCRIPTION "CB40 Alarm-Time-Delay"
		::= { bcmsplus4 343 }

bcms4-cb41-alarm-time-delay
	OBJECT-TYPE
	SYNTAX  INTEGER
	ACCESS  read-write
	STATUS  mandatory
	DESCRIPTION "CB41 Alarm-Time-Delay"
		::= { bcmsplus4 344 }

bcms4-cb42-alarm-time-delay
	OBJECT-TYPE
	SYNTAX  INTEGER
	ACCESS  read-write
	STATUS  mandatory
	DESCRIPTION "CB42 Alarm-Time-Delay"
		::= { bcmsplus4 345 }

bcms4-global-breaker-size
	OBJECT-TYPE
	SYNTAX  INTEGER
	ACCESS  read-write
	STATUS  mandatory
	DESCRIPTION "Global-breaker-size
		     Note for global breaker size: 10 = 10 amps
                     Range is 10 to 100 amps"
		::= { bcmsplus4 346 }

bcms4-global-warning-threshold
	OBJECT-TYPE
	SYNTAX  INTEGER
	ACCESS  read-write
	STATUS  mandatory
	DESCRIPTION "Global-warning-threshold
		     Note for global warning threshold: 70 = 70% of breaker size
                     range is 0-100%"
		::= { bcmsplus4 347 }

bcms4-global-alarm-threshold
	OBJECT-TYPE
	SYNTAX  INTEGER
	ACCESS  read-write
	STATUS  mandatory
	DESCRIPTION "Global-alarm-threshold
		     Note for global alarm threshold: 80 = 80% of breaker size
                     range is 0-100%"
		::= { bcmsplus4 348 }

bcms4-global-warning-time-delay
	OBJECT-TYPE
	SYNTAX  INTEGER
	ACCESS  read-write
	STATUS  mandatory
	DESCRIPTION "Global-warning-time-delay
		     Note for global warning time delay: units are in seconds"                     
		::= { bcmsplus4 349 }

bcms4-global-alarm-time-delay
	OBJECT-TYPE
	SYNTAX  INTEGER
	ACCESS  read-write
	STATUS  mandatory
	DESCRIPTION "Global-alarm-time-delay
		     Note for global alarm time delay: units are in seconds"                     
		::= { bcmsplus4 350 }

bcms4-min-max-reset
	OBJECT-TYPE
	SYNTAX  INTEGER
	ACCESS  read-write
	STATUS  mandatory
	DESCRIPTION "Min-max-Reset
                     Note for Min-max Reset: writing to this register will clear minimum
		     and maximum current values"
		::= { bcmsplus4 351 }

bcms4-global-warning-alarm-register
	OBJECT-TYPE
	SYNTAX  INTEGER
	ACCESS  read-only
	STATUS  mandatory
	DESCRIPTION "Global-Warning-Alarm-Register
			bit 0:	Warning Register 1
			bit 1:	Warning Register 2
			bit 2:	Warning Register 3
			bit 3:	Alarm Register 1
			bit 4:	Alarm Register 2
			bit 5:	Alarm Register 3
			bit 6:	Zero Current Register 1
			bit 7:	Zero Current Register 2
			bit 8:	Zero Current Register 3
			bits 9 – 15: Always read as 0"
		::= { bcmsplus4 352 }

bcms4-meter-alarm-status-latching
	OBJECT-TYPE
	SYNTAX  INTEGER
	ACCESS  read-write
	STATUS  mandatory
	DESCRIPTION "Meter-Alarm-Status-Latching
			bit 0:	Over Current panelboard
			bit 1:	Under Current panelboard
			bit 2: 	Over Current both panelboards 
			bit 3: 	Under Current both panelboards
			bit 4: 	Over Voltage main
			bit 5: 	Under Voltage main
			bit 6: 	Over Voltage alternate
			bit 7: 	Under Voltage alternate
			bits 8 – 15: Not Used"
		::= { bcmsplus4 353 }

bcms4-meter-alarm-status-nonlatching
	OBJECT-TYPE
	SYNTAX  INTEGER
	ACCESS  read-only
	STATUS  mandatory
	DESCRIPTION "Meter-Alarm-Status-Nonlatching
			bit 0:	Over Current panelboard
			bit 1:	Under Current panelboard
			bit 2: 	Over Current both panelboards 
			bit 3: 	Under Current both panelboards
			bit 4: 	Over Voltage main
			bit 5: 	Under Voltage main
			bit 6: 	Over Voltage alternate
			bit 7: 	Under Voltage alternate
			bits 8 – 15: Not Used"
		::= { bcmsplus4 354 }

bcms4-digital-alarm-status
	OBJECT-TYPE
	SYNTAX  INTEGER
	ACCESS  read-only
	STATUS  mandatory
	DESCRIPTION "Digital-Alarm-Status
			bit 0:	Digital alarm 1
			bit 1:	Digital alarm 2
			bit 2: 	Digital alarm 3
			bit 3: 	Digital alarm 4
			bits 4 – 15: Not Used"
		::= { bcmsplus4 355 }

bcms4-current-option-setting
	OBJECT-TYPE
	SYNTAX  INTEGER
	ACCESS  read-only
	STATUS  mandatory
	DESCRIPTION "Current-Option-Setting
			bit 0:	option 0
			bit 1:	option 1
			bit 2: 	option 2 
			bit 3: 	neutral CTs
			bit 4:	no branch CTs
		     Option 0: no main or panelboard CTs. 	(357-359 summation of branch)
								(367-376 not used)
		     Option 1: CTs on main input feeding both panelboards. 
								(357-359 summation of branch)
		     Option 2: CTs on each panel board. 	(367-376 summation of panelboard 1 and 2) 
		     Note: Neutral current monitoring is optional."
		::= { bcmsplus4 356 }

bcms4-current-phase-a-panelboard
	OBJECT-TYPE
	SYNTAX  INTEGER
	ACCESS  read-only
	STATUS  mandatory
	DESCRIPTION "Current-Phase-A-Panelboard
                     Note for all currents: 100 = 10.0 amps"
		::= { bcmsplus4 357 }

bcms4-current-phase-b-panelboard
	OBJECT-TYPE
	SYNTAX  INTEGER
	ACCESS  read-only
	STATUS  mandatory
	DESCRIPTION "Current-Phase-B-Panelboard"
		::= { bcmsplus4 358 }

bcms4-current-phase-c-panelboard
	OBJECT-TYPE
	SYNTAX  INTEGER
	ACCESS  read-only
	STATUS  mandatory
	DESCRIPTION "Current-Phase-C-Panelboard"
		::= { bcmsplus4 359 }

bcms4-current-neutral-panelboard
	OBJECT-TYPE
	SYNTAX  INTEGER
	ACCESS  read-only
	STATUS  mandatory
	DESCRIPTION "Current-Neutral-Panelboard"
		::= { bcmsplus4 360 }


bcms4-over-current-alarm-threshhold-pnlbd
	OBJECT-TYPE
	SYNTAX  INTEGER
	ACCESS  read-write
	STATUS  mandatory
	DESCRIPTION "Over-Current-Alarm-Threshhold-Pnlbd"
		::= { bcmsplus4 361 }

bcms4-under-current-alarm-threshhold-pnlbd
	OBJECT-TYPE
	SYNTAX  INTEGER
	ACCESS  read-write
	STATUS  mandatory
	DESCRIPTION "Under-Current-Alarm-Threshhold-Pnlbd"
		::= { bcmsplus4 362 }

bcms4-over-current-set-counter-pnlbd
	OBJECT-TYPE
	SYNTAX  INTEGER
	ACCESS  read-only
	STATUS  mandatory
	DESCRIPTION "Over-Current-Set-Counter-Pnlbd
		     Note for all counters:
                     The set counter is incremented when the value goes outside the threshold limit
                     The reset counter is incremented when the value is returns to  the threshold limit"
		::= { bcmsplus4 363 }

bcms4-over-current-reset-counter-pnlbd
	OBJECT-TYPE
	SYNTAX  INTEGER
	ACCESS  read-only
	STATUS  mandatory
	DESCRIPTION "Over-Current-Reset-Counter-Pnlbd"
		::= { bcmsplus4 364 }

bcms4-under-current-set-counter-pnlbd
	OBJECT-TYPE
	SYNTAX  INTEGER
	ACCESS  read-only
	STATUS  mandatory
	DESCRIPTION "Under-Current-Set-Counter-Pnlbd"
		::= { bcmsplus4 365 }

bcms4-under-current-reset-counter-pnlbd
	OBJECT-TYPE
	SYNTAX  INTEGER
	ACCESS  read-only
	STATUS  mandatory
	DESCRIPTION "Under-Current-Reset-Counter-Pnlbd"
		::= { bcmsplus4 366 }

bcms4-current-phase-a-both-pnlbd
	OBJECT-TYPE
	SYNTAX  INTEGER
	ACCESS  read-only
	STATUS  mandatory
	DESCRIPTION "Current-Phase-A-Both-Pnlbd"
		::= { bcmsplus4 367 }

bcms4-current-phase-b-both-pnlbd
	OBJECT-TYPE
	SYNTAX  INTEGER
	ACCESS  read-only
	STATUS  mandatory
	DESCRIPTION "Current-Phase-B-Both-Pnlbd"
		::= { bcmsplus4 368 }

bcms4-current-phase-c-both-pnlbd
	OBJECT-TYPE
	SYNTAX  INTEGER
	ACCESS  read-only
	STATUS  mandatory
	DESCRIPTION "Current-Phase-C-Both-Pnlbd"
		::= { bcmsplus4 369 }

bcms4-current-neutral-both-pnlbd
	OBJECT-TYPE
	SYNTAX  INTEGER
	ACCESS  read-only
	STATUS  mandatory
	DESCRIPTION "Current-Neutral-Both-Pnlbd"
		::= { bcmsplus4 370 }


bcms4-over-current-alarm-threshhold-both-pnlbd
	OBJECT-TYPE
	SYNTAX  INTEGER
	ACCESS  read-write
	STATUS  mandatory
	DESCRIPTION "Over-Current-Alarm-Threshhold-Both-Pnlbd"
		::= { bcmsplus4 371 }

bcms4-under-current-alarm-threshhold-both-pnlbd
	OBJECT-TYPE
	SYNTAX  INTEGER
	ACCESS  read-write
	STATUS  mandatory
	DESCRIPTION "Under-Current-Alarm-Threshhold-Both-Pnlbd"
		::= { bcmsplus4 372 }

bcms4-over-current-set-counter-both-pnlbd
	OBJECT-TYPE
	SYNTAX  INTEGER
	ACCESS  read-only
	STATUS  mandatory
	DESCRIPTION "Over-Current-Set-Counter-Both-Pnlbd"
		::= { bcmsplus4 373 }

bcms4-over-current-reset-counter-both-pnlbd
	OBJECT-TYPE
	SYNTAX  INTEGER
	ACCESS  read-only
	STATUS  mandatory
	DESCRIPTION "Over-Current-Reset-Counter-Both-Pnlbd"
		::= { bcmsplus4 374 }

bcms4-under-current-set-counter-both-pnlbd
	OBJECT-TYPE
	SYNTAX  INTEGER
	ACCESS  read-only
	STATUS  mandatory
	DESCRIPTION "Under-Current-Set-Counter-Both-Pnlbd"
		::= { bcmsplus4 375 }

bcms4-under-current-reset-counter-both-pnlbd
	OBJECT-TYPE
	SYNTAX  INTEGER
	ACCESS  read-only
	STATUS  mandatory
	DESCRIPTION "Under-Current-Reset-Counter-Both-Pnlbd"
		::= { bcmsplus4 376 }

bcms4-voltage-option-setting
	OBJECT-TYPE
	SYNTAX  INTEGER
	ACCESS  read-only
	STATUS  mandatory
	DESCRIPTION "Voltage-Option-Setting
			bit 0:	option 0
			bit 1:	option 1
			bit 2: 	option 2 
			bit 3: 	option 3 
			bits 4 – 15: Not Used
                     Option 0: no voltage monitoring. (378-414 not used)
                     Option 1: One voltage feeding 1 or 2 panel boards. (390-401 not used)
                     Option 2: One voltage feeding panelboard 1 and another feeding panelboard 2. (390-401 not used)
                     Option 3: Two voltages tied together through interlocked circuit breakers feeding both panelboards. 
                               Digital input 1 and 2 are used to determine which is feeding the panelboard. A set bit 
                               indicated closed.  If both are closed, main voltage is used."
		::= { bcmsplus4 377 }

bcms4-voltage-a-b-main
	OBJECT-TYPE
	SYNTAX  INTEGER
	ACCESS  read-only
	STATUS  mandatory
	DESCRIPTION "Voltage-A-B-Main
                     Note for all voltages: 1200 = 120.0 volts"
		::= { bcmsplus4 378 }

bcms4-voltage-b-c-main
	OBJECT-TYPE
	SYNTAX  INTEGER
	ACCESS  read-only
	STATUS  mandatory
	DESCRIPTION "Voltage-B-C-Main"
		::= { bcmsplus4 379 }

bcms4-voltage-c-a-main
	OBJECT-TYPE
	SYNTAX  INTEGER
	ACCESS  read-only
	STATUS  mandatory
	DESCRIPTION "Voltage-C-A-Main"
		::= { bcmsplus4 380 }

bcms4-voltage-a-n-main
	OBJECT-TYPE
	SYNTAX  INTEGER
	ACCESS  read-only
	STATUS  mandatory
	DESCRIPTION "Voltage-A-N-Main"
		::= { bcmsplus4 381 }

bcms4-voltage-b-n-main
	OBJECT-TYPE
	SYNTAX  INTEGER
	ACCESS  read-only
	STATUS  mandatory
	DESCRIPTION "Voltage-B-N-Main"
		::= { bcmsplus4 382 }

bcms4-voltage-c-n-main
	OBJECT-TYPE
	SYNTAX  INTEGER
	ACCESS  read-only
	STATUS  mandatory
	DESCRIPTION "Voltage-C-N-Main"
		::= { bcmsplus4 383 }

bcms4-over-voltage-alarm-threshhold-main
	OBJECT-TYPE
	SYNTAX  INTEGER
	ACCESS  read-write
	STATUS  mandatory
	DESCRIPTION "Over-Voltage-Alarm-Threshhold-Main
                     Note All Over and Under Voltage is for L-L values"
		::= { bcmsplus4 384 }

bcms4-under-voltage-alarm-threshhold-main
	OBJECT-TYPE
	SYNTAX  INTEGER
	ACCESS  read-write
	STATUS  mandatory
	DESCRIPTION "Under-Voltage-Alarm-Threshhold-Main"
		::= { bcmsplus4 385 }

bcms4-over-voltage-set-counter-main
	OBJECT-TYPE
	SYNTAX  INTEGER
	ACCESS  read-only
	STATUS  mandatory
	DESCRIPTION "Over-Voltage-Set-Counter-Main"
		::= { bcmsplus4 386 }

bcms4-over-voltage-reset-counter-main
	OBJECT-TYPE
	SYNTAX  INTEGER
	ACCESS  read-only
	STATUS  mandatory
	DESCRIPTION "Over-Voltage-Reset-Counter-Main"
		::= { bcmsplus4 387 }

bcms4-under-voltage-set-counter-main
	OBJECT-TYPE
	SYNTAX  INTEGER
	ACCESS  read-only
	STATUS  mandatory
	DESCRIPTION "Under-Voltage-Set-Counter-Main"
		::= { bcmsplus4 388 }

bcms4-under-voltage-reset-counter-main
	OBJECT-TYPE
	SYNTAX  INTEGER
	ACCESS  read-only
	STATUS  mandatory
	DESCRIPTION "Under-Voltage-Reset-Counter-Main"
		::= { bcmsplus4 389 }


bcms4-voltage-frequency-main
	OBJECT-TYPE
	SYNTAX  INTEGER
	ACCESS  read-only
	STATUS  mandatory
	DESCRIPTION "Voltage-Frequency-Main
                     note for frequency: 600 = 60.0Hz
                     Range is 40-70Hz
                     Note if insufficient voltage is present frequency will read 0xFFFF"
		::= { bcmsplus4 390 }

bcms4-voltage-a-b-alternate
	OBJECT-TYPE
	SYNTAX  INTEGER
	ACCESS  read-only
	STATUS  mandatory
	DESCRIPTION "Voltage-A-B-Alternate"
		::= { bcmsplus4 391 }

bcms4-voltage-b-c-alternate
	OBJECT-TYPE
	SYNTAX  INTEGER
	ACCESS  read-only
	STATUS  mandatory
	DESCRIPTION "Voltage-B-C-Alternate"
		::= { bcmsplus4 392 }

bcms4-voltage-c-a-alternate
	OBJECT-TYPE
	SYNTAX  INTEGER
	ACCESS  read-only
	STATUS  mandatory
	DESCRIPTION "Voltage-C-A-Alternate"
		::= { bcmsplus4 393 }

bcms4-voltage-a-n-alternate
	OBJECT-TYPE
	SYNTAX  INTEGER
	ACCESS  read-only
	STATUS  mandatory
	DESCRIPTION "Voltage-A-N-Alternate"
		::= { bcmsplus4 394 }

bcms4-voltage-b-N-alternate
	OBJECT-TYPE
	SYNTAX  INTEGER
	ACCESS  read-only
	STATUS  mandatory
	DESCRIPTION "Voltage-B-N-Alternate"
		::= { bcmsplus4 395 }

bcms4-voltage-c-n-alternate
	OBJECT-TYPE
	SYNTAX  INTEGER
	ACCESS  read-only
	STATUS  mandatory
	DESCRIPTION "Voltage-C-N-Alternate"
		::= { bcmsplus4 396 }

bcms4-over-voltage-alarm-threshhold-alternate
	OBJECT-TYPE
	SYNTAX  INTEGER
	ACCESS  read-write
	STATUS  mandatory
	DESCRIPTION "Over-Voltage-Alarm-Threshhold-Alternate"
		::= { bcmsplus4 397 }

bcms4-under-voltage-alarm-threshhold-alternate
	OBJECT-TYPE
	SYNTAX  INTEGER
	ACCESS  read-write
	STATUS  mandatory
	DESCRIPTION "Under-Voltage-Alarm-Threshhold-Alternate"
		::= { bcmsplus4 398 }

bcms4-over-voltage-set-counter-alternate
	OBJECT-TYPE
	SYNTAX  INTEGER
	ACCESS  read-only
	STATUS  mandatory
	DESCRIPTION "Over-Voltage-Set-Counter-Alternate"
		::= { bcmsplus4 399 }

bcms4-over-voltage-reset-counter-alternate
	OBJECT-TYPE
	SYNTAX  INTEGER
	ACCESS  read-only
	STATUS  mandatory
	DESCRIPTION "Over-Voltage-Reset-Counter-Alternate"
		::= { bcmsplus4 400 }

bcms4-under-voltage-set-counter-alternate
	OBJECT-TYPE
	SYNTAX  INTEGER
	ACCESS  read-only
	STATUS  mandatory
	DESCRIPTION "Under-Voltage-Set-Counter-Alternate"
		::= { bcmsplus4 401 }

bcms4-under-voltage-reset-counter-alternate
	OBJECT-TYPE
	SYNTAX  INTEGER
	ACCESS  read-only
	STATUS  mandatory
	DESCRIPTION "Under-Voltage-Reset-Counter-Alternate"
		::= { bcmsplus4 402 }

bcms4-real-power-kw
	OBJECT-TYPE
	SYNTAX  INTEGER
	ACCESS  read-only
	STATUS  mandatory
	DESCRIPTION "Real-Power-KW
                     Note for all KWs: 100 = 10.0 KW"
		::= { bcmsplus4 403 }

bcms4-peal-power-phase-a
	OBJECT-TYPE
	SYNTAX  INTEGER
	ACCESS  read-only
	STATUS  mandatory
	DESCRIPTION "Real-Power-Phase-A"
		::= { bcmsplus4 404 }

bcms4-real-power-phase-b
	OBJECT-TYPE
	SYNTAX  INTEGER
	ACCESS  read-only
	STATUS  mandatory
	DESCRIPTION "Real-Power-Phase-B"
		::= { bcmsplus4 405 }

bcms4-real-power-phase-c
	OBJECT-TYPE
	SYNTAX  INTEGER
	ACCESS  read-only
	STATUS  mandatory
	DESCRIPTION "Real-Power-Phase-C"
		::= { bcmsplus4 406 }

bcms4-reactive-power-kvar
	OBJECT-TYPE
	SYNTAX  INTEGER
	ACCESS  read-only
	STATUS  mandatory
	DESCRIPTION "Reactive-Power-KVAR
                     Note for KVAR: 100 = 10.0 KVAR"
		::= { bcmsplus4 407 }

bcms4-apparent-Power-kva
	OBJECT-TYPE
	SYNTAX  INTEGER
	ACCESS  read-only
	STATUS  mandatory
	DESCRIPTION "Apparent-Power-KVA
                     Note for KVA: 100 = 10.0 KVA"
		::= { bcmsplus4 408 }

bcms4-total-power-factor
	OBJECT-TYPE
	SYNTAX  INTEGER
	ACCESS  read-only
	STATUS  mandatory
	DESCRIPTION "Total-Power-Factor
                     Note for all Power Factor: 1000 = 100.0 PF"
		::= { bcmsplus4 409 }

bcms4-power-factor-phase-a
	OBJECT-TYPE
	SYNTAX  INTEGER
	ACCESS  read-only
	STATUS  mandatory
	DESCRIPTION "Power-Factor-Phase-A"
		::= { bcmsplus4 410 }

bcms4-Power-factor-phase-b
	OBJECT-TYPE
	SYNTAX  INTEGER
	ACCESS  read-only
	STATUS  mandatory
	DESCRIPTION "Power-Factor-Phase-B"
		::= { bcmsplus4 411 }

bcms4-Power-factor-phase-c
	OBJECT-TYPE
	SYNTAX  INTEGER
	ACCESS  read-only
	STATUS  mandatory
	DESCRIPTION "Power-Factor-Phase-C"
		::= { bcmsplus4 412 }

bcms4-energy-consumption-kwh-lower-word-integer
	OBJECT-TYPE
	SYNTAX  INTEGER
	ACCESS  read-write
	STATUS  mandatory
	DESCRIPTION "Energy-Consumption-KWh-Lower-Word-Integer
		     Note for KWh: 100 = 100KWh
                     Combine lower and upper integers into a word for total KWh"
		::= { bcmsplus4 413 }

bcms4-energy-consumption-kwh-upper-word-integer
	OBJECT-TYPE
	SYNTAX  INTEGER
	ACCESS  read-write
	STATUS  mandatory
	DESCRIPTION "Energy-Consumption-KWh-Upper-Word-Integer"
		::= { bcmsplus4 414 }

bcms4-main-voltage-thd-phase-a
	OBJECT-TYPE
	SYNTAX  INTEGER
	ACCESS  read-only
	STATUS  mandatory
	DESCRIPTION "Main-Voltage-THD-Phase-A"
		::= { bcmsplus4 415 }

bcms4-main-voltage-thd-phase-b
	OBJECT-TYPE
	SYNTAX  INTEGER
	ACCESS  read-only
	STATUS  mandatory
	DESCRIPTION "Main-Voltage-THD-Phase-B"
		::= { bcmsplus4 416 }

bcms4-main-voltage-thd-phase-c
	OBJECT-TYPE
	SYNTAX  INTEGER
	ACCESS  read-only
	STATUS  mandatory
	DESCRIPTION "Main-Voltage-THD-Phase-C"
		::= { bcmsplus4 417 }

bcms4-alt-voltage-thd-phase-a
	OBJECT-TYPE
	SYNTAX  INTEGER
	ACCESS  read-only
	STATUS  mandatory
	DESCRIPTION "Alt-Voltage-THD-Phase-A"
		::= { bcmsplus4 418 }

bcms4-alt-voltage-thd-phase-b
	OBJECT-TYPE
	SYNTAX  INTEGER
	ACCESS  read-only
	STATUS  mandatory
	DESCRIPTION "Alt-Voltage-THD-Phase-B"
		::= { bcmsplus4 419 }

bcms4-alt-voltage-thd-phase-c
	OBJECT-TYPE
	SYNTAX  INTEGER
	ACCESS  read-only
	STATUS  mandatory
	DESCRIPTION "Alt-Voltage-THD-Phase-C"
		::= { bcmsplus4 420 }

bcms4-current-ground-panelboard
	OBJECT-TYPE
	SYNTAX  INTEGER
	ACCESS  read-only
	STATUS  mandatory
	DESCRIPTION "Current-Ground-Panelboard"
		::= { bcmsplus4 421 }

bcms4-percent-load-phase-a
	OBJECT-TYPE
	SYNTAX  INTEGER
	ACCESS  read-only
	STATUS  mandatory
	DESCRIPTION "Percent Load Phase A"
		::= { bcmsplus4 422 }

bcms4-percent-load-phase-b
	OBJECT-TYPE
	SYNTAX  INTEGER
	ACCESS  read-only
	STATUS  mandatory
	DESCRIPTION "Percent Load Phase B"
		::= { bcmsplus4 423 }

bcms4-percent-load-phase-c
	OBJECT-TYPE
	SYNTAX  INTEGER
	ACCESS  read-only
	STATUS  mandatory
	DESCRIPTION "Percent Load Phase C"
		::= { bcmsplus4 424 }

bcms4-full-load-current
	OBJECT-TYPE
	SYNTAX  INTEGER
	ACCESS  read-write
	STATUS  mandatory
	DESCRIPTION "Full Load Current"
		::= { bcmsplus4 425 }

--------------------------------------------------------------------------------
-- BCMSPLUS register values
--------------------------------------------------------------------------------

bcms5-cb1-current
	OBJECT-TYPE
	SYNTAX  INTEGER
	ACCESS  read-only
	STATUS  mandatory
	DESCRIPTION "CB1 Current
		     Note for all currents 1-42: 100 = 10.0 amps"
		::= { bcmsplus5 1 }
  
bcms5-cb2-current
	OBJECT-TYPE
	SYNTAX  INTEGER
	ACCESS  read-only
	STATUS  mandatory
	DESCRIPTION "CB2 Current"
		::= { bcmsplus5 2 }

bcms5-cb3-current
	OBJECT-TYPE
	SYNTAX  INTEGER
	ACCESS  read-only
	STATUS  mandatory
	DESCRIPTION "CB3 Current"
		::= { bcmsplus5 3 }

bcms5-cb4-current
	OBJECT-TYPE
	SYNTAX  INTEGER
	ACCESS  read-only
	STATUS  mandatory
	DESCRIPTION "CB4 Current"
		::= { bcmsplus5 4 }

bcms5-cb5-current
	OBJECT-TYPE
	SYNTAX  INTEGER
	ACCESS  read-only
	STATUS  mandatory
	DESCRIPTION "CB5 Current"
		::= { bcmsplus5 5 }

bcms5-cb6-current
	OBJECT-TYPE
	SYNTAX  INTEGER
	ACCESS  read-only
	STATUS  mandatory
	DESCRIPTION "CB6 Current"
		::= { bcmsplus5 6 }

bcms5-cb7-current
	OBJECT-TYPE
	SYNTAX  INTEGER
	ACCESS  read-only
	STATUS  mandatory
	DESCRIPTION "CB7 Current"
		::= { bcmsplus5 7 }

bcms5-cb8-current
	OBJECT-TYPE
	SYNTAX  INTEGER
	ACCESS  read-only
	STATUS  mandatory
	DESCRIPTION "CB8 Current"
		::= { bcmsplus5 8 }

bcms5-cb9-current
	OBJECT-TYPE
	SYNTAX  INTEGER
	ACCESS  read-only
	STATUS  mandatory
	DESCRIPTION "CB9 Current"
		::= { bcmsplus5 9 }

bcms5-cb10-current
	OBJECT-TYPE
	SYNTAX  INTEGER
	ACCESS  read-only
	STATUS  mandatory
	DESCRIPTION "CB10 Current"
		::= { bcmsplus5 10 }

bcms5-cb11-current
	OBJECT-TYPE
	SYNTAX  INTEGER
	ACCESS  read-only
	STATUS  mandatory
	DESCRIPTION "CB11 Current"
		::= { bcmsplus5 11 }
  
bcms5-cb12-current
	OBJECT-TYPE
	SYNTAX  INTEGER
	ACCESS  read-only
	STATUS  mandatory
	DESCRIPTION "CB12 Current"
		::= { bcmsplus5 12 }

bcms5-cb13-current
	OBJECT-TYPE
	SYNTAX  INTEGER
	ACCESS  read-only
	STATUS  mandatory
	DESCRIPTION "CB13 Current"
		::= { bcmsplus5 13 }

bcms5-cb14-current
	OBJECT-TYPE
	SYNTAX  INTEGER
	ACCESS  read-only
	STATUS  mandatory
	DESCRIPTION "CB14 Current"
		::= { bcmsplus5 14 }

bcms5-cb15-current
	OBJECT-TYPE
	SYNTAX  INTEGER
	ACCESS  read-only
	STATUS  mandatory
	DESCRIPTION "CB15 Current"
		::= { bcmsplus5 15 }

bcms5-cb16-current
	OBJECT-TYPE
	SYNTAX  INTEGER
	ACCESS  read-only
	STATUS  mandatory
	DESCRIPTION "CB16 Current"
		::= { bcmsplus5 16 }

bcms5-cb17-current
	OBJECT-TYPE
	SYNTAX  INTEGER
	ACCESS  read-only
	STATUS  mandatory
	DESCRIPTION "CB17 Current"
		::= { bcmsplus5 17 }

bcms5-cb18-current
	OBJECT-TYPE
	SYNTAX  INTEGER
	ACCESS  read-only
	STATUS  mandatory
	DESCRIPTION "CB18 Current"
		::= { bcmsplus5 18 }

bcms5-cb19-current
	OBJECT-TYPE
	SYNTAX  INTEGER
	ACCESS  read-only
	STATUS  mandatory
	DESCRIPTION "CB19 Current"
		::= { bcmsplus5 19 }

bcms5-cb20-current
	OBJECT-TYPE
	SYNTAX  INTEGER
	ACCESS  read-only
	STATUS  mandatory
	DESCRIPTION "CB20 Current"
		::= { bcmsplus5 20 }

bcms5-cb21-current
	OBJECT-TYPE
	SYNTAX  INTEGER
	ACCESS  read-only
	STATUS  mandatory
	DESCRIPTION "CB21 Current"
		::= { bcmsplus5 21 }
  
bcms5-cb22-current
	OBJECT-TYPE
	SYNTAX  INTEGER
	ACCESS  read-only
	STATUS  mandatory
	DESCRIPTION "CB22 Current"
		::= { bcmsplus5 22 }

bcms5-cb23-current
	OBJECT-TYPE
	SYNTAX  INTEGER
	ACCESS  read-only
	STATUS  mandatory
	DESCRIPTION "CB23 Current"
		::= { bcmsplus5 23 }

bcms5-cb24-current
	OBJECT-TYPE
	SYNTAX  INTEGER
	ACCESS  read-only
	STATUS  mandatory
	DESCRIPTION "CB24 Current"
		::= { bcmsplus5 24 }

bcms5-cb25-current
	OBJECT-TYPE
	SYNTAX  INTEGER
	ACCESS  read-only
	STATUS  mandatory
	DESCRIPTION "CB25 Current"
		::= { bcmsplus5 25 }

bcms5-cb26-current
	OBJECT-TYPE
	SYNTAX  INTEGER
	ACCESS  read-only
	STATUS  mandatory
	DESCRIPTION "CB26 Current"
		::= { bcmsplus5 26 }

bcms5-cb27-current
	OBJECT-TYPE
	SYNTAX  INTEGER
	ACCESS  read-only
	STATUS  mandatory
	DESCRIPTION "CB27 Current"
		::= { bcmsplus5 27 }

bcms5-cb28-current
	OBJECT-TYPE
	SYNTAX  INTEGER
	ACCESS  read-only
	STATUS  mandatory
	DESCRIPTION "CB28 Current"
		::= { bcmsplus5 28 }

bcms5-cb29-current
	OBJECT-TYPE
	SYNTAX  INTEGER
	ACCESS  read-only
	STATUS  mandatory
	DESCRIPTION "CB29 Current"
		::= { bcmsplus5 29 }

bcms5-cb30-current
	OBJECT-TYPE
	SYNTAX  INTEGER
	ACCESS  read-only
	STATUS  mandatory
	DESCRIPTION "CB30 Current"
		::= { bcmsplus5 30 }

bcms5-cb31-current
	OBJECT-TYPE
	SYNTAX  INTEGER
	ACCESS  read-only
	STATUS  mandatory
	DESCRIPTION "CB31 Current"
		::= { bcmsplus5 31 }
  
bcms5-cb32-current
	OBJECT-TYPE
	SYNTAX  INTEGER
	ACCESS  read-only
	STATUS  mandatory
	DESCRIPTION "CB32 Current"
		::= { bcmsplus5 32 }

bcms5-cb33-current
	OBJECT-TYPE
	SYNTAX  INTEGER
	ACCESS  read-only
	STATUS  mandatory
	DESCRIPTION "CB33 Current"
		::= { bcmsplus5 33 }

bcms5-cb34-current
	OBJECT-TYPE
	SYNTAX  INTEGER
	ACCESS  read-only
	STATUS  mandatory
	DESCRIPTION "CB34 Current"
		::= { bcmsplus5 34 }

bcms5-cb35-current
	OBJECT-TYPE
	SYNTAX  INTEGER
	ACCESS  read-only
	STATUS  mandatory
	DESCRIPTION "CB35 Current"
		::= { bcmsplus5 35 }

bcms5-cb36-current
	OBJECT-TYPE
	SYNTAX  INTEGER
	ACCESS  read-only
	STATUS  mandatory
	DESCRIPTION "CB36 Current"
		::= { bcmsplus5 36 }

bcms5-cb37-current
	OBJECT-TYPE
	SYNTAX  INTEGER
	ACCESS  read-only
	STATUS  mandatory
	DESCRIPTION "CB37 Current"
		::= { bcmsplus5 37 }

bcms5-cb38-current
	OBJECT-TYPE
	SYNTAX  INTEGER
	ACCESS  read-only
	STATUS  mandatory
	DESCRIPTION "CB38 Current"
		::= { bcmsplus5 38 }

bcms5-cb39-current
	OBJECT-TYPE
	SYNTAX  INTEGER
	ACCESS  read-only
	STATUS  mandatory
	DESCRIPTION "CB39 Current"
		::= { bcmsplus5 39 }

bcms5-cb40-current
	OBJECT-TYPE
	SYNTAX  INTEGER
	ACCESS  read-only
	STATUS  mandatory
	DESCRIPTION "CB40 Current"
		::= { bcmsplus5 40 }

bcms5-cb41-current
	OBJECT-TYPE
	SYNTAX  INTEGER
	ACCESS  read-only
	STATUS  mandatory
	DESCRIPTION "CB41 Current"
		::= { bcmsplus5 41 }
  
bcms5-cb42-current
	OBJECT-TYPE
	SYNTAX  INTEGER
	ACCESS  read-only
	STATUS  mandatory
	DESCRIPTION "CB42 Current"
		::= { bcmsplus5 42 }

bcms5-cb1-min
	OBJECT-TYPE
	SYNTAX  INTEGER
	ACCESS  read-only
	STATUS  mandatory
	DESCRIPTION "CB1 Min
		     Note for all minumum currents 1-42: 100 = 10.0 amps"
		::= { bcmsplus5 43 }

bcms5-cb2-min
	OBJECT-TYPE
	SYNTAX  INTEGER
	ACCESS  read-only
	STATUS  mandatory
	DESCRIPTION "CB2 Min"
		::= { bcmsplus5 44 }

bcms5-cb3-min
	OBJECT-TYPE
	SYNTAX  INTEGER
	ACCESS  read-only
	STATUS  mandatory
	DESCRIPTION "CB3 Min"
		::= { bcmsplus5 45 }

bcms5-cb4-min
	OBJECT-TYPE
	SYNTAX  INTEGER
	ACCESS  read-only
	STATUS  mandatory
	DESCRIPTION "CB4 Min"
		::= { bcmsplus5 46 }

bcms5-cb5-min
	OBJECT-TYPE
	SYNTAX  INTEGER
	ACCESS  read-only
	STATUS  mandatory
	DESCRIPTION "CB5 Min"
		::= { bcmsplus5 47 }

bcms5-cb6-min
	OBJECT-TYPE
	SYNTAX  INTEGER
	ACCESS  read-only
	STATUS  mandatory
	DESCRIPTION "CB6 Min"
		::= { bcmsplus5 48 }

bcms5-cb7-min
	OBJECT-TYPE
	SYNTAX  INTEGER
	ACCESS  read-only
	STATUS  mandatory
	DESCRIPTION "CB7 Min"
		::= { bcmsplus5 49 }

bcms5-cb8-min
	OBJECT-TYPE
	SYNTAX  INTEGER
	ACCESS  read-only
	STATUS  mandatory
	DESCRIPTION "CB8 Min"
		::= { bcmsplus5 50 }

bcms5-cb9-min
	OBJECT-TYPE
	SYNTAX  INTEGER
	ACCESS  read-only
	STATUS  mandatory
	DESCRIPTION "CB9 Min"
		::= { bcmsplus5 51 }
  
bcms5-cb10-min
	OBJECT-TYPE
	SYNTAX  INTEGER
	ACCESS  read-only
	STATUS  mandatory
	DESCRIPTION "CB10 Min"
		::= { bcmsplus5 52 }

bcms5-cb11-min
	OBJECT-TYPE
	SYNTAX  INTEGER
	ACCESS  read-only
	STATUS  mandatory
	DESCRIPTION "CB11 Min"
		::= { bcmsplus5 53 }

bcms5-cb12-min
	OBJECT-TYPE
	SYNTAX  INTEGER
	ACCESS  read-only
	STATUS  mandatory
	DESCRIPTION "CB12 Min"
		::= { bcmsplus5 54 }

bcms5-cb13-min
	OBJECT-TYPE
	SYNTAX  INTEGER
	ACCESS  read-only
	STATUS  mandatory
	DESCRIPTION "CB13 Min"
		::= { bcmsplus5 55 }

bcms5-cb14-min
	OBJECT-TYPE
	SYNTAX  INTEGER
	ACCESS  read-only
	STATUS  mandatory
	DESCRIPTION "CB14 Min"
		::= { bcmsplus5 56 }

bcms5-cb15-min
	OBJECT-TYPE
	SYNTAX  INTEGER
	ACCESS  read-only
	STATUS  mandatory
	DESCRIPTION "CB15 Min"
		::= { bcmsplus5 57 }

bcms5-cb16-min
	OBJECT-TYPE
	SYNTAX  INTEGER
	ACCESS  read-only
	STATUS  mandatory
	DESCRIPTION "CB16 Min"
		::= { bcmsplus5 58 }

bcms5-cb17-min
	OBJECT-TYPE
	SYNTAX  INTEGER
	ACCESS  read-only
	STATUS  mandatory
	DESCRIPTION "CB17 Min"
		::= { bcmsplus5 59 }


bcms5-cb18-min
	OBJECT-TYPE
	SYNTAX  INTEGER
	ACCESS  read-only
	STATUS  mandatory
	DESCRIPTION "CB18 Min"
		::= { bcmsplus5 60 }

bcms5-cb19-min
	OBJECT-TYPE
	SYNTAX  INTEGER
	ACCESS  read-only
	STATUS  mandatory
	DESCRIPTION "CB19 Min"
		::= { bcmsplus5 61 }
  
bcms5-cb20-min
	OBJECT-TYPE
	SYNTAX  INTEGER
	ACCESS  read-only
	STATUS  mandatory
	DESCRIPTION "CB20 Min"
		::= { bcmsplus5 62 }

bcms5-cb21-min
	OBJECT-TYPE
	SYNTAX  INTEGER
	ACCESS  read-only
	STATUS  mandatory
	DESCRIPTION "CB21 Min"
		::= { bcmsplus5 63 }

bcms5-cb22-min
	OBJECT-TYPE
	SYNTAX  INTEGER
	ACCESS  read-only
	STATUS  mandatory
	DESCRIPTION "CB22 Min"
		::= { bcmsplus5 64 }

bcms5-cb23-min
	OBJECT-TYPE
	SYNTAX  INTEGER
	ACCESS  read-only
	STATUS  mandatory
	DESCRIPTION "CB23 Min"
		::= { bcmsplus5 65 }

bcms5-cb24-min
	OBJECT-TYPE
	SYNTAX  INTEGER
	ACCESS  read-only
	STATUS  mandatory
	DESCRIPTION "CB24 Min"
		::= { bcmsplus5 66 }

bcms5-cb25-min
	OBJECT-TYPE
	SYNTAX  INTEGER
	ACCESS  read-only
	STATUS  mandatory
	DESCRIPTION "CB25 Min"
		::= { bcmsplus5 67 }

bcms5-cb26-min
	OBJECT-TYPE
	SYNTAX  INTEGER
	ACCESS  read-only
	STATUS  mandatory
	DESCRIPTION "CB26 Min"
		::= { bcmsplus5 68 }

bcms5-cb27-min
	OBJECT-TYPE
	SYNTAX  INTEGER
	ACCESS  read-only
	STATUS  mandatory
	DESCRIPTION "CB27 Min"
		::= { bcmsplus5 69 }

bcms5-cb28-min
	OBJECT-TYPE
	SYNTAX  INTEGER
	ACCESS  read-only
	STATUS  mandatory
	DESCRIPTION "CB28 Min"
		::= { bcmsplus5 70 }

bcms5-cb29-min
	OBJECT-TYPE
	SYNTAX  INTEGER
	ACCESS  read-only
	STATUS  mandatory
	DESCRIPTION "CB29 Min"
		::= { bcmsplus5 71 }
  
bcms5-cb30-min
	OBJECT-TYPE
	SYNTAX  INTEGER
	ACCESS  read-only
	STATUS  mandatory
	DESCRIPTION "CB30 Min"
		::= { bcmsplus5 72 }

bcms5-cb31-min
	OBJECT-TYPE
	SYNTAX  INTEGER
	ACCESS  read-only
	STATUS  mandatory
	DESCRIPTION "CB31 Min"
		::= { bcmsplus5 73 }

bcms5-cb32-min
	OBJECT-TYPE
	SYNTAX  INTEGER
	ACCESS  read-only
	STATUS  mandatory
	DESCRIPTION "CB32 Min"
		::= { bcmsplus5 74 }

bcms5-cb33-min
	OBJECT-TYPE
	SYNTAX  INTEGER
	ACCESS  read-only
	STATUS  mandatory
	DESCRIPTION "CB33 Min"
		::= { bcmsplus5 75 }

bcms5-cb34-min
	OBJECT-TYPE
	SYNTAX  INTEGER
	ACCESS  read-only
	STATUS  mandatory
	DESCRIPTION "CB34 Min"
		::= { bcmsplus5 76 }

bcms5-cb35-min
	OBJECT-TYPE
	SYNTAX  INTEGER
	ACCESS  read-only
	STATUS  mandatory
	DESCRIPTION "CB35 Min"
		::= { bcmsplus5 77 }

bcms5-cb36-min
	OBJECT-TYPE
	SYNTAX  INTEGER
	ACCESS  read-only
	STATUS  mandatory
	DESCRIPTION "CB36 Min"
		::= { bcmsplus5 78 }

bcms5-cb37-min
	OBJECT-TYPE
	SYNTAX  INTEGER
	ACCESS  read-only
	STATUS  mandatory
	DESCRIPTION "CB37 Min"
		::= { bcmsplus5 79 }

bcms5-cb38-min
	OBJECT-TYPE
	SYNTAX  INTEGER
	ACCESS  read-only
	STATUS  mandatory
	DESCRIPTION "CB38 Min"
		::= { bcmsplus5 80 }

bcms5-cb39-min
	OBJECT-TYPE
	SYNTAX  INTEGER
	ACCESS  read-only
	STATUS  mandatory
	DESCRIPTION "CB39 Min"
		::= { bcmsplus5 81 }
  
bcms5-cb40-min
	OBJECT-TYPE
	SYNTAX  INTEGER
	ACCESS  read-only
	STATUS  mandatory
	DESCRIPTION "CB40 Min"
		::= { bcmsplus5 82 }

bcms5-cb41-min
	OBJECT-TYPE
	SYNTAX  INTEGER
	ACCESS  read-only
	STATUS  mandatory
	DESCRIPTION "CB41 Min"
		::= { bcmsplus5 83 }

bcms5-cb42-min
	OBJECT-TYPE
	SYNTAX  INTEGER
	ACCESS  read-only
	STATUS  mandatory
	DESCRIPTION "CB42 Min"
		::= { bcmsplus5 84 }

bcms5-cb1-max
	OBJECT-TYPE
	SYNTAX  INTEGER
	ACCESS  read-only
	STATUS  mandatory
	DESCRIPTION "CB1 Max
		     Note for all maximum currents 1-42: 100 = 10.0 amps"
		::= { bcmsplus5 85 }

bcms5-cb2-max
	OBJECT-TYPE
	SYNTAX  INTEGER
	ACCESS  read-only
	STATUS  mandatory
	DESCRIPTION "CB2 Max"
		::= { bcmsplus5 86 }

bcms5-cb3-max
	OBJECT-TYPE
	SYNTAX  INTEGER
	ACCESS  read-only
	STATUS  mandatory
	DESCRIPTION "CB3 Max"
		::= { bcmsplus5 87 }

bcms5-cb4-max
	OBJECT-TYPE
	SYNTAX  INTEGER
	ACCESS  read-only
	STATUS  mandatory
	DESCRIPTION "CB4 Max"
		::= { bcmsplus5 88 }

bcms5-cb5-max
	OBJECT-TYPE
	SYNTAX  INTEGER
	ACCESS  read-only
	STATUS  mandatory
	DESCRIPTION "CB5 Max"
		::= { bcmsplus5 89 }

bcms5-cb6-max
	OBJECT-TYPE
	SYNTAX  INTEGER
	ACCESS  read-only
	STATUS  mandatory
	DESCRIPTION "CB6 Max"
		::= { bcmsplus5 90 }

bcms5-cb7-max
	OBJECT-TYPE
	SYNTAX  INTEGER
	ACCESS  read-only
	STATUS  mandatory
	DESCRIPTION "CB7 Max"
		::= { bcmsplus5 91 }
  
bcms5-cb8-max
	OBJECT-TYPE
	SYNTAX  INTEGER
	ACCESS  read-only
	STATUS  mandatory
	DESCRIPTION "CB8 Max"
		::= { bcmsplus5 92 }

bcms5-cb9-max
	OBJECT-TYPE
	SYNTAX  INTEGER
	ACCESS  read-only
	STATUS  mandatory
	DESCRIPTION "CB9 Max"
		::= { bcmsplus5 93 }

bcms5-cb10-max
	OBJECT-TYPE
	SYNTAX  INTEGER
	ACCESS  read-only
	STATUS  mandatory
	DESCRIPTION "CB10 Max"
		::= { bcmsplus5 94 }

bcms5-cb11-max
	OBJECT-TYPE
	SYNTAX  INTEGER
	ACCESS  read-only
	STATUS  mandatory
	DESCRIPTION "CB11 Max"
		::= { bcmsplus5 95 }

bcms5-cb12-max
	OBJECT-TYPE
	SYNTAX  INTEGER
	ACCESS  read-only
	STATUS  mandatory
	DESCRIPTION "CB12 Max"
		::= { bcmsplus5 96 }

bcms5-cb13-max
	OBJECT-TYPE
	SYNTAX  INTEGER
	ACCESS  read-only
	STATUS  mandatory
	DESCRIPTION "CB13 Max"
		::= { bcmsplus5 97 }

bcms5-cb14-max
	OBJECT-TYPE
	SYNTAX  INTEGER
	ACCESS  read-only
	STATUS  mandatory
	DESCRIPTION "CB14 Max"
		::= { bcmsplus5 98 }

bcms5-cb15-max
	OBJECT-TYPE
	SYNTAX  INTEGER
	ACCESS  read-only
	STATUS  mandatory
	DESCRIPTION "CB15 Max"
		::= { bcmsplus5 99 }


bcms5-cb16-max
	OBJECT-TYPE
	SYNTAX  INTEGER
	ACCESS  read-only
	STATUS  mandatory
	DESCRIPTION "CB16 Max"
		::= { bcmsplus5 100 }

bcms5-cb17-max
	OBJECT-TYPE
	SYNTAX  INTEGER
	ACCESS  read-only
	STATUS  mandatory
	DESCRIPTION "CB17 Max"
		::= { bcmsplus5 101 }
  
bcms5-cb18-max
	OBJECT-TYPE
	SYNTAX  INTEGER
	ACCESS  read-only
	STATUS  mandatory
	DESCRIPTION "CB18 Max"
		::= { bcmsplus5 102 }

bcms5-cb19-max
	OBJECT-TYPE
	SYNTAX  INTEGER
	ACCESS  read-only
	STATUS  mandatory
	DESCRIPTION "CB19 Max"
		::= { bcmsplus5 103 }

bcms5-cb20-max
	OBJECT-TYPE
	SYNTAX  INTEGER
	ACCESS  read-only
	STATUS  mandatory
	DESCRIPTION "CB20 Max"
		::= { bcmsplus5 104 }

bcms5-cb21-max
	OBJECT-TYPE
	SYNTAX  INTEGER
	ACCESS  read-only
	STATUS  mandatory
	DESCRIPTION "CB21 Max"
		::= { bcmsplus5 105 }

bcms5-cb22-max
	OBJECT-TYPE
	SYNTAX  INTEGER
	ACCESS  read-only
	STATUS  mandatory
	DESCRIPTION "CB22 Max"
		::= { bcmsplus5 106 }

bcms5-cb23-max
	OBJECT-TYPE
	SYNTAX  INTEGER
	ACCESS  read-only
	STATUS  mandatory
	DESCRIPTION "CB23 Max"
		::= { bcmsplus5 107 }

bcms5-cb24-max
	OBJECT-TYPE
	SYNTAX  INTEGER
	ACCESS  read-only
	STATUS  mandatory
	DESCRIPTION "CB24 Max"
		::= { bcmsplus5 108 }

bcms5-cb25-max
	OBJECT-TYPE
	SYNTAX  INTEGER
	ACCESS  read-only
	STATUS  mandatory
	DESCRIPTION "CB25 Max"
		::= { bcmsplus5 109 }

bcms5-cb26-max
	OBJECT-TYPE
	SYNTAX  INTEGER
	ACCESS  read-only
	STATUS  mandatory
	DESCRIPTION "CB26 Max"
		::= { bcmsplus5 110 }

bcms5-cb27-max
	OBJECT-TYPE
	SYNTAX  INTEGER
	ACCESS  read-only
	STATUS  mandatory
	DESCRIPTION "CB27 Max"
		::= { bcmsplus5 111 }
  
bcms5-cb28-max
	OBJECT-TYPE
	SYNTAX  INTEGER
	ACCESS  read-only
	STATUS  mandatory
	DESCRIPTION "CB28 Max"
		::= { bcmsplus5 112 }

bcms5-cb29-max
	OBJECT-TYPE
	SYNTAX  INTEGER
	ACCESS  read-only
	STATUS  mandatory
	DESCRIPTION "CB29 Max"
		::= { bcmsplus5 113 }

bcms5-cb30-max
	OBJECT-TYPE
	SYNTAX  INTEGER
	ACCESS  read-only
	STATUS  mandatory
	DESCRIPTION "CB30 Max"
		::= { bcmsplus5 114 }

bcms5-cb31-max
	OBJECT-TYPE
	SYNTAX  INTEGER
	ACCESS  read-only
	STATUS  mandatory
	DESCRIPTION "CB31 Max"
		::= { bcmsplus5 115 }

bcms5-cb32-max
	OBJECT-TYPE
	SYNTAX  INTEGER
	ACCESS  read-only
	STATUS  mandatory
	DESCRIPTION "CB32 Max"
		::= { bcmsplus5 116 }

bcms5-cb33-max
	OBJECT-TYPE
	SYNTAX  INTEGER
	ACCESS  read-only
	STATUS  mandatory
	DESCRIPTION "CB33 Max"
		::= { bcmsplus5 117 }

bcms5-cb34-max
	OBJECT-TYPE
	SYNTAX  INTEGER
	ACCESS  read-only
	STATUS  mandatory
	DESCRIPTION "CB34 Max"
		::= { bcmsplus5 118 }

bcms5-cb35-max
	OBJECT-TYPE
	SYNTAX  INTEGER
	ACCESS  read-only
	STATUS  mandatory
	DESCRIPTION "CB35 Max"
		::= { bcmsplus5 119 }

bcms5-cb36-max
	OBJECT-TYPE
	SYNTAX  INTEGER
	ACCESS  read-only
	STATUS  mandatory
	DESCRIPTION "CB36 Max"
		::= { bcmsplus5 120 }

bcms5-cb37-max
	OBJECT-TYPE
	SYNTAX  INTEGER
	ACCESS  read-only
	STATUS  mandatory
	DESCRIPTION "CB37 Max"
		::= { bcmsplus5 121 }
  
bcms5-cb38-max
	OBJECT-TYPE
	SYNTAX  INTEGER
	ACCESS  read-only
	STATUS  mandatory
	DESCRIPTION "CB38 Max"
		::= { bcmsplus5 122 }

bcms5-cb39-max
	OBJECT-TYPE
	SYNTAX  INTEGER
	ACCESS  read-only
	STATUS  mandatory
	DESCRIPTION "CB39 Max"
		::= { bcmsplus5 123 }

bcms5-cb40-max
	OBJECT-TYPE
	SYNTAX  INTEGER
	ACCESS  read-only
	STATUS  mandatory
	DESCRIPTION "CB40 Max"
		::= { bcmsplus5 124 }

bcms5-cb41-max
	OBJECT-TYPE
	SYNTAX  INTEGER
	ACCESS  read-only
	STATUS  mandatory
	DESCRIPTION "CB41 Max"
		::= { bcmsplus5 125 }

bcms5-cb42-max
	OBJECT-TYPE
	SYNTAX  INTEGER
	ACCESS  read-only
	STATUS  mandatory
	DESCRIPTION "CB42 Max"
		::= { bcmsplus5 126 }

bcms5-cb1-16-zero
	OBJECT-TYPE
	SYNTAX  INTEGER
	ACCESS  read-write
	STATUS  mandatory
	DESCRIPTION "CB1-16 Zero
		       Bit 0 = CB1
                   Bit 15 = CB16"
		::= { bcmsplus5 127 }

bcms5-cb17-32-zero
	OBJECT-TYPE
	SYNTAX  INTEGER
	ACCESS  read-write
	STATUS  mandatory
	DESCRIPTION "CB17-32 Zero
		       Bit 0 = CB17
                   Bit 15 = CB32"
		::= { bcmsplus5 128 }

bcms5-cb33-42-zero
	OBJECT-TYPE
	SYNTAX  INTEGER
	ACCESS  read-write
	STATUS  mandatory
	DESCRIPTION "CB33-42 Zero
		       Bit 0 = CB33
                   Bit 9 = CB42
                   Bits 10-25 not used"
		::= { bcmsplus5 129 }

bcms5-cb1-16-warning
	OBJECT-TYPE
	SYNTAX  INTEGER
	ACCESS  read-write
	STATUS  mandatory
	DESCRIPTION "CB1-16 Warning
		       Bit 0 = CB1
                   Bit 15 = CB16"
		::= { bcmsplus5 130 }

bcms5-cb17-32-warning
	OBJECT-TYPE
	SYNTAX  INTEGER
	ACCESS  read-write
	STATUS  mandatory
	DESCRIPTION "CB17-32 Warning
		       Bit 0 = CB17
                   Bit 15 = CB32"
		::= { bcmsplus5 131 }
  
bcms5-cb33-42-warning
	OBJECT-TYPE
	SYNTAX  INTEGER
	ACCESS  read-write
	STATUS  mandatory
	DESCRIPTION "CB33-42 Warning
		       Bit 0 = CB33
                   Bit 9 = CB42
                   Bits 10-25 not used"
		::= { bcmsplus5 132 }

bcms5-cb1-16-alarm
	OBJECT-TYPE
	SYNTAX  INTEGER
	ACCESS  read-write
	STATUS  mandatory
	DESCRIPTION "CB1-16 Alarm
		       Bit 0 = CB1
                   Bit 15 = CB16"
		::= { bcmsplus5 133 }

bcms5-cb17-32-alarm
	OBJECT-TYPE
	SYNTAX  INTEGER
	ACCESS  read-write
	STATUS  mandatory
	DESCRIPTION "CB17-32 Alarm
		       Bit 0 = CB17
                   Bit 15 = CB32"
		::= { bcmsplus5 134 }

bcms5-cb33-42-alarm
	OBJECT-TYPE
	SYNTAX  INTEGER
	ACCESS  read-write
	STATUS  mandatory
	DESCRIPTION "CB33-42 Alarm
		       Bit 0 = CB33
                   Bit 9 = CB42
                   Bits 10-25 not used"
		::= { bcmsplus5 135 }

bcms5-cb1-breaker-size
	OBJECT-TYPE
	SYNTAX  INTEGER
	ACCESS  read-write
	STATUS  mandatory
	DESCRIPTION "CB1 Breaker-Size
		     Note for all breaker sizes 1-42: 10 = 10 amps
                     Range is 10 to 100 amps"
		::= { bcmsplus5 136 }

bcms5-cb2-breaker-size
	OBJECT-TYPE
	SYNTAX  INTEGER
	ACCESS  read-write
	STATUS  mandatory
	DESCRIPTION "CB2 Breaker-Size"
		::= { bcmsplus5 137 }

bcms5-cb3-breaker-size
	OBJECT-TYPE
	SYNTAX  INTEGER
	ACCESS  read-write
	STATUS  mandatory
	DESCRIPTION "CB3 Breaker-Size"
		::= { bcmsplus5 138 }

bcms5-cb4-breaker-size
	OBJECT-TYPE
	SYNTAX  INTEGER
	ACCESS  read-write
	STATUS  mandatory
	DESCRIPTION "CB4 Breaker-Size"
		::= { bcmsplus5 139 }

bcms5-cb5-breaker-size
	OBJECT-TYPE
	SYNTAX  INTEGER
	ACCESS  read-write
	STATUS  mandatory
	DESCRIPTION "CB5 Breaker-Size"
		::= { bcmsplus5 140 }

bcms5-cb6-breaker-size
	OBJECT-TYPE
	SYNTAX  INTEGER
	ACCESS  read-write
	STATUS  mandatory
	DESCRIPTION "CB6 Breaker-Size"
		::= { bcmsplus5 141 }
  
bcms5-cb7-breaker-size
	OBJECT-TYPE
	SYNTAX  INTEGER
	ACCESS  read-write
	STATUS  mandatory
	DESCRIPTION "CB7 Breaker-Size"
		::= { bcmsplus5 142 }

bcms5-cb8-breaker-size
	OBJECT-TYPE
	SYNTAX  INTEGER
	ACCESS  read-write
	STATUS  mandatory
	DESCRIPTION "CB8 Breaker-Size"
		::= { bcmsplus5 143 }

bcms5-cb9-breaker-size
	OBJECT-TYPE
	SYNTAX  INTEGER
	ACCESS  read-write
	STATUS  mandatory
	DESCRIPTION "CB9 Breaker-Size"
		::= { bcmsplus5 144 }

bcms5-cb10-breaker-size
	OBJECT-TYPE
	SYNTAX  INTEGER
	ACCESS  read-write
	STATUS  mandatory
	DESCRIPTION "CB10 Breaker-Size"
		::= { bcmsplus5 145 }

bcms5-cb11-breaker-size
	OBJECT-TYPE
	SYNTAX  INTEGER
	ACCESS  read-write
	STATUS  mandatory
	DESCRIPTION "CB11 Breaker-Size"
		::= { bcmsplus5 146 }

bcms5-cb12-breaker-size
	OBJECT-TYPE
	SYNTAX  INTEGER
	ACCESS  read-write
	STATUS  mandatory
	DESCRIPTION "CB12 Breaker-Size"
		::= { bcmsplus5 147 }

bcms5-cb13-breaker-size
	OBJECT-TYPE
	SYNTAX  INTEGER
	ACCESS  read-write
	STATUS  mandatory
	DESCRIPTION "CB13 Breaker-Size"
		::= { bcmsplus5 148 }

bcms5-cb14-breaker-size
	OBJECT-TYPE
	SYNTAX  INTEGER
	ACCESS  read-write
	STATUS  mandatory
	DESCRIPTION "CB14 Breaker-Size"
		::= { bcmsplus5 149 }

bcms5-cb15-breaker-size
	OBJECT-TYPE
	SYNTAX  INTEGER
	ACCESS  read-write
	STATUS  mandatory
	DESCRIPTION "CB15 Breaker-Size"
		::= { bcmsplus5 150 }

bcms5-cb16-breaker-size
	OBJECT-TYPE
	SYNTAX  INTEGER
	ACCESS  read-write
	STATUS  mandatory
	DESCRIPTION "CB16 Breaker-Size"
		::= { bcmsplus5 151 }
  
bcms5-cb17-breaker-size
	OBJECT-TYPE
	SYNTAX  INTEGER
	ACCESS  read-write
	STATUS  mandatory
	DESCRIPTION "CB17 Breaker-Size"
		::= { bcmsplus5 152 }

bcms5-cb18-breaker-size
	OBJECT-TYPE
	SYNTAX  INTEGER
	ACCESS  read-write
	STATUS  mandatory
	DESCRIPTION "CB18 Breaker-Size"
		::= { bcmsplus5 153 }

bcms5-cb19-breaker-size
	OBJECT-TYPE
	SYNTAX  INTEGER
	ACCESS  read-write
	STATUS  mandatory
	DESCRIPTION "CB19 Breaker-Size"
		::= { bcmsplus5 154 }

bcms5-cb20-breaker-size
	OBJECT-TYPE
	SYNTAX  INTEGER
	ACCESS  read-write
	STATUS  mandatory
	DESCRIPTION "CB20 Breaker-Size"
		::= { bcmsplus5 155 }

bcms5-cb21-breaker-size
	OBJECT-TYPE
	SYNTAX  INTEGER
	ACCESS  read-write
	STATUS  mandatory
	DESCRIPTION "CB21 Breaker-Size"
		::= { bcmsplus5 156 }

bcms5-cb22-breaker-size
	OBJECT-TYPE
	SYNTAX  INTEGER
	ACCESS  read-write
	STATUS  mandatory
	DESCRIPTION "CB22 Breaker-Size"
		::= { bcmsplus5 157 }

bcms5-cb23-breaker-size
	OBJECT-TYPE
	SYNTAX  INTEGER
	ACCESS  read-write
	STATUS  mandatory
	DESCRIPTION "CB23 Breaker-Size"
		::= { bcmsplus5 158 }

bcms5-cb24-breaker-size
	OBJECT-TYPE
	SYNTAX  INTEGER
	ACCESS  read-write
	STATUS  mandatory
	DESCRIPTION "CB24 Breaker-Size"
		::= { bcmsplus5 159 }

bcms5-cb25-breaker-size
	OBJECT-TYPE
	SYNTAX  INTEGER
	ACCESS  read-write
	STATUS  mandatory
	DESCRIPTION "CB25 Breaker-Size"
		::= { bcmsplus5 160 }

bcms5-cb26-breaker-size
	OBJECT-TYPE
	SYNTAX  INTEGER
	ACCESS  read-write
	STATUS  mandatory
	DESCRIPTION "CB26 Breaker-Size"
		::= { bcmsplus5 161 }
  
bcms5-cb27-breaker-size
	OBJECT-TYPE
	SYNTAX  INTEGER
	ACCESS  read-write
	STATUS  mandatory
	DESCRIPTION "CB27 Breaker-Size"
		::= { bcmsplus5 162 }

bcms5-cb28-breaker-size
	OBJECT-TYPE
	SYNTAX  INTEGER
	ACCESS  read-write
	STATUS  mandatory
	DESCRIPTION "CB28 Breaker-Size"
		::= { bcmsplus5 163 }

bcms5-cb29-breaker-size
	OBJECT-TYPE
	SYNTAX  INTEGER
	ACCESS  read-write
	STATUS  mandatory
	DESCRIPTION "CB29 Breaker-Size"
		::= { bcmsplus5 164 }

bcms5-cb30-breaker-size
	OBJECT-TYPE
	SYNTAX  INTEGER
	ACCESS  read-write
	STATUS  mandatory
	DESCRIPTION "CB30 Breaker-Size"
		::= { bcmsplus5 165 }

bcms5-cb31-breaker-size
	OBJECT-TYPE
	SYNTAX  INTEGER
	ACCESS  read-write
	STATUS  mandatory
	DESCRIPTION "CB31 Breaker-Size"
		::= { bcmsplus5 166 }

bcms5-cb32-breaker-size
	OBJECT-TYPE
	SYNTAX  INTEGER
	ACCESS  read-write
	STATUS  mandatory
	DESCRIPTION "CB32 Breaker-Size"
		::= { bcmsplus5 167 }

bcms5-cb33-breaker-size
	OBJECT-TYPE
	SYNTAX  INTEGER
	ACCESS  read-write
	STATUS  mandatory
	DESCRIPTION "CB33 Breaker-Size"
		::= { bcmsplus5 168 }

bcms5-cb34-breaker-size
	OBJECT-TYPE
	SYNTAX  INTEGER
	ACCESS  read-write
	STATUS  mandatory
	DESCRIPTION "CB34 Breaker-Size"
		::= { bcmsplus5 169 }

bcms5-cb35-breaker-size
	OBJECT-TYPE
	SYNTAX  INTEGER
	ACCESS  read-write
	STATUS  mandatory
	DESCRIPTION "CB35 Breaker-Size"
		::= { bcmsplus5 170 }

bcms5-cb36-breaker-size
	OBJECT-TYPE
	SYNTAX  INTEGER
	ACCESS  read-write
	STATUS  mandatory
	DESCRIPTION "CB36 Breaker-Size"
		::= { bcmsplus5 171 }
  
bcms5-cb37-breaker-size
	OBJECT-TYPE
	SYNTAX  INTEGER
	ACCESS  read-write
	STATUS  mandatory
	DESCRIPTION "CB37 Breaker-Size"
		::= { bcmsplus5 172 }

bcms5-cb38-breaker-size
	OBJECT-TYPE
	SYNTAX  INTEGER
	ACCESS  read-write
	STATUS  mandatory
	DESCRIPTION "CB38 Breaker-Size"
		::= { bcmsplus5 173 }

bcms5-cb39-breaker-size
	OBJECT-TYPE
	SYNTAX  INTEGER
	ACCESS  read-write
	STATUS  mandatory
	DESCRIPTION "CB39 Breaker-Size"
		::= { bcmsplus5 174 }

bcms5-cb40-breaker-size
	OBJECT-TYPE
	SYNTAX  INTEGER
	ACCESS  read-write
	STATUS  mandatory
	DESCRIPTION "CB40 Breaker-Size"
		::= { bcmsplus5 175 }

bcms5-cb41-breaker-size
	OBJECT-TYPE
	SYNTAX  INTEGER
	ACCESS  read-write
	STATUS  mandatory
	DESCRIPTION "CB41 Breaker-Size"
		::= { bcmsplus5 176 }

bcms5-cb42-breaker-size
	OBJECT-TYPE
	SYNTAX  INTEGER
	ACCESS  read-write
	STATUS  mandatory
	DESCRIPTION "CB42 Breaker-Size"
		::= { bcmsplus5 177 }

bcms5-cb1-warning-threshold
	OBJECT-TYPE
	SYNTAX  INTEGER
	ACCESS  read-write
	STATUS  mandatory
	DESCRIPTION "CB1 CB1-warning-threshold
		     Note for all warning thresholds 1-42: 70 = 70% of breaker size
                     range is 0-100%"
		::= { bcmsplus5 178 }

bcms5-cb2-warning-threshold
	OBJECT-TYPE
	SYNTAX  INTEGER
	ACCESS  read-write
	STATUS  mandatory
	DESCRIPTION "CB2 Warning-Threshold"
		::= { bcmsplus5 179 }

bcms5-cb3-warning-threshold
	OBJECT-TYPE
	SYNTAX  INTEGER
	ACCESS  read-write
	STATUS  mandatory
	DESCRIPTION "CB3 Warning-Threshold"
		::= { bcmsplus5 180 }

bcms5-cb4-warning-threshold
	OBJECT-TYPE
	SYNTAX  INTEGER
	ACCESS  read-write
	STATUS  mandatory
	DESCRIPTION "CB4 Warning-Threshold"
		::= { bcmsplus5 181 }
  
bcms5-cb5-warning-threshold
	OBJECT-TYPE
	SYNTAX  INTEGER
	ACCESS  read-write
	STATUS  mandatory
	DESCRIPTION "CB5 Warning-Threshold"
		::= { bcmsplus5 182 }

bcms5-cb6-warning-threshold
	OBJECT-TYPE
	SYNTAX  INTEGER
	ACCESS  read-write
	STATUS  mandatory
	DESCRIPTION "CB6 Warning-Threshold"
		::= { bcmsplus5 183 }

bcms5-cb7-warning-threshold
	OBJECT-TYPE
	SYNTAX  INTEGER
	ACCESS  read-write
	STATUS  mandatory
	DESCRIPTION "CB7 Warning-Threshold"
		::= { bcmsplus5 184 }

bcms5-cb8-warning-threshold
	OBJECT-TYPE
	SYNTAX  INTEGER
	ACCESS  read-write
	STATUS  mandatory
	DESCRIPTION "CB8 Warning-Threshold"
		::= { bcmsplus5 185 }

bcms5-cb9-warning-threshold
	OBJECT-TYPE
	SYNTAX  INTEGER
	ACCESS  read-write
	STATUS  mandatory
	DESCRIPTION "CB9 Warning-Threshold"
		::= { bcmsplus5 186 }

bcms5-cb10-warning-threshold
	OBJECT-TYPE
	SYNTAX  INTEGER
	ACCESS  read-write
	STATUS  mandatory
	DESCRIPTION "CB10 Warning-Threshold"
		::= { bcmsplus5 187 }

bcms5-cb11-warning-threshold
	OBJECT-TYPE
	SYNTAX  INTEGER
	ACCESS  read-write
	STATUS  mandatory
	DESCRIPTION "CB11 Warning-Threshold"
		::= { bcmsplus5 188 }

bcms5-cb12-warning-threshold
	OBJECT-TYPE
	SYNTAX  INTEGER
	ACCESS  read-write
	STATUS  mandatory
	DESCRIPTION "CB12 Warning-Threshold"
		::= { bcmsplus5 189 }

bcms5-cb13-warning-threshold
	OBJECT-TYPE
	SYNTAX  INTEGER
	ACCESS  read-write
	STATUS  mandatory
	DESCRIPTION "CB13 Warning-Threshold"
		::= { bcmsplus5 190 }

bcms5-cb14-warning-threshold
	OBJECT-TYPE
	SYNTAX  INTEGER
	ACCESS  read-write
	STATUS  mandatory
	DESCRIPTION "CB14 Warning-Threshold"
		::= { bcmsplus5 191 }
  
bcms5-cb15-warning-threshold
	OBJECT-TYPE
	SYNTAX  INTEGER
	ACCESS  read-write
	STATUS  mandatory
	DESCRIPTION "CB15 Warning-Threshold"
		::= { bcmsplus5 192 }

bcms5-cb16-warning-threshold
	OBJECT-TYPE
	SYNTAX  INTEGER
	ACCESS  read-write
	STATUS  mandatory
	DESCRIPTION "CB16 Warning-Threshold"
		::= { bcmsplus5 193 }

bcms5-cb17-warning-threshold
	OBJECT-TYPE
	SYNTAX  INTEGER
	ACCESS  read-write
	STATUS  mandatory
	DESCRIPTION "CB17 Warning-Threshold"
		::= { bcmsplus5 194 }

bcms5-cb18-warning-threshold
	OBJECT-TYPE
	SYNTAX  INTEGER
	ACCESS  read-write
	STATUS  mandatory
	DESCRIPTION "CB18 Warning-Threshold"
		::= { bcmsplus5 195 }

bcms5-cb19-warning-threshold
	OBJECT-TYPE
	SYNTAX  INTEGER
	ACCESS  read-write
	STATUS  mandatory
	DESCRIPTION "CB19 Warning-Threshold"
		::= { bcmsplus5 196 }

bcms5-cb20-warning-threshold
	OBJECT-TYPE
	SYNTAX  INTEGER
	ACCESS  read-write
	STATUS  mandatory
	DESCRIPTION "CB20 Warning-Threshold"
		::= { bcmsplus5 197 }

bcms5-cb21-warning-threshold
	OBJECT-TYPE
	SYNTAX  INTEGER
	ACCESS  read-write
	STATUS  mandatory
	DESCRIPTION "CB21 Warning-Threshold"
		::= { bcmsplus5 198 }

bcms5-cb22-warning-threshold
	OBJECT-TYPE
	SYNTAX  INTEGER
	ACCESS  read-write
	STATUS  mandatory
	DESCRIPTION "CB22 Warning-Threshold"
		::= { bcmsplus5 199 }

bcms5-cb23-warning-threshold
	OBJECT-TYPE
	SYNTAX  INTEGER
	ACCESS  read-write
	STATUS  mandatory
	DESCRIPTION "CB23 Warning-Threshold"
		::= { bcmsplus5 200 }

bcms5-cb24-warning-threshold
	OBJECT-TYPE
	SYNTAX  INTEGER
	ACCESS  read-write
	STATUS  mandatory
	DESCRIPTION "CB24 Warning-Threshold"
		::= { bcmsplus5 201 }
  
bcms5-cb25-warning-threshold
	OBJECT-TYPE
	SYNTAX  INTEGER
	ACCESS  read-write
	STATUS  mandatory
	DESCRIPTION "CB25 Warning-Threshold"
		::= { bcmsplus5 202 }

bcms5-cb26-warning-threshold
	OBJECT-TYPE
	SYNTAX  INTEGER
	ACCESS  read-write
	STATUS  mandatory
	DESCRIPTION "CB26 Warning-Threshold"
		::= { bcmsplus5 203 }

bcms5-cb27-warning-threshold
	OBJECT-TYPE
	SYNTAX  INTEGER
	ACCESS  read-write
	STATUS  mandatory
	DESCRIPTION "CB27 Warning-Threshold"
		::= { bcmsplus5 204 }

bcms5-cb28-warning-threshold
	OBJECT-TYPE
	SYNTAX  INTEGER
	ACCESS  read-write
	STATUS  mandatory
	DESCRIPTION "CB28 Warning-Threshold"
		::= { bcmsplus5 205 }

bcms5-cb29-warning-threshold
	OBJECT-TYPE
	SYNTAX  INTEGER
	ACCESS  read-write
	STATUS  mandatory
	DESCRIPTION "CB29 Warning-Threshold"
		::= { bcmsplus5 206 }

bcms5-cb30-warning-threshold
	OBJECT-TYPE
	SYNTAX  INTEGER
	ACCESS  read-write
	STATUS  mandatory
	DESCRIPTION "CB30 Warning-Threshold"
		::= { bcmsplus5 207 }

bcms5-cb31-warning-threshold
	OBJECT-TYPE
	SYNTAX  INTEGER
	ACCESS  read-write
	STATUS  mandatory
	DESCRIPTION "CB31 Warning-Threshold"
		::= { bcmsplus5 208 }

bcms5-cb32-warning-threshold
	OBJECT-TYPE
	SYNTAX  INTEGER
	ACCESS  read-write
	STATUS  mandatory
	DESCRIPTION "CB32 Warning-Threshold"
		::= { bcmsplus5 209 }

bcms5-cb33-warning-threshold
	OBJECT-TYPE
	SYNTAX  INTEGER
	ACCESS  read-write
	STATUS  mandatory
	DESCRIPTION "CB33 Warning-Threshold"
		::= { bcmsplus5 210 }

bcms5-cb34-warning-threshold
	OBJECT-TYPE
	SYNTAX  INTEGER
	ACCESS  read-write
	STATUS  mandatory
	DESCRIPTION "CB34 Warning-Threshold"
		::= { bcmsplus5 211 }
  
bcms5-cb35-warning-threshold
	OBJECT-TYPE
	SYNTAX  INTEGER
	ACCESS  read-write
	STATUS  mandatory
	DESCRIPTION "CB35 Warning-Threshold"
		::= { bcmsplus5 212 }

bcms5-cb36-warning-threshold
	OBJECT-TYPE
	SYNTAX  INTEGER
	ACCESS  read-write
	STATUS  mandatory
	DESCRIPTION "CB36 Warning-Threshold"
		::= { bcmsplus5 213 }

bcms5-cb37-warning-threshold
	OBJECT-TYPE
	SYNTAX  INTEGER
	ACCESS  read-write
	STATUS  mandatory
	DESCRIPTION "CB37 Warning-Threshold"
		::= { bcmsplus5 214 }

bcms5-cb38-warning-threshold
	OBJECT-TYPE
	SYNTAX  INTEGER
	ACCESS  read-write
	STATUS  mandatory
	DESCRIPTION "CB38 Warning-Threshold"
		::= { bcmsplus5 215 }

bcms5-cb39-warning-threshold
	OBJECT-TYPE
	SYNTAX  INTEGER
	ACCESS  read-write
	STATUS  mandatory
	DESCRIPTION "CB39 Warning-Threshold"
		::= { bcmsplus5 216 }

bcms5-cb40-warning-threshold
	OBJECT-TYPE
	SYNTAX  INTEGER
	ACCESS  read-write
	STATUS  mandatory
	DESCRIPTION "CB40 Warning-Threshold"
		::= { bcmsplus5 217 }

bcms5-cb41-warning-threshold
	OBJECT-TYPE
	SYNTAX  INTEGER
	ACCESS  read-write
	STATUS  mandatory
	DESCRIPTION "CB41 Warning-Threshold"
		::= { bcmsplus5 218 }

bcms5-cb42-warning-threshold
	OBJECT-TYPE
	SYNTAX  INTEGER
	ACCESS  read-write
	STATUS  mandatory
	DESCRIPTION "CB42 Warning-Threshold"
		::= { bcmsplus5 219 }

bcms5-cb1-alarm-threshold
	OBJECT-TYPE
	SYNTAX  INTEGER
	ACCESS  read-write
	STATUS  mandatory
	DESCRIPTION "CB1 Alarm-Threshold
		     Note for all alarm thresholds 1-42: 80 = 80% of breaker size
                     range is 0-100%"
		::= { bcmsplus5 220 }


bcms5-cb2-alarm-threshold
	OBJECT-TYPE
	SYNTAX  INTEGER
	ACCESS  read-write
	STATUS  mandatory
	DESCRIPTION "CB2 Alarm-Threshold"
		::= { bcmsplus5 221 }
  
bcms5-cb3-alarm-threshold
	OBJECT-TYPE
	SYNTAX  INTEGER
	ACCESS  read-write
	STATUS  mandatory
	DESCRIPTION "CB3 Alarm-Threshold"
		::= { bcmsplus5 222 }

bcms5-cb4-alarm-threshold
	OBJECT-TYPE
	SYNTAX  INTEGER
	ACCESS  read-write
	STATUS  mandatory
	DESCRIPTION "CB4 Alarm-Threshold"
		::= { bcmsplus5 223 }

bcms5-cb5-alarm-threshold
	OBJECT-TYPE
	SYNTAX  INTEGER
	ACCESS  read-write
	STATUS  mandatory
	DESCRIPTION "CB5 Alarm-Threshold"
		::= { bcmsplus5 224 }

bcms5-cb6-alarm-threshold
	OBJECT-TYPE
	SYNTAX  INTEGER
	ACCESS  read-write
	STATUS  mandatory
	DESCRIPTION "CB6 Alarm-Threshold"
		::= { bcmsplus5 225 }

bcms5-cb7-alarm-threshold
	OBJECT-TYPE
	SYNTAX  INTEGER
	ACCESS  read-write
	STATUS  mandatory
	DESCRIPTION "CB7 Alarm-Threshold"
		::= { bcmsplus5 226 }

bcms5-cb8-alarm-threshold
	OBJECT-TYPE
	SYNTAX  INTEGER
	ACCESS  read-write
	STATUS  mandatory
	DESCRIPTION "CB8 Alarm-Threshold"
		::= { bcmsplus5 227 }

bcms5-cb9-alarm-threshold
	OBJECT-TYPE
	SYNTAX  INTEGER
	ACCESS  read-write
	STATUS  mandatory
	DESCRIPTION "CB9 Alarm-Threshold"
		::= { bcmsplus5 228 }

bcms5-cb10-alarm-threshold
	OBJECT-TYPE
	SYNTAX  INTEGER
	ACCESS  read-write
	STATUS  mandatory
	DESCRIPTION "CB10 Alarm-Threshold"
		::= { bcmsplus5 229 }

bcms5-cb11-alarm-threshold
	OBJECT-TYPE
	SYNTAX  INTEGER
	ACCESS  read-write
	STATUS  mandatory
	DESCRIPTION "CB11 Alarm-Threshold"
		::= { bcmsplus5 230 }

bcms5-cb12-alarm-threshold
	OBJECT-TYPE
	SYNTAX  INTEGER
	ACCESS  read-write
	STATUS  mandatory
	DESCRIPTION "CB12 Alarm-Threshold"
		::= { bcmsplus5 231 }
  
bcms5-cb13-alarm-threshold
	OBJECT-TYPE
	SYNTAX  INTEGER
	ACCESS  read-write
	STATUS  mandatory
	DESCRIPTION "CB13 Alarm-Threshold"
		::= { bcmsplus5 232 }

bcms5-cb14-alarm-threshold
	OBJECT-TYPE
	SYNTAX  INTEGER
	ACCESS  read-write
	STATUS  mandatory
	DESCRIPTION "CB14 Alarm-Threshold"
		::= { bcmsplus5 233 }

bcms5-cb15-alarm-threshold
	OBJECT-TYPE
	SYNTAX  INTEGER
	ACCESS  read-write
	STATUS  mandatory
	DESCRIPTION "CB15 Alarm-Threshold"
		::= { bcmsplus5 234 }

bcms5-cb16-alarm-threshold
	OBJECT-TYPE
	SYNTAX  INTEGER
	ACCESS  read-write
	STATUS  mandatory
	DESCRIPTION "CB16 Alarm-Threshold"
		::= { bcmsplus5 235 }

bcms5-cb17-alarm-threshold
	OBJECT-TYPE
	SYNTAX  INTEGER
	ACCESS  read-write
	STATUS  mandatory
	DESCRIPTION "CB17 Alarm-Threshold"
		::= { bcmsplus5 236 }

bcms5-cb18-alarm-threshold
	OBJECT-TYPE
	SYNTAX  INTEGER
	ACCESS  read-write
	STATUS  mandatory
	DESCRIPTION "CB18 Alarm-Threshold"
		::= { bcmsplus5 237 }

bcms5-cb19-alarm-threshold
	OBJECT-TYPE
	SYNTAX  INTEGER
	ACCESS  read-write
	STATUS  mandatory
	DESCRIPTION "CB19 Alarm-Threshold"
		::= { bcmsplus5 238 }

bcms5-cb20-alarm-threshold
	OBJECT-TYPE
	SYNTAX  INTEGER
	ACCESS  read-write
	STATUS  mandatory
	DESCRIPTION "CB20 Alarm-Threshold"
		::= { bcmsplus5 239 }

bcms5-cb21-alarm-threshold
	OBJECT-TYPE
	SYNTAX  INTEGER
	ACCESS  read-write
	STATUS  mandatory
	DESCRIPTION "CB21 Alarm-Threshold"
		::= { bcmsplus5 240 }

bcms5-cb22-alarm-threshold
	OBJECT-TYPE
	SYNTAX  INTEGER
	ACCESS  read-write
	STATUS  mandatory
	DESCRIPTION "CB22 Alarm-Threshold"
		::= { bcmsplus5 241 }
  
bcms5-cb23-alarm-threshold
	OBJECT-TYPE
	SYNTAX  INTEGER
	ACCESS  read-write
	STATUS  mandatory
	DESCRIPTION "CB23 Alarm-Threshold"
		::= { bcmsplus5 242 }

bcms5-cb24-alarm-threshold
	OBJECT-TYPE
	SYNTAX  INTEGER
	ACCESS  read-write
	STATUS  mandatory
	DESCRIPTION "CB24 Alarm-Threshold"
		::= { bcmsplus5 243 }

bcms5-cb25-alarm-threshold
	OBJECT-TYPE
	SYNTAX  INTEGER
	ACCESS  read-write
	STATUS  mandatory
	DESCRIPTION "CB25 Alarm-Threshold"
		::= { bcmsplus5 244 }

bcms5-cb26-alarm-threshold
	OBJECT-TYPE
	SYNTAX  INTEGER
	ACCESS  read-write
	STATUS  mandatory
	DESCRIPTION "CB26 Alarm-Threshold"
		::= { bcmsplus5 245 }

bcms5-cb27-alarm-threshold
	OBJECT-TYPE
	SYNTAX  INTEGER
	ACCESS  read-write
	STATUS  mandatory
	DESCRIPTION "CB27 Alarm-Threshold"
		::= { bcmsplus5 246 }

bcms5-cb28-alarm-threshold
	OBJECT-TYPE
	SYNTAX  INTEGER
	ACCESS  read-write
	STATUS  mandatory
	DESCRIPTION "CB28 Alarm-Threshold"
		::= { bcmsplus5 247 }

bcms5-cb29-alarm-threshold
	OBJECT-TYPE
	SYNTAX  INTEGER
	ACCESS  read-write
	STATUS  mandatory
	DESCRIPTION "CB29 Alarm-Threshold"
		::= { bcmsplus5 248 }

bcms5-cb30-alarm-threshold
	OBJECT-TYPE
	SYNTAX  INTEGER
	ACCESS  read-write
	STATUS  mandatory
	DESCRIPTION "CB30 Alarm-Threshold"
		::= { bcmsplus5 249 }

bcms5-cb31-alarm-threshold
	OBJECT-TYPE
	SYNTAX  INTEGER
	ACCESS  read-write
	STATUS  mandatory
	DESCRIPTION "CB31 Alarm-Threshold"
		::= { bcmsplus5 250 }

bcms5-cb32-alarm-threshold
	OBJECT-TYPE
	SYNTAX  INTEGER
	ACCESS  read-write
	STATUS  mandatory
	DESCRIPTION "CB32 Alarm-Threshold"
		::= { bcmsplus5 251 }
  
bcms5-cb33-alarm-threshold
	OBJECT-TYPE
	SYNTAX  INTEGER
	ACCESS  read-write
	STATUS  mandatory
	DESCRIPTION "CB33 Alarm-Threshold"
		::= { bcmsplus5 252 }

bcms5-cb34-alarm-threshold
	OBJECT-TYPE
	SYNTAX  INTEGER
	ACCESS  read-write
	STATUS  mandatory
	DESCRIPTION "CB34 Alarm-Threshold"
		::= { bcmsplus5 253 }

bcms5-cb35-alarm-threshold
	OBJECT-TYPE
	SYNTAX  INTEGER
	ACCESS  read-write
	STATUS  mandatory
	DESCRIPTION "CB35 Alarm-Threshold"
		::= { bcmsplus5 254 }

bcms5-cb36-alarm-threshold
	OBJECT-TYPE
	SYNTAX  INTEGER
	ACCESS  read-write
	STATUS  mandatory
	DESCRIPTION "CB36 Alarm-Threshold"
		::= { bcmsplus5 255 }

bcms5-cb37-alarm-threshold
	OBJECT-TYPE
	SYNTAX  INTEGER
	ACCESS  read-write
	STATUS  mandatory
	DESCRIPTION "CB37 Alarm-Threshold"
		::= { bcmsplus5 256 }

bcms5-cb38-alarm-threshold
	OBJECT-TYPE
	SYNTAX  INTEGER
	ACCESS  read-write
	STATUS  mandatory
	DESCRIPTION "CB38 Alarm-Threshold"
		::= { bcmsplus5 257 }

bcms5-cb39-alarm-threshold
	OBJECT-TYPE
	SYNTAX  INTEGER
	ACCESS  read-write
	STATUS  mandatory
	DESCRIPTION "CB39 Alarm-Threshold"
		::= { bcmsplus5 258 }

bcms5-cb40-alarm-threshold
	OBJECT-TYPE
	SYNTAX  INTEGER
	ACCESS  read-write
	STATUS  mandatory
	DESCRIPTION "CB40 Alarm-Threshold"
		::= { bcmsplus5 259 }

bcms5-cb41-alarm-threshold
	OBJECT-TYPE
	SYNTAX  INTEGER
	ACCESS  read-write
	STATUS  mandatory
	DESCRIPTION "CB41 Alarm-Threshold"
		::= { bcmsplus5 260 }

bcms5-cb42-alarm-threshold
	OBJECT-TYPE
	SYNTAX  INTEGER
	ACCESS  read-write
	STATUS  mandatory
	DESCRIPTION "CB42 Alarm-Threshold"
		::= { bcmsplus5 261 }

bcms5-cb1-warning-time-delay
	OBJECT-TYPE
	SYNTAX  INTEGER
	ACCESS  read-write
	STATUS  mandatory
	DESCRIPTION "CB1 Warning-Time-Delay
		     Note for all warning time delays 1-42: units are in seconds"                     
		::= { bcmsplus5 262 }

bcms5-cb2-warning-time-delay
	OBJECT-TYPE
	SYNTAX  INTEGER
	ACCESS  read-write
	STATUS  mandatory
	DESCRIPTION "CB2 Warning-Time-Delay"
		::= { bcmsplus5 263 }
  
bcms5-cb3-warning-time-delay
	OBJECT-TYPE
	SYNTAX  INTEGER
	ACCESS  read-write
	STATUS  mandatory
	DESCRIPTION "CB3 Warning-Time-Delay"
		::= { bcmsplus5 264 }

bcms5-cb4-warning-time-delay
	OBJECT-TYPE
	SYNTAX  INTEGER
	ACCESS  read-write
	STATUS  mandatory
	DESCRIPTION "CB4 Warning-Time-Delay"
		::= { bcmsplus5 265 }

bcms5-cb5-warning-time-delay
	OBJECT-TYPE
	SYNTAX  INTEGER
	ACCESS  read-write
	STATUS  mandatory
	DESCRIPTION "CB5 Warning-Time-Delay"
		::= { bcmsplus5 266 }

bcms5-cb6-warning-time-delay
	OBJECT-TYPE
	SYNTAX  INTEGER
	ACCESS  read-write
	STATUS  mandatory
	DESCRIPTION "CB6 Warning-Time-Delay"
		::= { bcmsplus5 267 }

bcms5-cb7-warning-time-delay
	OBJECT-TYPE
	SYNTAX  INTEGER
	ACCESS  read-write
	STATUS  mandatory
	DESCRIPTION "CB7 Warning-Time-Delay"
		::= { bcmsplus5 268 }

bcms5-cb8-warning-time-delay
	OBJECT-TYPE
	SYNTAX  INTEGER
	ACCESS  read-write
	STATUS  mandatory
	DESCRIPTION "CB8 Warning-Time-Delay"
		::= { bcmsplus5 269 }

bcms5-cb9-warning-time-delay
	OBJECT-TYPE
	SYNTAX  INTEGER
	ACCESS  read-write
	STATUS  mandatory
	DESCRIPTION "CB9 Warning-Time-Delay"
		::= { bcmsplus5 270 }

bcms5-cb10-warning-time-delay
	OBJECT-TYPE
	SYNTAX  INTEGER
	ACCESS  read-write
	STATUS  mandatory
	DESCRIPTION "CB10 Warning-Time-Delay"
		::= { bcmsplus5 271 }

bcms5-cb11-warning-time-delay
	OBJECT-TYPE
	SYNTAX  INTEGER
	ACCESS  read-write
	STATUS  mandatory
	DESCRIPTION "CB11 Warning-Time-Delay"
		::= { bcmsplus5 272 }

bcms5-cb12-warning-time-delay
	OBJECT-TYPE
	SYNTAX  INTEGER
	ACCESS  read-write
	STATUS  mandatory
	DESCRIPTION "CB12 Warning-Time-Delay"
		::= { bcmsplus5 273 }
  
bcms5-cb13-warning-time-delay
	OBJECT-TYPE
	SYNTAX  INTEGER
	ACCESS  read-write
	STATUS  mandatory
	DESCRIPTION "CB13 Warning-Time-Delay"
		::= { bcmsplus5 274 }

bcms5-cb14-warning-time-delay
	OBJECT-TYPE
	SYNTAX  INTEGER
	ACCESS  read-write
	STATUS  mandatory
	DESCRIPTION "CB14 Warning-Time-Delay"
		::= { bcmsplus5 275 }

bcms5-cb15-warning-time-delay
	OBJECT-TYPE
	SYNTAX  INTEGER
	ACCESS  read-write
	STATUS  mandatory
	DESCRIPTION "CB15 Warning-Time-Delay"
		::= { bcmsplus5 276 }

bcms5-cb16-warning-time-delay
	OBJECT-TYPE
	SYNTAX  INTEGER
	ACCESS  read-write
	STATUS  mandatory
	DESCRIPTION "CB16 Warning-Time-Delay"
		::= { bcmsplus5 277 }

bcms5-cb17-warning-time-delay
	OBJECT-TYPE
	SYNTAX  INTEGER
	ACCESS  read-write
	STATUS  mandatory
	DESCRIPTION "CB17 Warning-Time-Delay"
		::= { bcmsplus5 278 }

bcms5-cb18-warning-time-delay
	OBJECT-TYPE
	SYNTAX  INTEGER
	ACCESS  read-write
	STATUS  mandatory
	DESCRIPTION "CB18 Warning-Time-Delay"
		::= { bcmsplus5 279 }

bcms5-cb19-warning-time-delay
	OBJECT-TYPE
	SYNTAX  INTEGER
	ACCESS  read-write
	STATUS  mandatory
	DESCRIPTION "CB19 Warning-Time-Delay"
		::= { bcmsplus5 280 }

bcms5-cb20-warning-time-delay
	OBJECT-TYPE
	SYNTAX  INTEGER
	ACCESS  read-write
	STATUS  mandatory
	DESCRIPTION "CB20 Warning-Time-Delay"
		::= { bcmsplus5 281 }

bcms5-cb21-warning-time-delay
	OBJECT-TYPE
	SYNTAX  INTEGER
	ACCESS  read-write
	STATUS  mandatory
	DESCRIPTION "CB21 Warning-Time-Delay"
		::= { bcmsplus5 282 }

bcms5-cb22-warning-time-delay
	OBJECT-TYPE
	SYNTAX  INTEGER
	ACCESS  read-write
	STATUS  mandatory
	DESCRIPTION "CB22 Warning-Time-Delay"
		::= { bcmsplus5 283 }
  
bcms5-cb23-warning-time-delay
	OBJECT-TYPE
	SYNTAX  INTEGER
	ACCESS  read-write
	STATUS  mandatory
	DESCRIPTION "CB23 Warning-Time-Delay"
		::= { bcmsplus5 284 }

bcms5-cb24-warning-time-delay
	OBJECT-TYPE
	SYNTAX  INTEGER
	ACCESS  read-write
	STATUS  mandatory
	DESCRIPTION "CB24 Warning-Time-Delay"
		::= { bcmsplus5 285 }

bcms5-cb25-warning-time-delay
	OBJECT-TYPE
	SYNTAX  INTEGER
	ACCESS  read-write
	STATUS  mandatory
	DESCRIPTION "CB25 Warning-Time-Delay"
		::= { bcmsplus5 286 }

bcms5-cb26-warning-time-delay
	OBJECT-TYPE
	SYNTAX  INTEGER
	ACCESS  read-write
	STATUS  mandatory
	DESCRIPTION "CB26 Warning-Time-Delay"
		::= { bcmsplus5 287 }

bcms5-cb27-warning-time-delay
	OBJECT-TYPE
	SYNTAX  INTEGER
	ACCESS  read-write
	STATUS  mandatory
	DESCRIPTION "CB27 Warning-Time-Delay"
		::= { bcmsplus5 288 }

bcms5-cb28-warning-time-delay
	OBJECT-TYPE
	SYNTAX  INTEGER
	ACCESS  read-write
	STATUS  mandatory
	DESCRIPTION "CB28 Warning-Time-Delay"
		::= { bcmsplus5 289 }

bcms5-cb29-warning-time-delay
	OBJECT-TYPE
	SYNTAX  INTEGER
	ACCESS  read-write
	STATUS  mandatory
	DESCRIPTION "CB29 Warning-Time-Delay"
		::= { bcmsplus5 290}

bcms5-cb30-warning-time-delay
	OBJECT-TYPE
	SYNTAX  INTEGER
	ACCESS  read-write
	STATUS  mandatory
	DESCRIPTION "CB30 Warning-Time-Delay"
		::= { bcmsplus5 291 }

bcms5-cb31-warning-time-delay
	OBJECT-TYPE
	SYNTAX  INTEGER
	ACCESS  read-write
	STATUS  mandatory
	DESCRIPTION "CB31 Warning-Time-Delay"
		::= { bcmsplus5 292 }

bcms5-cb32-warning-time-delay
	OBJECT-TYPE
	SYNTAX  INTEGER
	ACCESS  read-write
	STATUS  mandatory
	DESCRIPTION "CB32 Warning-Time-Delay"
		::= { bcmsplus5 293 }
  
bcms5-cb33-warning-time-delay
	OBJECT-TYPE
	SYNTAX  INTEGER
	ACCESS  read-write
	STATUS  mandatory
	DESCRIPTION "CB33 Warning-Time-Delay"
		::= { bcmsplus5 294 }

bcms5-cb34-warning-time-delay
	OBJECT-TYPE
	SYNTAX  INTEGER
	ACCESS  read-write
	STATUS  mandatory
	DESCRIPTION "CB34 Warning-Time-Delay"
		::= { bcmsplus5 295 }

bcms5-cb35-warning-time-delay
	OBJECT-TYPE
	SYNTAX  INTEGER
	ACCESS  read-write
	STATUS  mandatory
	DESCRIPTION "CB35 Warning-Time-Delay"
		::= { bcmsplus5 296 }

bcms5-cb36-warning-time-delay
	OBJECT-TYPE
	SYNTAX  INTEGER
	ACCESS  read-write
	STATUS  mandatory
	DESCRIPTION "CB36 Warning-Time-Delay"
		::= { bcmsplus5 297 }

bcms5-cb37-warning-time-delay
	OBJECT-TYPE
	SYNTAX  INTEGER
	ACCESS  read-write
	STATUS  mandatory
	DESCRIPTION "CB37 Warning-Time-Delay"
		::= { bcmsplus5 298 }

bcms5-cb38-warning-time-delay
	OBJECT-TYPE
	SYNTAX  INTEGER
	ACCESS  read-write
	STATUS  mandatory
	DESCRIPTION "CB38 Warning-Time-Delay"
		::= { bcmsplus5 299 }

bcms5-cb39-warning-time-delay
	OBJECT-TYPE
	SYNTAX  INTEGER
	ACCESS  read-write
	STATUS  mandatory
	DESCRIPTION "CB39 Warning-Time-Delay"
		::= { bcmsplus5 300 }

bcms5-cb40-warning-time-delay
	OBJECT-TYPE
	SYNTAX  INTEGER
	ACCESS  read-write
	STATUS  mandatory
	DESCRIPTION "CB40 Warning-Time-Delay"
		::= { bcmsplus5 301 }

bcms5-cb41-warning-time-delay
	OBJECT-TYPE
	SYNTAX  INTEGER
	ACCESS  read-write
	STATUS  mandatory
	DESCRIPTION "CB41 Warning-Time-Delay"
		::= { bcmsplus5 302 }

bcms5-cb42-warning-time-delay
	OBJECT-TYPE
	SYNTAX  INTEGER
	ACCESS  read-write
	STATUS  mandatory
	DESCRIPTION "CB42 Warning-Time-Delay"
		::= { bcmsplus5 303 }

bcms5-cb1-alarm-time-delay
	OBJECT-TYPE
	SYNTAX  INTEGER
	ACCESS  read-write
	STATUS  mandatory
	DESCRIPTION "CB1 Alarm-Time-Delay
		       Note for all alarm time delays 1-42: units are in seconds"                     
		::= { bcmsplus5 304 }

bcms5-cb2-alarm-time-delay
	OBJECT-TYPE
	SYNTAX  INTEGER
	ACCESS  read-write
	STATUS  mandatory
	DESCRIPTION "CB2 Alarm-Time-Delay"
		::= { bcmsplus5 305 }
  
bcms5-cb3-alarm-time-delay
	OBJECT-TYPE
	SYNTAX  INTEGER
	ACCESS  read-write
	STATUS  mandatory
	DESCRIPTION "CB3 Alarm-Time-Delay"
		::= { bcmsplus5 306 }

bcms5-cb4-alarm-time-delay
	OBJECT-TYPE
	SYNTAX  INTEGER
	ACCESS  read-write
	STATUS  mandatory
	DESCRIPTION "CB4 Alarm-Time-Delay"
		::= { bcmsplus5 307 }

bcms5-cb5-alarm-time-delay
	OBJECT-TYPE
	SYNTAX  INTEGER
	ACCESS  read-write
	STATUS  mandatory
	DESCRIPTION "CB5 Alarm-Time-Delay"
		::= { bcmsplus5 308 }

bcms5-cb6-alarm-time-delay
	OBJECT-TYPE
	SYNTAX  INTEGER
	ACCESS  read-write
	STATUS  mandatory
	DESCRIPTION "CB6 Alarm-Time-Delay"
		::= { bcmsplus5 309 }

bcms5-cb7-alarm-time-delay
	OBJECT-TYPE
	SYNTAX  INTEGER
	ACCESS  read-write
	STATUS  mandatory
	DESCRIPTION "CB7 Alarm-Time-Delay"
		::= { bcmsplus5 310 }

bcms5-cb8-alarm-time-delay
	OBJECT-TYPE
	SYNTAX  INTEGER
	ACCESS  read-write
	STATUS  mandatory
	DESCRIPTION "CB8 Alarm-Time-Delay"
		::= { bcmsplus5 311 }

bcms5-cb9-alarm-time-delay
	OBJECT-TYPE
	SYNTAX  INTEGER
	ACCESS  read-write
	STATUS  mandatory
	DESCRIPTION "CB9 Alarm-Time-Delay"
		::= { bcmsplus5 312 }

bcms5-cb10-alarm-time-delay
	OBJECT-TYPE
	SYNTAX  INTEGER
	ACCESS  read-write
	STATUS  mandatory
	DESCRIPTION "CB10 Alarm-Time-Delay"
		::= { bcmsplus5 313 }

bcms5-cb11-alarm-time-delay
	OBJECT-TYPE
	SYNTAX  INTEGER
	ACCESS  read-write
	STATUS  mandatory
	DESCRIPTION "CB11 Alarm-Time-Delay"
		::= { bcmsplus5 314 }

bcms5-cb12-alarm-time-delay
	OBJECT-TYPE
	SYNTAX  INTEGER
	ACCESS  read-write
	STATUS  mandatory
	DESCRIPTION "CB12 Alarm-Time-Delay"
		::= { bcmsplus5 315 }
  
bcms5-cb13-alarm-time-delay
	OBJECT-TYPE
	SYNTAX  INTEGER
	ACCESS  read-write
	STATUS  mandatory
	DESCRIPTION "CB13 Alarm-Time-Delay"
		::= { bcmsplus5 316 }

bcms5-cb14-alarm-time-delay
	OBJECT-TYPE
	SYNTAX  INTEGER
	ACCESS  read-write
	STATUS  mandatory
	DESCRIPTION "CB14 Alarm-Time-Delay"
		::= { bcmsplus5 317 }

bcms5-cb15-alarm-time-delay
	OBJECT-TYPE
	SYNTAX  INTEGER
	ACCESS  read-write
	STATUS  mandatory
	DESCRIPTION "CB15 Alarm-Time-Delay"
		::= { bcmsplus5 318 }

bcms5-cb16-alarm-time-delay
	OBJECT-TYPE
	SYNTAX  INTEGER
	ACCESS  read-write
	STATUS  mandatory
	DESCRIPTION "CB16 Alarm-Time-Delay"
		::= { bcmsplus5 319 }

bcms5-cb17-alarm-time-delay
	OBJECT-TYPE
	SYNTAX  INTEGER
	ACCESS  read-write
	STATUS  mandatory
	DESCRIPTION "CB17 Alarm-Time-Delay"
		::= { bcmsplus5 320 }

bcms5-cb18-alarm-time-delay
	OBJECT-TYPE
	SYNTAX  INTEGER
	ACCESS  read-write
	STATUS  mandatory
	DESCRIPTION "CB18 Alarm-Time-Delay"
		::= { bcmsplus5 321 }

bcms5-cb19-alarm-time-delay
	OBJECT-TYPE
	SYNTAX  INTEGER
	ACCESS  read-write
	STATUS  mandatory
	DESCRIPTION "CB19 Alarm-Time-Delay"
		::= { bcmsplus5 322 }

bcms5-cb20-alarm-time-delay
	OBJECT-TYPE
	SYNTAX  INTEGER
	ACCESS  read-write
	STATUS  mandatory
	DESCRIPTION "CB20 Alarm-Time-Delay"
		::= { bcmsplus5 323 }

bcms5-cb21-alarm-time-delay
	OBJECT-TYPE
	SYNTAX  INTEGER
	ACCESS  read-write
	STATUS  mandatory
	DESCRIPTION "CB21 Alarm-Time-Delay"
		::= { bcmsplus5 324 }

bcms5-cb22-alarm-time-delay
	OBJECT-TYPE
	SYNTAX  INTEGER
	ACCESS  read-write
	STATUS  mandatory
	DESCRIPTION "CB22 Alarm-Time-Delay"
		::= { bcmsplus5 325 }
  
bcms5-cb23-alarm-time-delay
	OBJECT-TYPE
	SYNTAX  INTEGER
	ACCESS  read-write
	STATUS  mandatory
	DESCRIPTION "CB23 Alarm-Time-Delay"
		::= { bcmsplus5 326 }

bcms5-cb24-alarm-time-delay
	OBJECT-TYPE
	SYNTAX  INTEGER
	ACCESS  read-write
	STATUS  mandatory
	DESCRIPTION "CB24 Alarm-Time-Delay"
		::= { bcmsplus5 327 }

bcms5-cb25-alarm-time-delay
	OBJECT-TYPE
	SYNTAX  INTEGER
	ACCESS  read-write
	STATUS  mandatory
	DESCRIPTION "CB25 Alarm-Time-Delay"
		::= { bcmsplus5 328 }

bcms5-cb26-alarm-time-delay
	OBJECT-TYPE
	SYNTAX  INTEGER
	ACCESS  read-write
	STATUS  mandatory
	DESCRIPTION "CB26 Alarm-Time-Delay"
		::= { bcmsplus5 329 }

bcms5-cb27-alarm-time-delay
	OBJECT-TYPE
	SYNTAX  INTEGER
	ACCESS  read-write
	STATUS  mandatory
	DESCRIPTION "CB27 Alarm-Time-Delay"
		::= { bcmsplus5 330 }

bcms5-cb28-alarm-time-delay
	OBJECT-TYPE
	SYNTAX  INTEGER
	ACCESS  read-write
	STATUS  mandatory
	DESCRIPTION "CB28 Alarm-Time-Delay"
		::= { bcmsplus5 331 }

bcms5-cb29-alarm-time-delay
	OBJECT-TYPE
	SYNTAX  INTEGER
	ACCESS  read-write
	STATUS  mandatory
	DESCRIPTION "CB29 Alarm-Time-Delay"
		::= { bcmsplus5 332 }

bcms5-cb30-alarm-time-delay
	OBJECT-TYPE
	SYNTAX  INTEGER
	ACCESS  read-write
	STATUS  mandatory
	DESCRIPTION "CB30 Alarm-Time-Delay"
		::= { bcmsplus5 333 }

bcms5-cb31-alarm-time-delay
	OBJECT-TYPE
	SYNTAX  INTEGER
	ACCESS  read-write
	STATUS  mandatory
	DESCRIPTION "CB31 Alarm-Time-Delay"
		::= { bcmsplus5 334 }

bcms5-cb32-alarm-time-delay
	OBJECT-TYPE
	SYNTAX  INTEGER
	ACCESS  read-write
	STATUS  mandatory
	DESCRIPTION "CB32 Alarm-Time-Delay"
		::= { bcmsplus5 335 }
  
bcms5-cb33-alarm-time-delay
	OBJECT-TYPE
	SYNTAX  INTEGER
	ACCESS  read-write
	STATUS  mandatory
	DESCRIPTION "CB33 Alarm-Time-Delay"
		::= { bcmsplus5 336 }

bcms5-cb34-alarm-time-delay
	OBJECT-TYPE
	SYNTAX  INTEGER
	ACCESS  read-write
	STATUS  mandatory
	DESCRIPTION "CB34 Alarm-Time-Delay"
		::= { bcmsplus5 337 }

bcms5-cb35-alarm-time-delay
	OBJECT-TYPE
	SYNTAX  INTEGER
	ACCESS  read-write
	STATUS  mandatory
	DESCRIPTION "CB35 Alarm-Time-Delay"
		::= { bcmsplus5 338 }

bcms5-cb36-alarm-time-delay
	OBJECT-TYPE
	SYNTAX  INTEGER
	ACCESS  read-write
	STATUS  mandatory
	DESCRIPTION "CB36 Alarm-Time-Delay"
		::= { bcmsplus5 339 }

bcms5-cb37-alarm-time-delay
	OBJECT-TYPE
	SYNTAX  INTEGER
	ACCESS  read-write
	STATUS  mandatory
	DESCRIPTION "CB37 Alarm-Time-Delay"
		::= { bcmsplus5 340 }

bcms5-cb38-alarm-time-delay
	OBJECT-TYPE
	SYNTAX  INTEGER
	ACCESS  read-write
	STATUS  mandatory
	DESCRIPTION "CB38 Alarm-Time-Delay"
		::= { bcmsplus5 341 }

bcms5-cb39-alarm-time-delay
	OBJECT-TYPE
	SYNTAX  INTEGER
	ACCESS  read-write
	STATUS  mandatory
	DESCRIPTION "CB39 Alarm-Time-Delay"
		::= { bcmsplus5 342 }

bcms5-cb40-alarm-time-delay
	OBJECT-TYPE
	SYNTAX  INTEGER
	ACCESS  read-write
	STATUS  mandatory
	DESCRIPTION "CB40 Alarm-Time-Delay"
		::= { bcmsplus5 343 }

bcms5-cb41-alarm-time-delay
	OBJECT-TYPE
	SYNTAX  INTEGER
	ACCESS  read-write
	STATUS  mandatory
	DESCRIPTION "CB41 Alarm-Time-Delay"
		::= { bcmsplus5 344 }

bcms5-cb42-alarm-time-delay
	OBJECT-TYPE
	SYNTAX  INTEGER
	ACCESS  read-write
	STATUS  mandatory
	DESCRIPTION "CB42 Alarm-Time-Delay"
		::= { bcmsplus5 345 }

bcms5-global-breaker-size
	OBJECT-TYPE
	SYNTAX  INTEGER
	ACCESS  read-write
	STATUS  mandatory
	DESCRIPTION "Global-breaker-size
		     Note for global breaker size: 10 = 10 amps
                     Range is 10 to 100 amps"
		::= { bcmsplus5 346 }

bcms5-global-warning-threshold
	OBJECT-TYPE
	SYNTAX  INTEGER
	ACCESS  read-write
	STATUS  mandatory
	DESCRIPTION "Global-warning-threshold
		     Note for global warning threshold: 70 = 70% of breaker size
                     range is 0-100%"
		::= { bcmsplus5 347 }

bcms5-global-alarm-threshold
	OBJECT-TYPE
	SYNTAX  INTEGER
	ACCESS  read-write
	STATUS  mandatory
	DESCRIPTION "Global-alarm-threshold
		     Note for global alarm threshold: 80 = 80% of breaker size
                     range is 0-100%"
		::= { bcmsplus5 348 }

bcms5-global-warning-time-delay
	OBJECT-TYPE
	SYNTAX  INTEGER
	ACCESS  read-write
	STATUS  mandatory
	DESCRIPTION "Global-warning-time-delay
		     Note for global warning time delay: units are in seconds"                     
		::= { bcmsplus5 349 }

bcms5-global-alarm-time-delay
	OBJECT-TYPE
	SYNTAX  INTEGER
	ACCESS  read-write
	STATUS  mandatory
	DESCRIPTION "Global-alarm-time-delay
		     Note for global alarm time delay: units are in seconds"                     
		::= { bcmsplus5 350 }

bcms5-min-max-reset
	OBJECT-TYPE
	SYNTAX  INTEGER
	ACCESS  read-write
	STATUS  mandatory
	DESCRIPTION "Min-max-Reset
                     Note for Min-max Reset: writing to this register will clear minimum
		     and maximum current values"
		::= { bcmsplus5 351 }

bcms5-global-warning-alarm-register
	OBJECT-TYPE
	SYNTAX  INTEGER
	ACCESS  read-only
	STATUS  mandatory
	DESCRIPTION "Global-Warning-Alarm-Register
			bit 0:	Warning Register 1
			bit 1:	Warning Register 2
			bit 2:	Warning Register 3
			bit 3:	Alarm Register 1
			bit 4:	Alarm Register 2
			bit 5:	Alarm Register 3
			bit 6:	Zero Current Register 1
			bit 7:	Zero Current Register 2
			bit 8:	Zero Current Register 3
			bits 9 – 15: Always read as 0"
		::= { bcmsplus5 352 }

bcms5-meter-alarm-status-latching
	OBJECT-TYPE
	SYNTAX  INTEGER
	ACCESS  read-write
	STATUS  mandatory
	DESCRIPTION "Meter-Alarm-Status-Latching
			bit 0:	Over Current panelboard
			bit 1:	Under Current panelboard
			bit 2: 	Over Current both panelboards 
			bit 3: 	Under Current both panelboards
			bit 4: 	Over Voltage main
			bit 5: 	Under Voltage main
			bit 6: 	Over Voltage alternate
			bit 7: 	Under Voltage alternate
			bits 8 – 15: Not Used"
		::= { bcmsplus5 353 }

bcms5-meter-alarm-status-nonlatching
	OBJECT-TYPE
	SYNTAX  INTEGER
	ACCESS  read-only
	STATUS  mandatory
	DESCRIPTION "Meter-Alarm-Status-Nonlatching
			bit 0:	Over Current panelboard
			bit 1:	Under Current panelboard
			bit 2: 	Over Current both panelboards 
			bit 3: 	Under Current both panelboards
			bit 4: 	Over Voltage main
			bit 5: 	Under Voltage main
			bit 6: 	Over Voltage alternate
			bit 7: 	Under Voltage alternate
			bits 8 – 15: Not Used"
		::= { bcmsplus5 354 }

bcms5-digital-alarm-status
	OBJECT-TYPE
	SYNTAX  INTEGER
	ACCESS  read-only
	STATUS  mandatory
	DESCRIPTION "Digital-Alarm-Status
			bit 0:	Digital alarm 1
			bit 1:	Digital alarm 2
			bit 2: 	Digital alarm 3
			bit 3: 	Digital alarm 4
			bits 4 – 15: Not Used"
		::= { bcmsplus5 355 }

bcms5-current-option-setting
	OBJECT-TYPE
	SYNTAX  INTEGER
	ACCESS  read-only
	STATUS  mandatory
	DESCRIPTION "Current-Option-Setting
			bit 0:	option 0
			bit 1:	option 1
			bit 2: 	option 2 
			bit 3: 	neutral CTs
			bit 4:	no branch CTs
		     Option 0: no main or panelboard CTs. 	(357-359 summation of branch)
								(367-376 not used)
		     Option 1: CTs on main input feeding both panelboards. 
								(357-359 summation of branch)
		     Option 2: CTs on each panel board. 	(367-376 summation of panelboard 1 and 2) 
		     Note: Neutral current monitoring is optional."
		::= { bcmsplus5 356 }

bcms5-current-phase-a-panelboard
	OBJECT-TYPE
	SYNTAX  INTEGER
	ACCESS  read-only
	STATUS  mandatory
	DESCRIPTION "Current-Phase-A-Panelboard
                     Note for all currents: 100 = 10.0 amps"
		::= { bcmsplus5 357 }

bcms5-current-phase-b-panelboard
	OBJECT-TYPE
	SYNTAX  INTEGER
	ACCESS  read-only
	STATUS  mandatory
	DESCRIPTION "Current-Phase-B-Panelboard"
		::= { bcmsplus5 358 }

bcms5-current-phase-c-panelboard
	OBJECT-TYPE
	SYNTAX  INTEGER
	ACCESS  read-only
	STATUS  mandatory
	DESCRIPTION "Current-Phase-C-Panelboard"
		::= { bcmsplus5 359 }

bcms5-current-neutral-panelboard
	OBJECT-TYPE
	SYNTAX  INTEGER
	ACCESS  read-only
	STATUS  mandatory
	DESCRIPTION "Current-Neutral-Panelboard"
		::= { bcmsplus5 360 }


bcms5-over-current-alarm-threshhold-pnlbd
	OBJECT-TYPE
	SYNTAX  INTEGER
	ACCESS  read-write
	STATUS  mandatory
	DESCRIPTION "Over-Current-Alarm-Threshhold-Pnlbd"
		::= { bcmsplus5 361 }

bcms5-under-current-alarm-threshhold-pnlbd
	OBJECT-TYPE
	SYNTAX  INTEGER
	ACCESS  read-write
	STATUS  mandatory
	DESCRIPTION "Under-Current-Alarm-Threshhold-Pnlbd"
		::= { bcmsplus5 362 }

bcms5-over-current-set-counter-pnlbd
	OBJECT-TYPE
	SYNTAX  INTEGER
	ACCESS  read-only
	STATUS  mandatory
	DESCRIPTION "Over-Current-Set-Counter-Pnlbd
		     Note for all counters:
                     The set counter is incremented when the value goes outside the threshold limit
                     The reset counter is incremented when the value is returns to  the threshold limit"
		::= { bcmsplus5 363 }

bcms5-over-current-reset-counter-pnlbd
	OBJECT-TYPE
	SYNTAX  INTEGER
	ACCESS  read-only
	STATUS  mandatory
	DESCRIPTION "Over-Current-Reset-Counter-Pnlbd"
		::= { bcmsplus5 364 }

bcms5-under-current-set-counter-pnlbd
	OBJECT-TYPE
	SYNTAX  INTEGER
	ACCESS  read-only
	STATUS  mandatory
	DESCRIPTION "Under-Current-Set-Counter-Pnlbd"
		::= { bcmsplus5 365 }

bcms5-under-current-reset-counter-pnlbd
	OBJECT-TYPE
	SYNTAX  INTEGER
	ACCESS  read-only
	STATUS  mandatory
	DESCRIPTION "Under-Current-Reset-Counter-Pnlbd"
		::= { bcmsplus5 366 }

bcms5-current-phase-a-both-pnlbd
	OBJECT-TYPE
	SYNTAX  INTEGER
	ACCESS  read-only
	STATUS  mandatory
	DESCRIPTION "Current-Phase-A-Both-Pnlbd"
		::= { bcmsplus5 367 }

bcms5-current-phase-b-both-pnlbd
	OBJECT-TYPE
	SYNTAX  INTEGER
	ACCESS  read-only
	STATUS  mandatory
	DESCRIPTION "Current-Phase-B-Both-Pnlbd"
		::= { bcmsplus5 368 }

bcms5-current-phase-c-both-pnlbd
	OBJECT-TYPE
	SYNTAX  INTEGER
	ACCESS  read-only
	STATUS  mandatory
	DESCRIPTION "Current-Phase-C-Both-Pnlbd"
		::= { bcmsplus5 369 }

bcms5-current-neutral-both-pnlbd
	OBJECT-TYPE
	SYNTAX  INTEGER
	ACCESS  read-only
	STATUS  mandatory
	DESCRIPTION "Current-Neutral-Both-Pnlbd"
		::= { bcmsplus5 370 }


bcms5-over-current-alarm-threshhold-both-pnlbd
	OBJECT-TYPE
	SYNTAX  INTEGER
	ACCESS  read-write
	STATUS  mandatory
	DESCRIPTION "Over-Current-Alarm-Threshhold-Both-Pnlbd"
		::= { bcmsplus5 371 }

bcms5-under-current-alarm-threshhold-both-pnlbd
	OBJECT-TYPE
	SYNTAX  INTEGER
	ACCESS  read-write
	STATUS  mandatory
	DESCRIPTION "Under-Current-Alarm-Threshhold-Both-Pnlbd"
		::= { bcmsplus5 372 }

bcms5-over-current-set-counter-both-pnlbd
	OBJECT-TYPE
	SYNTAX  INTEGER
	ACCESS  read-only
	STATUS  mandatory
	DESCRIPTION "Over-Current-Set-Counter-Both-Pnlbd"
		::= { bcmsplus5 373 }

bcms5-over-current-reset-counter-both-pnlbd
	OBJECT-TYPE
	SYNTAX  INTEGER
	ACCESS  read-only
	STATUS  mandatory
	DESCRIPTION "Over-Current-Reset-Counter-Both-Pnlbd"
		::= { bcmsplus5 374 }

bcms5-under-current-set-counter-both-pnlbd
	OBJECT-TYPE
	SYNTAX  INTEGER
	ACCESS  read-only
	STATUS  mandatory
	DESCRIPTION "Under-Current-Set-Counter-Both-Pnlbd"
		::= { bcmsplus5 375 }

bcms5-under-current-reset-counter-both-pnlbd
	OBJECT-TYPE
	SYNTAX  INTEGER
	ACCESS  read-only
	STATUS  mandatory
	DESCRIPTION "Under-Current-Reset-Counter-Both-Pnlbd"
		::= { bcmsplus5 376 }

bcms5-voltage-option-setting
	OBJECT-TYPE
	SYNTAX  INTEGER
	ACCESS  read-only
	STATUS  mandatory
	DESCRIPTION "Voltage-Option-Setting
			bit 0:	option 0
			bit 1:	option 1
			bit 2: 	option 2 
			bit 3: 	option 3 
			bits 4 – 15: Not Used
                     Option 0: no voltage monitoring. (378-414 not used)
                     Option 1: One voltage feeding 1 or 2 panel boards. (390-401 not used)
                     Option 2: One voltage feeding panelboard 1 and another feeding panelboard 2. (390-401 not used)
                     Option 3: Two voltages tied together through interlocked circuit breakers feeding both panelboards. 
                               Digital input 1 and 2 are used to determine which is feeding the panelboard. A set bit 
                               indicated closed.  If both are closed, main voltage is used."
		::= { bcmsplus5 377 }

bcms5-voltage-a-b-main
	OBJECT-TYPE
	SYNTAX  INTEGER
	ACCESS  read-only
	STATUS  mandatory
	DESCRIPTION "Voltage-A-B-Main
                     Note for all voltages: 1200 = 120.0 volts"
		::= { bcmsplus5 378 }

bcms5-voltage-b-c-main
	OBJECT-TYPE
	SYNTAX  INTEGER
	ACCESS  read-only
	STATUS  mandatory
	DESCRIPTION "Voltage-B-C-Main"
		::= { bcmsplus5 379 }

bcms5-voltage-c-a-main
	OBJECT-TYPE
	SYNTAX  INTEGER
	ACCESS  read-only
	STATUS  mandatory
	DESCRIPTION "Voltage-C-A-Main"
		::= { bcmsplus5 380 }

bcms5-voltage-a-n-main
	OBJECT-TYPE
	SYNTAX  INTEGER
	ACCESS  read-only
	STATUS  mandatory
	DESCRIPTION "Voltage-A-N-Main"
		::= { bcmsplus5 381 }

bcms5-voltage-b-n-main
	OBJECT-TYPE
	SYNTAX  INTEGER
	ACCESS  read-only
	STATUS  mandatory
	DESCRIPTION "Voltage-B-N-Main"
		::= { bcmsplus5 382 }

bcms5-voltage-c-n-main
	OBJECT-TYPE
	SYNTAX  INTEGER
	ACCESS  read-only
	STATUS  mandatory
	DESCRIPTION "Voltage-C-N-Main"
		::= { bcmsplus5 383 }

bcms5-over-voltage-alarm-threshhold-main
	OBJECT-TYPE
	SYNTAX  INTEGER
	ACCESS  read-write
	STATUS  mandatory
	DESCRIPTION "Over-Voltage-Alarm-Threshhold-Main
                     Note All Over and Under Voltage is for L-L values"
		::= { bcmsplus5 384 }

bcms5-under-voltage-alarm-threshhold-main
	OBJECT-TYPE
	SYNTAX  INTEGER
	ACCESS  read-write
	STATUS  mandatory
	DESCRIPTION "Under-Voltage-Alarm-Threshhold-Main"
		::= { bcmsplus5 385 }

bcms5-over-voltage-set-counter-main
	OBJECT-TYPE
	SYNTAX  INTEGER
	ACCESS  read-only
	STATUS  mandatory
	DESCRIPTION "Over-Voltage-Set-Counter-Main"
		::= { bcmsplus5 386 }

bcms5-over-voltage-reset-counter-main
	OBJECT-TYPE
	SYNTAX  INTEGER
	ACCESS  read-only
	STATUS  mandatory
	DESCRIPTION "Over-Voltage-Reset-Counter-Main"
		::= { bcmsplus5 387 }

bcms5-under-voltage-set-counter-main
	OBJECT-TYPE
	SYNTAX  INTEGER
	ACCESS  read-only
	STATUS  mandatory
	DESCRIPTION "Under-Voltage-Set-Counter-Main"
		::= { bcmsplus5 388 }

bcms5-under-voltage-reset-counter-main
	OBJECT-TYPE
	SYNTAX  INTEGER
	ACCESS  read-only
	STATUS  mandatory
	DESCRIPTION "Under-Voltage-Reset-Counter-Main"
		::= { bcmsplus5 389 }


bcms5-voltage-frequency-main
	OBJECT-TYPE
	SYNTAX  INTEGER
	ACCESS  read-only
	STATUS  mandatory
	DESCRIPTION "Voltage-Frequency-Main
                     note for frequency: 600 = 60.0Hz
                     Range is 40-70Hz
                     Note if insufficient voltage is present frequency will read 0xFFFF"
		::= { bcmsplus5 390 }

bcms5-voltage-a-b-alternate
	OBJECT-TYPE
	SYNTAX  INTEGER
	ACCESS  read-only
	STATUS  mandatory
	DESCRIPTION "Voltage-A-B-Alternate"
		::= { bcmsplus5 391 }

bcms5-voltage-b-c-alternate
	OBJECT-TYPE
	SYNTAX  INTEGER
	ACCESS  read-only
	STATUS  mandatory
	DESCRIPTION "Voltage-B-C-Alternate"
		::= { bcmsplus5 392 }

bcms5-voltage-c-a-alternate
	OBJECT-TYPE
	SYNTAX  INTEGER
	ACCESS  read-only
	STATUS  mandatory
	DESCRIPTION "Voltage-C-A-Alternate"
		::= { bcmsplus5 393 }

bcms5-voltage-a-n-alternate
	OBJECT-TYPE
	SYNTAX  INTEGER
	ACCESS  read-only
	STATUS  mandatory
	DESCRIPTION "Voltage-A-N-Alternate"
		::= { bcmsplus5 394 }

bcms5-voltage-b-N-alternate
	OBJECT-TYPE
	SYNTAX  INTEGER
	ACCESS  read-only
	STATUS  mandatory
	DESCRIPTION "Voltage-B-N-Alternate"
		::= { bcmsplus5 395 }

bcms5-voltage-c-n-alternate
	OBJECT-TYPE
	SYNTAX  INTEGER
	ACCESS  read-only
	STATUS  mandatory
	DESCRIPTION "Voltage-C-N-Alternate"
		::= { bcmsplus5 396 }

bcms5-over-voltage-alarm-threshhold-alternate
	OBJECT-TYPE
	SYNTAX  INTEGER
	ACCESS  read-write
	STATUS  mandatory
	DESCRIPTION "Over-Voltage-Alarm-Threshhold-Alternate"
		::= { bcmsplus5 397 }

bcms5-under-voltage-alarm-threshhold-alternate
	OBJECT-TYPE
	SYNTAX  INTEGER
	ACCESS  read-write
	STATUS  mandatory
	DESCRIPTION "Under-Voltage-Alarm-Threshhold-Alternate"
		::= { bcmsplus5 398 }

bcms5-over-voltage-set-counter-alternate
	OBJECT-TYPE
	SYNTAX  INTEGER
	ACCESS  read-only
	STATUS  mandatory
	DESCRIPTION "Over-Voltage-Set-Counter-Alternate"
		::= { bcmsplus5 399 }

bcms5-over-voltage-reset-counter-alternate
	OBJECT-TYPE
	SYNTAX  INTEGER
	ACCESS  read-only
	STATUS  mandatory
	DESCRIPTION "Over-Voltage-Reset-Counter-Alternate"
		::= { bcmsplus5 400 }

bcms5-under-voltage-set-counter-alternate
	OBJECT-TYPE
	SYNTAX  INTEGER
	ACCESS  read-only
	STATUS  mandatory
	DESCRIPTION "Under-Voltage-Set-Counter-Alternate"
		::= { bcmsplus5 401 }

bcms5-under-voltage-reset-counter-alternate
	OBJECT-TYPE
	SYNTAX  INTEGER
	ACCESS  read-only
	STATUS  mandatory
	DESCRIPTION "Under-Voltage-Reset-Counter-Alternate"
		::= { bcmsplus5 402 }

bcms5-real-power-kw
	OBJECT-TYPE
	SYNTAX  INTEGER
	ACCESS  read-only
	STATUS  mandatory
	DESCRIPTION "Real-Power-KW
                     Note for all KWs: 100 = 10.0 KW"
		::= { bcmsplus5 403 }

bcms5-peal-power-phase-a
	OBJECT-TYPE
	SYNTAX  INTEGER
	ACCESS  read-only
	STATUS  mandatory
	DESCRIPTION "Real-Power-Phase-A"
		::= { bcmsplus5 404 }

bcms5-real-power-phase-b
	OBJECT-TYPE
	SYNTAX  INTEGER
	ACCESS  read-only
	STATUS  mandatory
	DESCRIPTION "Real-Power-Phase-B"
		::= { bcmsplus5 405 }

bcms5-real-power-phase-c
	OBJECT-TYPE
	SYNTAX  INTEGER
	ACCESS  read-only
	STATUS  mandatory
	DESCRIPTION "Real-Power-Phase-C"
		::= { bcmsplus5 406 }

bcms5-reactive-power-kvar
	OBJECT-TYPE
	SYNTAX  INTEGER
	ACCESS  read-only
	STATUS  mandatory
	DESCRIPTION "Reactive-Power-KVAR
                     Note for KVAR: 100 = 10.0 KVAR"
		::= { bcmsplus5 407 }

bcms5-apparent-Power-kva
	OBJECT-TYPE
	SYNTAX  INTEGER
	ACCESS  read-only
	STATUS  mandatory
	DESCRIPTION "Apparent-Power-KVA
                     Note for KVA: 100 = 10.0 KVA"
		::= { bcmsplus5 408 }

bcms5-total-power-factor
	OBJECT-TYPE
	SYNTAX  INTEGER
	ACCESS  read-only
	STATUS  mandatory
	DESCRIPTION "Total-Power-Factor
                     Note for all Power Factor: 1000 = 100.0 PF"
		::= { bcmsplus5 409 }

bcms5-power-factor-phase-a
	OBJECT-TYPE
	SYNTAX  INTEGER
	ACCESS  read-only
	STATUS  mandatory
	DESCRIPTION "Power-Factor-Phase-A"
		::= { bcmsplus5 410 }

bcms5-Power-factor-phase-b
	OBJECT-TYPE
	SYNTAX  INTEGER
	ACCESS  read-only
	STATUS  mandatory
	DESCRIPTION "Power-Factor-Phase-B"
		::= { bcmsplus5 411 }

bcms5-Power-factor-phase-c
	OBJECT-TYPE
	SYNTAX  INTEGER
	ACCESS  read-only
	STATUS  mandatory
	DESCRIPTION "Power-Factor-Phase-C"
		::= { bcmsplus5 412 }

bcms5-energy-consumption-kwh-lower-word-integer
	OBJECT-TYPE
	SYNTAX  INTEGER
	ACCESS  read-write
	STATUS  mandatory
	DESCRIPTION "Energy-Consumption-KWh-Lower-Word-Integer
		     Note for KWh: 100 = 100KWh
                     Combine lower and upper integers into a word for total KWh"
		::= { bcmsplus5 413 }

bcms5-energy-consumption-kwh-upper-word-integer
	OBJECT-TYPE
	SYNTAX  INTEGER
	ACCESS  read-write
	STATUS  mandatory
	DESCRIPTION "Energy-Consumption-KWh-Upper-Word-Integer"
		::= { bcmsplus5 414 }

bcms5-main-voltage-thd-phase-a
	OBJECT-TYPE
	SYNTAX  INTEGER
	ACCESS  read-only
	STATUS  mandatory
	DESCRIPTION "Main-Voltage-THD-Phase-A"
		::= { bcmsplus5 415 }

bcms5-main-voltage-thd-phase-b
	OBJECT-TYPE
	SYNTAX  INTEGER
	ACCESS  read-only
	STATUS  mandatory
	DESCRIPTION "Main-Voltage-THD-Phase-B"
		::= { bcmsplus5 416 }

bcms5-main-voltage-thd-phase-c
	OBJECT-TYPE
	SYNTAX  INTEGER
	ACCESS  read-only
	STATUS  mandatory
	DESCRIPTION "Main-Voltage-THD-Phase-C"
		::= { bcmsplus5 417 }

bcms5-alt-voltage-thd-phase-a
	OBJECT-TYPE
	SYNTAX  INTEGER
	ACCESS  read-only
	STATUS  mandatory
	DESCRIPTION "Alt-Voltage-THD-Phase-A"
		::= { bcmsplus5 418 }

bcms5-alt-voltage-thd-phase-b
	OBJECT-TYPE
	SYNTAX  INTEGER
	ACCESS  read-only
	STATUS  mandatory
	DESCRIPTION "Alt-Voltage-THD-Phase-B"
		::= { bcmsplus5 419 }

bcms5-alt-voltage-thd-phase-c
	OBJECT-TYPE
	SYNTAX  INTEGER
	ACCESS  read-only
	STATUS  mandatory
	DESCRIPTION "Alt-Voltage-THD-Phase-C"
		::= { bcmsplus5 420 }

bcms5-current-ground-panelboard
	OBJECT-TYPE
	SYNTAX  INTEGER
	ACCESS  read-only
	STATUS  mandatory
	DESCRIPTION "Current-Ground-Panelboard"
		::= { bcmsplus5 421 }

bcms5-percent-load-phase-a
	OBJECT-TYPE
	SYNTAX  INTEGER
	ACCESS  read-only
	STATUS  mandatory
	DESCRIPTION "Percent Load Phase A"
		::= { bcmsplus5 422 }

bcms5-percent-load-phase-b
	OBJECT-TYPE
	SYNTAX  INTEGER
	ACCESS  read-only
	STATUS  mandatory
	DESCRIPTION "Percent Load Phase B"
		::= { bcmsplus5 423 }

bcms5-percent-load-phase-c
	OBJECT-TYPE
	SYNTAX  INTEGER
	ACCESS  read-only
	STATUS  mandatory
	DESCRIPTION "Percent Load Phase C"
		::= { bcmsplus5 424 }

bcms5-full-load-current
	OBJECT-TYPE
	SYNTAX  INTEGER
	ACCESS  read-write
	STATUS  mandatory
	DESCRIPTION "Full Load Current"
		::= { bcmsplus5 425 }

--------------------------------------------------------------------------------
-- BCMSPLUS register values
--------------------------------------------------------------------------------

bcms6-cb1-current
	OBJECT-TYPE
	SYNTAX  INTEGER
	ACCESS  read-only
	STATUS  mandatory
	DESCRIPTION "CB1 Current
		     Note for all currents 1-42: 100 = 10.0 amps"
		::= { bcmsplus6 1 }
  
bcms6-cb2-current
	OBJECT-TYPE
	SYNTAX  INTEGER
	ACCESS  read-only
	STATUS  mandatory
	DESCRIPTION "CB2 Current"
		::= { bcmsplus6 2 }

bcms6-cb3-current
	OBJECT-TYPE
	SYNTAX  INTEGER
	ACCESS  read-only
	STATUS  mandatory
	DESCRIPTION "CB3 Current"
		::= { bcmsplus6 3 }

bcms6-cb4-current
	OBJECT-TYPE
	SYNTAX  INTEGER
	ACCESS  read-only
	STATUS  mandatory
	DESCRIPTION "CB4 Current"
		::= { bcmsplus6 4 }

bcms6-cb5-current
	OBJECT-TYPE
	SYNTAX  INTEGER
	ACCESS  read-only
	STATUS  mandatory
	DESCRIPTION "CB5 Current"
		::= { bcmsplus6 5 }

bcms6-cb6-current
	OBJECT-TYPE
	SYNTAX  INTEGER
	ACCESS  read-only
	STATUS  mandatory
	DESCRIPTION "CB6 Current"
		::= { bcmsplus6 6 }

bcms6-cb7-current
	OBJECT-TYPE
	SYNTAX  INTEGER
	ACCESS  read-only
	STATUS  mandatory
	DESCRIPTION "CB7 Current"
		::= { bcmsplus6 7 }

bcms6-cb8-current
	OBJECT-TYPE
	SYNTAX  INTEGER
	ACCESS  read-only
	STATUS  mandatory
	DESCRIPTION "CB8 Current"
		::= { bcmsplus6 8 }

bcms6-cb9-current
	OBJECT-TYPE
	SYNTAX  INTEGER
	ACCESS  read-only
	STATUS  mandatory
	DESCRIPTION "CB9 Current"
		::= { bcmsplus6 9 }

bcms6-cb10-current
	OBJECT-TYPE
	SYNTAX  INTEGER
	ACCESS  read-only
	STATUS  mandatory
	DESCRIPTION "CB10 Current"
		::= { bcmsplus6 10 }

bcms6-cb11-current
	OBJECT-TYPE
	SYNTAX  INTEGER
	ACCESS  read-only
	STATUS  mandatory
	DESCRIPTION "CB11 Current"
		::= { bcmsplus6 11 }
  
bcms6-cb12-current
	OBJECT-TYPE
	SYNTAX  INTEGER
	ACCESS  read-only
	STATUS  mandatory
	DESCRIPTION "CB12 Current"
		::= { bcmsplus6 12 }

bcms6-cb13-current
	OBJECT-TYPE
	SYNTAX  INTEGER
	ACCESS  read-only
	STATUS  mandatory
	DESCRIPTION "CB13 Current"
		::= { bcmsplus6 13 }

bcms6-cb14-current
	OBJECT-TYPE
	SYNTAX  INTEGER
	ACCESS  read-only
	STATUS  mandatory
	DESCRIPTION "CB14 Current"
		::= { bcmsplus6 14 }

bcms6-cb15-current
	OBJECT-TYPE
	SYNTAX  INTEGER
	ACCESS  read-only
	STATUS  mandatory
	DESCRIPTION "CB15 Current"
		::= { bcmsplus6 15 }

bcms6-cb16-current
	OBJECT-TYPE
	SYNTAX  INTEGER
	ACCESS  read-only
	STATUS  mandatory
	DESCRIPTION "CB16 Current"
		::= { bcmsplus6 16 }

bcms6-cb17-current
	OBJECT-TYPE
	SYNTAX  INTEGER
	ACCESS  read-only
	STATUS  mandatory
	DESCRIPTION "CB17 Current"
		::= { bcmsplus6 17 }

bcms6-cb18-current
	OBJECT-TYPE
	SYNTAX  INTEGER
	ACCESS  read-only
	STATUS  mandatory
	DESCRIPTION "CB18 Current"
		::= { bcmsplus6 18 }

bcms6-cb19-current
	OBJECT-TYPE
	SYNTAX  INTEGER
	ACCESS  read-only
	STATUS  mandatory
	DESCRIPTION "CB19 Current"
		::= { bcmsplus6 19 }

bcms6-cb20-current
	OBJECT-TYPE
	SYNTAX  INTEGER
	ACCESS  read-only
	STATUS  mandatory
	DESCRIPTION "CB20 Current"
		::= { bcmsplus6 20 }

bcms6-cb21-current
	OBJECT-TYPE
	SYNTAX  INTEGER
	ACCESS  read-only
	STATUS  mandatory
	DESCRIPTION "CB21 Current"
		::= { bcmsplus6 21 }
  
bcms6-cb22-current
	OBJECT-TYPE
	SYNTAX  INTEGER
	ACCESS  read-only
	STATUS  mandatory
	DESCRIPTION "CB22 Current"
		::= { bcmsplus6 22 }

bcms6-cb23-current
	OBJECT-TYPE
	SYNTAX  INTEGER
	ACCESS  read-only
	STATUS  mandatory
	DESCRIPTION "CB23 Current"
		::= { bcmsplus6 23 }

bcms6-cb24-current
	OBJECT-TYPE
	SYNTAX  INTEGER
	ACCESS  read-only
	STATUS  mandatory
	DESCRIPTION "CB24 Current"
		::= { bcmsplus6 24 }

bcms6-cb25-current
	OBJECT-TYPE
	SYNTAX  INTEGER
	ACCESS  read-only
	STATUS  mandatory
	DESCRIPTION "CB25 Current"
		::= { bcmsplus6 25 }

bcms6-cb26-current
	OBJECT-TYPE
	SYNTAX  INTEGER
	ACCESS  read-only
	STATUS  mandatory
	DESCRIPTION "CB26 Current"
		::= { bcmsplus6 26 }

bcms6-cb27-current
	OBJECT-TYPE
	SYNTAX  INTEGER
	ACCESS  read-only
	STATUS  mandatory
	DESCRIPTION "CB27 Current"
		::= { bcmsplus6 27 }

bcms6-cb28-current
	OBJECT-TYPE
	SYNTAX  INTEGER
	ACCESS  read-only
	STATUS  mandatory
	DESCRIPTION "CB28 Current"
		::= { bcmsplus6 28 }

bcms6-cb29-current
	OBJECT-TYPE
	SYNTAX  INTEGER
	ACCESS  read-only
	STATUS  mandatory
	DESCRIPTION "CB29 Current"
		::= { bcmsplus6 29 }

bcms6-cb30-current
	OBJECT-TYPE
	SYNTAX  INTEGER
	ACCESS  read-only
	STATUS  mandatory
	DESCRIPTION "CB30 Current"
		::= { bcmsplus6 30 }

bcms6-cb31-current
	OBJECT-TYPE
	SYNTAX  INTEGER
	ACCESS  read-only
	STATUS  mandatory
	DESCRIPTION "CB31 Current"
		::= { bcmsplus6 31 }
  
bcms6-cb32-current
	OBJECT-TYPE
	SYNTAX  INTEGER
	ACCESS  read-only
	STATUS  mandatory
	DESCRIPTION "CB32 Current"
		::= { bcmsplus6 32 }

bcms6-cb33-current
	OBJECT-TYPE
	SYNTAX  INTEGER
	ACCESS  read-only
	STATUS  mandatory
	DESCRIPTION "CB33 Current"
		::= { bcmsplus6 33 }

bcms6-cb34-current
	OBJECT-TYPE
	SYNTAX  INTEGER
	ACCESS  read-only
	STATUS  mandatory
	DESCRIPTION "CB34 Current"
		::= { bcmsplus6 34 }

bcms6-cb35-current
	OBJECT-TYPE
	SYNTAX  INTEGER
	ACCESS  read-only
	STATUS  mandatory
	DESCRIPTION "CB35 Current"
		::= { bcmsplus6 35 }

bcms6-cb36-current
	OBJECT-TYPE
	SYNTAX  INTEGER
	ACCESS  read-only
	STATUS  mandatory
	DESCRIPTION "CB36 Current"
		::= { bcmsplus6 36 }

bcms6-cb37-current
	OBJECT-TYPE
	SYNTAX  INTEGER
	ACCESS  read-only
	STATUS  mandatory
	DESCRIPTION "CB37 Current"
		::= { bcmsplus6 37 }

bcms6-cb38-current
	OBJECT-TYPE
	SYNTAX  INTEGER
	ACCESS  read-only
	STATUS  mandatory
	DESCRIPTION "CB38 Current"
		::= { bcmsplus6 38 }

bcms6-cb39-current
	OBJECT-TYPE
	SYNTAX  INTEGER
	ACCESS  read-only
	STATUS  mandatory
	DESCRIPTION "CB39 Current"
		::= { bcmsplus6 39 }

bcms6-cb40-current
	OBJECT-TYPE
	SYNTAX  INTEGER
	ACCESS  read-only
	STATUS  mandatory
	DESCRIPTION "CB40 Current"
		::= { bcmsplus6 40 }

bcms6-cb41-current
	OBJECT-TYPE
	SYNTAX  INTEGER
	ACCESS  read-only
	STATUS  mandatory
	DESCRIPTION "CB41 Current"
		::= { bcmsplus6 41 }
  
bcms6-cb42-current
	OBJECT-TYPE
	SYNTAX  INTEGER
	ACCESS  read-only
	STATUS  mandatory
	DESCRIPTION "CB42 Current"
		::= { bcmsplus6 42 }

bcms6-cb1-min
	OBJECT-TYPE
	SYNTAX  INTEGER
	ACCESS  read-only
	STATUS  mandatory
	DESCRIPTION "CB1 Min
		     Note for all minumum currents 1-42: 100 = 10.0 amps"
		::= { bcmsplus6 43 }

bcms6-cb2-min
	OBJECT-TYPE
	SYNTAX  INTEGER
	ACCESS  read-only
	STATUS  mandatory
	DESCRIPTION "CB2 Min"
		::= { bcmsplus6 44 }

bcms6-cb3-min
	OBJECT-TYPE
	SYNTAX  INTEGER
	ACCESS  read-only
	STATUS  mandatory
	DESCRIPTION "CB3 Min"
		::= { bcmsplus6 45 }

bcms6-cb4-min
	OBJECT-TYPE
	SYNTAX  INTEGER
	ACCESS  read-only
	STATUS  mandatory
	DESCRIPTION "CB4 Min"
		::= { bcmsplus6 46 }

bcms6-cb5-min
	OBJECT-TYPE
	SYNTAX  INTEGER
	ACCESS  read-only
	STATUS  mandatory
	DESCRIPTION "CB5 Min"
		::= { bcmsplus6 47 }

bcms6-cb6-min
	OBJECT-TYPE
	SYNTAX  INTEGER
	ACCESS  read-only
	STATUS  mandatory
	DESCRIPTION "CB6 Min"
		::= { bcmsplus6 48 }

bcms6-cb7-min
	OBJECT-TYPE
	SYNTAX  INTEGER
	ACCESS  read-only
	STATUS  mandatory
	DESCRIPTION "CB7 Min"
		::= { bcmsplus6 49 }

bcms6-cb8-min
	OBJECT-TYPE
	SYNTAX  INTEGER
	ACCESS  read-only
	STATUS  mandatory
	DESCRIPTION "CB8 Min"
		::= { bcmsplus6 50 }

bcms6-cb9-min
	OBJECT-TYPE
	SYNTAX  INTEGER
	ACCESS  read-only
	STATUS  mandatory
	DESCRIPTION "CB9 Min"
		::= { bcmsplus6 51 }
  
bcms6-cb10-min
	OBJECT-TYPE
	SYNTAX  INTEGER
	ACCESS  read-only
	STATUS  mandatory
	DESCRIPTION "CB10 Min"
		::= { bcmsplus6 52 }

bcms6-cb11-min
	OBJECT-TYPE
	SYNTAX  INTEGER
	ACCESS  read-only
	STATUS  mandatory
	DESCRIPTION "CB11 Min"
		::= { bcmsplus6 53 }

bcms6-cb12-min
	OBJECT-TYPE
	SYNTAX  INTEGER
	ACCESS  read-only
	STATUS  mandatory
	DESCRIPTION "CB12 Min"
		::= { bcmsplus6 54 }

bcms6-cb13-min
	OBJECT-TYPE
	SYNTAX  INTEGER
	ACCESS  read-only
	STATUS  mandatory
	DESCRIPTION "CB13 Min"
		::= { bcmsplus6 55 }

bcms6-cb14-min
	OBJECT-TYPE
	SYNTAX  INTEGER
	ACCESS  read-only
	STATUS  mandatory
	DESCRIPTION "CB14 Min"
		::= { bcmsplus6 56 }

bcms6-cb15-min
	OBJECT-TYPE
	SYNTAX  INTEGER
	ACCESS  read-only
	STATUS  mandatory
	DESCRIPTION "CB15 Min"
		::= { bcmsplus6 57 }

bcms6-cb16-min
	OBJECT-TYPE
	SYNTAX  INTEGER
	ACCESS  read-only
	STATUS  mandatory
	DESCRIPTION "CB16 Min"
		::= { bcmsplus6 58 }

bcms6-cb17-min
	OBJECT-TYPE
	SYNTAX  INTEGER
	ACCESS  read-only
	STATUS  mandatory
	DESCRIPTION "CB17 Min"
		::= { bcmsplus6 59 }


bcms6-cb18-min
	OBJECT-TYPE
	SYNTAX  INTEGER
	ACCESS  read-only
	STATUS  mandatory
	DESCRIPTION "CB18 Min"
		::= { bcmsplus6 60 }

bcms6-cb19-min
	OBJECT-TYPE
	SYNTAX  INTEGER
	ACCESS  read-only
	STATUS  mandatory
	DESCRIPTION "CB19 Min"
		::= { bcmsplus6 61 }
  
bcms6-cb20-min
	OBJECT-TYPE
	SYNTAX  INTEGER
	ACCESS  read-only
	STATUS  mandatory
	DESCRIPTION "CB20 Min"
		::= { bcmsplus6 62 }

bcms6-cb21-min
	OBJECT-TYPE
	SYNTAX  INTEGER
	ACCESS  read-only
	STATUS  mandatory
	DESCRIPTION "CB21 Min"
		::= { bcmsplus6 63 }

bcms6-cb22-min
	OBJECT-TYPE
	SYNTAX  INTEGER
	ACCESS  read-only
	STATUS  mandatory
	DESCRIPTION "CB22 Min"
		::= { bcmsplus6 64 }

bcms6-cb23-min
	OBJECT-TYPE
	SYNTAX  INTEGER
	ACCESS  read-only
	STATUS  mandatory
	DESCRIPTION "CB23 Min"
		::= { bcmsplus6 65 }

bcms6-cb24-min
	OBJECT-TYPE
	SYNTAX  INTEGER
	ACCESS  read-only
	STATUS  mandatory
	DESCRIPTION "CB24 Min"
		::= { bcmsplus6 66 }

bcms6-cb25-min
	OBJECT-TYPE
	SYNTAX  INTEGER
	ACCESS  read-only
	STATUS  mandatory
	DESCRIPTION "CB25 Min"
		::= { bcmsplus6 67 }

bcms6-cb26-min
	OBJECT-TYPE
	SYNTAX  INTEGER
	ACCESS  read-only
	STATUS  mandatory
	DESCRIPTION "CB26 Min"
		::= { bcmsplus6 68 }

bcms6-cb27-min
	OBJECT-TYPE
	SYNTAX  INTEGER
	ACCESS  read-only
	STATUS  mandatory
	DESCRIPTION "CB27 Min"
		::= { bcmsplus6 69 }

bcms6-cb28-min
	OBJECT-TYPE
	SYNTAX  INTEGER
	ACCESS  read-only
	STATUS  mandatory
	DESCRIPTION "CB28 Min"
		::= { bcmsplus6 70 }

bcms6-cb29-min
	OBJECT-TYPE
	SYNTAX  INTEGER
	ACCESS  read-only
	STATUS  mandatory
	DESCRIPTION "CB29 Min"
		::= { bcmsplus6 71 }
  
bcms6-cb30-min
	OBJECT-TYPE
	SYNTAX  INTEGER
	ACCESS  read-only
	STATUS  mandatory
	DESCRIPTION "CB30 Min"
		::= { bcmsplus6 72 }

bcms6-cb31-min
	OBJECT-TYPE
	SYNTAX  INTEGER
	ACCESS  read-only
	STATUS  mandatory
	DESCRIPTION "CB31 Min"
		::= { bcmsplus6 73 }

bcms6-cb32-min
	OBJECT-TYPE
	SYNTAX  INTEGER
	ACCESS  read-only
	STATUS  mandatory
	DESCRIPTION "CB32 Min"
		::= { bcmsplus6 74 }

bcms6-cb33-min
	OBJECT-TYPE
	SYNTAX  INTEGER
	ACCESS  read-only
	STATUS  mandatory
	DESCRIPTION "CB33 Min"
		::= { bcmsplus6 75 }

bcms6-cb34-min
	OBJECT-TYPE
	SYNTAX  INTEGER
	ACCESS  read-only
	STATUS  mandatory
	DESCRIPTION "CB34 Min"
		::= { bcmsplus6 76 }

bcms6-cb35-min
	OBJECT-TYPE
	SYNTAX  INTEGER
	ACCESS  read-only
	STATUS  mandatory
	DESCRIPTION "CB35 Min"
		::= { bcmsplus6 77 }

bcms6-cb36-min
	OBJECT-TYPE
	SYNTAX  INTEGER
	ACCESS  read-only
	STATUS  mandatory
	DESCRIPTION "CB36 Min"
		::= { bcmsplus6 78 }

bcms6-cb37-min
	OBJECT-TYPE
	SYNTAX  INTEGER
	ACCESS  read-only
	STATUS  mandatory
	DESCRIPTION "CB37 Min"
		::= { bcmsplus6 79 }

bcms6-cb38-min
	OBJECT-TYPE
	SYNTAX  INTEGER
	ACCESS  read-only
	STATUS  mandatory
	DESCRIPTION "CB38 Min"
		::= { bcmsplus6 80 }

bcms6-cb39-min
	OBJECT-TYPE
	SYNTAX  INTEGER
	ACCESS  read-only
	STATUS  mandatory
	DESCRIPTION "CB39 Min"
		::= { bcmsplus6 81 }
  
bcms6-cb40-min
	OBJECT-TYPE
	SYNTAX  INTEGER
	ACCESS  read-only
	STATUS  mandatory
	DESCRIPTION "CB40 Min"
		::= { bcmsplus6 82 }

bcms6-cb41-min
	OBJECT-TYPE
	SYNTAX  INTEGER
	ACCESS  read-only
	STATUS  mandatory
	DESCRIPTION "CB41 Min"
		::= { bcmsplus6 83 }

bcms6-cb42-min
	OBJECT-TYPE
	SYNTAX  INTEGER
	ACCESS  read-only
	STATUS  mandatory
	DESCRIPTION "CB42 Min"
		::= { bcmsplus6 84 }

bcms6-cb1-max
	OBJECT-TYPE
	SYNTAX  INTEGER
	ACCESS  read-only
	STATUS  mandatory
	DESCRIPTION "CB1 Max
		     Note for all maximum currents 1-42: 100 = 10.0 amps"
		::= { bcmsplus6 85 }

bcms6-cb2-max
	OBJECT-TYPE
	SYNTAX  INTEGER
	ACCESS  read-only
	STATUS  mandatory
	DESCRIPTION "CB2 Max"
		::= { bcmsplus6 86 }

bcms6-cb3-max
	OBJECT-TYPE
	SYNTAX  INTEGER
	ACCESS  read-only
	STATUS  mandatory
	DESCRIPTION "CB3 Max"
		::= { bcmsplus6 87 }

bcms6-cb4-max
	OBJECT-TYPE
	SYNTAX  INTEGER
	ACCESS  read-only
	STATUS  mandatory
	DESCRIPTION "CB4 Max"
		::= { bcmsplus6 88 }

bcms6-cb5-max
	OBJECT-TYPE
	SYNTAX  INTEGER
	ACCESS  read-only
	STATUS  mandatory
	DESCRIPTION "CB5 Max"
		::= { bcmsplus6 89 }

bcms6-cb6-max
	OBJECT-TYPE
	SYNTAX  INTEGER
	ACCESS  read-only
	STATUS  mandatory
	DESCRIPTION "CB6 Max"
		::= { bcmsplus6 90 }

bcms6-cb7-max
	OBJECT-TYPE
	SYNTAX  INTEGER
	ACCESS  read-only
	STATUS  mandatory
	DESCRIPTION "CB7 Max"
		::= { bcmsplus6 91 }
  
bcms6-cb8-max
	OBJECT-TYPE
	SYNTAX  INTEGER
	ACCESS  read-only
	STATUS  mandatory
	DESCRIPTION "CB8 Max"
		::= { bcmsplus6 92 }

bcms6-cb9-max
	OBJECT-TYPE
	SYNTAX  INTEGER
	ACCESS  read-only
	STATUS  mandatory
	DESCRIPTION "CB9 Max"
		::= { bcmsplus6 93 }

bcms6-cb10-max
	OBJECT-TYPE
	SYNTAX  INTEGER
	ACCESS  read-only
	STATUS  mandatory
	DESCRIPTION "CB10 Max"
		::= { bcmsplus6 94 }

bcms6-cb11-max
	OBJECT-TYPE
	SYNTAX  INTEGER
	ACCESS  read-only
	STATUS  mandatory
	DESCRIPTION "CB11 Max"
		::= { bcmsplus6 95 }

bcms6-cb12-max
	OBJECT-TYPE
	SYNTAX  INTEGER
	ACCESS  read-only
	STATUS  mandatory
	DESCRIPTION "CB12 Max"
		::= { bcmsplus6 96 }

bcms6-cb13-max
	OBJECT-TYPE
	SYNTAX  INTEGER
	ACCESS  read-only
	STATUS  mandatory
	DESCRIPTION "CB13 Max"
		::= { bcmsplus6 97 }

bcms6-cb14-max
	OBJECT-TYPE
	SYNTAX  INTEGER
	ACCESS  read-only
	STATUS  mandatory
	DESCRIPTION "CB14 Max"
		::= { bcmsplus6 98 }

bcms6-cb15-max
	OBJECT-TYPE
	SYNTAX  INTEGER
	ACCESS  read-only
	STATUS  mandatory
	DESCRIPTION "CB15 Max"
		::= { bcmsplus6 99 }


bcms6-cb16-max
	OBJECT-TYPE
	SYNTAX  INTEGER
	ACCESS  read-only
	STATUS  mandatory
	DESCRIPTION "CB16 Max"
		::= { bcmsplus6 100 }

bcms6-cb17-max
	OBJECT-TYPE
	SYNTAX  INTEGER
	ACCESS  read-only
	STATUS  mandatory
	DESCRIPTION "CB17 Max"
		::= { bcmsplus6 101 }
  
bcms6-cb18-max
	OBJECT-TYPE
	SYNTAX  INTEGER
	ACCESS  read-only
	STATUS  mandatory
	DESCRIPTION "CB18 Max"
		::= { bcmsplus6 102 }

bcms6-cb19-max
	OBJECT-TYPE
	SYNTAX  INTEGER
	ACCESS  read-only
	STATUS  mandatory
	DESCRIPTION "CB19 Max"
		::= { bcmsplus6 103 }

bcms6-cb20-max
	OBJECT-TYPE
	SYNTAX  INTEGER
	ACCESS  read-only
	STATUS  mandatory
	DESCRIPTION "CB20 Max"
		::= { bcmsplus6 104 }

bcms6-cb21-max
	OBJECT-TYPE
	SYNTAX  INTEGER
	ACCESS  read-only
	STATUS  mandatory
	DESCRIPTION "CB21 Max"
		::= { bcmsplus6 105 }

bcms6-cb22-max
	OBJECT-TYPE
	SYNTAX  INTEGER
	ACCESS  read-only
	STATUS  mandatory
	DESCRIPTION "CB22 Max"
		::= { bcmsplus6 106 }

bcms6-cb23-max
	OBJECT-TYPE
	SYNTAX  INTEGER
	ACCESS  read-only
	STATUS  mandatory
	DESCRIPTION "CB23 Max"
		::= { bcmsplus6 107 }

bcms6-cb24-max
	OBJECT-TYPE
	SYNTAX  INTEGER
	ACCESS  read-only
	STATUS  mandatory
	DESCRIPTION "CB24 Max"
		::= { bcmsplus6 108 }

bcms6-cb25-max
	OBJECT-TYPE
	SYNTAX  INTEGER
	ACCESS  read-only
	STATUS  mandatory
	DESCRIPTION "CB25 Max"
		::= { bcmsplus6 109 }

bcms6-cb26-max
	OBJECT-TYPE
	SYNTAX  INTEGER
	ACCESS  read-only
	STATUS  mandatory
	DESCRIPTION "CB26 Max"
		::= { bcmsplus6 110 }

bcms6-cb27-max
	OBJECT-TYPE
	SYNTAX  INTEGER
	ACCESS  read-only
	STATUS  mandatory
	DESCRIPTION "CB27 Max"
		::= { bcmsplus6 111 }
  
bcms6-cb28-max
	OBJECT-TYPE
	SYNTAX  INTEGER
	ACCESS  read-only
	STATUS  mandatory
	DESCRIPTION "CB28 Max"
		::= { bcmsplus6 112 }

bcms6-cb29-max
	OBJECT-TYPE
	SYNTAX  INTEGER
	ACCESS  read-only
	STATUS  mandatory
	DESCRIPTION "CB29 Max"
		::= { bcmsplus6 113 }

bcms6-cb30-max
	OBJECT-TYPE
	SYNTAX  INTEGER
	ACCESS  read-only
	STATUS  mandatory
	DESCRIPTION "CB30 Max"
		::= { bcmsplus6 114 }

bcms6-cb31-max
	OBJECT-TYPE
	SYNTAX  INTEGER
	ACCESS  read-only
	STATUS  mandatory
	DESCRIPTION "CB31 Max"
		::= { bcmsplus6 115 }

bcms6-cb32-max
	OBJECT-TYPE
	SYNTAX  INTEGER
	ACCESS  read-only
	STATUS  mandatory
	DESCRIPTION "CB32 Max"
		::= { bcmsplus6 116 }

bcms6-cb33-max
	OBJECT-TYPE
	SYNTAX  INTEGER
	ACCESS  read-only
	STATUS  mandatory
	DESCRIPTION "CB33 Max"
		::= { bcmsplus6 117 }

bcms6-cb34-max
	OBJECT-TYPE
	SYNTAX  INTEGER
	ACCESS  read-only
	STATUS  mandatory
	DESCRIPTION "CB34 Max"
		::= { bcmsplus6 118 }

bcms6-cb35-max
	OBJECT-TYPE
	SYNTAX  INTEGER
	ACCESS  read-only
	STATUS  mandatory
	DESCRIPTION "CB35 Max"
		::= { bcmsplus6 119 }

bcms6-cb36-max
	OBJECT-TYPE
	SYNTAX  INTEGER
	ACCESS  read-only
	STATUS  mandatory
	DESCRIPTION "CB36 Max"
		::= { bcmsplus6 120 }

bcms6-cb37-max
	OBJECT-TYPE
	SYNTAX  INTEGER
	ACCESS  read-only
	STATUS  mandatory
	DESCRIPTION "CB37 Max"
		::= { bcmsplus6 121 }
  
bcms6-cb38-max
	OBJECT-TYPE
	SYNTAX  INTEGER
	ACCESS  read-only
	STATUS  mandatory
	DESCRIPTION "CB38 Max"
		::= { bcmsplus6 122 }

bcms6-cb39-max
	OBJECT-TYPE
	SYNTAX  INTEGER
	ACCESS  read-only
	STATUS  mandatory
	DESCRIPTION "CB39 Max"
		::= { bcmsplus6 123 }

bcms6-cb40-max
	OBJECT-TYPE
	SYNTAX  INTEGER
	ACCESS  read-only
	STATUS  mandatory
	DESCRIPTION "CB40 Max"
		::= { bcmsplus6 124 }

bcms6-cb41-max
	OBJECT-TYPE
	SYNTAX  INTEGER
	ACCESS  read-only
	STATUS  mandatory
	DESCRIPTION "CB41 Max"
		::= { bcmsplus6 125 }

bcms6-cb42-max
	OBJECT-TYPE
	SYNTAX  INTEGER
	ACCESS  read-only
	STATUS  mandatory
	DESCRIPTION "CB42 Max"
		::= { bcmsplus6 126 }

bcms6-cb1-16-zero
	OBJECT-TYPE
	SYNTAX  INTEGER
	ACCESS  read-write
	STATUS  mandatory
	DESCRIPTION "CB1-16 Zero
		       Bit 0 = CB1
                   Bit 15 = CB16"
		::= { bcmsplus6 127 }

bcms6-cb17-32-zero
	OBJECT-TYPE
	SYNTAX  INTEGER
	ACCESS  read-write
	STATUS  mandatory
	DESCRIPTION "CB17-32 Zero
		       Bit 0 = CB17
                   Bit 15 = CB32"
		::= { bcmsplus6 128 }

bcms6-cb33-42-zero
	OBJECT-TYPE
	SYNTAX  INTEGER
	ACCESS  read-write
	STATUS  mandatory
	DESCRIPTION "CB33-42 Zero
		       Bit 0 = CB33
                   Bit 9 = CB42
                   Bits 10-25 not used"
		::= { bcmsplus6 129 }

bcms6-cb1-16-warning
	OBJECT-TYPE
	SYNTAX  INTEGER
	ACCESS  read-write
	STATUS  mandatory
	DESCRIPTION "CB1-16 Warning
		       Bit 0 = CB1
                   Bit 15 = CB16"
		::= { bcmsplus6 130 }

bcms6-cb17-32-warning
	OBJECT-TYPE
	SYNTAX  INTEGER
	ACCESS  read-write
	STATUS  mandatory
	DESCRIPTION "CB17-32 Warning
		       Bit 0 = CB17
                   Bit 15 = CB32"
		::= { bcmsplus6 131 }
  
bcms6-cb33-42-warning
	OBJECT-TYPE
	SYNTAX  INTEGER
	ACCESS  read-write
	STATUS  mandatory
	DESCRIPTION "CB33-42 Warning
		       Bit 0 = CB33
                   Bit 9 = CB42
                   Bits 10-25 not used"
		::= { bcmsplus6 132 }

bcms6-cb1-16-alarm
	OBJECT-TYPE
	SYNTAX  INTEGER
	ACCESS  read-write
	STATUS  mandatory
	DESCRIPTION "CB1-16 Alarm
		       Bit 0 = CB1
                   Bit 15 = CB16"
		::= { bcmsplus6 133 }

bcms6-cb17-32-alarm
	OBJECT-TYPE
	SYNTAX  INTEGER
	ACCESS  read-write
	STATUS  mandatory
	DESCRIPTION "CB17-32 Alarm
		       Bit 0 = CB17
                   Bit 15 = CB32"
		::= { bcmsplus6 134 }

bcms6-cb33-42-alarm
	OBJECT-TYPE
	SYNTAX  INTEGER
	ACCESS  read-write
	STATUS  mandatory
	DESCRIPTION "CB33-42 Alarm
		       Bit 0 = CB33
                   Bit 9 = CB42
                   Bits 10-25 not used"
		::= { bcmsplus6 135 }

bcms6-cb1-breaker-size
	OBJECT-TYPE
	SYNTAX  INTEGER
	ACCESS  read-write
	STATUS  mandatory
	DESCRIPTION "CB1 Breaker-Size
		     Note for all breaker sizes 1-42: 10 = 10 amps
                     Range is 10 to 100 amps"
		::= { bcmsplus6 136 }

bcms6-cb2-breaker-size
	OBJECT-TYPE
	SYNTAX  INTEGER
	ACCESS  read-write
	STATUS  mandatory
	DESCRIPTION "CB2 Breaker-Size"
		::= { bcmsplus6 137 }

bcms6-cb3-breaker-size
	OBJECT-TYPE
	SYNTAX  INTEGER
	ACCESS  read-write
	STATUS  mandatory
	DESCRIPTION "CB3 Breaker-Size"
		::= { bcmsplus6 138 }

bcms6-cb4-breaker-size
	OBJECT-TYPE
	SYNTAX  INTEGER
	ACCESS  read-write
	STATUS  mandatory
	DESCRIPTION "CB4 Breaker-Size"
		::= { bcmsplus6 139 }

bcms6-cb5-breaker-size
	OBJECT-TYPE
	SYNTAX  INTEGER
	ACCESS  read-write
	STATUS  mandatory
	DESCRIPTION "CB5 Breaker-Size"
		::= { bcmsplus6 140 }

bcms6-cb6-breaker-size
	OBJECT-TYPE
	SYNTAX  INTEGER
	ACCESS  read-write
	STATUS  mandatory
	DESCRIPTION "CB6 Breaker-Size"
		::= { bcmsplus6 141 }
  
bcms6-cb7-breaker-size
	OBJECT-TYPE
	SYNTAX  INTEGER
	ACCESS  read-write
	STATUS  mandatory
	DESCRIPTION "CB7 Breaker-Size"
		::= { bcmsplus6 142 }

bcms6-cb8-breaker-size
	OBJECT-TYPE
	SYNTAX  INTEGER
	ACCESS  read-write
	STATUS  mandatory
	DESCRIPTION "CB8 Breaker-Size"
		::= { bcmsplus6 143 }

bcms6-cb9-breaker-size
	OBJECT-TYPE
	SYNTAX  INTEGER
	ACCESS  read-write
	STATUS  mandatory
	DESCRIPTION "CB9 Breaker-Size"
		::= { bcmsplus6 144 }

bcms6-cb10-breaker-size
	OBJECT-TYPE
	SYNTAX  INTEGER
	ACCESS  read-write
	STATUS  mandatory
	DESCRIPTION "CB10 Breaker-Size"
		::= { bcmsplus6 145 }

bcms6-cb11-breaker-size
	OBJECT-TYPE
	SYNTAX  INTEGER
	ACCESS  read-write
	STATUS  mandatory
	DESCRIPTION "CB11 Breaker-Size"
		::= { bcmsplus6 146 }

bcms6-cb12-breaker-size
	OBJECT-TYPE
	SYNTAX  INTEGER
	ACCESS  read-write
	STATUS  mandatory
	DESCRIPTION "CB12 Breaker-Size"
		::= { bcmsplus6 147 }

bcms6-cb13-breaker-size
	OBJECT-TYPE
	SYNTAX  INTEGER
	ACCESS  read-write
	STATUS  mandatory
	DESCRIPTION "CB13 Breaker-Size"
		::= { bcmsplus6 148 }

bcms6-cb14-breaker-size
	OBJECT-TYPE
	SYNTAX  INTEGER
	ACCESS  read-write
	STATUS  mandatory
	DESCRIPTION "CB14 Breaker-Size"
		::= { bcmsplus6 149 }

bcms6-cb15-breaker-size
	OBJECT-TYPE
	SYNTAX  INTEGER
	ACCESS  read-write
	STATUS  mandatory
	DESCRIPTION "CB15 Breaker-Size"
		::= { bcmsplus6 150 }

bcms6-cb16-breaker-size
	OBJECT-TYPE
	SYNTAX  INTEGER
	ACCESS  read-write
	STATUS  mandatory
	DESCRIPTION "CB16 Breaker-Size"
		::= { bcmsplus6 151 }
  
bcms6-cb17-breaker-size
	OBJECT-TYPE
	SYNTAX  INTEGER
	ACCESS  read-write
	STATUS  mandatory
	DESCRIPTION "CB17 Breaker-Size"
		::= { bcmsplus6 152 }

bcms6-cb18-breaker-size
	OBJECT-TYPE
	SYNTAX  INTEGER
	ACCESS  read-write
	STATUS  mandatory
	DESCRIPTION "CB18 Breaker-Size"
		::= { bcmsplus6 153 }

bcms6-cb19-breaker-size
	OBJECT-TYPE
	SYNTAX  INTEGER
	ACCESS  read-write
	STATUS  mandatory
	DESCRIPTION "CB19 Breaker-Size"
		::= { bcmsplus6 154 }

bcms6-cb20-breaker-size
	OBJECT-TYPE
	SYNTAX  INTEGER
	ACCESS  read-write
	STATUS  mandatory
	DESCRIPTION "CB20 Breaker-Size"
		::= { bcmsplus6 155 }

bcms6-cb21-breaker-size
	OBJECT-TYPE
	SYNTAX  INTEGER
	ACCESS  read-write
	STATUS  mandatory
	DESCRIPTION "CB21 Breaker-Size"
		::= { bcmsplus6 156 }

bcms6-cb22-breaker-size
	OBJECT-TYPE
	SYNTAX  INTEGER
	ACCESS  read-write
	STATUS  mandatory
	DESCRIPTION "CB22 Breaker-Size"
		::= { bcmsplus6 157 }

bcms6-cb23-breaker-size
	OBJECT-TYPE
	SYNTAX  INTEGER
	ACCESS  read-write
	STATUS  mandatory
	DESCRIPTION "CB23 Breaker-Size"
		::= { bcmsplus6 158 }

bcms6-cb24-breaker-size
	OBJECT-TYPE
	SYNTAX  INTEGER
	ACCESS  read-write
	STATUS  mandatory
	DESCRIPTION "CB24 Breaker-Size"
		::= { bcmsplus6 159 }

bcms6-cb25-breaker-size
	OBJECT-TYPE
	SYNTAX  INTEGER
	ACCESS  read-write
	STATUS  mandatory
	DESCRIPTION "CB25 Breaker-Size"
		::= { bcmsplus6 160 }

bcms6-cb26-breaker-size
	OBJECT-TYPE
	SYNTAX  INTEGER
	ACCESS  read-write
	STATUS  mandatory
	DESCRIPTION "CB26 Breaker-Size"
		::= { bcmsplus6 161 }
  
bcms6-cb27-breaker-size
	OBJECT-TYPE
	SYNTAX  INTEGER
	ACCESS  read-write
	STATUS  mandatory
	DESCRIPTION "CB27 Breaker-Size"
		::= { bcmsplus6 162 }

bcms6-cb28-breaker-size
	OBJECT-TYPE
	SYNTAX  INTEGER
	ACCESS  read-write
	STATUS  mandatory
	DESCRIPTION "CB28 Breaker-Size"
		::= { bcmsplus6 163 }

bcms6-cb29-breaker-size
	OBJECT-TYPE
	SYNTAX  INTEGER
	ACCESS  read-write
	STATUS  mandatory
	DESCRIPTION "CB29 Breaker-Size"
		::= { bcmsplus6 164 }

bcms6-cb30-breaker-size
	OBJECT-TYPE
	SYNTAX  INTEGER
	ACCESS  read-write
	STATUS  mandatory
	DESCRIPTION "CB30 Breaker-Size"
		::= { bcmsplus6 165 }

bcms6-cb31-breaker-size
	OBJECT-TYPE
	SYNTAX  INTEGER
	ACCESS  read-write
	STATUS  mandatory
	DESCRIPTION "CB31 Breaker-Size"
		::= { bcmsplus6 166 }

bcms6-cb32-breaker-size
	OBJECT-TYPE
	SYNTAX  INTEGER
	ACCESS  read-write
	STATUS  mandatory
	DESCRIPTION "CB32 Breaker-Size"
		::= { bcmsplus6 167 }

bcms6-cb33-breaker-size
	OBJECT-TYPE
	SYNTAX  INTEGER
	ACCESS  read-write
	STATUS  mandatory
	DESCRIPTION "CB33 Breaker-Size"
		::= { bcmsplus6 168 }

bcms6-cb34-breaker-size
	OBJECT-TYPE
	SYNTAX  INTEGER
	ACCESS  read-write
	STATUS  mandatory
	DESCRIPTION "CB34 Breaker-Size"
		::= { bcmsplus6 169 }

bcms6-cb35-breaker-size
	OBJECT-TYPE
	SYNTAX  INTEGER
	ACCESS  read-write
	STATUS  mandatory
	DESCRIPTION "CB35 Breaker-Size"
		::= { bcmsplus6 170 }

bcms6-cb36-breaker-size
	OBJECT-TYPE
	SYNTAX  INTEGER
	ACCESS  read-write
	STATUS  mandatory
	DESCRIPTION "CB36 Breaker-Size"
		::= { bcmsplus6 171 }
  
bcms6-cb37-breaker-size
	OBJECT-TYPE
	SYNTAX  INTEGER
	ACCESS  read-write
	STATUS  mandatory
	DESCRIPTION "CB37 Breaker-Size"
		::= { bcmsplus6 172 }

bcms6-cb38-breaker-size
	OBJECT-TYPE
	SYNTAX  INTEGER
	ACCESS  read-write
	STATUS  mandatory
	DESCRIPTION "CB38 Breaker-Size"
		::= { bcmsplus6 173 }

bcms6-cb39-breaker-size
	OBJECT-TYPE
	SYNTAX  INTEGER
	ACCESS  read-write
	STATUS  mandatory
	DESCRIPTION "CB39 Breaker-Size"
		::= { bcmsplus6 174 }

bcms6-cb40-breaker-size
	OBJECT-TYPE
	SYNTAX  INTEGER
	ACCESS  read-write
	STATUS  mandatory
	DESCRIPTION "CB40 Breaker-Size"
		::= { bcmsplus6 175 }

bcms6-cb41-breaker-size
	OBJECT-TYPE
	SYNTAX  INTEGER
	ACCESS  read-write
	STATUS  mandatory
	DESCRIPTION "CB41 Breaker-Size"
		::= { bcmsplus6 176 }

bcms6-cb42-breaker-size
	OBJECT-TYPE
	SYNTAX  INTEGER
	ACCESS  read-write
	STATUS  mandatory
	DESCRIPTION "CB42 Breaker-Size"
		::= { bcmsplus6 177 }

bcms6-cb1-warning-threshold
	OBJECT-TYPE
	SYNTAX  INTEGER
	ACCESS  read-write
	STATUS  mandatory
	DESCRIPTION "CB1 CB1-warning-threshold
		     Note for all warning thresholds 1-42: 70 = 70% of breaker size
                     range is 0-100%"
		::= { bcmsplus6 178 }

bcms6-cb2-warning-threshold
	OBJECT-TYPE
	SYNTAX  INTEGER
	ACCESS  read-write
	STATUS  mandatory
	DESCRIPTION "CB2 Warning-Threshold"
		::= { bcmsplus6 179 }

bcms6-cb3-warning-threshold
	OBJECT-TYPE
	SYNTAX  INTEGER
	ACCESS  read-write
	STATUS  mandatory
	DESCRIPTION "CB3 Warning-Threshold"
		::= { bcmsplus6 180 }

bcms6-cb4-warning-threshold
	OBJECT-TYPE
	SYNTAX  INTEGER
	ACCESS  read-write
	STATUS  mandatory
	DESCRIPTION "CB4 Warning-Threshold"
		::= { bcmsplus6 181 }
  
bcms6-cb5-warning-threshold
	OBJECT-TYPE
	SYNTAX  INTEGER
	ACCESS  read-write
	STATUS  mandatory
	DESCRIPTION "CB5 Warning-Threshold"
		::= { bcmsplus6 182 }

bcms6-cb6-warning-threshold
	OBJECT-TYPE
	SYNTAX  INTEGER
	ACCESS  read-write
	STATUS  mandatory
	DESCRIPTION "CB6 Warning-Threshold"
		::= { bcmsplus6 183 }

bcms6-cb7-warning-threshold
	OBJECT-TYPE
	SYNTAX  INTEGER
	ACCESS  read-write
	STATUS  mandatory
	DESCRIPTION "CB7 Warning-Threshold"
		::= { bcmsplus6 184 }

bcms6-cb8-warning-threshold
	OBJECT-TYPE
	SYNTAX  INTEGER
	ACCESS  read-write
	STATUS  mandatory
	DESCRIPTION "CB8 Warning-Threshold"
		::= { bcmsplus6 185 }

bcms6-cb9-warning-threshold
	OBJECT-TYPE
	SYNTAX  INTEGER
	ACCESS  read-write
	STATUS  mandatory
	DESCRIPTION "CB9 Warning-Threshold"
		::= { bcmsplus6 186 }

bcms6-cb10-warning-threshold
	OBJECT-TYPE
	SYNTAX  INTEGER
	ACCESS  read-write
	STATUS  mandatory
	DESCRIPTION "CB10 Warning-Threshold"
		::= { bcmsplus6 187 }

bcms6-cb11-warning-threshold
	OBJECT-TYPE
	SYNTAX  INTEGER
	ACCESS  read-write
	STATUS  mandatory
	DESCRIPTION "CB11 Warning-Threshold"
		::= { bcmsplus6 188 }

bcms6-cb12-warning-threshold
	OBJECT-TYPE
	SYNTAX  INTEGER
	ACCESS  read-write
	STATUS  mandatory
	DESCRIPTION "CB12 Warning-Threshold"
		::= { bcmsplus6 189 }

bcms6-cb13-warning-threshold
	OBJECT-TYPE
	SYNTAX  INTEGER
	ACCESS  read-write
	STATUS  mandatory
	DESCRIPTION "CB13 Warning-Threshold"
		::= { bcmsplus6 190 }

bcms6-cb14-warning-threshold
	OBJECT-TYPE
	SYNTAX  INTEGER
	ACCESS  read-write
	STATUS  mandatory
	DESCRIPTION "CB14 Warning-Threshold"
		::= { bcmsplus6 191 }
  
bcms6-cb15-warning-threshold
	OBJECT-TYPE
	SYNTAX  INTEGER
	ACCESS  read-write
	STATUS  mandatory
	DESCRIPTION "CB15 Warning-Threshold"
		::= { bcmsplus6 192 }

bcms6-cb16-warning-threshold
	OBJECT-TYPE
	SYNTAX  INTEGER
	ACCESS  read-write
	STATUS  mandatory
	DESCRIPTION "CB16 Warning-Threshold"
		::= { bcmsplus6 193 }

bcms6-cb17-warning-threshold
	OBJECT-TYPE
	SYNTAX  INTEGER
	ACCESS  read-write
	STATUS  mandatory
	DESCRIPTION "CB17 Warning-Threshold"
		::= { bcmsplus6 194 }

bcms6-cb18-warning-threshold
	OBJECT-TYPE
	SYNTAX  INTEGER
	ACCESS  read-write
	STATUS  mandatory
	DESCRIPTION "CB18 Warning-Threshold"
		::= { bcmsplus6 195 }

bcms6-cb19-warning-threshold
	OBJECT-TYPE
	SYNTAX  INTEGER
	ACCESS  read-write
	STATUS  mandatory
	DESCRIPTION "CB19 Warning-Threshold"
		::= { bcmsplus6 196 }

bcms6-cb20-warning-threshold
	OBJECT-TYPE
	SYNTAX  INTEGER
	ACCESS  read-write
	STATUS  mandatory
	DESCRIPTION "CB20 Warning-Threshold"
		::= { bcmsplus6 197 }

bcms6-cb21-warning-threshold
	OBJECT-TYPE
	SYNTAX  INTEGER
	ACCESS  read-write
	STATUS  mandatory
	DESCRIPTION "CB21 Warning-Threshold"
		::= { bcmsplus6 198 }

bcms6-cb22-warning-threshold
	OBJECT-TYPE
	SYNTAX  INTEGER
	ACCESS  read-write
	STATUS  mandatory
	DESCRIPTION "CB22 Warning-Threshold"
		::= { bcmsplus6 199 }

bcms6-cb23-warning-threshold
	OBJECT-TYPE
	SYNTAX  INTEGER
	ACCESS  read-write
	STATUS  mandatory
	DESCRIPTION "CB23 Warning-Threshold"
		::= { bcmsplus6 200 }

bcms6-cb24-warning-threshold
	OBJECT-TYPE
	SYNTAX  INTEGER
	ACCESS  read-write
	STATUS  mandatory
	DESCRIPTION "CB24 Warning-Threshold"
		::= { bcmsplus6 201 }
  
bcms6-cb25-warning-threshold
	OBJECT-TYPE
	SYNTAX  INTEGER
	ACCESS  read-write
	STATUS  mandatory
	DESCRIPTION "CB25 Warning-Threshold"
		::= { bcmsplus6 202 }

bcms6-cb26-warning-threshold
	OBJECT-TYPE
	SYNTAX  INTEGER
	ACCESS  read-write
	STATUS  mandatory
	DESCRIPTION "CB26 Warning-Threshold"
		::= { bcmsplus6 203 }

bcms6-cb27-warning-threshold
	OBJECT-TYPE
	SYNTAX  INTEGER
	ACCESS  read-write
	STATUS  mandatory
	DESCRIPTION "CB27 Warning-Threshold"
		::= { bcmsplus6 204 }

bcms6-cb28-warning-threshold
	OBJECT-TYPE
	SYNTAX  INTEGER
	ACCESS  read-write
	STATUS  mandatory
	DESCRIPTION "CB28 Warning-Threshold"
		::= { bcmsplus6 205 }

bcms6-cb29-warning-threshold
	OBJECT-TYPE
	SYNTAX  INTEGER
	ACCESS  read-write
	STATUS  mandatory
	DESCRIPTION "CB29 Warning-Threshold"
		::= { bcmsplus6 206 }

bcms6-cb30-warning-threshold
	OBJECT-TYPE
	SYNTAX  INTEGER
	ACCESS  read-write
	STATUS  mandatory
	DESCRIPTION "CB30 Warning-Threshold"
		::= { bcmsplus6 207 }

bcms6-cb31-warning-threshold
	OBJECT-TYPE
	SYNTAX  INTEGER
	ACCESS  read-write
	STATUS  mandatory
	DESCRIPTION "CB31 Warning-Threshold"
		::= { bcmsplus6 208 }

bcms6-cb32-warning-threshold
	OBJECT-TYPE
	SYNTAX  INTEGER
	ACCESS  read-write
	STATUS  mandatory
	DESCRIPTION "CB32 Warning-Threshold"
		::= { bcmsplus6 209 }

bcms6-cb33-warning-threshold
	OBJECT-TYPE
	SYNTAX  INTEGER
	ACCESS  read-write
	STATUS  mandatory
	DESCRIPTION "CB33 Warning-Threshold"
		::= { bcmsplus6 210 }

bcms6-cb34-warning-threshold
	OBJECT-TYPE
	SYNTAX  INTEGER
	ACCESS  read-write
	STATUS  mandatory
	DESCRIPTION "CB34 Warning-Threshold"
		::= { bcmsplus6 211 }
  
bcms6-cb35-warning-threshold
	OBJECT-TYPE
	SYNTAX  INTEGER
	ACCESS  read-write
	STATUS  mandatory
	DESCRIPTION "CB35 Warning-Threshold"
		::= { bcmsplus6 212 }

bcms6-cb36-warning-threshold
	OBJECT-TYPE
	SYNTAX  INTEGER
	ACCESS  read-write
	STATUS  mandatory
	DESCRIPTION "CB36 Warning-Threshold"
		::= { bcmsplus6 213 }

bcms6-cb37-warning-threshold
	OBJECT-TYPE
	SYNTAX  INTEGER
	ACCESS  read-write
	STATUS  mandatory
	DESCRIPTION "CB37 Warning-Threshold"
		::= { bcmsplus6 214 }

bcms6-cb38-warning-threshold
	OBJECT-TYPE
	SYNTAX  INTEGER
	ACCESS  read-write
	STATUS  mandatory
	DESCRIPTION "CB38 Warning-Threshold"
		::= { bcmsplus6 215 }

bcms6-cb39-warning-threshold
	OBJECT-TYPE
	SYNTAX  INTEGER
	ACCESS  read-write
	STATUS  mandatory
	DESCRIPTION "CB39 Warning-Threshold"
		::= { bcmsplus6 216 }

bcms6-cb40-warning-threshold
	OBJECT-TYPE
	SYNTAX  INTEGER
	ACCESS  read-write
	STATUS  mandatory
	DESCRIPTION "CB40 Warning-Threshold"
		::= { bcmsplus6 217 }

bcms6-cb41-warning-threshold
	OBJECT-TYPE
	SYNTAX  INTEGER
	ACCESS  read-write
	STATUS  mandatory
	DESCRIPTION "CB41 Warning-Threshold"
		::= { bcmsplus6 218 }

bcms6-cb42-warning-threshold
	OBJECT-TYPE
	SYNTAX  INTEGER
	ACCESS  read-write
	STATUS  mandatory
	DESCRIPTION "CB42 Warning-Threshold"
		::= { bcmsplus6 219 }

bcms6-cb1-alarm-threshold
	OBJECT-TYPE
	SYNTAX  INTEGER
	ACCESS  read-write
	STATUS  mandatory
	DESCRIPTION "CB1 Alarm-Threshold
		     Note for all alarm thresholds 1-42: 80 = 80% of breaker size
                     range is 0-100%"
		::= { bcmsplus6 220 }


bcms6-cb2-alarm-threshold
	OBJECT-TYPE
	SYNTAX  INTEGER
	ACCESS  read-write
	STATUS  mandatory
	DESCRIPTION "CB2 Alarm-Threshold"
		::= { bcmsplus6 221 }
  
bcms6-cb3-alarm-threshold
	OBJECT-TYPE
	SYNTAX  INTEGER
	ACCESS  read-write
	STATUS  mandatory
	DESCRIPTION "CB3 Alarm-Threshold"
		::= { bcmsplus6 222 }

bcms6-cb4-alarm-threshold
	OBJECT-TYPE
	SYNTAX  INTEGER
	ACCESS  read-write
	STATUS  mandatory
	DESCRIPTION "CB4 Alarm-Threshold"
		::= { bcmsplus6 223 }

bcms6-cb5-alarm-threshold
	OBJECT-TYPE
	SYNTAX  INTEGER
	ACCESS  read-write
	STATUS  mandatory
	DESCRIPTION "CB5 Alarm-Threshold"
		::= { bcmsplus6 224 }

bcms6-cb6-alarm-threshold
	OBJECT-TYPE
	SYNTAX  INTEGER
	ACCESS  read-write
	STATUS  mandatory
	DESCRIPTION "CB6 Alarm-Threshold"
		::= { bcmsplus6 225 }

bcms6-cb7-alarm-threshold
	OBJECT-TYPE
	SYNTAX  INTEGER
	ACCESS  read-write
	STATUS  mandatory
	DESCRIPTION "CB7 Alarm-Threshold"
		::= { bcmsplus6 226 }

bcms6-cb8-alarm-threshold
	OBJECT-TYPE
	SYNTAX  INTEGER
	ACCESS  read-write
	STATUS  mandatory
	DESCRIPTION "CB8 Alarm-Threshold"
		::= { bcmsplus6 227 }

bcms6-cb9-alarm-threshold
	OBJECT-TYPE
	SYNTAX  INTEGER
	ACCESS  read-write
	STATUS  mandatory
	DESCRIPTION "CB9 Alarm-Threshold"
		::= { bcmsplus6 228 }

bcms6-cb10-alarm-threshold
	OBJECT-TYPE
	SYNTAX  INTEGER
	ACCESS  read-write
	STATUS  mandatory
	DESCRIPTION "CB10 Alarm-Threshold"
		::= { bcmsplus6 229 }

bcms6-cb11-alarm-threshold
	OBJECT-TYPE
	SYNTAX  INTEGER
	ACCESS  read-write
	STATUS  mandatory
	DESCRIPTION "CB11 Alarm-Threshold"
		::= { bcmsplus6 230 }

bcms6-cb12-alarm-threshold
	OBJECT-TYPE
	SYNTAX  INTEGER
	ACCESS  read-write
	STATUS  mandatory
	DESCRIPTION "CB12 Alarm-Threshold"
		::= { bcmsplus6 231 }
  
bcms6-cb13-alarm-threshold
	OBJECT-TYPE
	SYNTAX  INTEGER
	ACCESS  read-write
	STATUS  mandatory
	DESCRIPTION "CB13 Alarm-Threshold"
		::= { bcmsplus6 232 }

bcms6-cb14-alarm-threshold
	OBJECT-TYPE
	SYNTAX  INTEGER
	ACCESS  read-write
	STATUS  mandatory
	DESCRIPTION "CB14 Alarm-Threshold"
		::= { bcmsplus6 233 }

bcms6-cb15-alarm-threshold
	OBJECT-TYPE
	SYNTAX  INTEGER
	ACCESS  read-write
	STATUS  mandatory
	DESCRIPTION "CB15 Alarm-Threshold"
		::= { bcmsplus6 234 }

bcms6-cb16-alarm-threshold
	OBJECT-TYPE
	SYNTAX  INTEGER
	ACCESS  read-write
	STATUS  mandatory
	DESCRIPTION "CB16 Alarm-Threshold"
		::= { bcmsplus6 235 }

bcms6-cb17-alarm-threshold
	OBJECT-TYPE
	SYNTAX  INTEGER
	ACCESS  read-write
	STATUS  mandatory
	DESCRIPTION "CB17 Alarm-Threshold"
		::= { bcmsplus6 236 }

bcms6-cb18-alarm-threshold
	OBJECT-TYPE
	SYNTAX  INTEGER
	ACCESS  read-write
	STATUS  mandatory
	DESCRIPTION "CB18 Alarm-Threshold"
		::= { bcmsplus6 237 }

bcms6-cb19-alarm-threshold
	OBJECT-TYPE
	SYNTAX  INTEGER
	ACCESS  read-write
	STATUS  mandatory
	DESCRIPTION "CB19 Alarm-Threshold"
		::= { bcmsplus6 238 }

bcms6-cb20-alarm-threshold
	OBJECT-TYPE
	SYNTAX  INTEGER
	ACCESS  read-write
	STATUS  mandatory
	DESCRIPTION "CB20 Alarm-Threshold"
		::= { bcmsplus6 239 }

bcms6-cb21-alarm-threshold
	OBJECT-TYPE
	SYNTAX  INTEGER
	ACCESS  read-write
	STATUS  mandatory
	DESCRIPTION "CB21 Alarm-Threshold"
		::= { bcmsplus6 240 }

bcms6-cb22-alarm-threshold
	OBJECT-TYPE
	SYNTAX  INTEGER
	ACCESS  read-write
	STATUS  mandatory
	DESCRIPTION "CB22 Alarm-Threshold"
		::= { bcmsplus6 241 }
  
bcms6-cb23-alarm-threshold
	OBJECT-TYPE
	SYNTAX  INTEGER
	ACCESS  read-write
	STATUS  mandatory
	DESCRIPTION "CB23 Alarm-Threshold"
		::= { bcmsplus6 242 }

bcms6-cb24-alarm-threshold
	OBJECT-TYPE
	SYNTAX  INTEGER
	ACCESS  read-write
	STATUS  mandatory
	DESCRIPTION "CB24 Alarm-Threshold"
		::= { bcmsplus6 243 }

bcms6-cb25-alarm-threshold
	OBJECT-TYPE
	SYNTAX  INTEGER
	ACCESS  read-write
	STATUS  mandatory
	DESCRIPTION "CB25 Alarm-Threshold"
		::= { bcmsplus6 244 }

bcms6-cb26-alarm-threshold
	OBJECT-TYPE
	SYNTAX  INTEGER
	ACCESS  read-write
	STATUS  mandatory
	DESCRIPTION "CB26 Alarm-Threshold"
		::= { bcmsplus6 245 }

bcms6-cb27-alarm-threshold
	OBJECT-TYPE
	SYNTAX  INTEGER
	ACCESS  read-write
	STATUS  mandatory
	DESCRIPTION "CB27 Alarm-Threshold"
		::= { bcmsplus6 246 }

bcms6-cb28-alarm-threshold
	OBJECT-TYPE
	SYNTAX  INTEGER
	ACCESS  read-write
	STATUS  mandatory
	DESCRIPTION "CB28 Alarm-Threshold"
		::= { bcmsplus6 247 }

bcms6-cb29-alarm-threshold
	OBJECT-TYPE
	SYNTAX  INTEGER
	ACCESS  read-write
	STATUS  mandatory
	DESCRIPTION "CB29 Alarm-Threshold"
		::= { bcmsplus6 248 }

bcms6-cb30-alarm-threshold
	OBJECT-TYPE
	SYNTAX  INTEGER
	ACCESS  read-write
	STATUS  mandatory
	DESCRIPTION "CB30 Alarm-Threshold"
		::= { bcmsplus6 249 }

bcms6-cb31-alarm-threshold
	OBJECT-TYPE
	SYNTAX  INTEGER
	ACCESS  read-write
	STATUS  mandatory
	DESCRIPTION "CB31 Alarm-Threshold"
		::= { bcmsplus6 250 }

bcms6-cb32-alarm-threshold
	OBJECT-TYPE
	SYNTAX  INTEGER
	ACCESS  read-write
	STATUS  mandatory
	DESCRIPTION "CB32 Alarm-Threshold"
		::= { bcmsplus6 251 }
  
bcms6-cb33-alarm-threshold
	OBJECT-TYPE
	SYNTAX  INTEGER
	ACCESS  read-write
	STATUS  mandatory
	DESCRIPTION "CB33 Alarm-Threshold"
		::= { bcmsplus6 252 }

bcms6-cb34-alarm-threshold
	OBJECT-TYPE
	SYNTAX  INTEGER
	ACCESS  read-write
	STATUS  mandatory
	DESCRIPTION "CB34 Alarm-Threshold"
		::= { bcmsplus6 253 }

bcms6-cb35-alarm-threshold
	OBJECT-TYPE
	SYNTAX  INTEGER
	ACCESS  read-write
	STATUS  mandatory
	DESCRIPTION "CB35 Alarm-Threshold"
		::= { bcmsplus6 254 }

bcms6-cb36-alarm-threshold
	OBJECT-TYPE
	SYNTAX  INTEGER
	ACCESS  read-write
	STATUS  mandatory
	DESCRIPTION "CB36 Alarm-Threshold"
		::= { bcmsplus6 255 }

bcms6-cb37-alarm-threshold
	OBJECT-TYPE
	SYNTAX  INTEGER
	ACCESS  read-write
	STATUS  mandatory
	DESCRIPTION "CB37 Alarm-Threshold"
		::= { bcmsplus6 256 }

bcms6-cb38-alarm-threshold
	OBJECT-TYPE
	SYNTAX  INTEGER
	ACCESS  read-write
	STATUS  mandatory
	DESCRIPTION "CB38 Alarm-Threshold"
		::= { bcmsplus6 257 }

bcms6-cb39-alarm-threshold
	OBJECT-TYPE
	SYNTAX  INTEGER
	ACCESS  read-write
	STATUS  mandatory
	DESCRIPTION "CB39 Alarm-Threshold"
		::= { bcmsplus6 258 }

bcms6-cb40-alarm-threshold
	OBJECT-TYPE
	SYNTAX  INTEGER
	ACCESS  read-write
	STATUS  mandatory
	DESCRIPTION "CB40 Alarm-Threshold"
		::= { bcmsplus6 259 }

bcms6-cb41-alarm-threshold
	OBJECT-TYPE
	SYNTAX  INTEGER
	ACCESS  read-write
	STATUS  mandatory
	DESCRIPTION "CB41 Alarm-Threshold"
		::= { bcmsplus6 260 }

bcms6-cb42-alarm-threshold
	OBJECT-TYPE
	SYNTAX  INTEGER
	ACCESS  read-write
	STATUS  mandatory
	DESCRIPTION "CB42 Alarm-Threshold"
		::= { bcmsplus6 261 }

bcms6-cb1-warning-time-delay
	OBJECT-TYPE
	SYNTAX  INTEGER
	ACCESS  read-write
	STATUS  mandatory
	DESCRIPTION "CB1 Warning-Time-Delay
		     Note for all warning time delays 1-42: units are in seconds"                     
		::= { bcmsplus6 262 }

bcms6-cb2-warning-time-delay
	OBJECT-TYPE
	SYNTAX  INTEGER
	ACCESS  read-write
	STATUS  mandatory
	DESCRIPTION "CB2 Warning-Time-Delay"
		::= { bcmsplus6 263 }
  
bcms6-cb3-warning-time-delay
	OBJECT-TYPE
	SYNTAX  INTEGER
	ACCESS  read-write
	STATUS  mandatory
	DESCRIPTION "CB3 Warning-Time-Delay"
		::= { bcmsplus6 264 }

bcms6-cb4-warning-time-delay
	OBJECT-TYPE
	SYNTAX  INTEGER
	ACCESS  read-write
	STATUS  mandatory
	DESCRIPTION "CB4 Warning-Time-Delay"
		::= { bcmsplus6 265 }

bcms6-cb5-warning-time-delay
	OBJECT-TYPE
	SYNTAX  INTEGER
	ACCESS  read-write
	STATUS  mandatory
	DESCRIPTION "CB5 Warning-Time-Delay"
		::= { bcmsplus6 266 }

bcms6-cb6-warning-time-delay
	OBJECT-TYPE
	SYNTAX  INTEGER
	ACCESS  read-write
	STATUS  mandatory
	DESCRIPTION "CB6 Warning-Time-Delay"
		::= { bcmsplus6 267 }

bcms6-cb7-warning-time-delay
	OBJECT-TYPE
	SYNTAX  INTEGER
	ACCESS  read-write
	STATUS  mandatory
	DESCRIPTION "CB7 Warning-Time-Delay"
		::= { bcmsplus6 268 }

bcms6-cb8-warning-time-delay
	OBJECT-TYPE
	SYNTAX  INTEGER
	ACCESS  read-write
	STATUS  mandatory
	DESCRIPTION "CB8 Warning-Time-Delay"
		::= { bcmsplus6 269 }

bcms6-cb9-warning-time-delay
	OBJECT-TYPE
	SYNTAX  INTEGER
	ACCESS  read-write
	STATUS  mandatory
	DESCRIPTION "CB9 Warning-Time-Delay"
		::= { bcmsplus6 270 }

bcms6-cb10-warning-time-delay
	OBJECT-TYPE
	SYNTAX  INTEGER
	ACCESS  read-write
	STATUS  mandatory
	DESCRIPTION "CB10 Warning-Time-Delay"
		::= { bcmsplus6 271 }

bcms6-cb11-warning-time-delay
	OBJECT-TYPE
	SYNTAX  INTEGER
	ACCESS  read-write
	STATUS  mandatory
	DESCRIPTION "CB11 Warning-Time-Delay"
		::= { bcmsplus6 272 }

bcms6-cb12-warning-time-delay
	OBJECT-TYPE
	SYNTAX  INTEGER
	ACCESS  read-write
	STATUS  mandatory
	DESCRIPTION "CB12 Warning-Time-Delay"
		::= { bcmsplus6 273 }
  
bcms6-cb13-warning-time-delay
	OBJECT-TYPE
	SYNTAX  INTEGER
	ACCESS  read-write
	STATUS  mandatory
	DESCRIPTION "CB13 Warning-Time-Delay"
		::= { bcmsplus6 274 }

bcms6-cb14-warning-time-delay
	OBJECT-TYPE
	SYNTAX  INTEGER
	ACCESS  read-write
	STATUS  mandatory
	DESCRIPTION "CB14 Warning-Time-Delay"
		::= { bcmsplus6 275 }

bcms6-cb15-warning-time-delay
	OBJECT-TYPE
	SYNTAX  INTEGER
	ACCESS  read-write
	STATUS  mandatory
	DESCRIPTION "CB15 Warning-Time-Delay"
		::= { bcmsplus6 276 }

bcms6-cb16-warning-time-delay
	OBJECT-TYPE
	SYNTAX  INTEGER
	ACCESS  read-write
	STATUS  mandatory
	DESCRIPTION "CB16 Warning-Time-Delay"
		::= { bcmsplus6 277 }

bcms6-cb17-warning-time-delay
	OBJECT-TYPE
	SYNTAX  INTEGER
	ACCESS  read-write
	STATUS  mandatory
	DESCRIPTION "CB17 Warning-Time-Delay"
		::= { bcmsplus6 278 }

bcms6-cb18-warning-time-delay
	OBJECT-TYPE
	SYNTAX  INTEGER
	ACCESS  read-write
	STATUS  mandatory
	DESCRIPTION "CB18 Warning-Time-Delay"
		::= { bcmsplus6 279 }

bcms6-cb19-warning-time-delay
	OBJECT-TYPE
	SYNTAX  INTEGER
	ACCESS  read-write
	STATUS  mandatory
	DESCRIPTION "CB19 Warning-Time-Delay"
		::= { bcmsplus6 280 }

bcms6-cb20-warning-time-delay
	OBJECT-TYPE
	SYNTAX  INTEGER
	ACCESS  read-write
	STATUS  mandatory
	DESCRIPTION "CB20 Warning-Time-Delay"
		::= { bcmsplus6 281 }

bcms6-cb21-warning-time-delay
	OBJECT-TYPE
	SYNTAX  INTEGER
	ACCESS  read-write
	STATUS  mandatory
	DESCRIPTION "CB21 Warning-Time-Delay"
		::= { bcmsplus6 282 }

bcms6-cb22-warning-time-delay
	OBJECT-TYPE
	SYNTAX  INTEGER
	ACCESS  read-write
	STATUS  mandatory
	DESCRIPTION "CB22 Warning-Time-Delay"
		::= { bcmsplus6 283 }
  
bcms6-cb23-warning-time-delay
	OBJECT-TYPE
	SYNTAX  INTEGER
	ACCESS  read-write
	STATUS  mandatory
	DESCRIPTION "CB23 Warning-Time-Delay"
		::= { bcmsplus6 284 }

bcms6-cb24-warning-time-delay
	OBJECT-TYPE
	SYNTAX  INTEGER
	ACCESS  read-write
	STATUS  mandatory
	DESCRIPTION "CB24 Warning-Time-Delay"
		::= { bcmsplus6 285 }

bcms6-cb25-warning-time-delay
	OBJECT-TYPE
	SYNTAX  INTEGER
	ACCESS  read-write
	STATUS  mandatory
	DESCRIPTION "CB25 Warning-Time-Delay"
		::= { bcmsplus6 286 }

bcms6-cb26-warning-time-delay
	OBJECT-TYPE
	SYNTAX  INTEGER
	ACCESS  read-write
	STATUS  mandatory
	DESCRIPTION "CB26 Warning-Time-Delay"
		::= { bcmsplus6 287 }

bcms6-cb27-warning-time-delay
	OBJECT-TYPE
	SYNTAX  INTEGER
	ACCESS  read-write
	STATUS  mandatory
	DESCRIPTION "CB27 Warning-Time-Delay"
		::= { bcmsplus6 288 }

bcms6-cb28-warning-time-delay
	OBJECT-TYPE
	SYNTAX  INTEGER
	ACCESS  read-write
	STATUS  mandatory
	DESCRIPTION "CB28 Warning-Time-Delay"
		::= { bcmsplus6 289 }

bcms6-cb29-warning-time-delay
	OBJECT-TYPE
	SYNTAX  INTEGER
	ACCESS  read-write
	STATUS  mandatory
	DESCRIPTION "CB29 Warning-Time-Delay"
		::= { bcmsplus6 290}

bcms6-cb30-warning-time-delay
	OBJECT-TYPE
	SYNTAX  INTEGER
	ACCESS  read-write
	STATUS  mandatory
	DESCRIPTION "CB30 Warning-Time-Delay"
		::= { bcmsplus6 291 }

bcms6-cb31-warning-time-delay
	OBJECT-TYPE
	SYNTAX  INTEGER
	ACCESS  read-write
	STATUS  mandatory
	DESCRIPTION "CB31 Warning-Time-Delay"
		::= { bcmsplus6 292 }

bcms6-cb32-warning-time-delay
	OBJECT-TYPE
	SYNTAX  INTEGER
	ACCESS  read-write
	STATUS  mandatory
	DESCRIPTION "CB32 Warning-Time-Delay"
		::= { bcmsplus6 293 }
  
bcms6-cb33-warning-time-delay
	OBJECT-TYPE
	SYNTAX  INTEGER
	ACCESS  read-write
	STATUS  mandatory
	DESCRIPTION "CB33 Warning-Time-Delay"
		::= { bcmsplus6 294 }

bcms6-cb34-warning-time-delay
	OBJECT-TYPE
	SYNTAX  INTEGER
	ACCESS  read-write
	STATUS  mandatory
	DESCRIPTION "CB34 Warning-Time-Delay"
		::= { bcmsplus6 295 }

bcms6-cb35-warning-time-delay
	OBJECT-TYPE
	SYNTAX  INTEGER
	ACCESS  read-write
	STATUS  mandatory
	DESCRIPTION "CB35 Warning-Time-Delay"
		::= { bcmsplus6 296 }

bcms6-cb36-warning-time-delay
	OBJECT-TYPE
	SYNTAX  INTEGER
	ACCESS  read-write
	STATUS  mandatory
	DESCRIPTION "CB36 Warning-Time-Delay"
		::= { bcmsplus6 297 }

bcms6-cb37-warning-time-delay
	OBJECT-TYPE
	SYNTAX  INTEGER
	ACCESS  read-write
	STATUS  mandatory
	DESCRIPTION "CB37 Warning-Time-Delay"
		::= { bcmsplus6 298 }

bcms6-cb38-warning-time-delay
	OBJECT-TYPE
	SYNTAX  INTEGER
	ACCESS  read-write
	STATUS  mandatory
	DESCRIPTION "CB38 Warning-Time-Delay"
		::= { bcmsplus6 299 }

bcms6-cb39-warning-time-delay
	OBJECT-TYPE
	SYNTAX  INTEGER
	ACCESS  read-write
	STATUS  mandatory
	DESCRIPTION "CB39 Warning-Time-Delay"
		::= { bcmsplus6 300 }

bcms6-cb40-warning-time-delay
	OBJECT-TYPE
	SYNTAX  INTEGER
	ACCESS  read-write
	STATUS  mandatory
	DESCRIPTION "CB40 Warning-Time-Delay"
		::= { bcmsplus6 301 }

bcms6-cb41-warning-time-delay
	OBJECT-TYPE
	SYNTAX  INTEGER
	ACCESS  read-write
	STATUS  mandatory
	DESCRIPTION "CB41 Warning-Time-Delay"
		::= { bcmsplus6 302 }

bcms6-cb42-warning-time-delay
	OBJECT-TYPE
	SYNTAX  INTEGER
	ACCESS  read-write
	STATUS  mandatory
	DESCRIPTION "CB42 Warning-Time-Delay"
		::= { bcmsplus6 303 }

bcms6-cb1-alarm-time-delay
	OBJECT-TYPE
	SYNTAX  INTEGER
	ACCESS  read-write
	STATUS  mandatory
	DESCRIPTION "CB1 Alarm-Time-Delay
		       Note for all alarm time delays 1-42: units are in seconds"                     
		::= { bcmsplus6 304 }

bcms6-cb2-alarm-time-delay
	OBJECT-TYPE
	SYNTAX  INTEGER
	ACCESS  read-write
	STATUS  mandatory
	DESCRIPTION "CB2 Alarm-Time-Delay"
		::= { bcmsplus6 305 }
  
bcms6-cb3-alarm-time-delay
	OBJECT-TYPE
	SYNTAX  INTEGER
	ACCESS  read-write
	STATUS  mandatory
	DESCRIPTION "CB3 Alarm-Time-Delay"
		::= { bcmsplus6 306 }

bcms6-cb4-alarm-time-delay
	OBJECT-TYPE
	SYNTAX  INTEGER
	ACCESS  read-write
	STATUS  mandatory
	DESCRIPTION "CB4 Alarm-Time-Delay"
		::= { bcmsplus6 307 }

bcms6-cb5-alarm-time-delay
	OBJECT-TYPE
	SYNTAX  INTEGER
	ACCESS  read-write
	STATUS  mandatory
	DESCRIPTION "CB5 Alarm-Time-Delay"
		::= { bcmsplus6 308 }

bcms6-cb6-alarm-time-delay
	OBJECT-TYPE
	SYNTAX  INTEGER
	ACCESS  read-write
	STATUS  mandatory
	DESCRIPTION "CB6 Alarm-Time-Delay"
		::= { bcmsplus6 309 }

bcms6-cb7-alarm-time-delay
	OBJECT-TYPE
	SYNTAX  INTEGER
	ACCESS  read-write
	STATUS  mandatory
	DESCRIPTION "CB7 Alarm-Time-Delay"
		::= { bcmsplus6 310 }

bcms6-cb8-alarm-time-delay
	OBJECT-TYPE
	SYNTAX  INTEGER
	ACCESS  read-write
	STATUS  mandatory
	DESCRIPTION "CB8 Alarm-Time-Delay"
		::= { bcmsplus6 311 }

bcms6-cb9-alarm-time-delay
	OBJECT-TYPE
	SYNTAX  INTEGER
	ACCESS  read-write
	STATUS  mandatory
	DESCRIPTION "CB9 Alarm-Time-Delay"
		::= { bcmsplus6 312 }

bcms6-cb10-alarm-time-delay
	OBJECT-TYPE
	SYNTAX  INTEGER
	ACCESS  read-write
	STATUS  mandatory
	DESCRIPTION "CB10 Alarm-Time-Delay"
		::= { bcmsplus6 313 }

bcms6-cb11-alarm-time-delay
	OBJECT-TYPE
	SYNTAX  INTEGER
	ACCESS  read-write
	STATUS  mandatory
	DESCRIPTION "CB11 Alarm-Time-Delay"
		::= { bcmsplus6 314 }

bcms6-cb12-alarm-time-delay
	OBJECT-TYPE
	SYNTAX  INTEGER
	ACCESS  read-write
	STATUS  mandatory
	DESCRIPTION "CB12 Alarm-Time-Delay"
		::= { bcmsplus6 315 }
  
bcms6-cb13-alarm-time-delay
	OBJECT-TYPE
	SYNTAX  INTEGER
	ACCESS  read-write
	STATUS  mandatory
	DESCRIPTION "CB13 Alarm-Time-Delay"
		::= { bcmsplus6 316 }

bcms6-cb14-alarm-time-delay
	OBJECT-TYPE
	SYNTAX  INTEGER
	ACCESS  read-write
	STATUS  mandatory
	DESCRIPTION "CB14 Alarm-Time-Delay"
		::= { bcmsplus6 317 }

bcms6-cb15-alarm-time-delay
	OBJECT-TYPE
	SYNTAX  INTEGER
	ACCESS  read-write
	STATUS  mandatory
	DESCRIPTION "CB15 Alarm-Time-Delay"
		::= { bcmsplus6 318 }

bcms6-cb16-alarm-time-delay
	OBJECT-TYPE
	SYNTAX  INTEGER
	ACCESS  read-write
	STATUS  mandatory
	DESCRIPTION "CB16 Alarm-Time-Delay"
		::= { bcmsplus6 319 }

bcms6-cb17-alarm-time-delay
	OBJECT-TYPE
	SYNTAX  INTEGER
	ACCESS  read-write
	STATUS  mandatory
	DESCRIPTION "CB17 Alarm-Time-Delay"
		::= { bcmsplus6 320 }

bcms6-cb18-alarm-time-delay
	OBJECT-TYPE
	SYNTAX  INTEGER
	ACCESS  read-write
	STATUS  mandatory
	DESCRIPTION "CB18 Alarm-Time-Delay"
		::= { bcmsplus6 321 }

bcms6-cb19-alarm-time-delay
	OBJECT-TYPE
	SYNTAX  INTEGER
	ACCESS  read-write
	STATUS  mandatory
	DESCRIPTION "CB19 Alarm-Time-Delay"
		::= { bcmsplus6 322 }

bcms6-cb20-alarm-time-delay
	OBJECT-TYPE
	SYNTAX  INTEGER
	ACCESS  read-write
	STATUS  mandatory
	DESCRIPTION "CB20 Alarm-Time-Delay"
		::= { bcmsplus6 323 }

bcms6-cb21-alarm-time-delay
	OBJECT-TYPE
	SYNTAX  INTEGER
	ACCESS  read-write
	STATUS  mandatory
	DESCRIPTION "CB21 Alarm-Time-Delay"
		::= { bcmsplus6 324 }

bcms6-cb22-alarm-time-delay
	OBJECT-TYPE
	SYNTAX  INTEGER
	ACCESS  read-write
	STATUS  mandatory
	DESCRIPTION "CB22 Alarm-Time-Delay"
		::= { bcmsplus6 325 }
  
bcms6-cb23-alarm-time-delay
	OBJECT-TYPE
	SYNTAX  INTEGER
	ACCESS  read-write
	STATUS  mandatory
	DESCRIPTION "CB23 Alarm-Time-Delay"
		::= { bcmsplus6 326 }

bcms6-cb24-alarm-time-delay
	OBJECT-TYPE
	SYNTAX  INTEGER
	ACCESS  read-write
	STATUS  mandatory
	DESCRIPTION "CB24 Alarm-Time-Delay"
		::= { bcmsplus6 327 }

bcms6-cb25-alarm-time-delay
	OBJECT-TYPE
	SYNTAX  INTEGER
	ACCESS  read-write
	STATUS  mandatory
	DESCRIPTION "CB25 Alarm-Time-Delay"
		::= { bcmsplus6 328 }

bcms6-cb26-alarm-time-delay
	OBJECT-TYPE
	SYNTAX  INTEGER
	ACCESS  read-write
	STATUS  mandatory
	DESCRIPTION "CB26 Alarm-Time-Delay"
		::= { bcmsplus6 329 }

bcms6-cb27-alarm-time-delay
	OBJECT-TYPE
	SYNTAX  INTEGER
	ACCESS  read-write
	STATUS  mandatory
	DESCRIPTION "CB27 Alarm-Time-Delay"
		::= { bcmsplus6 330 }

bcms6-cb28-alarm-time-delay
	OBJECT-TYPE
	SYNTAX  INTEGER
	ACCESS  read-write
	STATUS  mandatory
	DESCRIPTION "CB28 Alarm-Time-Delay"
		::= { bcmsplus6 331 }

bcms6-cb29-alarm-time-delay
	OBJECT-TYPE
	SYNTAX  INTEGER
	ACCESS  read-write
	STATUS  mandatory
	DESCRIPTION "CB29 Alarm-Time-Delay"
		::= { bcmsplus6 332 }

bcms6-cb30-alarm-time-delay
	OBJECT-TYPE
	SYNTAX  INTEGER
	ACCESS  read-write
	STATUS  mandatory
	DESCRIPTION "CB30 Alarm-Time-Delay"
		::= { bcmsplus6 333 }

bcms6-cb31-alarm-time-delay
	OBJECT-TYPE
	SYNTAX  INTEGER
	ACCESS  read-write
	STATUS  mandatory
	DESCRIPTION "CB31 Alarm-Time-Delay"
		::= { bcmsplus6 334 }

bcms6-cb32-alarm-time-delay
	OBJECT-TYPE
	SYNTAX  INTEGER
	ACCESS  read-write
	STATUS  mandatory
	DESCRIPTION "CB32 Alarm-Time-Delay"
		::= { bcmsplus6 335 }
  
bcms6-cb33-alarm-time-delay
	OBJECT-TYPE
	SYNTAX  INTEGER
	ACCESS  read-write
	STATUS  mandatory
	DESCRIPTION "CB33 Alarm-Time-Delay"
		::= { bcmsplus6 336 }

bcms6-cb34-alarm-time-delay
	OBJECT-TYPE
	SYNTAX  INTEGER
	ACCESS  read-write
	STATUS  mandatory
	DESCRIPTION "CB34 Alarm-Time-Delay"
		::= { bcmsplus6 337 }

bcms6-cb35-alarm-time-delay
	OBJECT-TYPE
	SYNTAX  INTEGER
	ACCESS  read-write
	STATUS  mandatory
	DESCRIPTION "CB35 Alarm-Time-Delay"
		::= { bcmsplus6 338 }

bcms6-cb36-alarm-time-delay
	OBJECT-TYPE
	SYNTAX  INTEGER
	ACCESS  read-write
	STATUS  mandatory
	DESCRIPTION "CB36 Alarm-Time-Delay"
		::= { bcmsplus6 339 }

bcms6-cb37-alarm-time-delay
	OBJECT-TYPE
	SYNTAX  INTEGER
	ACCESS  read-write
	STATUS  mandatory
	DESCRIPTION "CB37 Alarm-Time-Delay"
		::= { bcmsplus6 340 }

bcms6-cb38-alarm-time-delay
	OBJECT-TYPE
	SYNTAX  INTEGER
	ACCESS  read-write
	STATUS  mandatory
	DESCRIPTION "CB38 Alarm-Time-Delay"
		::= { bcmsplus6 341 }

bcms6-cb39-alarm-time-delay
	OBJECT-TYPE
	SYNTAX  INTEGER
	ACCESS  read-write
	STATUS  mandatory
	DESCRIPTION "CB39 Alarm-Time-Delay"
		::= { bcmsplus6 342 }

bcms6-cb40-alarm-time-delay
	OBJECT-TYPE
	SYNTAX  INTEGER
	ACCESS  read-write
	STATUS  mandatory
	DESCRIPTION "CB40 Alarm-Time-Delay"
		::= { bcmsplus6 343 }

bcms6-cb41-alarm-time-delay
	OBJECT-TYPE
	SYNTAX  INTEGER
	ACCESS  read-write
	STATUS  mandatory
	DESCRIPTION "CB41 Alarm-Time-Delay"
		::= { bcmsplus6 344 }

bcms6-cb42-alarm-time-delay
	OBJECT-TYPE
	SYNTAX  INTEGER
	ACCESS  read-write
	STATUS  mandatory
	DESCRIPTION "CB42 Alarm-Time-Delay"
		::= { bcmsplus6 345 }

bcms6-global-breaker-size
	OBJECT-TYPE
	SYNTAX  INTEGER
	ACCESS  read-write
	STATUS  mandatory
	DESCRIPTION "Global-breaker-size
		     Note for global breaker size: 10 = 10 amps
                     Range is 10 to 100 amps"
		::= { bcmsplus6 346 }

bcms6-global-warning-threshold
	OBJECT-TYPE
	SYNTAX  INTEGER
	ACCESS  read-write
	STATUS  mandatory
	DESCRIPTION "Global-warning-threshold
		     Note for global warning threshold: 70 = 70% of breaker size
                     range is 0-100%"
		::= { bcmsplus6 347 }

bcms6-global-alarm-threshold
	OBJECT-TYPE
	SYNTAX  INTEGER
	ACCESS  read-write
	STATUS  mandatory
	DESCRIPTION "Global-alarm-threshold
		     Note for global alarm threshold: 80 = 80% of breaker size
                     range is 0-100%"
		::= { bcmsplus6 348 }

bcms6-global-warning-time-delay
	OBJECT-TYPE
	SYNTAX  INTEGER
	ACCESS  read-write
	STATUS  mandatory
	DESCRIPTION "Global-warning-time-delay
		     Note for global warning time delay: units are in seconds"                     
		::= { bcmsplus6 349 }

bcms6-global-alarm-time-delay
	OBJECT-TYPE
	SYNTAX  INTEGER
	ACCESS  read-write
	STATUS  mandatory
	DESCRIPTION "Global-alarm-time-delay
		     Note for global alarm time delay: units are in seconds"                     
		::= { bcmsplus6 350 }

bcms6-min-max-reset
	OBJECT-TYPE
	SYNTAX  INTEGER
	ACCESS  read-write
	STATUS  mandatory
	DESCRIPTION "Min-max-Reset
                     Note for Min-max Reset: writing to this register will clear minimum
		     and maximum current values"
		::= { bcmsplus6 351 }

bcms6-global-warning-alarm-register
	OBJECT-TYPE
	SYNTAX  INTEGER
	ACCESS  read-only
	STATUS  mandatory
	DESCRIPTION "Global-Warning-Alarm-Register
			bit 0:	Warning Register 1
			bit 1:	Warning Register 2
			bit 2:	Warning Register 3
			bit 3:	Alarm Register 1
			bit 4:	Alarm Register 2
			bit 5:	Alarm Register 3
			bit 6:	Zero Current Register 1
			bit 7:	Zero Current Register 2
			bit 8:	Zero Current Register 3
			bits 9 – 15: Always read as 0"
		::= { bcmsplus6 352 }

bcms6-meter-alarm-status-latching
	OBJECT-TYPE
	SYNTAX  INTEGER
	ACCESS  read-write
	STATUS  mandatory
	DESCRIPTION "Meter-Alarm-Status-Latching
			bit 0:	Over Current panelboard
			bit 1:	Under Current panelboard
			bit 2: 	Over Current both panelboards 
			bit 3: 	Under Current both panelboards
			bit 4: 	Over Voltage main
			bit 5: 	Under Voltage main
			bit 6: 	Over Voltage alternate
			bit 7: 	Under Voltage alternate
			bits 8 – 15: Not Used"
		::= { bcmsplus6 353 }

bcms6-meter-alarm-status-nonlatching
	OBJECT-TYPE
	SYNTAX  INTEGER
	ACCESS  read-only
	STATUS  mandatory
	DESCRIPTION "Meter-Alarm-Status-Nonlatching
			bit 0:	Over Current panelboard
			bit 1:	Under Current panelboard
			bit 2: 	Over Current both panelboards 
			bit 3: 	Under Current both panelboards
			bit 4: 	Over Voltage main
			bit 5: 	Under Voltage main
			bit 6: 	Over Voltage alternate
			bit 7: 	Under Voltage alternate
			bits 8 – 15: Not Used"
		::= { bcmsplus6 354 }

bcms6-digital-alarm-status
	OBJECT-TYPE
	SYNTAX  INTEGER
	ACCESS  read-only
	STATUS  mandatory
	DESCRIPTION "Digital-Alarm-Status
			bit 0:	Digital alarm 1
			bit 1:	Digital alarm 2
			bit 2: 	Digital alarm 3
			bit 3: 	Digital alarm 4
			bits 4 – 15: Not Used"
		::= { bcmsplus6 355 }

bcms6-current-option-setting
	OBJECT-TYPE
	SYNTAX  INTEGER
	ACCESS  read-only
	STATUS  mandatory
	DESCRIPTION "Current-Option-Setting
			bit 0:	option 0
			bit 1:	option 1
			bit 2: 	option 2 
			bit 3: 	neutral CTs
			bit 4:	no branch CTs
		     Option 0: no main or panelboard CTs. 	(357-359 summation of branch)
								(367-376 not used)
		     Option 1: CTs on main input feeding both panelboards. 
								(357-359 summation of branch)
		     Option 2: CTs on each panel board. 	(367-376 summation of panelboard 1 and 2) 
		     Note: Neutral current monitoring is optional."
		::= { bcmsplus6 356 }

bcms6-current-phase-a-panelboard
	OBJECT-TYPE
	SYNTAX  INTEGER
	ACCESS  read-only
	STATUS  mandatory
	DESCRIPTION "Current-Phase-A-Panelboard
                     Note for all currents: 100 = 10.0 amps"
		::= { bcmsplus6 357 }

bcms6-current-phase-b-panelboard
	OBJECT-TYPE
	SYNTAX  INTEGER
	ACCESS  read-only
	STATUS  mandatory
	DESCRIPTION "Current-Phase-B-Panelboard"
		::= { bcmsplus6 358 }

bcms6-current-phase-c-panelboard
	OBJECT-TYPE
	SYNTAX  INTEGER
	ACCESS  read-only
	STATUS  mandatory
	DESCRIPTION "Current-Phase-C-Panelboard"
		::= { bcmsplus6 359 }

bcms6-current-neutral-panelboard
	OBJECT-TYPE
	SYNTAX  INTEGER
	ACCESS  read-only
	STATUS  mandatory
	DESCRIPTION "Current-Neutral-Panelboard"
		::= { bcmsplus6 360 }


bcms6-over-current-alarm-threshhold-pnlbd
	OBJECT-TYPE
	SYNTAX  INTEGER
	ACCESS  read-write
	STATUS  mandatory
	DESCRIPTION "Over-Current-Alarm-Threshhold-Pnlbd"
		::= { bcmsplus6 361 }

bcms6-under-current-alarm-threshhold-pnlbd
	OBJECT-TYPE
	SYNTAX  INTEGER
	ACCESS  read-write
	STATUS  mandatory
	DESCRIPTION "Under-Current-Alarm-Threshhold-Pnlbd"
		::= { bcmsplus6 362 }

bcms6-over-current-set-counter-pnlbd
	OBJECT-TYPE
	SYNTAX  INTEGER
	ACCESS  read-only
	STATUS  mandatory
	DESCRIPTION "Over-Current-Set-Counter-Pnlbd
		     Note for all counters:
                     The set counter is incremented when the value goes outside the threshold limit
                     The reset counter is incremented when the value is returns to  the threshold limit"
		::= { bcmsplus6 363 }

bcms6-over-current-reset-counter-pnlbd
	OBJECT-TYPE
	SYNTAX  INTEGER
	ACCESS  read-only
	STATUS  mandatory
	DESCRIPTION "Over-Current-Reset-Counter-Pnlbd"
		::= { bcmsplus6 364 }

bcms6-under-current-set-counter-pnlbd
	OBJECT-TYPE
	SYNTAX  INTEGER
	ACCESS  read-only
	STATUS  mandatory
	DESCRIPTION "Under-Current-Set-Counter-Pnlbd"
		::= { bcmsplus6 365 }

bcms6-under-current-reset-counter-pnlbd
	OBJECT-TYPE
	SYNTAX  INTEGER
	ACCESS  read-only
	STATUS  mandatory
	DESCRIPTION "Under-Current-Reset-Counter-Pnlbd"
		::= { bcmsplus6 366 }

bcms6-current-phase-a-both-pnlbd
	OBJECT-TYPE
	SYNTAX  INTEGER
	ACCESS  read-only
	STATUS  mandatory
	DESCRIPTION "Current-Phase-A-Both-Pnlbd"
		::= { bcmsplus6 367 }

bcms6-current-phase-b-both-pnlbd
	OBJECT-TYPE
	SYNTAX  INTEGER
	ACCESS  read-only
	STATUS  mandatory
	DESCRIPTION "Current-Phase-B-Both-Pnlbd"
		::= { bcmsplus6 368 }

bcms6-current-phase-c-both-pnlbd
	OBJECT-TYPE
	SYNTAX  INTEGER
	ACCESS  read-only
	STATUS  mandatory
	DESCRIPTION "Current-Phase-C-Both-Pnlbd"
		::= { bcmsplus6 369 }

bcms6-current-neutral-both-pnlbd
	OBJECT-TYPE
	SYNTAX  INTEGER
	ACCESS  read-only
	STATUS  mandatory
	DESCRIPTION "Current-Neutral-Both-Pnlbd"
		::= { bcmsplus6 370 }


bcms6-over-current-alarm-threshhold-both-pnlbd
	OBJECT-TYPE
	SYNTAX  INTEGER
	ACCESS  read-write
	STATUS  mandatory
	DESCRIPTION "Over-Current-Alarm-Threshhold-Both-Pnlbd"
		::= { bcmsplus6 371 }

bcms6-under-current-alarm-threshhold-both-pnlbd
	OBJECT-TYPE
	SYNTAX  INTEGER
	ACCESS  read-write
	STATUS  mandatory
	DESCRIPTION "Under-Current-Alarm-Threshhold-Both-Pnlbd"
		::= { bcmsplus6 372 }

bcms6-over-current-set-counter-both-pnlbd
	OBJECT-TYPE
	SYNTAX  INTEGER
	ACCESS  read-only
	STATUS  mandatory
	DESCRIPTION "Over-Current-Set-Counter-Both-Pnlbd"
		::= { bcmsplus6 373 }

bcms6-over-current-reset-counter-both-pnlbd
	OBJECT-TYPE
	SYNTAX  INTEGER
	ACCESS  read-only
	STATUS  mandatory
	DESCRIPTION "Over-Current-Reset-Counter-Both-Pnlbd"
		::= { bcmsplus6 374 }

bcms6-under-current-set-counter-both-pnlbd
	OBJECT-TYPE
	SYNTAX  INTEGER
	ACCESS  read-only
	STATUS  mandatory
	DESCRIPTION "Under-Current-Set-Counter-Both-Pnlbd"
		::= { bcmsplus6 375 }

bcms6-under-current-reset-counter-both-pnlbd
	OBJECT-TYPE
	SYNTAX  INTEGER
	ACCESS  read-only
	STATUS  mandatory
	DESCRIPTION "Under-Current-Reset-Counter-Both-Pnlbd"
		::= { bcmsplus6 376 }

bcms6-voltage-option-setting
	OBJECT-TYPE
	SYNTAX  INTEGER
	ACCESS  read-only
	STATUS  mandatory
	DESCRIPTION "Voltage-Option-Setting
			bit 0:	option 0
			bit 1:	option 1
			bit 2: 	option 2 
			bit 3: 	option 3 
			bits 4 – 15: Not Used
                     Option 0: no voltage monitoring. (378-414 not used)
                     Option 1: One voltage feeding 1 or 2 panel boards. (390-401 not used)
                     Option 2: One voltage feeding panelboard 1 and another feeding panelboard 2. (390-401 not used)
                     Option 3: Two voltages tied together through interlocked circuit breakers feeding both panelboards. 
                               Digital input 1 and 2 are used to determine which is feeding the panelboard. A set bit 
                               indicated closed.  If both are closed, main voltage is used."
		::= { bcmsplus6 377 }

bcms6-voltage-a-b-main
	OBJECT-TYPE
	SYNTAX  INTEGER
	ACCESS  read-only
	STATUS  mandatory
	DESCRIPTION "Voltage-A-B-Main
                     Note for all voltages: 1200 = 120.0 volts"
		::= { bcmsplus6 378 }

bcms6-voltage-b-c-main
	OBJECT-TYPE
	SYNTAX  INTEGER
	ACCESS  read-only
	STATUS  mandatory
	DESCRIPTION "Voltage-B-C-Main"
		::= { bcmsplus6 379 }

bcms6-voltage-c-a-main
	OBJECT-TYPE
	SYNTAX  INTEGER
	ACCESS  read-only
	STATUS  mandatory
	DESCRIPTION "Voltage-C-A-Main"
		::= { bcmsplus6 380 }

bcms6-voltage-a-n-main
	OBJECT-TYPE
	SYNTAX  INTEGER
	ACCESS  read-only
	STATUS  mandatory
	DESCRIPTION "Voltage-A-N-Main"
		::= { bcmsplus6 381 }

bcms6-voltage-b-n-main
	OBJECT-TYPE
	SYNTAX  INTEGER
	ACCESS  read-only
	STATUS  mandatory
	DESCRIPTION "Voltage-B-N-Main"
		::= { bcmsplus6 382 }

bcms6-voltage-c-n-main
	OBJECT-TYPE
	SYNTAX  INTEGER
	ACCESS  read-only
	STATUS  mandatory
	DESCRIPTION "Voltage-C-N-Main"
		::= { bcmsplus6 383 }

bcms6-over-voltage-alarm-threshhold-main
	OBJECT-TYPE
	SYNTAX  INTEGER
	ACCESS  read-write
	STATUS  mandatory
	DESCRIPTION "Over-Voltage-Alarm-Threshhold-Main
                     Note All Over and Under Voltage is for L-L values"
		::= { bcmsplus6 384 }

bcms6-under-voltage-alarm-threshhold-main
	OBJECT-TYPE
	SYNTAX  INTEGER
	ACCESS  read-write
	STATUS  mandatory
	DESCRIPTION "Under-Voltage-Alarm-Threshhold-Main"
		::= { bcmsplus6 385 }

bcms6-over-voltage-set-counter-main
	OBJECT-TYPE
	SYNTAX  INTEGER
	ACCESS  read-only
	STATUS  mandatory
	DESCRIPTION "Over-Voltage-Set-Counter-Main"
		::= { bcmsplus6 386 }

bcms6-over-voltage-reset-counter-main
	OBJECT-TYPE
	SYNTAX  INTEGER
	ACCESS  read-only
	STATUS  mandatory
	DESCRIPTION "Over-Voltage-Reset-Counter-Main"
		::= { bcmsplus6 387 }

bcms6-under-voltage-set-counter-main
	OBJECT-TYPE
	SYNTAX  INTEGER
	ACCESS  read-only
	STATUS  mandatory
	DESCRIPTION "Under-Voltage-Set-Counter-Main"
		::= { bcmsplus6 388 }

bcms6-under-voltage-reset-counter-main
	OBJECT-TYPE
	SYNTAX  INTEGER
	ACCESS  read-only
	STATUS  mandatory
	DESCRIPTION "Under-Voltage-Reset-Counter-Main"
		::= { bcmsplus6 389 }


bcms6-voltage-frequency-main
	OBJECT-TYPE
	SYNTAX  INTEGER
	ACCESS  read-only
	STATUS  mandatory
	DESCRIPTION "Voltage-Frequency-Main
                     note for frequency: 600 = 60.0Hz
                     Range is 40-70Hz
                     Note if insufficient voltage is present frequency will read 0xFFFF"
		::= { bcmsplus6 390 }

bcms6-voltage-a-b-alternate
	OBJECT-TYPE
	SYNTAX  INTEGER
	ACCESS  read-only
	STATUS  mandatory
	DESCRIPTION "Voltage-A-B-Alternate"
		::= { bcmsplus6 391 }

bcms6-voltage-b-c-alternate
	OBJECT-TYPE
	SYNTAX  INTEGER
	ACCESS  read-only
	STATUS  mandatory
	DESCRIPTION "Voltage-B-C-Alternate"
		::= { bcmsplus6 392 }

bcms6-voltage-c-a-alternate
	OBJECT-TYPE
	SYNTAX  INTEGER
	ACCESS  read-only
	STATUS  mandatory
	DESCRIPTION "Voltage-C-A-Alternate"
		::= { bcmsplus6 393 }

bcms6-voltage-a-n-alternate
	OBJECT-TYPE
	SYNTAX  INTEGER
	ACCESS  read-only
	STATUS  mandatory
	DESCRIPTION "Voltage-A-N-Alternate"
		::= { bcmsplus6 394 }

bcms6-voltage-b-N-alternate
	OBJECT-TYPE
	SYNTAX  INTEGER
	ACCESS  read-only
	STATUS  mandatory
	DESCRIPTION "Voltage-B-N-Alternate"
		::= { bcmsplus6 395 }

bcms6-voltage-c-n-alternate
	OBJECT-TYPE
	SYNTAX  INTEGER
	ACCESS  read-only
	STATUS  mandatory
	DESCRIPTION "Voltage-C-N-Alternate"
		::= { bcmsplus6 396 }

bcms6-over-voltage-alarm-threshhold-alternate
	OBJECT-TYPE
	SYNTAX  INTEGER
	ACCESS  read-write
	STATUS  mandatory
	DESCRIPTION "Over-Voltage-Alarm-Threshhold-Alternate"
		::= { bcmsplus6 397 }

bcms6-under-voltage-alarm-threshhold-alternate
	OBJECT-TYPE
	SYNTAX  INTEGER
	ACCESS  read-write
	STATUS  mandatory
	DESCRIPTION "Under-Voltage-Alarm-Threshhold-Alternate"
		::= { bcmsplus6 398 }

bcms6-over-voltage-set-counter-alternate
	OBJECT-TYPE
	SYNTAX  INTEGER
	ACCESS  read-only
	STATUS  mandatory
	DESCRIPTION "Over-Voltage-Set-Counter-Alternate"
		::= { bcmsplus6 399 }

bcms6-over-voltage-reset-counter-alternate
	OBJECT-TYPE
	SYNTAX  INTEGER
	ACCESS  read-only
	STATUS  mandatory
	DESCRIPTION "Over-Voltage-Reset-Counter-Alternate"
		::= { bcmsplus6 400 }

bcms6-under-voltage-set-counter-alternate
	OBJECT-TYPE
	SYNTAX  INTEGER
	ACCESS  read-only
	STATUS  mandatory
	DESCRIPTION "Under-Voltage-Set-Counter-Alternate"
		::= { bcmsplus6 401 }

bcms6-under-voltage-reset-counter-alternate
	OBJECT-TYPE
	SYNTAX  INTEGER
	ACCESS  read-only
	STATUS  mandatory
	DESCRIPTION "Under-Voltage-Reset-Counter-Alternate"
		::= { bcmsplus6 402 }

bcms6-real-power-kw
	OBJECT-TYPE
	SYNTAX  INTEGER
	ACCESS  read-only
	STATUS  mandatory
	DESCRIPTION "Real-Power-KW
                     Note for all KWs: 100 = 10.0 KW"
		::= { bcmsplus6 403 }

bcms6-peal-power-phase-a
	OBJECT-TYPE
	SYNTAX  INTEGER
	ACCESS  read-only
	STATUS  mandatory
	DESCRIPTION "Real-Power-Phase-A"
		::= { bcmsplus6 404 }

bcms6-real-power-phase-b
	OBJECT-TYPE
	SYNTAX  INTEGER
	ACCESS  read-only
	STATUS  mandatory
	DESCRIPTION "Real-Power-Phase-B"
		::= { bcmsplus6 405 }

bcms6-real-power-phase-c
	OBJECT-TYPE
	SYNTAX  INTEGER
	ACCESS  read-only
	STATUS  mandatory
	DESCRIPTION "Real-Power-Phase-C"
		::= { bcmsplus6 406 }

bcms6-reactive-power-kvar
	OBJECT-TYPE
	SYNTAX  INTEGER
	ACCESS  read-only
	STATUS  mandatory
	DESCRIPTION "Reactive-Power-KVAR
                     Note for KVAR: 100 = 10.0 KVAR"
		::= { bcmsplus6 407 }

bcms6-apparent-Power-kva
	OBJECT-TYPE
	SYNTAX  INTEGER
	ACCESS  read-only
	STATUS  mandatory
	DESCRIPTION "Apparent-Power-KVA
                     Note for KVA: 100 = 10.0 KVA"
		::= { bcmsplus6 408 }

bcms6-total-power-factor
	OBJECT-TYPE
	SYNTAX  INTEGER
	ACCESS  read-only
	STATUS  mandatory
	DESCRIPTION "Total-Power-Factor
                     Note for all Power Factor: 1000 = 100.0 PF"
		::= { bcmsplus6 409 }

bcms6-power-factor-phase-a
	OBJECT-TYPE
	SYNTAX  INTEGER
	ACCESS  read-only
	STATUS  mandatory
	DESCRIPTION "Power-Factor-Phase-A"
		::= { bcmsplus6 410 }

bcms6-Power-factor-phase-b
	OBJECT-TYPE
	SYNTAX  INTEGER
	ACCESS  read-only
	STATUS  mandatory
	DESCRIPTION "Power-Factor-Phase-B"
		::= { bcmsplus6 411 }

bcms6-Power-factor-phase-c
	OBJECT-TYPE
	SYNTAX  INTEGER
	ACCESS  read-only
	STATUS  mandatory
	DESCRIPTION "Power-Factor-Phase-C"
		::= { bcmsplus6 412 }

bcms6-energy-consumption-kwh-lower-word-integer
	OBJECT-TYPE
	SYNTAX  INTEGER
	ACCESS  read-write
	STATUS  mandatory
	DESCRIPTION "Energy-Consumption-KWh-Lower-Word-Integer
		     Note for KWh: 100 = 100KWh
                     Combine lower and upper integers into a word for total KWh"
		::= { bcmsplus6 413 }

bcms6-energy-consumption-kwh-upper-word-integer
	OBJECT-TYPE
	SYNTAX  INTEGER
	ACCESS  read-write
	STATUS  mandatory
	DESCRIPTION "Energy-Consumption-KWh-Upper-Word-Integer"
		::= { bcmsplus6 414 }

bcms6-main-voltage-thd-phase-a
	OBJECT-TYPE
	SYNTAX  INTEGER
	ACCESS  read-only
	STATUS  mandatory
	DESCRIPTION "Main-Voltage-THD-Phase-A"
		::= { bcmsplus6 415 }

bcms6-main-voltage-thd-phase-b
	OBJECT-TYPE
	SYNTAX  INTEGER
	ACCESS  read-only
	STATUS  mandatory
	DESCRIPTION "Main-Voltage-THD-Phase-B"
		::= { bcmsplus6 416 }

bcms6-main-voltage-thd-phase-c
	OBJECT-TYPE
	SYNTAX  INTEGER
	ACCESS  read-only
	STATUS  mandatory
	DESCRIPTION "Main-Voltage-THD-Phase-C"
		::= { bcmsplus6 417 }

bcms6-alt-voltage-thd-phase-a
	OBJECT-TYPE
	SYNTAX  INTEGER
	ACCESS  read-only
	STATUS  mandatory
	DESCRIPTION "Alt-Voltage-THD-Phase-A"
		::= { bcmsplus6 418 }

bcms6-alt-voltage-thd-phase-b
	OBJECT-TYPE
	SYNTAX  INTEGER
	ACCESS  read-only
	STATUS  mandatory
	DESCRIPTION "Alt-Voltage-THD-Phase-B"
		::= { bcmsplus6 419 }

bcms6-alt-voltage-thd-phase-c
	OBJECT-TYPE
	SYNTAX  INTEGER
	ACCESS  read-only
	STATUS  mandatory
	DESCRIPTION "Alt-Voltage-THD-Phase-C"
		::= { bcmsplus6 420 }

bcms6-current-ground-panelboard
	OBJECT-TYPE
	SYNTAX  INTEGER
	ACCESS  read-only
	STATUS  mandatory
	DESCRIPTION "Current-Ground-Panelboard"
		::= { bcmsplus6 421 }

bcms6-percent-load-phase-a
	OBJECT-TYPE
	SYNTAX  INTEGER
	ACCESS  read-only
	STATUS  mandatory
	DESCRIPTION "Percent Load Phase A"
		::= { bcmsplus6 422 }

bcms6-percent-load-phase-b
	OBJECT-TYPE
	SYNTAX  INTEGER
	ACCESS  read-only
	STATUS  mandatory
	DESCRIPTION "Percent Load Phase B"
		::= { bcmsplus6 423 }

bcms6-percent-load-phase-c
	OBJECT-TYPE
	SYNTAX  INTEGER
	ACCESS  read-only
	STATUS  mandatory
	DESCRIPTION "Percent Load Phase C"
		::= { bcmsplus6 424 }

bcms6-full-load-current
	OBJECT-TYPE
	SYNTAX  INTEGER
	ACCESS  read-write
	STATUS  mandatory
	DESCRIPTION "Full Load Current"
		::= { bcmsplus6 425 }

--------------------------------------------------------------------------------
-- Trap register values
--------------------------------------------------------------------------------

display-summary-trap
        TRAP-TYPE
	  ENTERPRISE	pdi
	  VARIABLES		{ display-alarm }
	  DESCRIPTION	"Dispaly Summary Alarm Trap"
	  ::= 1

END
