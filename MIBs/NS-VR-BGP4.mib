-- These MIBs were created on 1/2/2003
-- This module defines enterprise MIBs for NS BGP
-- 
-- Copyright (c) 1999-2004, Juniper Networks, Inc.
-- All rights reserved.
-- 

-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Descr
--    This module defines the object that are used to monitor
--    NS's BGP configuration  
--
--  Last modified date: 06/20/2005
--  Created from NS-BGP4.MIB  with modified VR table index
--

NETSCREEN-VR-BGP4-MIB DEFINITIONS ::= BEGIN

                IMPORTS
                    MODULE-IDENTITY, OBJECT-TYPE, NOTIFICATION-TYPE,
                    IpAddress, Integer32, Counter32, Gauge32
                        FROM SNMPv2-SMI
                    netscreenTrapDesc, netscreenTrapType
                        FROM NETSCREEN-TRAP-MIB
                    netscreenVR
                        FROM NETSCREEN-SMI;

                nsVrBgp MODULE-IDENTITY
                    LAST-UPDATED "0301020000Z"
                    ORGANIZATION "NS BGP Working Group"
                    CONTACT-INFO
                                "   Customer Support
									NetScreen
									350 Oakmead Parkway
                                    Sunnyvale, CA  94085
                                    USA

                               Tel: 1.877.NETSCREEN
                               E-mail: support@netscreen.com
                               Http://www.netscreen.com"
                        DESCRIPTION
                                "The MIB module for NS-BGP-4."
                    ::= { netscreenVR 6 }

                -- BGP Info table.  This table contains, one entry per
                -- VR, information about the BGP's Version, LocalAs and Identifier.

                nsVrBgpInfoTable OBJECT-TYPE
                    SYNTAX     SEQUENCE OF NsVrBgpInfoEntry
                    MAX-ACCESS not-accessible
                    STATUS     current
                    DESCRIPTION
                            "BGP info table.  This table contains,
                            one entry per VR, information about
                            the BGP's Version, LocalAs and Identifier."
                    ::= { nsVrBgp 1 }

                nsVrBgpInfoEntry OBJECT-TYPE
                    SYNTAX     NsVrBgpInfoEntry
                    MAX-ACCESS not-accessible
                    STATUS     current
                    DESCRIPTION
                            "Entry containing information about the
                            BGP's Version, LocalAs and Identifier"
                    INDEX { nsVrBgpInfoVRID }
                    ::= { nsVrBgpInfoTable 1 }

                NsVrBgpInfoEntry ::= SEQUENCE {
                        nsVrBgpInfoVersion
                            OCTET STRING,
                        nsVrBgpInfoLocalAs
                            INTEGER,
                        nsVrBgpInfoIdentifier
                            IpAddress,
                        nsVrBgpInfoVRID
                            INTEGER
						}

                nsVrBgpInfoVersion OBJECT-TYPE
                    SYNTAX     OCTET STRING (SIZE (1..255))
                    MAX-ACCESS read-only
                    STATUS     current
                    DESCRIPTION
                            "Vector of supported BGP protocol version
                            numbers.  Each peer negotiates the version
                            from this vector.  Versions are identified
                            via the string of bits contained within this
                            object.  The first octet contains bits 0 to
                            7, the second octet contains bits 8 to 15,
                            and so on, with the most significant bit
                            referring to the lowest bit number in the
                            octet (e.g., the MSB of the first octet
                            refers to bit 0).  If a bit, i, is present
                            and set, then the version (i+1) of the BGP
                            is supported."
                    ::= { nsVrBgpInfoEntry 1 }

                nsVrBgpInfoLocalAs OBJECT-TYPE
                    SYNTAX     INTEGER (0..65535)
                    MAX-ACCESS read-only
                    STATUS     current
                    DESCRIPTION
                            "The local autonomous system number."
                    ::= { nsVrBgpInfoEntry 2 }

                nsVrBgpInfoIdentifier OBJECT-TYPE
                    SYNTAX     IpAddress
                    MAX-ACCESS read-only
                    STATUS     current
                    DESCRIPTION
                            "The BGP Identifier of local system."
                    ::= { nsVrBgpInfoEntry 3 }

                nsVrBgpInfoVRID OBJECT-TYPE
                    SYNTAX     INTEGER (0..65535)
                    MAX-ACCESS read-only
                    STATUS     current
                    DESCRIPTION
                            "Virtual Router ID"
                    ::= { nsVrBgpInfoEntry 4 }

                -- BGP Peer table.  This table contains, one entry per
                -- BGP peer, information about the BGP peer.

                nsVrBgpPeerTable OBJECT-TYPE
                    SYNTAX     SEQUENCE OF NsVrBgpPeerEntry
                    MAX-ACCESS not-accessible
                    STATUS     current
                    DESCRIPTION
                            "BGP peer table.  This table contains,
                            one entry per BGP peer, information about
                            the connections with BGP peers."
                    ::= { nsVrBgp 3 }

                nsVrBgpPeerEntry OBJECT-TYPE
                    SYNTAX     NsVrBgpPeerEntry
                    MAX-ACCESS not-accessible
                    STATUS     current
                    DESCRIPTION
                            "Entry containing information about the
                            connection with a BGP peer."
                    INDEX { nsVrBgpPeerRemoteAddr,
                            nsVrBgpPeerVRID }
                    ::= { nsVrBgpPeerTable 1 }

                NsVrBgpPeerEntry ::= SEQUENCE {
                        nsVrBgpPeerIdentifier
                            IpAddress,
                        nsVrBgpPeerState
                            INTEGER,
                        nsVrBgpPeerAdminStatus
                            INTEGER,
                        nsVrBgpPeerNegotiatedVersion
                            Integer32,
                        nsVrBgpPeerLocalAddr
                            IpAddress,
                        nsVrBgpPeerLocalPort
                            INTEGER,
                        nsVrBgpPeerRemoteAddr
                            IpAddress,
                        nsVrBgpPeerRemotePort
                            INTEGER,
                        nsVrBgpPeerRemoteAs
                            INTEGER,
                        nsVrBgpPeerInUpdates
                            Counter32,
                        nsVrBgpPeerOutUpdates
                            Counter32,
                        nsVrBgpPeerInTotalMessages
                            Counter32,
                        nsVrBgpPeerOutTotalMessages
                            Counter32,
                        nsVrBgpPeerLastError
                            OCTET STRING,
                        nsVrBgpPeerFsmEstablishedTransitions
                            Counter32,
                        nsVrBgpPeerFsmEstablishedTime
                            Gauge32,
                        nsVrBgpPeerConnectRetryInterval
                            INTEGER,
                        nsVrBgpPeerHoldTime
                            INTEGER,
                        nsVrBgpPeerKeepAlive

                            INTEGER,
                        nsVrBgpPeerHoldTimeConfigured
                            INTEGER,
                        nsVrBgpPeerKeepAliveConfigured
                            INTEGER,
                        nsVrBgpPeerMinASOriginationInterval
                            INTEGER,
                        nsVrBgpPeerMinRouteAdvertisementInterval
                            INTEGER,
                        nsVrBgpPeerInUpdateElapsedTime
                            Gauge32,
                        nsVrBgpPeerVRID
                            INTEGER
                        }

                nsVrBgpPeerIdentifier OBJECT-TYPE
                    SYNTAX     IpAddress
                    MAX-ACCESS read-only
                    STATUS     current
                    DESCRIPTION
                            "The BGP Identifier of this entry's BGP
                            peer."
                    ::= { nsVrBgpPeerEntry 1 }

                nsVrBgpPeerState OBJECT-TYPE
                    SYNTAX     INTEGER {
                                        idle(1),
                                        connect(2),
                                        active(3),
                                        opensent(4),
                                        openconfirm(5),
                                        established(6)
                               }
                    MAX-ACCESS read-only
                    STATUS     current
                    DESCRIPTION
                            "The BGP peer connection state."
                    ::= { nsVrBgpPeerEntry 2 }

                nsVrBgpPeerAdminStatus OBJECT-TYPE
                    SYNTAX     INTEGER {
                                        stop(1),
                                        start(2)
                               }
                    MAX-ACCESS read-only
                    STATUS     current
                    DESCRIPTION
                            "The desired state of the BGP connection.
                            A transition from 'stop' to 'start' will
                            cause the BGP Start Event to be generated.

                            A transition from 'start' to 'stop' will
                            cause the BGP Stop Event to be generated.
                            This parameter can be used to restart BGP
                            peer connections.  Care should be used in
                            providing write access to this object
                            without adequate authentication."
                    ::= { nsVrBgpPeerEntry 3 }

                nsVrBgpPeerNegotiatedVersion OBJECT-TYPE
                    SYNTAX     Integer32
                    MAX-ACCESS read-only
                    STATUS     current
                    DESCRIPTION
                            "The negotiated version of BGP running
                            between the two peers."
                    ::= { nsVrBgpPeerEntry 4 }

                nsVrBgpPeerLocalAddr OBJECT-TYPE
                    SYNTAX     IpAddress
                    MAX-ACCESS read-only
                    STATUS     current
                    DESCRIPTION
                            "The local IP address of this entry's BGP
                            connection."
                    ::= { nsVrBgpPeerEntry 5 }

                nsVrBgpPeerLocalPort OBJECT-TYPE
                    SYNTAX     INTEGER (0..65535)
                    MAX-ACCESS read-only
                    STATUS     current
                    DESCRIPTION
                            "The local port for the TCP connection
                            between the BGP peers."
                    ::= { nsVrBgpPeerEntry 6 }

                nsVrBgpPeerRemoteAddr OBJECT-TYPE
                    SYNTAX     IpAddress
                    MAX-ACCESS read-only
                    STATUS     current
                    DESCRIPTION
                            "The remote IP address of this entry's BGP
                            peer."
                    ::= { nsVrBgpPeerEntry 7 }

                nsVrBgpPeerRemotePort OBJECT-TYPE
                    SYNTAX     INTEGER (0..65535)
                    MAX-ACCESS read-only
                    STATUS     current

                    DESCRIPTION
                            "The remote port for the TCP connection
                            between the BGP peers.  Note that the
                            objects nsVrBgpPeerLocalAddr,
                            nsVrBgpPeerLocalPort, nsVrBgpPeerRemoteAddr and
                            nsVrBgpPeerRemotePort provide the appropriate
                            reference to the standard MIB TCP
                            connection table."
                    ::= { nsVrBgpPeerEntry 8 }

                nsVrBgpPeerRemoteAs OBJECT-TYPE
                    SYNTAX     INTEGER (0..65535)
                    MAX-ACCESS read-only
                    STATUS     current
                    DESCRIPTION
                            "The remote autonomous system number."
                    ::= { nsVrBgpPeerEntry 9 }

                nsVrBgpPeerInUpdates OBJECT-TYPE
                    SYNTAX     Counter32
                    MAX-ACCESS read-only
                    STATUS     current
                    DESCRIPTION
                            "The number of BGP UPDATE messages
                            received on this connection.  This object
                            should be initialized to zero (0) when the
                            connection is established."
                    ::= { nsVrBgpPeerEntry 10 }

                nsVrBgpPeerOutUpdates OBJECT-TYPE
                    SYNTAX     Counter32
                    MAX-ACCESS read-only
                    STATUS     current
                    DESCRIPTION
                            "The number of BGP UPDATE messages
                            transmitted on this connection.  This
                            object should be initialized to zero (0)
                            when the connection is established."
                    ::= { nsVrBgpPeerEntry 11 }

                nsVrBgpPeerInTotalMessages OBJECT-TYPE
                    SYNTAX     Counter32
                    MAX-ACCESS read-only
                    STATUS     current
                    DESCRIPTION
                            "The total number of messages received
                            from the remote peer on this connection.
                            This object should be initialized to zero

                            when the connection is established."
                    ::= { nsVrBgpPeerEntry 12 }

                nsVrBgpPeerOutTotalMessages OBJECT-TYPE
                    SYNTAX     Counter32
                    MAX-ACCESS read-only
                    STATUS     current
                    DESCRIPTION
                            "The total number of messages transmitted to
                            the remote peer on this connection.  This
                            object should be initialized to zero when
                            the connection is established."
                    ::= { nsVrBgpPeerEntry 13 }

                nsVrBgpPeerLastError OBJECT-TYPE
                    SYNTAX     OCTET STRING (SIZE (2))
                    MAX-ACCESS read-only
                    STATUS     current
                    DESCRIPTION
                            "The last error code and subcode seen by this
                            peer on this connection.  If no error has
                            occurred, this field is zero.  Otherwise, the
                            first byte of this two byte OCTET STRING
                            contains the error code, and the second byte
                            contains the subcode."
                    ::= { nsVrBgpPeerEntry 14 }

                nsVrBgpPeerFsmEstablishedTransitions OBJECT-TYPE
                    SYNTAX     Counter32
                    MAX-ACCESS read-only
                    STATUS     current
                    DESCRIPTION
                            "The total number of times the BGP FSM
                            transitioned into the established state."
                    ::= { nsVrBgpPeerEntry 15 }

                nsVrBgpPeerFsmEstablishedTime OBJECT-TYPE
                    SYNTAX     Gauge32
                    MAX-ACCESS read-only
                    STATUS     current
                    DESCRIPTION
                            "This timer indicates how long (in
                            seconds) this peer has been in the
                            Established state or how long
                            since this peer was last in the
                            Established state.  It is set to zero when
                            a new peer is configured or the router is
                            booted."

                    ::= { nsVrBgpPeerEntry 16 }

                nsVrBgpPeerConnectRetryInterval OBJECT-TYPE
                    SYNTAX     INTEGER (1..65535)
                    MAX-ACCESS read-only
                    STATUS     current
                    DESCRIPTION
                            "Time interval in seconds for the
                            ConnectRetry timer.  The suggested value
                            for this timer is 120 seconds."
                    ::= { nsVrBgpPeerEntry 17 }

                nsVrBgpPeerHoldTime OBJECT-TYPE
                    SYNTAX     INTEGER  ( 0 | 3..65535 )
                    MAX-ACCESS read-only
                    STATUS     current
                    DESCRIPTION
                            "Time interval in seconds for the Hold
                            Timer established with the peer.  The
                            value of this object is calculated by this
                            BGP speaker by using the smaller of the
                            value in nsVrBgpPeerHoldTimeConfigured and the
                            Hold Time received in the OPEN message.
                            This value must be at lease three seconds
                            if it is not zero (0) in which case the
                            Hold Timer has not been established with
                            the peer, or, the value of
                            nsVrBgpPeerHoldTimeConfigured is zero (0)."
                    ::= { nsVrBgpPeerEntry 18 }

                nsVrBgpPeerKeepAlive OBJECT-TYPE
                    SYNTAX     INTEGER ( 0 | 1..21845 )
                    MAX-ACCESS read-only
                    STATUS     current
                    DESCRIPTION
                            "Time interval in seconds for the KeepAlive
                            timer established with the peer.  The value
                            of this object is calculated by this BGP
                            speaker such that, when compared with
                            nsVrBgpPeerHoldTime, it has the same
                            proportion as what
                            nsVrBgpPeerKeepAliveConfigured has when
                            compared with nsVrBgpPeerHoldTimeConfigured.
                            If the value of this object is zero (0),
                            it indicates that the KeepAlive timer has
                            not been established with the peer, or,
                            the value of nsVrBgpPeerKeepAliveConfigured is
                            zero (0)."

                    ::= { nsVrBgpPeerEntry 19 }

                nsVrBgpPeerHoldTimeConfigured OBJECT-TYPE
                    SYNTAX     INTEGER ( 0 | 3..65535 )
                    MAX-ACCESS read-only
                    STATUS     current
                    DESCRIPTION
                            "Time interval in seconds for the Hold Time
                            configured for this BGP speaker with this
                            peer.  This value is placed in an OPEN
                            message sent to this peer by this BGP
                            speaker, and is compared with the Hold
                            Time field in an OPEN message received
                            from the peer when determining the Hold
                            Time (nsVrBgpPeerHoldTime) with the peer.
                            This value must not be less than three
                            seconds if it is not zero (0) in which
                            case the Hold Time is NOT to be
                            established with the peer.  The suggested
                            value for this timer is 90 seconds."
                    ::= { nsVrBgpPeerEntry 20 }

                nsVrBgpPeerKeepAliveConfigured OBJECT-TYPE
                    SYNTAX     INTEGER ( 0 | 1..21845 )
                    MAX-ACCESS read-only
                    STATUS     current
                    DESCRIPTION
                            "Time interval in seconds for the
                            KeepAlive timer configured for this BGP
                            speaker with this peer.  The value of this
                            object will only determine the
                            KEEPALIVE messages' frequency relative to
                            the value specified in
                            nsVrBgpPeerHoldTimeConfigured; the actual
                            time interval for the KEEPALIVE messages
                            is indicated by nsVrBgpPeerKeepAlive.  A
                            reasonable maximum value for this timer
                            would be configured to be one
                            third of that of
                            nsVrBgpPeerHoldTimeConfigured.
                            If the value of this object is zero (0),
                            no periodical KEEPALIVE messages are sent
                            to the peer after the BGP connection has
                            been established.  The suggested value for
                            this timer is 30 seconds."
                    ::= { nsVrBgpPeerEntry 21 }

                nsVrBgpPeerMinASOriginationInterval OBJECT-TYPE
                    SYNTAX     INTEGER (1..65535)
                    MAX-ACCESS read-only
                    STATUS     current
                    DESCRIPTION
                            "Time interval in seconds for the
                            MinASOriginationInterval timer.
                            The suggested value for this timer is 15
                            seconds."
                    ::= { nsVrBgpPeerEntry 22 }

                nsVrBgpPeerMinRouteAdvertisementInterval OBJECT-TYPE
                    SYNTAX     INTEGER (1..65535)
                    MAX-ACCESS read-only
                    STATUS     current
                    DESCRIPTION
                            "Time interval in seconds for the
                            MinRouteAdvertisementInterval timer.
                            The suggested value for this timer is 30
                            seconds."
                    ::= { nsVrBgpPeerEntry 23 }

                nsVrBgpPeerInUpdateElapsedTime OBJECT-TYPE
                    SYNTAX     Gauge32
                    MAX-ACCESS read-only
                    STATUS     current
                    DESCRIPTION
                            "Elapsed time in seconds since the last BGP
                            UPDATE message was received from the peer.
                            Each time nsVrBgpPeerInUpdates is incremented,
                            the value of this object is set to zero
                            (0)."
                    ::= { nsVrBgpPeerEntry 24 }

                nsVrBgpPeerVRID OBJECT-TYPE
                    SYNTAX     INTEGER (0..65535)
                    MAX-ACCESS read-only
                    STATUS     current
                    DESCRIPTION
                            "Virtual Router ID"
                    ::= { nsVrBgpPeerEntry 25 }

                
                -- BGP-4 Received Path Attribute Table.  This table
                -- contains, one entry per path to a network, path
                -- attributes received from all peers running BGP-4.

                nsVrBgp4PathAttrTable OBJECT-TYPE
                    SYNTAX     SEQUENCE OF NsVrBgp4PathAttrEntry
                    MAX-ACCESS not-accessible
                    STATUS     current
                    DESCRIPTION
                            "The BGP-4 Received Path Attribute Table
                            contains information about paths to
                            destination networks received from all
                            BGP4 peers."
                    ::= { nsVrBgp 6 }

                nsVrBgp4PathAttrEntry OBJECT-TYPE
                    SYNTAX     NsVrBgp4PathAttrEntry
                    MAX-ACCESS not-accessible
                    STATUS     current
                    DESCRIPTION
                            "Information about a path to a network."
                    INDEX { nsVrBgp4PathAttrIpAddrPrefix,
                            nsVrBgp4PathAttrIpAddrPrefixLen,
                            nsVrBgp4PathAttrPeer,
                            nsVrBgp4PathAttrVRID            }
                    ::= { nsVrBgp4PathAttrTable 1 }

                NsVrBgp4PathAttrEntry ::= SEQUENCE {
                    nsVrBgp4PathAttrPeer
                         IpAddress,
                    nsVrBgp4PathAttrIpAddrPrefixLen
                         INTEGER,
                    nsVrBgp4PathAttrIpAddrPrefix
                         IpAddress,
                    nsVrBgp4PathAttrOrigin
                         INTEGER,
                    nsVrBgp4PathAttrASPathSegment

                         OCTET STRING,
                    nsVrBgp4PathAttrNextHop
                         IpAddress,
                    nsVrBgp4PathAttrMultiExitDisc
                         INTEGER,
                    nsVrBgp4PathAttrLocalPref
                         INTEGER,
                    nsVrBgp4PathAttrAtomicAggregate
                         INTEGER,
                    nsVrBgp4PathAttrAggregatorAS
                         INTEGER,
                    nsVrBgp4PathAttrAggregatorAddr
                         IpAddress,
                    nsVrBgp4PathAttrCalcLocalPref
                         INTEGER,
                    nsVrBgp4PathAttrBest
                         INTEGER,
                    nsVrBgp4PathAttrUnknown
                         OCTET STRING,
                    nsVrBgp4PathAttrVRID
                         INTEGER

                }

                nsVrBgp4PathAttrPeer OBJECT-TYPE
                    SYNTAX     IpAddress
                    MAX-ACCESS read-only
                    STATUS     current
                    DESCRIPTION
                            "The IP address of the peer where the path
                            information was learned."
                    ::= { nsVrBgp4PathAttrEntry 1 }

                nsVrBgp4PathAttrIpAddrPrefixLen OBJECT-TYPE
                    SYNTAX     INTEGER (0..32)
                    MAX-ACCESS read-only
                    STATUS     current
                    DESCRIPTION
                            "Length in bits of the IP address prefix
                            in the Network Layer Reachability
                            Information field."
                    ::= { nsVrBgp4PathAttrEntry 2 }

                nsVrBgp4PathAttrIpAddrPrefix OBJECT-TYPE
                    SYNTAX     IpAddress
                    MAX-ACCESS read-only
                    STATUS     current
                    DESCRIPTION
                            "An IP address prefix in the Network Layer
                            Reachability Information field.  This object

                            is an IP address containing the prefix with
                            length specified by
                            nsVrBgp4PathAttrIpAddrPrefixLen.
                            Any bits beyond the length specified by
                            nsVrBgp4PathAttrIpAddrPrefixLen are zeroed."
                    ::= { nsVrBgp4PathAttrEntry 3 }

                nsVrBgp4PathAttrOrigin OBJECT-TYPE
                    SYNTAX     INTEGER {
                                         igp(1),-- networks are interior
                                         egp(2),-- networks learned
                                                -- via EGP
                                         incomplete(3) -- undetermined
                                       }
                    MAX-ACCESS read-only
                    STATUS     current
                    DESCRIPTION
                            "The ultimate origin of the path
                            information."
                    ::= { nsVrBgp4PathAttrEntry 4 }

                nsVrBgp4PathAttrASPathSegment OBJECT-TYPE
                    SYNTAX     OCTET STRING (SIZE (2..255))
                    MAX-ACCESS read-only
                    STATUS     current
                    DESCRIPTION
                            "The sequence of AS path segments.  Each AS
                            path segment is represented by a triple
                            <type, length, value>.

                            The type is a 1-octet field which has two
                            possible values:
                                 1      AS_SET: unordered set of ASs a
                                             route in the UPDATE
                                             message has traversed
                                 2      AS_SEQUENCE: ordered set of ASs
                                             a route in the UPDATE
                                             message has traversed.

                            The length is a 1-octet field containing the
                            number of ASs in the value field.

                            The value field contains one or more AS
                            numbers, each AS is represented in the octet
                            string as a pair of octets according to the
                            following algorithm:

                                first-byte-of-pair = ASNumber / 256;
                                second-byte-of-pair = ASNumber & 255;"
                    ::= { nsVrBgp4PathAttrEntry 5 }

                nsVrBgp4PathAttrNextHop OBJECT-TYPE
                    SYNTAX     IpAddress
                    MAX-ACCESS read-only
                    STATUS     current
                    DESCRIPTION
                            "The address of the border router that
                            should be used for the destination
                            network."
                    ::= { nsVrBgp4PathAttrEntry 6 }

                nsVrBgp4PathAttrMultiExitDisc OBJECT-TYPE
                    SYNTAX     INTEGER (-1..2147483647)
                    MAX-ACCESS read-only
                    STATUS     current
                    DESCRIPTION
                            "This metric is used to discriminate
                            between multiple exit points to an
                            adjacent autonomous system.  A value of -1
                            indicates the absence of this attribute."
                    ::= { nsVrBgp4PathAttrEntry 7 }

                nsVrBgp4PathAttrLocalPref OBJECT-TYPE
                    SYNTAX     INTEGER (-1..2147483647)
                    MAX-ACCESS read-only
                    STATUS     current
                    DESCRIPTION
                            "The originating BGP4 speaker's degree of
                            preference for an advertised route.  A
                            value of -1 indicates the absence of this
                            attribute."
                    ::= { nsVrBgp4PathAttrEntry 8 }

                nsVrBgp4PathAttrAtomicAggregate OBJECT-TYPE
                    SYNTAX     INTEGER {
                                   lessSpecificRrouteNotSelected(1),
                                   lessSpecificRouteSelected(2)
                               }
                    MAX-ACCESS read-only
                    STATUS     current
                    DESCRIPTION
                            "Whether or not the local system has
                            selected a less specific route without
                            selecting a more specific route."
                    ::= { nsVrBgp4PathAttrEntry 9 }

                nsVrBgp4PathAttrAggregatorAS OBJECT-TYPE
                    SYNTAX     INTEGER (0..65535)
                    MAX-ACCESS read-only
                    STATUS     current
                    DESCRIPTION
                            "The AS number of the last BGP4 speaker that
                            performed route aggregation.  A value of
                            zero (0) indicates the absence of this
                            attribute."
                    ::= { nsVrBgp4PathAttrEntry 10 }

                nsVrBgp4PathAttrAggregatorAddr OBJECT-TYPE
                    SYNTAX     IpAddress
                    MAX-ACCESS read-only
                    STATUS     current
                    DESCRIPTION
                            "The IP address of the last BGP4 speaker
                            that performed route aggregation.  A value
                            of 0.0.0.0 indicates the absence of this
                            attribute."
                    ::= { nsVrBgp4PathAttrEntry 11 }

                nsVrBgp4PathAttrCalcLocalPref OBJECT-TYPE
                    SYNTAX     INTEGER (-1..2147483647)
                    MAX-ACCESS read-only
                    STATUS     current
                    DESCRIPTION
                            "The degree of preference calculated by the
                            receiving BGP4 speaker for an advertised
                            route.  A value of -1 indicates the
                            absence of this attribute."
                    ::= { nsVrBgp4PathAttrEntry 12 }

                nsVrBgp4PathAttrBest OBJECT-TYPE
                    SYNTAX     INTEGER {
                                   false(1),-- not chosen as best route
                                   true(2) -- chosen as best route
                               }
                    MAX-ACCESS read-only
                    STATUS     current
                    DESCRIPTION
                            "An indication of whether or not this route
                            was chosen as the best BGP4 route."
                    ::= { nsVrBgp4PathAttrEntry 13 }

               nsVrBgp4PathAttrUnknown OBJECT-TYPE
                    SYNTAX     OCTET STRING (SIZE(0..255))
                    MAX-ACCESS read-only

                    STATUS     current
                    DESCRIPTION
                            "One or more path attributes not understood
                             by this BGP4 speaker.  Size zero (0)
                             indicates the absence of such
                             attribute(s).  Octets beyond the maximum
                             size, if any, are not recorded by this
                             object."
                    ::= { nsVrBgp4PathAttrEntry 14 }

                nsVrBgp4PathAttrVRID OBJECT-TYPE
                    SYNTAX     INTEGER (0..65535)
                    MAX-ACCESS read-only
                    STATUS     current
                    DESCRIPTION
                            "Virtual Router ID"
                    ::= { nsVrBgp4PathAttrEntry 15 }

                -- Traps.

                nsVrBgpTraps                OBJECT IDENTIFIER ::= { nsVrBgp 7 }

                nsVrBgpEstablished NOTIFICATION-TYPE
                    OBJECTS { netscreenTrapType,
                              netscreenTrapDesc,
                              nsVrBgpPeerIdentifier,
                              nsVrBgpPeerVRID,
                              nsVrBgpPeerLastError,
                              nsVrBgpPeerState      }
                    STATUS  current
                    DESCRIPTION
                            "The BGP Established event is generated when
                            the BGP FSM enters the ESTABLISHED state."
                    ::= { nsVrBgpTraps 1 }


END
