-- Copyright (c) Phonetics, Inc. 2002.
-- Sensaphone is a Trademark of Phonetics, Inc.
-- Version : 1.4 07/12/05
--	History
--	1.4 -  added Web programming configs
--	1.3 -  changed HP trap severitys to MAJOR/MINOR/NORMAL

-- Title: SENSAPHONE TOP LEVEL MIB for Unit 1

-- *************************************************************************
-- ************************************************************************
-- SENSAPHONE-MIB { iso org(3) dod(6) internet(1) private(4)
--    enterprises(1) sensaphone(8338) }

-- Uncomment the #condInclude's to compile with SMICng. Set env using:
-- SMICINCL=/opt/mibs
-- export SMICINCL

--#condInclude "rfc1155.inc"
--#condInclude "rfc1213.inc"
--#condInclude "rfc1212.inc"
--#condInclude "rfc1215.inc"

SENSAPHONE-MIB DEFINITIONS ::= BEGIN

IMPORTS
   enterprises								            FROM RFC1155-SMI
   DisplayString                                FROM RFC1213-MIB
   OBJECT-TYPE                                  FROM RFC-1212
   TRAP-TYPE                                    FROM RFC-1215;

sensaphone          OBJECT IDENTIFIER ::=  { enterprises 8338 }
products            OBJECT IDENTIFIER ::=  { sensaphone 1 }
hardware            OBJECT IDENTIFIER ::=  { products 1 }
ims4000             OBJECT IDENTIFIER ::=  { hardware 1 }
imsLite             OBJECT IDENTIFIER ::=  { hardware 2 }
imsTrapArgs         OBJECT IDENTIFIER ::=  { hardware 100 }

-- Units

host                OBJECT IDENTIFIER ::=  { ims4000 1 }
node1               OBJECT IDENTIFIER ::=  { ims4000 2 }
node2               OBJECT IDENTIFIER ::=  { ims4000 3 }
node3               OBJECT IDENTIFIER ::=  { ims4000 4 }
node4               OBJECT IDENTIFIER ::=  { ims4000 5 }
node5               OBJECT IDENTIFIER ::=  { ims4000 6 }
node6               OBJECT IDENTIFIER ::=  { ims4000 7 }
node7               OBJECT IDENTIFIER ::=  { ims4000 8 }
node8               OBJECT IDENTIFIER ::=  { ims4000 9 }
node9               OBJECT IDENTIFIER ::=  { ims4000 10 }
node10              OBJECT IDENTIFIER ::=  { ims4000 11 }
node11              OBJECT IDENTIFIER ::=  { ims4000 12 }
node12              OBJECT IDENTIFIER ::=  { ims4000 13 }
node13              OBJECT IDENTIFIER ::=  { ims4000 14 }
node14              OBJECT IDENTIFIER ::=  { ims4000 15 }
node15              OBJECT IDENTIFIER ::=  { ims4000 16 }
node16              OBJECT IDENTIFIER ::=  { ims4000 17 }
node17              OBJECT IDENTIFIER ::=  { ims4000 18 }
node18              OBJECT IDENTIFIER ::=  { ims4000 19 }
node19              OBJECT IDENTIFIER ::=  { ims4000 20 }
node20              OBJECT IDENTIFIER ::=  { ims4000 21 }
node21              OBJECT IDENTIFIER ::=  { ims4000 22 }
node22              OBJECT IDENTIFIER ::=  { ims4000 23 }
node23              OBJECT IDENTIFIER ::=  { ims4000 24 }
node24              OBJECT IDENTIFIER ::=  { ims4000 25 }
node25              OBJECT IDENTIFIER ::=  { ims4000 26 }
node26              OBJECT IDENTIFIER ::=  { ims4000 27 }
node27              OBJECT IDENTIFIER ::=  { ims4000 28 }
node28              OBJECT IDENTIFIER ::=  { ims4000 29 }
node29              OBJECT IDENTIFIER ::=  { ims4000 30 }
node30              OBJECT IDENTIFIER ::=  { ims4000 31 }
node31              OBJECT IDENTIFIER ::=  { ims4000 32 }

-- Sections

hostSystem          OBJECT IDENTIFIER ::=  { host 1 }
hostProfiles        OBJECT IDENTIFIER ::=  { host 2 }
hostClasses  				OBJECT IDENTIFIER ::=  { host 3 }
hostSecurity        OBJECT IDENTIFIER ::=  { host 4 }
hostDatalog        	OBJECT IDENTIFIER ::=  { host 5 }
hostTemplates				OBJECT IDENTIFIER ::=  { host 6 }
hostCameras					OBJECT IDENTIFIER ::=  { host 7 }
hostEnv             OBJECT IDENTIFIER ::=  { host 8 }
hostIP              OBJECT IDENTIFIER ::=  { host 9 }
hostUnit						OBJECT IDENTIFIER ::=  { host 10 }
hostPG							OBJECT IDENTIFIER ::=  { host 11 }
hostDiags						OBJECT IDENTIFIER ::=  { host 12 }

node1Env             OBJECT IDENTIFIER ::=  { node1 8 }
node1IP              OBJECT IDENTIFIER ::=  { node1 9 }
node1Unit            OBJECT IDENTIFIER ::=  { node1 10 }
node1PG		           OBJECT IDENTIFIER ::=  { node1 11 }
node1Diags	         OBJECT IDENTIFIER ::=  { node1 12}
node2Env             OBJECT IDENTIFIER ::=  { node2 8 }
node2IP              OBJECT IDENTIFIER ::=  { node2 9 }
node2Unit            OBJECT IDENTIFIER ::=  { node2 10 }
node2PG		           OBJECT IDENTIFIER ::=  { node2 11}
node2Diags	         OBJECT IDENTIFIER ::=  { node2 12}
node3Env             OBJECT IDENTIFIER ::=  { node3 8 }
node3IP              OBJECT IDENTIFIER ::=  { node3 9 }
node3Unit            OBJECT IDENTIFIER ::=  { node3 10 }
node3PG		           OBJECT IDENTIFIER ::=  { node3 11}
node3Diags	         OBJECT IDENTIFIER ::=  { node3 12}
node4Env             OBJECT IDENTIFIER ::=  { node4 8 }
node4IP              OBJECT IDENTIFIER ::=  { node4 9 }
node4Unit            OBJECT IDENTIFIER ::=  { node4 10 }
node4PG		           OBJECT IDENTIFIER ::=  { node4 11}
node4Diags	         OBJECT IDENTIFIER ::=  { node4 12}
node5Env             OBJECT IDENTIFIER ::=  { node5 8 }
node5IP              OBJECT IDENTIFIER ::=  { node5 9 }
node5Unit            OBJECT IDENTIFIER ::=  { node5 10}
node5PG		           OBJECT IDENTIFIER ::=  { node5 11}
node5Diags	         OBJECT IDENTIFIER ::=  { node5 12}
node6Env             OBJECT IDENTIFIER ::=  { node6 8 }
node6IP              OBJECT IDENTIFIER ::=  { node6 9 }
node6Unit            OBJECT IDENTIFIER ::=  { node6 10}
node6PG		           OBJECT IDENTIFIER ::=  { node6 11}
node6Diags	         OBJECT IDENTIFIER ::=  { node6 12}
node7Env             OBJECT IDENTIFIER ::=  { node7 8 }
node7IP              OBJECT IDENTIFIER ::=  { node7 9 }
node7Unit            OBJECT IDENTIFIER ::=  { node7 10}
node7PG		           OBJECT IDENTIFIER ::=  { node7 11}
node7Diags	         OBJECT IDENTIFIER ::=  { node7 12}
node8Env             OBJECT IDENTIFIER ::=  { node8 8 }
node8IP              OBJECT IDENTIFIER ::=  { node8 9 }
node8Unit            OBJECT IDENTIFIER ::=  { node8 10}
node8PG		           OBJECT IDENTIFIER ::=  { node8 11}
node8Diags	         OBJECT IDENTIFIER ::=  { node8 12}
node9Env             OBJECT IDENTIFIER ::=  { node9 8 }
node9IP              OBJECT IDENTIFIER ::=  { node9 9 }
node9Unit            OBJECT IDENTIFIER ::=  { node9 10}
node9PG		           OBJECT IDENTIFIER ::=  { node9 11}
node9Diags	         OBJECT IDENTIFIER ::=  { node9 12}
node10Env            OBJECT IDENTIFIER ::=  { node10 8 }
node10IP             OBJECT IDENTIFIER ::=  { node10 9 }
node10Unit           OBJECT IDENTIFIER ::=  { node10 10}
node10PG		         OBJECT IDENTIFIER ::= 	{ node10 11}
node10Diags	         OBJECT IDENTIFIER ::=  { node10 12}
node11Env            OBJECT IDENTIFIER ::=  { node11 8 }
node11IP             OBJECT IDENTIFIER ::=  { node11 9 }
node11Unit           OBJECT IDENTIFIER ::=  { node11 10}
node11PG		         OBJECT IDENTIFIER ::= 	{ node11 11}
node11Diags	         OBJECT IDENTIFIER ::=  { node11 12}
node12Env            OBJECT IDENTIFIER ::=  { node12 8 }
node12IP             OBJECT IDENTIFIER ::=  { node12 9 }
node12Unit           OBJECT IDENTIFIER ::=  { node12 10}
node12PG		         OBJECT IDENTIFIER ::=  { node12 11}
node12Diags	         OBJECT IDENTIFIER ::=  { node12 12}
node13Env            OBJECT IDENTIFIER ::=  { node13 8 }
node13IP             OBJECT IDENTIFIER ::=  { node13 9 }
node13Unit           OBJECT IDENTIFIER ::=  { node13 10}
node13PG		         OBJECT IDENTIFIER ::=  { node13 11}
node13Diags	         OBJECT IDENTIFIER ::=  { node13 12}
node14Env            OBJECT IDENTIFIER ::=  { node14 8 }
node14IP             OBJECT IDENTIFIER ::=  { node14 9 }
node14Unit           OBJECT IDENTIFIER ::=  { node14 10}
node14PG		         OBJECT IDENTIFIER ::=  { node14 11}
node14Diags	         OBJECT IDENTIFIER ::=  { node14 12}
node15Env            OBJECT IDENTIFIER ::=  { node15 8 }
node15IP             OBJECT IDENTIFIER ::=  { node15 9 }
node15Unit           OBJECT IDENTIFIER ::=  { node15 10}
node15PG		         OBJECT IDENTIFIER ::=  { node15 11}
node15Diags	         OBJECT IDENTIFIER ::=  { node15 12}
node16Env            OBJECT IDENTIFIER ::=  { node16 8 }
node16IP             OBJECT IDENTIFIER ::=  { node16 9 }
node16Unit           OBJECT IDENTIFIER ::=  { node16 10}
node16PG		         OBJECT IDENTIFIER ::=  { node16 11}
node16Diags	         OBJECT IDENTIFIER ::=  { node16 12}
node17Env            OBJECT IDENTIFIER ::=  { node17 8 }
node17IP             OBJECT IDENTIFIER ::=  { node17 9 }
node17Unit           OBJECT IDENTIFIER ::=  { node17 10}
node17PG		         OBJECT IDENTIFIER ::=  { node17 11}
node17Diags	         OBJECT IDENTIFIER ::=  { node17 12}
node18Env            OBJECT IDENTIFIER ::=  { node18 8 }
node18IP             OBJECT IDENTIFIER ::=  { node18 9 }
node18Unit           OBJECT IDENTIFIER ::=  { node18 10}
node18PG		         OBJECT IDENTIFIER ::=  { node18 11}
node18Diags	         OBJECT IDENTIFIER ::=  { node18 12}
node19Env            OBJECT IDENTIFIER ::=  { node19 8 }
node19IP             OBJECT IDENTIFIER ::=  { node19 9 }
node19Unit           OBJECT IDENTIFIER ::=  { node19 10}
node19PG		         OBJECT IDENTIFIER ::=  { node19 11}
node19Diags	         OBJECT IDENTIFIER ::=  { node19 12}
node20Env            OBJECT IDENTIFIER ::=  { node20 8 }
node20IP             OBJECT IDENTIFIER ::=  { node20 9 }
node20Unit           OBJECT IDENTIFIER ::=  { node20 10}
node20PG		         OBJECT IDENTIFIER ::=  { node20 11}
node20Diags	         OBJECT IDENTIFIER ::=  { node20 12}
node21Env            OBJECT IDENTIFIER ::=  { node21 8 }
node21IP             OBJECT IDENTIFIER ::=  { node21 9 }
node21Unit           OBJECT IDENTIFIER ::=  { node21 10}
node21PG		         OBJECT IDENTIFIER ::=  { node21 11}
node21Diags	         OBJECT IDENTIFIER ::=  { node21 12}
node22Env            OBJECT IDENTIFIER ::=  { node22 8 }
node22IP             OBJECT IDENTIFIER ::=  { node22 9 }
node22Unit           OBJECT IDENTIFIER ::=  { node22 10}
node22PG		         OBJECT IDENTIFIER ::=  { node22 11}
node22Diags	         OBJECT IDENTIFIER ::=  { node22 12}
node23Env            OBJECT IDENTIFIER ::=  { node23 8 }
node23IP             OBJECT IDENTIFIER ::=  { node23 9 }
node23Unit           OBJECT IDENTIFIER ::=  { node23 10}
node23PG		         OBJECT IDENTIFIER ::=  { node23 11}
node23Diags	         OBJECT IDENTIFIER ::=  { node23 12}
node24Env            OBJECT IDENTIFIER ::=  { node24 8 }
node24IP             OBJECT IDENTIFIER ::=  { node24 9 }
node24Unit           OBJECT IDENTIFIER ::=  { node24 10}
node24PG		         OBJECT IDENTIFIER ::=  { node24 11}
node24Diags	         OBJECT IDENTIFIER ::=  { node24 12}
node25Env            OBJECT IDENTIFIER ::=  { node25 8 }
node25IP             OBJECT IDENTIFIER ::=  { node25 9 }
node25Unit           OBJECT IDENTIFIER ::=  { node25 10}
node25PG		         OBJECT IDENTIFIER ::=  { node25 11}
node25Diags	         OBJECT IDENTIFIER ::=  { node25 12}
node26Env            OBJECT IDENTIFIER ::=  { node26 8 }
node26IP             OBJECT IDENTIFIER ::=  { node26 9 }
node26Unit           OBJECT IDENTIFIER ::=  { node26 10}
node26PG		         OBJECT IDENTIFIER ::=  { node26 11}
node26Diags	         OBJECT IDENTIFIER ::=  { node26 12}
node27Env            OBJECT IDENTIFIER ::=  { node27 8 }
node27IP             OBJECT IDENTIFIER ::=  { node27 9 }
node27Unit           OBJECT IDENTIFIER ::=  { node27 10}
node27PG		         OBJECT IDENTIFIER ::=  { node27 11}
node27Diags	         OBJECT IDENTIFIER ::=  { node27 12}
node28Env            OBJECT IDENTIFIER ::=  { node28 8 }
node28IP             OBJECT IDENTIFIER ::=  { node28 9 }
node28Unit           OBJECT IDENTIFIER ::=  { node28 10}
node28PG		         OBJECT IDENTIFIER ::=  { node28 11}
node28Diags	         OBJECT IDENTIFIER ::=  { node28 12}
node29Env            OBJECT IDENTIFIER ::=  { node29 8 }
node29IP             OBJECT IDENTIFIER ::=  { node29 9 }
node29Unit           OBJECT IDENTIFIER ::=  { node29 10}
node29PG		         OBJECT IDENTIFIER ::=  { node29 11}
node29Diags	         OBJECT IDENTIFIER ::=  { node29 12}
node30Env            OBJECT IDENTIFIER ::=  { node30 8 }
node30IP             OBJECT IDENTIFIER ::=  { node30 9 }
node30Unit           OBJECT IDENTIFIER ::=  { node30 10}
node30PG		         OBJECT IDENTIFIER ::=  { node30 11}
node30Diags	         OBJECT IDENTIFIER ::=  { node30 12}
node31Env            OBJECT IDENTIFIER ::=  { node31 8}
node31IP             OBJECT IDENTIFIER ::=  { node31 9 }
node31Unit           OBJECT IDENTIFIER ::=  { node31 10}
node31PG		         OBJECT IDENTIFIER ::=  { node31 11}
node31Diags					 OBJECT IDENTIFIER ::=  { node31 12}

-- Env tables

envHostTable	OBJECT-TYPE
	SYNTAX	SEQUENCE OF	EnvHostEntry
	ACCESS not-accessible
	STATUS	mandatory
	DESCRIPTION
		"A List of Env entries"
	::= { hostEnv	1 }

envHostEntry	OBJECT-TYPE
	SYNTAX EnvHostEntry
	ACCESS not-accessible
	STATUS	mandatory
	DESCRIPTION
		"A Env entry"
	INDEX { envHostIndex }
	::= { envHostTable 1 }

EnvHostEntry ::=
	SEQUENCE {
		envHostIndex
			INTEGER,
		envHostInputName
			DisplayString,
		envHostInputType
			INTEGER,
		envHostInputInUse
			INTEGER,
		envHostInputUserInUse
			INTEGER,
		envHostInputEnable
			INTEGER,
		envHostInputValue
			INTEGER,
		envHostInputStatus
			INTEGER,
		envHostInputMin
			INTEGER,
		envHostInputMax
			INTEGER,
		envHostInputLastAlarm
			DisplayString,
		envHostInputLastAck
			DisplayString,
		envHostInputLowLimit
			INTEGER,
		envHostInputHighLimit
			INTEGER,
		envHostInputCalib
			INTEGER,
		envHostInputRecTime
			INTEGER,
		envHostInputResetTime
			INTEGER,
		envHostInputAlarmOnRTN
			INTEGER,
		envHostInputClass
			INTEGER,
		envHostInputDatalogEnable
			INTEGER,
		envHostInputCustomVoice
			DisplayString,
		envHostInputAck
			INTEGER
	}

envHostIndex				OBJECT-TYPE
	SYNTAX				INTEGER (1..11)
	ACCESS				read-write
	STATUS				mandatory
	DESCRIPTION	"The index of the env entry 1..11"
	::= { envHostEntry 1 }

envHostInputName		OBJECT-TYPE
	SYNTAX				DisplayString
	ACCESS				read-write
	STATUS				mandatory
	DESCRIPTION	"Name for Input"
	::= { envHostEntry 2 }

envHostInputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envHostEntry 3 }

envHostInputInUse	OBJECT-TYPE
	SYNTAX		INTEGER {	false(1),true(2) }
	ACCESS		read-only
	STATUS		mandatory
	DESCRIPTION	"Sensor plugged in"
	::= { envHostEntry 4 }

envHostInputUserInUse	OBJECT-TYPE
	SYNTAX		INTEGER {	false(1),true(2) }
	ACCESS		read-write
	STATUS		mandatory
	DESCRIPTION	"Channel Enable"
	::= { envHostEntry 5 }

envHostInputEnable	OBJECT-TYPE
	SYNTAX		INTEGER { false(1),true(2) }
	ACCESS		read-only
	STATUS		mandatory
	DESCRIPTION	"Input enabled by scheduler"
	::= { envHostEntry 6 }

envHostInputValue	OBJECT-TYPE
	SYNTAX		INTEGER
	ACCESS		read-only
	STATUS		mandatory
	DESCRIPTION	"Real time value of this input"
	::= { envHostEntry 7 }

envHostInputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envHostEntry 8 }

envHostInputMin		OBJECT-TYPE
	SYNTAX		INTEGER
	ACCESS		read-only
	STATUS		mandatory
	DESCRIPTION	"The minimum value this input has reached"
	::= { envHostEntry 9 }

envHostInputMax		OBJECT-TYPE
	SYNTAX		INTEGER
	ACCESS		read-only
	STATUS		mandatory
	DESCRIPTION	"The maximum value this input has reached"
	::= { envHostEntry 10 }

envHostInputLastAlarm	OBJECT-TYPE
	SYNTAX		DisplayString
	ACCESS		read-only
	STATUS		mandatory
	DESCRIPTION	"Timestamp of the last alarm"
	::= {  envHostEntry 11 }

envHostInputLastAck	OBJECT-TYPE
	SYNTAX		DisplayString
	ACCESS		read-only
	STATUS		mandatory
	DESCRIPTION	"Timestamp of the last alarm Ack"
	::= { envHostEntry 12 }

envHostInputLowLimit	OBJECT-TYPE
	SYNTAX		INTEGER
	ACCESS		read-write
	STATUS		mandatory
	DESCRIPTION	"The low alarm threshold"
	::= { envHostEntry 13 }

envHostInputHighLimit	OBJECT-TYPE
	SYNTAX		INTEGER
	ACCESS		read-write
	STATUS		mandatory
	DESCRIPTION	"The high alarm threshold"
	::= { envHostEntry 14}

envHostInputCalib	OBJECT-TYPE
	SYNTAX		INTEGER
	ACCESS		read-write
	STATUS		mandatory
	DESCRIPTION	"Calibration offset"
	::= { envHostEntry 15 }

envHostInputRecTime	OBJECT-TYPE
	SYNTAX		INTEGER
	ACCESS		read-write
	STATUS		mandatory
	DESCRIPTION	"Time in seconds for an alarm to be recognized"
	::= { envHostEntry 16 }

envHostInputResetTime	OBJECT-TYPE
	SYNTAX		INTEGER
	ACCESS		read-write
	STATUS		mandatory
	DESCRIPTION	"A value &gt;= 30 mins enables feature, 0 disables"
	::= { envHostEntry 17 }

envHostInputAlarmOnRTN	OBJECT-TYPE
	SYNTAX		INTEGER { false(1),true(2) }
	ACCESS		read-write
	STATUS		mandatory
	DESCRIPTION	"Allow an alarm to occur when a condition goes back to normal"
	::= { envHostEntry 18 }

envHostInputClass	OBJECT-TYPE
	SYNTAX		INTEGER
	ACCESS		read-write
	STATUS		mandatory
	DESCRIPTION	"Alarm class of Input (255 is none)"
	::= { envHostEntry 19 }

envHostInputDatalogEnable	OBJECT-TYPE
	SYNTAX		INTEGER { false(1),true(2) }
	ACCESS		read-write
	STATUS		mandatory
	DESCRIPTION	"Datalog Input"
	::= { envHostEntry 20 }

envHostInputCustomVoice	OBJECT-TYPE
	SYNTAX		DisplayString
	ACCESS		read-write
	STATUS		mandatory
	DESCRIPTION	"WAV file for the custom voice message"
	::= { envHostEntry 21 }

envHostInputAck	OBJECT-TYPE
	SYNTAX		INTEGER { false(1),true(2) }
	ACCESS		read-write
	STATUS		mandatory
	DESCRIPTION	"Ack alarm"
	::= { envHostEntry 22 }

envNode1Table	OBJECT-TYPE
	SYNTAX	SEQUENCE OF	EnvNode1Entry
	ACCESS not-accessible
	STATUS	mandatory
	DESCRIPTION
		"A List of Env entries"
	::= { node1Env	1 }

envNode1Entry	OBJECT-TYPE
	SYNTAX EnvNode1Entry
	ACCESS not-accessible
	STATUS	mandatory
	DESCRIPTION
		"A Env entry"
	INDEX { envNode1Index }
	::= { envNode1Table 1 }

EnvNode1Entry ::=
	SEQUENCE {
		envNode1Index
			INTEGER,
		envNode1InputName
			DisplayString,
		envNode1InputType
			INTEGER,
		envNode1InputInUse
			INTEGER,
		envNode1InputUserInUse
			INTEGER,
		envNode1InputEnable
			INTEGER,
		envNode1InputValue
			INTEGER,
		envNode1InputStatus
			INTEGER,
		envNode1InputMin
			INTEGER,
		envNode1InputMax
			INTEGER,
		envNode1InputLastAlarm
			DisplayString,
		envNode1InputLastAck
			DisplayString,
		envNode1InputLowLimit
			INTEGER,
		envNode1InputHighLimit
			INTEGER,
		envNode1InputCalib
			INTEGER,
		envNode1InputRecTime
			INTEGER,
		envNode1InputResetTime
			INTEGER,
		envNode1InputAlarmOnRTN
			INTEGER,
		envNode1InputClass
			INTEGER,
		envNode1InputDatalogEnable
			INTEGER,
		envNode1InputCustomVoice
			DisplayString,
		envNode1InputAck
			INTEGER
	}

envNode1Index				OBJECT-TYPE
	SYNTAX				INTEGER (1..11)
	ACCESS				read-write
	STATUS				mandatory
	DESCRIPTION	"The index of the env entry 1..11"
	::= { envNode1Entry 1 }

envNode1InputName		OBJECT-TYPE
	SYNTAX				DisplayString
	ACCESS				read-write
	STATUS				mandatory
	DESCRIPTION	"Name for Input"
	::= { envNode1Entry 2 }

envNode1InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),	undef1(14),undef2(15),none(16),hostPower(17),
		nodePower(18),battery(19),sound(20),ip(21)
	}
	ACCESS				read-only
	STATUS				mandatory
	DESCRIPTION	"Type of sensor"
	::= { envNode1Entry 3 }

envNode1InputInUse	OBJECT-TYPE
	SYNTAX		INTEGER {	false(1),true(2) }
	ACCESS		read-only
	STATUS		mandatory
	DESCRIPTION	"Sensor plugged in"
	::= { envNode1Entry 4 }

envNode1InputUserInUse	OBJECT-TYPE
	SYNTAX		INTEGER {	false(1),true(2) }
	ACCESS		read-write
	STATUS		mandatory
	DESCRIPTION	"Channel Enable"
	::= { envNode1Entry 5 }

envNode1InputEnable	OBJECT-TYPE
	SYNTAX		INTEGER { false(1),true(2) }
	ACCESS		read-only
	STATUS		mandatory
	DESCRIPTION	"Input enabled by scheduler"
	::= { envNode1Entry 6 }

envNode1InputValue	OBJECT-TYPE
	SYNTAX		INTEGER
	ACCESS		read-only
	STATUS		mandatory
	DESCRIPTION	"Real time value of this input"
	::= { envNode1Entry 7 }

envNode1InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode1Entry 8 }

envNode1InputMin		OBJECT-TYPE
	SYNTAX		INTEGER
	ACCESS		read-only
	STATUS		mandatory
	DESCRIPTION	"The minimum value this input has reached"
	::= { envNode1Entry 9 }

envNode1InputMax		OBJECT-TYPE
	SYNTAX		INTEGER
	ACCESS		read-only
	STATUS		mandatory
	DESCRIPTION	"The maximum value this input has reached"
	::= { envNode1Entry 10 }

envNode1InputLastAlarm	OBJECT-TYPE
	SYNTAX		DisplayString
	ACCESS		read-only
	STATUS		mandatory
	DESCRIPTION	"Timestamp of the last alarm"
	::= {  envNode1Entry 11 }

envNode1InputLastAck	OBJECT-TYPE
	SYNTAX		DisplayString
	ACCESS		read-only
	STATUS		mandatory
	DESCRIPTION	"Timestamp of the last alarm Ack"
	::= { envNode1Entry 12 }

envNode1InputLowLimit	OBJECT-TYPE
	SYNTAX		INTEGER
	ACCESS		read-write
	STATUS		mandatory
	DESCRIPTION	"The low alarm threshold"
	::= { envNode1Entry 13 }

envNode1InputHighLimit	OBJECT-TYPE
	SYNTAX		INTEGER
	ACCESS		read-write
	STATUS		mandatory
	DESCRIPTION	"The high alarm threshold"
	::= { envNode1Entry 14 }

envNode1InputCalib	OBJECT-TYPE
	SYNTAX		INTEGER
	ACCESS		read-write
	STATUS		mandatory
	DESCRIPTION	"Calibration offset"
	::= { envNode1Entry 15 }

envNode1InputRecTime	OBJECT-TYPE
	SYNTAX		INTEGER
	ACCESS		read-write
	STATUS		mandatory
	DESCRIPTION	"Time in seconds for an alarm to be recognized"
	::= { envNode1Entry 16 }

envNode1InputResetTime	OBJECT-TYPE
	SYNTAX		INTEGER
	ACCESS		read-write
	STATUS		mandatory
	DESCRIPTION	"A value &gt;= 30 mins enables feature, 0 disables"
	::= { envNode1Entry 17 }

envNode1InputAlarmOnRTN	OBJECT-TYPE
	SYNTAX		INTEGER { false(1),true(2) }
	ACCESS		read-write
	STATUS		mandatory
	DESCRIPTION	"Allow an alarm to occur when a condition goes back to normal"
	::= { envNode1Entry 18 }

envNode1InputClass	OBJECT-TYPE
	SYNTAX		INTEGER
	ACCESS		read-write
	STATUS		mandatory
	DESCRIPTION	"Alarm class of Input (255 is none)"
	::= { envNode1Entry 19 }

envNode1InputDatalogEnable	OBJECT-TYPE
	SYNTAX		INTEGER { false(1),true(2) }
	ACCESS		read-write
	STATUS		mandatory
	DESCRIPTION	"Allow this input being included into the data logger"
	::= { envNode1Entry 20 }

envNode1InputCustomVoice	OBJECT-TYPE
	SYNTAX		DisplayString
	ACCESS		read-write
	STATUS		mandatory
	DESCRIPTION	"WAV file for the custom voice message"
	::= { envNode1Entry 21 }

envNode1InputAck	OBJECT-TYPE
	SYNTAX		INTEGER { false(1),true(2) }
	ACCESS		read-write
	STATUS		mandatory
	DESCRIPTION	"Ack alarm"
	::= { envNode1Entry 22 }

envNode2Table	OBJECT-TYPE
	SYNTAX	SEQUENCE OF	EnvNode2Entry
	ACCESS not-accessible
	STATUS	mandatory
	DESCRIPTION
		"A List of Env entries"
	::= { node2Env	1 }

envNode2Entry	OBJECT-TYPE
	SYNTAX EnvNode2Entry
	ACCESS not-accessible
	STATUS	mandatory
	DESCRIPTION
		"A Env entry"
	INDEX { envNode2Index }
	::= { envNode2Table 1 }

EnvNode2Entry ::=
	SEQUENCE {
		envNode2Index
			INTEGER,
		envNode2InputName
			DisplayString,
		envNode2InputType
			INTEGER,
		envNode2InputInUse
			INTEGER,
		envNode2InputUserInUse
			INTEGER,
		envNode2InputEnable
			INTEGER,
		envNode2InputValue
			INTEGER,
		envNode2InputStatus
			INTEGER,
		envNode2InputMin
			INTEGER,
		envNode2InputMax
			INTEGER,
		envNode2InputLastAlarm
			DisplayString,
		envNode2InputLastAck
			DisplayString,
		envNode2InputLowLimit
			INTEGER,
		envNode2InputHighLimit
			INTEGER,
		envNode2InputCalib
			INTEGER,
		envNode2InputRecTime
			INTEGER,
		envNode2InputResetTime
			INTEGER,
		envNode2InputAlarmOnRTN
			INTEGER,
		envNode2InputClass
			INTEGER,
		envNode2InputDatalogEnable
			INTEGER,
		envNode2InputCustomVoice
			DisplayString,
		envNode2InputAck
			INTEGER
	}

envNode2Index				OBJECT-TYPE
	SYNTAX				INTEGER (1..11)
	ACCESS				read-write
	STATUS				mandatory
	DESCRIPTION	"The index of the env entry 1..11"
	::= { envNode2Entry 1 }

envNode2InputName		OBJECT-TYPE
	SYNTAX				DisplayString
	ACCESS				read-write
	STATUS				mandatory
	DESCRIPTION	"Name for Input"
	::= { envNode2Entry 2 }

envNode2InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode2Entry 3 }

envNode2InputInUse	OBJECT-TYPE
	SYNTAX		INTEGER {	false(1),true(2) }
	ACCESS		read-only
	STATUS		mandatory
	DESCRIPTION	"Sensor plugged in"
	::= { envNode2Entry 4 }

envNode2InputUserInUse	OBJECT-TYPE
	SYNTAX		INTEGER {	false(1),true(2) }
	ACCESS		read-write
	STATUS		mandatory
	DESCRIPTION	"Channel Enable"
	::= { envNode2Entry 5 }

envNode2InputEnable	OBJECT-TYPE
	SYNTAX		INTEGER { false(1),true(2) }
	ACCESS		read-only
	STATUS		mandatory
	DESCRIPTION	"Input enabled by scheduler"
	::= { envNode2Entry 6 }

envNode2InputValue	OBJECT-TYPE
	SYNTAX		INTEGER
	ACCESS		read-only
	STATUS		mandatory
	DESCRIPTION	"Real time value of this input"
	::= { envNode2Entry 7 }

envNode2InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode2Entry 8 }

envNode2InputMin		OBJECT-TYPE
	SYNTAX		INTEGER
	ACCESS		read-only
	STATUS		mandatory
	DESCRIPTION	"The minimum value this input has reached"
	::= { envNode2Entry 9 }

envNode2InputMax		OBJECT-TYPE
	SYNTAX		INTEGER
	ACCESS		read-only
	STATUS		mandatory
	DESCRIPTION	"The maximum value this input has reached"
	::= { envNode2Entry 10 }

envNode2InputLastAlarm	OBJECT-TYPE
	SYNTAX		DisplayString
	ACCESS		read-only
	STATUS		mandatory
	DESCRIPTION	"Timestamp of the last alarm"
	::= {  envNode2Entry 11 }

envNode2InputLastAck	OBJECT-TYPE
	SYNTAX		DisplayString
	ACCESS		read-only
	STATUS		mandatory
	DESCRIPTION	"Timestamp of the last alarm Ack"
	::= { envNode2Entry 12 }

envNode2InputLowLimit	OBJECT-TYPE
	SYNTAX		INTEGER
	ACCESS		read-write
	STATUS		mandatory
	DESCRIPTION	"The low alarm threshold"
	::= { envNode2Entry 13 }

envNode2InputHighLimit	OBJECT-TYPE
	SYNTAX		INTEGER
	ACCESS		read-write
	STATUS		mandatory
	DESCRIPTION	"The high alarm threshold"
	::= { envNode2Entry 14 }

envNode2InputCalib	OBJECT-TYPE
	SYNTAX		INTEGER
	ACCESS		read-write
	STATUS		mandatory
	DESCRIPTION	"Calibration offset"
	::= { envNode2Entry 15 }

envNode2InputRecTime	OBJECT-TYPE
	SYNTAX		INTEGER
	ACCESS		read-write
	STATUS		mandatory
	DESCRIPTION	"Time in seconds for an alarm to be recognized"
	::= { envNode2Entry 16 }

envNode2InputResetTime	OBJECT-TYPE
	SYNTAX		INTEGER
	ACCESS		read-write
	STATUS		mandatory
	DESCRIPTION	""
	::= { envNode2Entry 17 }

envNode2InputAlarmOnRTN	OBJECT-TYPE
	SYNTAX		INTEGER { false(1),true(2) }
	ACCESS		read-write
	STATUS		mandatory
	DESCRIPTION	"Allow an alarm to occur when a condition goes back to normal"
	::= { envNode2Entry 18 }

envNode2InputClass	OBJECT-TYPE
	SYNTAX		INTEGER
	ACCESS		read-write
	STATUS		mandatory
	DESCRIPTION	"Alarm class of Input (255 is none)"
	::= { envNode2Entry 19 }

envNode2InputDatalogEnable	OBJECT-TYPE
	SYNTAX		INTEGER { false(1),true(2) }
	ACCESS		read-write
	STATUS		mandatory
	DESCRIPTION	"Datalog input"
	::= { envNode2Entry 20 }

envNode2InputCustomVoice	OBJECT-TYPE
	SYNTAX		DisplayString
	ACCESS		read-write
	STATUS		mandatory
	DESCRIPTION	"WAV file for the custom voice message"
	::= { envNode2Entry 21 }

envNode2InputAck	OBJECT-TYPE
	SYNTAX		INTEGER { false(1),true(2) }
	ACCESS		read-write
	STATUS		mandatory
	DESCRIPTION	"Ack alarm"
	::= { envNode2Entry 22 }

envNode3Table	OBJECT-TYPE
	SYNTAX	SEQUENCE OF	EnvNode3Entry
	ACCESS not-accessible
	STATUS	mandatory
	DESCRIPTION
		"A List of Env entries"
	::= { node3Env	1 }

envNode3Entry	OBJECT-TYPE
	SYNTAX EnvNode3Entry
	ACCESS not-accessible
	STATUS	mandatory
	DESCRIPTION
		"A Env entry"
	INDEX { envNode3Index }
	::= { envNode3Table 1 }

EnvNode3Entry ::=
	SEQUENCE {
		envNode3Index
			INTEGER,
		envNode3InputName
			DisplayString,
		envNode3InputType
			INTEGER,
		envNode3InputInUse
			INTEGER,
		envNode3InputUserInUse
			INTEGER,
		envNode3InputEnable
			INTEGER,
		envNode3InputValue
			INTEGER,
		envNode3InputStatus
			INTEGER,
		envNode3InputMin
			INTEGER,
		envNode3InputMax
			INTEGER,
		envNode3InputLastAlarm
			DisplayString,
		envNode3InputLastAck
			DisplayString,
		envNode3InputLowLimit
			INTEGER,
		envNode3InputHighLimit
			INTEGER,
		envNode3InputCalib
			INTEGER,
		envNode3InputRecTime
			INTEGER,
		envNode3InputResetTime
			INTEGER,
		envNode3InputAlarmOnRTN
			INTEGER,
		envNode3InputClass
			INTEGER,
		envNode3InputDatalogEnable
			INTEGER,
		envNode3InputCustomVoice
			DisplayString,
		envNode3InputAck
			INTEGER
	}

envNode3Index				OBJECT-TYPE
	SYNTAX				INTEGER (1..11)
	ACCESS				read-write
	STATUS				mandatory
	DESCRIPTION	"The index of the env entry 1..11"
	::= { envNode3Entry 1 }

envNode3InputName		OBJECT-TYPE
	SYNTAX				DisplayString
	ACCESS				read-write
	STATUS				mandatory
	DESCRIPTION	"Name for Input"
	::= { envNode3Entry 2 }

envNode3InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode3Entry 3 }

envNode3InputInUse	OBJECT-TYPE
	SYNTAX		INTEGER {	false(1),true(2) }
	ACCESS		read-only
	STATUS		mandatory
	DESCRIPTION	"Sensor plugged in"
	::= { envNode3Entry 4 }

envNode3InputUserInUse	OBJECT-TYPE
	SYNTAX		INTEGER {	false(1),true(2) }
	ACCESS		read-write
	STATUS		mandatory
	DESCRIPTION	"Channel Enable"
	::= { envNode3Entry 5 }

envNode3InputEnable	OBJECT-TYPE
	SYNTAX		INTEGER { false(1),true(2) }
	ACCESS		read-only
	STATUS		mandatory
	DESCRIPTION	"Input enabled by scheduler"
	::= { envNode3Entry 6 }

envNode3InputValue	OBJECT-TYPE
	SYNTAX		INTEGER
	ACCESS		read-only
	STATUS		mandatory
	DESCRIPTION	"Real time value of this input"
	::= { envNode3Entry 7 }

envNode3InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode3Entry 8 }

envNode3InputMin		OBJECT-TYPE
	SYNTAX		INTEGER
	ACCESS		read-only
	STATUS		mandatory
	DESCRIPTION	"The minimum value this input has reached"
	::= { envNode3Entry 9 }

envNode3InputMax		OBJECT-TYPE
	SYNTAX		INTEGER
	ACCESS		read-only
	STATUS		mandatory
	DESCRIPTION	"The maximum value this input has reached"
	::= { envNode3Entry 10}

envNode3InputLastAlarm	OBJECT-TYPE
	SYNTAX		DisplayString
	ACCESS		read-only
	STATUS		mandatory
	DESCRIPTION	"Timestamp of the last alarm"
	::= {  envNode3Entry 11 }

envNode3InputLastAck	OBJECT-TYPE
	SYNTAX		DisplayString
	ACCESS		read-only
	STATUS		mandatory
	DESCRIPTION	"Timestamp of the last alarm Ack"
	::= { envNode3Entry 12 }

envNode3InputLowLimit	OBJECT-TYPE
	SYNTAX		INTEGER
	ACCESS		read-write
	STATUS		mandatory
	DESCRIPTION	"The low alarm threshold"
	::= { envNode3Entry 13 }

envNode3InputHighLimit	OBJECT-TYPE
	SYNTAX		INTEGER
	ACCESS		read-write
	STATUS		mandatory
	DESCRIPTION	"The high alarm threshold"
	::= { envNode3Entry 14}

envNode3InputCalib	OBJECT-TYPE
	SYNTAX		INTEGER
	ACCESS		read-write
	STATUS		mandatory
	DESCRIPTION	"Calibration offset"
	::= { envNode3Entry 15 }

envNode3InputRecTime	OBJECT-TYPE
	SYNTAX		INTEGER
	ACCESS		read-write
	STATUS		mandatory
	DESCRIPTION	"Time in seconds for an alarm to be recognized"
	::= { envNode3Entry 16 }

envNode3InputResetTime	OBJECT-TYPE
	SYNTAX		INTEGER
	ACCESS		read-write
	STATUS		mandatory
	DESCRIPTION	"A value &gt;= 30 mins enables feature, 0 disables"
	::= { envNode3Entry 17 }

envNode3InputAlarmOnRTN	OBJECT-TYPE
	SYNTAX		INTEGER { false(1),true(2) }
	ACCESS		read-write
	STATUS		mandatory
	DESCRIPTION	"Allow an alarm to occur when a condition goes back to normal"
	::= { envNode3Entry 18 }

envNode3InputClass	OBJECT-TYPE
	SYNTAX		INTEGER
	ACCESS		read-write
	STATUS		mandatory
	DESCRIPTION	"Alarm class of Input (255 is none)"
	::= { envNode3Entry 19 }

envNode3InputDatalogEnable	OBJECT-TYPE
	SYNTAX		INTEGER { false(1),true(2) }
	ACCESS		read-write
	STATUS		mandatory
	DESCRIPTION	"Allow this input being included into the data logger"
	::= { envNode3Entry 20 }

envNode3InputCustomVoice	OBJECT-TYPE
	SYNTAX		DisplayString
	ACCESS		read-write
	STATUS		mandatory
	DESCRIPTION	"WAV file for the custom voice message"
	::= { envNode3Entry 21 }

envNode3InputAck	OBJECT-TYPE
	SYNTAX		INTEGER { false(1),true(2) }
	ACCESS		read-write
	STATUS		mandatory
	DESCRIPTION	"Ack alarm"
	::= { envNode3Entry 22 }

envNode4Table	OBJECT-TYPE
	SYNTAX	SEQUENCE OF	EnvNode4Entry
	ACCESS not-accessible
	STATUS	mandatory
	DESCRIPTION
		"A List of Env entries"
	::= { node4Env	1 }

envNode4Entry	OBJECT-TYPE
	SYNTAX EnvNode4Entry
	ACCESS not-accessible
	STATUS	mandatory
	DESCRIPTION
		"A Env entry"
	INDEX { envNode4Index }
	::= { envNode4Table 1 }

EnvNode4Entry ::=
	SEQUENCE {
		envNode4Index
			INTEGER,
		envNode4InputName
			DisplayString,
		envNode4InputType
			INTEGER,
		envNode4InputInUse
			INTEGER,
		envNode4InputUserInUse
			INTEGER,
		envNode4InputEnable
			INTEGER,
		envNode4InputValue
			INTEGER,
		envNode4InputStatus
			INTEGER,
		envNode4InputMin
			INTEGER,
		envNode4InputMax
			INTEGER,
		envNode4InputLastAlarm
			DisplayString,
		envNode4InputLastAck
			DisplayString,
		envNode4InputLowLimit
			INTEGER,
		envNode4InputHighLimit
			INTEGER,
		envNode4InputCalib
			INTEGER,
		envNode4InputRecTime
			INTEGER,
		envNode4InputResetTime
			INTEGER,
		envNode4InputAlarmOnRTN
			INTEGER,
		envNode4InputClass
			INTEGER,
		envNode4InputDatalogEnable
			INTEGER,
		envNode4InputCustomVoice
			DisplayString,
		envNode4InputAck
			INTEGER
	}

envNode4Index				OBJECT-TYPE
	SYNTAX				INTEGER (1..11)
	ACCESS				read-write
	STATUS				mandatory
	DESCRIPTION	"The index of the env entry 1..11"
	::= { envNode4Entry 1 }

envNode4InputName		OBJECT-TYPE
	SYNTAX				DisplayString
	ACCESS				read-write
	STATUS				mandatory
	DESCRIPTION	"Name for Input"
	::= { envNode4Entry 2 }

envNode4InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode4Entry 3 }

envNode4InputInUse	OBJECT-TYPE
	SYNTAX		INTEGER {	false(1),true(2) }
	ACCESS		read-only
	STATUS		mandatory
	DESCRIPTION	"Sensor plugged in"
	::= { envNode4Entry 4 }

envNode4InputUserInUse	OBJECT-TYPE
	SYNTAX		INTEGER {	false(1),true(2) }
	ACCESS		read-write
	STATUS		mandatory
	DESCRIPTION	"Channel Enable"
	::= { envNode4Entry 5 }

envNode4InputEnable	OBJECT-TYPE
	SYNTAX		INTEGER { false(1),true(2) }
	ACCESS		read-only
	STATUS		mandatory
	DESCRIPTION	"Input enabled by scheduler"
	::= { envNode4Entry 6 }

envNode4InputValue	OBJECT-TYPE
	SYNTAX		INTEGER
	ACCESS		read-only
	STATUS		mandatory
	DESCRIPTION	"Real time value of this input"
	::= { envNode4Entry 7 }

envNode4InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode4Entry 8 }

envNode4InputMin		OBJECT-TYPE
	SYNTAX		INTEGER
	ACCESS		read-only
	STATUS		mandatory
	DESCRIPTION	"The minimum value this input has reached"
	::= { envNode4Entry 9 }

envNode4InputMax		OBJECT-TYPE
	SYNTAX		INTEGER
	ACCESS		read-only
	STATUS		mandatory
	DESCRIPTION	"The maximum value this input has reached"
	::= { envNode4Entry 10}

envNode4InputLastAlarm	OBJECT-TYPE
	SYNTAX		DisplayString
	ACCESS		read-only
	STATUS		mandatory
	DESCRIPTION	"Timestamp of the last alarm"
	::= {  envNode4Entry 11 }

envNode4InputLastAck	OBJECT-TYPE
	SYNTAX		DisplayString
	ACCESS		read-only
	STATUS		mandatory
	DESCRIPTION	"Timestamp of the last alarm Ack"
	::= { envNode4Entry 12 }

envNode4InputLowLimit	OBJECT-TYPE
	SYNTAX		INTEGER
	ACCESS		read-write
	STATUS		mandatory
	DESCRIPTION	"The low alarm threshold"
	::= { envNode4Entry 13 }

envNode4InputHighLimit	OBJECT-TYPE
	SYNTAX		INTEGER
	ACCESS		read-write
	STATUS		mandatory
	DESCRIPTION	"The high alarm threshold"
	::= { envNode4Entry 14}

envNode4InputCalib	OBJECT-TYPE
	SYNTAX		INTEGER
	ACCESS		read-write
	STATUS		mandatory
	DESCRIPTION	"Calibration offset"
	::= { envNode4Entry 15 }

envNode4InputRecTime	OBJECT-TYPE
	SYNTAX		INTEGER
	ACCESS		read-write
	STATUS		mandatory
	DESCRIPTION	"Time in seconds for an alarm to be recognized"
	::= { envNode4Entry 16 }

envNode4InputResetTime	OBJECT-TYPE
	SYNTAX		INTEGER
	ACCESS		read-write
	STATUS		mandatory
	DESCRIPTION	"A value &gt;= 30 mins enables feature, 0 disables"
	::= { envNode4Entry 17 }

envNode4InputAlarmOnRTN	OBJECT-TYPE
	SYNTAX		INTEGER { false(1),true(2) }
	ACCESS		read-write
	STATUS		mandatory
	DESCRIPTION	"Allow an alarm to occur when a condition goes back to normal"
	::= { envNode4Entry 18 }

envNode4InputClass	OBJECT-TYPE
	SYNTAX		INTEGER
	ACCESS		read-write
	STATUS		mandatory
	DESCRIPTION	"Alarm class of Input (255 is none)"
	::= { envNode4Entry 19 }

envNode4InputDatalogEnable	OBJECT-TYPE
	SYNTAX		INTEGER { false(1),true(2) }
	ACCESS		read-write
	STATUS		mandatory
	DESCRIPTION	"Datalog input"
	::= { envNode4Entry 20 }

envNode4InputCustomVoice	OBJECT-TYPE
	SYNTAX		DisplayString
	ACCESS		read-write
	STATUS		mandatory
	DESCRIPTION	"WAV file for the custom voice message"
	::= { envNode4Entry 21 }

envNode4InputAck	OBJECT-TYPE
	SYNTAX		INTEGER { false(1),true(2) }
	ACCESS		read-write
	STATUS		mandatory
	DESCRIPTION	"Ack alarm"
	::= { envNode4Entry 22 }

envNode5Table	OBJECT-TYPE
	SYNTAX	SEQUENCE OF	EnvNode5Entry
	ACCESS not-accessible
	STATUS	mandatory
	DESCRIPTION
		"A List of Env entries"
	::= { node5Env	1 }

envNode5Entry	OBJECT-TYPE
	SYNTAX EnvNode5Entry
	ACCESS not-accessible
	STATUS	mandatory
	DESCRIPTION
		"A Env entry"
	INDEX { envNode5Index }
	::= { envNode5Table 1 }

EnvNode5Entry ::=
	SEQUENCE {
		envNode5Index
			INTEGER,
		envNode5InputName
			DisplayString,
		envNode5InputType
			INTEGER,
		envNode5InputInUse
			INTEGER,
		envNode5InputUserInUse
			INTEGER,
		envNode5InputEnable
			INTEGER,
		envNode5InputValue
			INTEGER,
		envNode5InputStatus
			INTEGER,
		envNode5InputMin
			INTEGER,
		envNode5InputMax
			INTEGER,
		envNode5InputLastAlarm
			DisplayString,
		envNode5InputLastAck
			DisplayString,
		envNode5InputLowLimit
			INTEGER,
		envNode5InputHighLimit
			INTEGER,
		envNode5InputCalib
			INTEGER,
		envNode5InputRecTime
			INTEGER,
		envNode5InputResetTime
			INTEGER,
		envNode5InputAlarmOnRTN
			INTEGER,
		envNode5InputClass
			INTEGER,
		envNode5InputDatalogEnable
			INTEGER,
		envNode5InputCustomVoice
			DisplayString,
		envNode5InputAck
			INTEGER
	}

envNode5Index				OBJECT-TYPE
	SYNTAX				INTEGER (1..11)
	ACCESS				read-write
	STATUS				mandatory
	DESCRIPTION	"The index of the env entry 1..11"
	::= { envNode5Entry 1 }

envNode5InputName		OBJECT-TYPE
	SYNTAX				DisplayString
	ACCESS				read-write
	STATUS				mandatory
	DESCRIPTION	"Name for Input"
	::= { envNode5Entry 2 }

envNode5InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode5Entry 3 }

envNode5InputInUse	OBJECT-TYPE
	SYNTAX		INTEGER {	false(1),true(2) }
	ACCESS		read-only
	STATUS		mandatory
	DESCRIPTION	"Sensor plugged in"
	::= { envNode5Entry 4 }

envNode5InputUserInUse	OBJECT-TYPE
	SYNTAX		INTEGER {	false(1),true(2) }
	ACCESS		read-write
	STATUS		mandatory
	DESCRIPTION	"Channel Enable"
	::= { envNode5Entry 5 }

envNode5InputEnable	OBJECT-TYPE
	SYNTAX		INTEGER { false(1),true(2) }
	ACCESS		read-only
	STATUS		mandatory
	DESCRIPTION	"Input enabled by scheduler"
	::= { envNode5Entry 6 }

envNode5InputValue	OBJECT-TYPE
	SYNTAX		INTEGER
	ACCESS		read-only
	STATUS		mandatory
	DESCRIPTION	"Real time value of this input"
	::= { envNode5Entry 7 }

envNode5InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode5Entry 8 }

envNode5InputMin		OBJECT-TYPE
	SYNTAX		INTEGER
	ACCESS		read-only
	STATUS		mandatory
	DESCRIPTION	"The minimum value this input has reached"
	::= { envNode5Entry 9 }

envNode5InputMax		OBJECT-TYPE
	SYNTAX		INTEGER
	ACCESS		read-only
	STATUS		mandatory
	DESCRIPTION	"The maximum value this input has reached"
	::= { envNode5Entry 10}

envNode5InputLastAlarm	OBJECT-TYPE
	SYNTAX		DisplayString
	ACCESS		read-only
	STATUS		mandatory
	DESCRIPTION	"Timestamp of the last alarm"
	::= {  envNode5Entry 11 }

envNode5InputLastAck	OBJECT-TYPE
	SYNTAX		DisplayString
	ACCESS		read-only
	STATUS		mandatory
	DESCRIPTION	"Timestamp of the last alarm Ack"
	::= { envNode5Entry 12 }

envNode5InputLowLimit	OBJECT-TYPE
	SYNTAX		INTEGER
	ACCESS		read-write
	STATUS		mandatory
	DESCRIPTION	"The low alarm threshold"
	::= { envNode5Entry 13 }

envNode5InputHighLimit	OBJECT-TYPE
	SYNTAX		INTEGER
	ACCESS		read-write
	STATUS		mandatory
	DESCRIPTION	"The high alarm threshold"
	::= { envNode5Entry 14}

envNode5InputCalib	OBJECT-TYPE
	SYNTAX		INTEGER
	ACCESS		read-write
	STATUS		mandatory
	DESCRIPTION	"Calibration offset"
	::= { envNode5Entry 15 }

envNode5InputRecTime	OBJECT-TYPE
	SYNTAX		INTEGER
	ACCESS		read-write
	STATUS		mandatory
	DESCRIPTION	"Time in seconds for an alarm to be recognized"
	::= { envNode5Entry 16 }

envNode5InputResetTime	OBJECT-TYPE
	SYNTAX		INTEGER
	ACCESS		read-write
	STATUS		mandatory
	DESCRIPTION	"A value &gt;= 30 mins enables feature, 0 disables"
	::= { envNode5Entry 17 }

envNode5InputAlarmOnRTN	OBJECT-TYPE
	SYNTAX		INTEGER { false(1),true(2) }
	ACCESS		read-write
	STATUS		mandatory
	DESCRIPTION	"Allow an alarm to occur when a condition goes back to normal"
	::= { envNode5Entry 18 }

envNode5InputClass	OBJECT-TYPE
	SYNTAX		INTEGER
	ACCESS		read-write
	STATUS		mandatory
	DESCRIPTION	"Alarm class of Input (255 is none)"
	::= { envNode5Entry 19 }

envNode5InputDatalogEnable	OBJECT-TYPE
	SYNTAX		INTEGER { false(1),true(2) }
	ACCESS		read-write
	STATUS		mandatory
	DESCRIPTION	"Datalog Input"
	::= { envNode5Entry 20 }

envNode5InputCustomVoice	OBJECT-TYPE
	SYNTAX		DisplayString
	ACCESS		read-write
	STATUS		mandatory
	DESCRIPTION	"WAV file for the custom voice message"
	::= { envNode5Entry 21 }

envNode5InputAck	OBJECT-TYPE
	SYNTAX		INTEGER { false(1),true(2) }
	ACCESS		read-write
	STATUS		mandatory
	DESCRIPTION	"Ack alarm"
	::= { envNode5Entry 22 }

envNode6Table	OBJECT-TYPE
	SYNTAX	SEQUENCE OF	EnvNode6Entry
	ACCESS not-accessible
	STATUS	mandatory
	DESCRIPTION
		"A List of Env entries"
	::= { node6Env	1 }

envNode6Entry	OBJECT-TYPE
	SYNTAX EnvNode6Entry
	ACCESS not-accessible
	STATUS	mandatory
	DESCRIPTION
		"A Env entry"
	INDEX { envNode6Index }
	::= { envNode6Table 1 }

EnvNode6Entry ::=
	SEQUENCE {
		envNode6Index
			INTEGER,
		envNode6InputName
			DisplayString,
		envNode6InputType
			INTEGER,
		envNode6InputInUse
			INTEGER,
		envNode6InputUserInUse
			INTEGER,
		envNode6InputEnable
			INTEGER,
		envNode6InputValue
			INTEGER,
		envNode6InputStatus
			INTEGER,
		envNode6InputMin
			INTEGER,
		envNode6InputMax
			INTEGER,
		envNode6InputLastAlarm
			DisplayString,
		envNode6InputLastAck
			DisplayString,
		envNode6InputLowLimit
			INTEGER,
		envNode6InputHighLimit
			INTEGER,
		envNode6InputCalib
			INTEGER,
		envNode6InputRecTime
			INTEGER,
		envNode6InputResetTime
			INTEGER,
		envNode6InputAlarmOnRTN
			INTEGER,
		envNode6InputClass
			INTEGER,
		envNode6InputDatalogEnable
			INTEGER,
		envNode6InputCustomVoice
			DisplayString,
		envNode6InputAck
			INTEGER
	}

envNode6Index				OBJECT-TYPE
	SYNTAX				INTEGER (1..11)
	ACCESS				read-write
	STATUS				mandatory
	DESCRIPTION	"The index of the env entry 1..11"
	::= { envNode6Entry 1 }

envNode6InputName		OBJECT-TYPE
	SYNTAX				DisplayString
	ACCESS				read-write
	STATUS				mandatory
	DESCRIPTION	"Name for Input"
	::= { envNode6Entry 2 }

envNode6InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode6Entry 3 }

envNode6InputInUse	OBJECT-TYPE
	SYNTAX		INTEGER {	false(1),true(2) }
	ACCESS		read-only
	STATUS		mandatory
	DESCRIPTION	"Sensor plugged in"
	::= { envNode6Entry 4 }

envNode6InputUserInUse	OBJECT-TYPE
	SYNTAX		INTEGER {	false(1),true(2) }
	ACCESS		read-write
	STATUS		mandatory
	DESCRIPTION	"Channel Enable"
	::= { envNode6Entry 5 }

envNode6InputEnable	OBJECT-TYPE
	SYNTAX		INTEGER { false(1),true(2) }
	ACCESS		read-only
	STATUS		mandatory
	DESCRIPTION	"Input enabled by scheduler"
	::= { envNode6Entry 6 }

envNode6InputValue	OBJECT-TYPE
	SYNTAX		INTEGER
	ACCESS		read-only
	STATUS		mandatory
	DESCRIPTION	"Real time value of this input"
	::= { envNode6Entry 7 }

envNode6InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode6Entry 8 }

envNode6InputMin		OBJECT-TYPE
	SYNTAX		INTEGER
	ACCESS		read-only
	STATUS		mandatory
	DESCRIPTION	"The minimum value this input has reached"
	::= { envNode6Entry 9 }

envNode6InputMax		OBJECT-TYPE
	SYNTAX		INTEGER
	ACCESS		read-only
	STATUS		mandatory
	DESCRIPTION	"The maximum value this input has reached"
	::= { envNode6Entry 10}

envNode6InputLastAlarm	OBJECT-TYPE
	SYNTAX		DisplayString
	ACCESS		read-only
	STATUS		mandatory
	DESCRIPTION	"Timestamp of the last alarm"
	::= {  envNode6Entry 11 }

envNode6InputLastAck	OBJECT-TYPE
	SYNTAX		DisplayString
	ACCESS		read-only
	STATUS		mandatory
	DESCRIPTION	"Timestamp of the last alarm Ack"
	::= { envNode6Entry 12 }

envNode6InputLowLimit	OBJECT-TYPE
	SYNTAX		INTEGER
	ACCESS		read-write
	STATUS		mandatory
	DESCRIPTION	"The low alarm threshold"
	::= { envNode6Entry 13 }

envNode6InputHighLimit	OBJECT-TYPE
	SYNTAX		INTEGER
	ACCESS		read-write
	STATUS		mandatory
	DESCRIPTION	"The high alarm threshold"
	::= { envNode6Entry 14}

envNode6InputCalib	OBJECT-TYPE
	SYNTAX		INTEGER
	ACCESS		read-write
	STATUS		mandatory
	DESCRIPTION	"Calibration offset"
	::= { envNode6Entry 15 }

envNode6InputRecTime	OBJECT-TYPE
	SYNTAX		INTEGER
	ACCESS		read-write
	STATUS		mandatory
	DESCRIPTION	"Time in seconds for an alarm to be recognized"
	::= { envNode6Entry 16 }

envNode6InputResetTime	OBJECT-TYPE
	SYNTAX		INTEGER
	ACCESS		read-write
	STATUS		mandatory
	DESCRIPTION	"A value &gt;= 30 mins enables feature, 0 disables"
	::= { envNode6Entry 17 }

envNode6InputAlarmOnRTN	OBJECT-TYPE
	SYNTAX		INTEGER { false(1),true(2) }
	ACCESS		read-write
	STATUS		mandatory
	DESCRIPTION	"Allow an alarm to occur when a condition goes back to normal"
	::= { envNode6Entry 18 }

envNode6InputClass	OBJECT-TYPE
	SYNTAX		INTEGER
	ACCESS		read-write
	STATUS		mandatory
	DESCRIPTION	"Alarm class of Input (255 is none)"
	::= { envNode6Entry 19 }

envNode6InputDatalogEnable	OBJECT-TYPE
	SYNTAX		INTEGER { false(1),true(2) }
	ACCESS		read-write
	STATUS		mandatory
	DESCRIPTION	"Datalog input"
	::= { envNode6Entry 20 }

envNode6InputCustomVoice	OBJECT-TYPE
	SYNTAX		DisplayString
	ACCESS		read-write
	STATUS		mandatory
	DESCRIPTION	"WAV file for the custom voice message"
	::= { envNode6Entry 21 }

envNode6InputAck	OBJECT-TYPE
	SYNTAX		INTEGER { false(1),true(2) }
	ACCESS		read-write
	STATUS		mandatory
	DESCRIPTION	"Ack alarm"
	::= { envNode6Entry 22 }

envNode7Table	OBJECT-TYPE
	SYNTAX	SEQUENCE OF	EnvNode7Entry
	ACCESS not-accessible
	STATUS	mandatory
	DESCRIPTION
		"A List of Env entries"
	::= { node7Env	1 }

envNode7Entry	OBJECT-TYPE
	SYNTAX EnvNode7Entry
	ACCESS not-accessible
	STATUS	mandatory
	DESCRIPTION
		"A Env entry"
	INDEX { envNode7Index }
	::= { envNode7Table 1 }

EnvNode7Entry ::=
	SEQUENCE {
		envNode7Index
			INTEGER,
		envNode7InputName
			DisplayString,
		envNode7InputType
			INTEGER,
		envNode7InputInUse
			INTEGER,
		envNode7InputUserInUse
			INTEGER,
		envNode7InputEnable
			INTEGER,
		envNode7InputValue
			INTEGER,
		envNode7InputStatus
			INTEGER,
		envNode7InputMin
			INTEGER,
		envNode7InputMax
			INTEGER,
		envNode7InputLastAlarm
			DisplayString,
		envNode7InputLastAck
			DisplayString,
		envNode7InputLowLimit
			INTEGER,
		envNode7InputHighLimit
			INTEGER,
		envNode7InputCalib
			INTEGER,
		envNode7InputRecTime
			INTEGER,
		envNode7InputResetTime
			INTEGER,
		envNode7InputAlarmOnRTN
			INTEGER,
		envNode7InputClass
			INTEGER,
		envNode7InputDatalogEnable
			INTEGER,
		envNode7InputCustomVoice
			DisplayString,
		envNode7InputAck
			INTEGER
	}

envNode7Index				OBJECT-TYPE
	SYNTAX				INTEGER (1..11)
	ACCESS				read-write
	STATUS				mandatory
	DESCRIPTION	"The index of the env entry 1..11"
	::= { envNode7Entry 1 }

envNode7InputName		OBJECT-TYPE
	SYNTAX				DisplayString
	ACCESS				read-write
	STATUS				mandatory
	DESCRIPTION	"Name for Input"
	::= { envNode7Entry 2 }

envNode7InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode7Entry 3 }

envNode7InputInUse	OBJECT-TYPE
	SYNTAX		INTEGER {	false(1),true(2) }
	ACCESS		read-only
	STATUS		mandatory
	DESCRIPTION	"Sensor plugged in"
	::= { envNode7Entry 4 }

envNode7InputUserInUse	OBJECT-TYPE
	SYNTAX		INTEGER {	false(1),true(2) }
	ACCESS		read-write
	STATUS		mandatory
	DESCRIPTION	"Channel Enable"
	::= { envNode7Entry 5 }

envNode7InputEnable	OBJECT-TYPE
	SYNTAX		INTEGER { false(1),true(2) }
	ACCESS		read-only
	STATUS		mandatory
	DESCRIPTION	"Input enabled by scheduler"
	::= { envNode7Entry 6 }

envNode7InputValue	OBJECT-TYPE
	SYNTAX		INTEGER
	ACCESS		read-only
	STATUS		mandatory
	DESCRIPTION	"Real time value of this input"
	::= { envNode7Entry 7 }

envNode7InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode7Entry 8 }

envNode7InputMin		OBJECT-TYPE
	SYNTAX		INTEGER
	ACCESS		read-only
	STATUS		mandatory
	DESCRIPTION	"The minimum value this input has reached"
	::= { envNode7Entry 9 }

envNode7InputMax		OBJECT-TYPE
	SYNTAX		INTEGER
	ACCESS		read-only
	STATUS		mandatory
	DESCRIPTION	"The maximum value this input has reached"
	::= { envNode7Entry 10}

envNode7InputLastAlarm	OBJECT-TYPE
	SYNTAX		DisplayString
	ACCESS		read-only
	STATUS		mandatory
	DESCRIPTION	"Timestamp of the last alarm"
	::= {  envNode7Entry 11 }

envNode7InputLastAck	OBJECT-TYPE
	SYNTAX		DisplayString
	ACCESS		read-only
	STATUS		mandatory
	DESCRIPTION	"Timestamp of the last alarm Ack"
	::= { envNode7Entry 12 }

envNode7InputLowLimit	OBJECT-TYPE
	SYNTAX		INTEGER
	ACCESS		read-write
	STATUS		mandatory
	DESCRIPTION	"The low alarm threshold"
	::= { envNode7Entry 13 }

envNode7InputHighLimit	OBJECT-TYPE
	SYNTAX		INTEGER
	ACCESS		read-write
	STATUS		mandatory
	DESCRIPTION	"The high alarm threshold"
	::= { envNode7Entry 14}

envNode7InputCalib	OBJECT-TYPE
	SYNTAX		INTEGER
	ACCESS		read-write
	STATUS		mandatory
	DESCRIPTION	"Calibration offset"
	::= { envNode7Entry 15 }

envNode7InputRecTime	OBJECT-TYPE
	SYNTAX		INTEGER
	ACCESS		read-write
	STATUS		mandatory
	DESCRIPTION	"Time in seconds for an alarm to be recognized"
	::= { envNode7Entry 16 }

envNode7InputResetTime	OBJECT-TYPE
	SYNTAX		INTEGER
	ACCESS		read-write
	STATUS		mandatory
	DESCRIPTION	"A value &gt;= 30 mins enables feature, 0 disables"
	::= { envNode7Entry 17 }

envNode7InputAlarmOnRTN	OBJECT-TYPE
	SYNTAX		INTEGER { false(1),true(2) }
	ACCESS		read-write
	STATUS		mandatory
	DESCRIPTION	"Allow an alarm to occur when a condition goes back to normal"
	::= { envNode7Entry 18 }

envNode7InputClass	OBJECT-TYPE
	SYNTAX		INTEGER
	ACCESS		read-write
	STATUS		mandatory
	DESCRIPTION	"Alarm class of Input (255 is none)"
	::= { envNode7Entry 19 }

envNode7InputDatalogEnable	OBJECT-TYPE
	SYNTAX		INTEGER { false(1),true(2) }
	ACCESS		read-write
	STATUS		mandatory
	DESCRIPTION	"Datalog input"
	::= { envNode7Entry 20 }

envNode7InputCustomVoice	OBJECT-TYPE
	SYNTAX		DisplayString
	ACCESS		read-write
	STATUS		mandatory
	DESCRIPTION	"WAV file for the custom voice message"
	::= { envNode7Entry 21 }

envNode7InputAck	OBJECT-TYPE
	SYNTAX		INTEGER { false(1),true(2) }
	ACCESS		read-write
	STATUS		mandatory
	DESCRIPTION	"Ack alarm"
	::= { envNode7Entry 22 }

envNode8Table	OBJECT-TYPE
	SYNTAX	SEQUENCE OF	EnvNode8Entry
	ACCESS not-accessible
	STATUS	mandatory
	DESCRIPTION
		"A List of Env entries"
	::= { node8Env	1 }

envNode8Entry	OBJECT-TYPE
	SYNTAX EnvNode8Entry
	ACCESS not-accessible
	STATUS	mandatory
	DESCRIPTION
		"A Env entry"
	INDEX { envNode8Index }
	::= { envNode8Table 1 }

EnvNode8Entry ::=
	SEQUENCE {
		envNode8Index
			INTEGER,
		envNode8InputName
			DisplayString,
		envNode8InputType
			INTEGER,
		envNode8InputInUse
			INTEGER,
		envNode8InputUserInUse
			INTEGER,
		envNode8InputEnable
			INTEGER,
		envNode8InputValue
			INTEGER,
		envNode8InputStatus
			INTEGER,
		envNode8InputMin
			INTEGER,
		envNode8InputMax
			INTEGER,
		envNode8InputLastAlarm
			DisplayString,
		envNode8InputLastAck
			DisplayString,
		envNode8InputLowLimit
			INTEGER,
		envNode8InputHighLimit
			INTEGER,
		envNode8InputCalib
			INTEGER,
		envNode8InputRecTime
			INTEGER,
		envNode8InputResetTime
			INTEGER,
		envNode8InputAlarmOnRTN
			INTEGER,
		envNode8InputClass
			INTEGER,
		envNode8InputDatalogEnable
			INTEGER,
		envNode8InputCustomVoice
			DisplayString,
		envNode8InputAck
			INTEGER
	}

envNode8Index				OBJECT-TYPE
	SYNTAX				INTEGER (1..11)
	ACCESS				read-write
	STATUS				mandatory
	DESCRIPTION	"The index of the env entry 1..11"
	::= { envNode8Entry 1 }

envNode8InputName		OBJECT-TYPE
	SYNTAX				DisplayString
	ACCESS				read-write
	STATUS				mandatory
	DESCRIPTION	"Name for Input"
	::= { envNode8Entry 2 }

envNode8InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode8Entry 3 }

envNode8InputInUse	OBJECT-TYPE
	SYNTAX		INTEGER {	false(1),true(2) }
	ACCESS		read-only
	STATUS		mandatory
	DESCRIPTION	"Sensor plugged in"
	::= { envNode8Entry 4 }

envNode8InputUserInUse	OBJECT-TYPE
	SYNTAX		INTEGER {	false(1),true(2) }
	ACCESS		read-write
	STATUS		mandatory
	DESCRIPTION	"Channel Enable"
	::= { envNode8Entry 5 }

envNode8InputEnable	OBJECT-TYPE
	SYNTAX		INTEGER { false(1),true(2) }
	ACCESS		read-only
	STATUS		mandatory
	DESCRIPTION	"Input enabled by scheduler"
	::= { envNode8Entry 6 }

envNode8InputValue	OBJECT-TYPE
	SYNTAX		INTEGER
	ACCESS		read-only
	STATUS		mandatory
	DESCRIPTION	"Real time value of this input"
	::= { envNode8Entry 7 }

envNode8InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode8Entry 8 }

envNode8InputMin		OBJECT-TYPE
	SYNTAX		INTEGER
	ACCESS		read-only
	STATUS		mandatory
	DESCRIPTION	"The minimum value this input has reached"
	::= { envNode8Entry 9 }

envNode8InputMax		OBJECT-TYPE
	SYNTAX		INTEGER
	ACCESS		read-only
	STATUS		mandatory
	DESCRIPTION	"The maximum value this input has reached"
	::= { envNode8Entry 10}

envNode8InputLastAlarm	OBJECT-TYPE
	SYNTAX		DisplayString
	ACCESS		read-only
	STATUS		mandatory
	DESCRIPTION	"Timestamp of the last alarm"
	::= {  envNode8Entry 11 }

envNode8InputLastAck	OBJECT-TYPE
	SYNTAX		DisplayString
	ACCESS		read-only
	STATUS		mandatory
	DESCRIPTION	"Timestamp of the last alarm Ack"
	::= { envNode8Entry 12 }

envNode8InputLowLimit	OBJECT-TYPE
	SYNTAX		INTEGER
	ACCESS		read-write
	STATUS		mandatory
	DESCRIPTION	"The low alarm threshold"
	::= { envNode8Entry 13 }

envNode8InputHighLimit	OBJECT-TYPE
	SYNTAX		INTEGER
	ACCESS		read-write
	STATUS		mandatory
	DESCRIPTION	"The high alarm threshold"
	::= { envNode8Entry 14}

envNode8InputCalib	OBJECT-TYPE
	SYNTAX		INTEGER
	ACCESS		read-write
	STATUS		mandatory
	DESCRIPTION	"Calibration offset"
	::= { envNode8Entry 15 }

envNode8InputRecTime	OBJECT-TYPE
	SYNTAX		INTEGER
	ACCESS		read-write
	STATUS		mandatory
	DESCRIPTION	"Time in seconds for an alarm to be recognized"
	::= { envNode8Entry 16 }

envNode8InputResetTime	OBJECT-TYPE
	SYNTAX		INTEGER
	ACCESS		read-write
	STATUS		mandatory
	DESCRIPTION	"A value &gt;= 30 mins enables feature, 0 disables"
	::= { envNode8Entry 17 }

envNode8InputAlarmOnRTN	OBJECT-TYPE
	SYNTAX		INTEGER { false(1),true(2) }
	ACCESS		read-write
	STATUS		mandatory
	DESCRIPTION	"Allow an alarm to occur when a condition goes back to normal"
	::= { envNode8Entry 18 }

envNode8InputClass	OBJECT-TYPE
	SYNTAX		INTEGER
	ACCESS		read-write
	STATUS		mandatory
	DESCRIPTION	"Alarm class of Input (255 is none)"
	::= { envNode8Entry 19 }

envNode8InputDatalogEnable	OBJECT-TYPE
	SYNTAX		INTEGER { false(1),true(2) }
	ACCESS		read-write
	STATUS		mandatory
	DESCRIPTION	"Datalog input"
	::= { envNode8Entry 20 }

envNode8InputCustomVoice	OBJECT-TYPE
	SYNTAX		DisplayString
	ACCESS		read-write
	STATUS		mandatory
	DESCRIPTION	"WAV file for the custom voice message"
	::= { envNode8Entry 21 }

envNode8InputAck	OBJECT-TYPE
	SYNTAX		INTEGER { false(1),true(2) }
	ACCESS		read-write
	STATUS		mandatory
	DESCRIPTION	"Ack alarm"
	::= { envNode8Entry 22 }

envNode9Table	OBJECT-TYPE
	SYNTAX	SEQUENCE OF	EnvNode9Entry
	ACCESS not-accessible
	STATUS	mandatory
	DESCRIPTION
		"A List of Env entries"
	::= { node9Env	1 }

envNode9Entry	OBJECT-TYPE
	SYNTAX EnvNode9Entry
	ACCESS not-accessible
	STATUS	mandatory
	DESCRIPTION
		"A Env entry"
	INDEX { envNode9Index }
	::= { envNode9Table 1 }

EnvNode9Entry ::=
	SEQUENCE {
		envNode9Index
			INTEGER,
		envNode9InputName
			DisplayString,
		envNode9InputType
			INTEGER,
		envNode9InputInUse
			INTEGER,
		envNode9InputUserInUse
			INTEGER,
		envNode9InputEnable
			INTEGER,
		envNode9InputValue
			INTEGER,
		envNode9InputStatus
			INTEGER,
		envNode9InputMin
			INTEGER,
		envNode9InputMax
			INTEGER,
		envNode9InputLastAlarm
			DisplayString,
		envNode9InputLastAck
			DisplayString,
		envNode9InputLowLimit
			INTEGER,
		envNode9InputHighLimit
			INTEGER,
		envNode9InputCalib
			INTEGER,
		envNode9InputRecTime
			INTEGER,
		envNode9InputResetTime
			INTEGER,
		envNode9InputAlarmOnRTN
			INTEGER,
		envNode9InputClass
			INTEGER,
		envNode9InputDatalogEnable
			INTEGER,
		envNode9InputCustomVoice
			DisplayString,
		envNode9InputAck
			INTEGER
	}

envNode9Index				OBJECT-TYPE
	SYNTAX				INTEGER (1..11)
	ACCESS				read-write
	STATUS				mandatory
	DESCRIPTION	"The index of the env entry 1..11"
	::= { envNode9Entry 1 }

envNode9InputName		OBJECT-TYPE
	SYNTAX				DisplayString
	ACCESS				read-write
	STATUS				mandatory
	DESCRIPTION	"Name for Input"
	::= { envNode9Entry 2 }

envNode9InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode9Entry 3 }

envNode9InputInUse	OBJECT-TYPE
	SYNTAX		INTEGER {	false(1),true(2) }
	ACCESS		read-only
	STATUS		mandatory
	DESCRIPTION	"Sensor plugged in"
	::= { envNode9Entry 4 }

envNode9InputUserInUse	OBJECT-TYPE
	SYNTAX		INTEGER {	false(1),true(2) }
	ACCESS		read-write
	STATUS		mandatory
	DESCRIPTION	"Channel Enable"
	::= { envNode9Entry 5 }

envNode9InputEnable	OBJECT-TYPE
	SYNTAX		INTEGER { false(1),true(2) }
	ACCESS		read-only
	STATUS		mandatory
	DESCRIPTION	"True if this input is enabled by the scheduler"
	::= { envNode9Entry 6 }

envNode9InputValue	OBJECT-TYPE
	SYNTAX		INTEGER
	ACCESS		read-only
	STATUS		mandatory
	DESCRIPTION	"Real time value of this input"
	::= { envNode9Entry 7 }

envNode9InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode9Entry 8 }

envNode9InputMin		OBJECT-TYPE
	SYNTAX		INTEGER
	ACCESS		read-only
	STATUS		mandatory
	DESCRIPTION	"The minimum value this input has reached"
	::= { envNode9Entry 9 }

envNode9InputMax		OBJECT-TYPE
	SYNTAX		INTEGER
	ACCESS		read-only
	STATUS		mandatory
	DESCRIPTION	"The maximum value this input has reached"
	::= { envNode9Entry 10}

envNode9InputLastAlarm	OBJECT-TYPE
	SYNTAX		DisplayString
	ACCESS		read-only
	STATUS		mandatory
	DESCRIPTION	"Timestamp of the last alarm"
	::= {  envNode9Entry 11 }

envNode9InputLastAck	OBJECT-TYPE
	SYNTAX		DisplayString
	ACCESS		read-only
	STATUS		mandatory
	DESCRIPTION	"Timestamp of the last alarm Ack"
	::= { envNode9Entry 12 }

envNode9InputLowLimit	OBJECT-TYPE
	SYNTAX		INTEGER
	ACCESS		read-write
	STATUS		mandatory
	DESCRIPTION	"The low alarm threshold"
	::= { envNode9Entry 13 }

envNode9InputHighLimit	OBJECT-TYPE
	SYNTAX		INTEGER
	ACCESS		read-write
	STATUS		mandatory
	DESCRIPTION	"The high alarm threshold"
	::= { envNode9Entry 14}

envNode9InputCalib	OBJECT-TYPE
	SYNTAX		INTEGER
	ACCESS		read-write
	STATUS		mandatory
	DESCRIPTION	"Calibration offset"
	::= { envNode9Entry 15 }

envNode9InputRecTime	OBJECT-TYPE
	SYNTAX		INTEGER
	ACCESS		read-write
	STATUS		mandatory
	DESCRIPTION	"Time in seconds for an alarm to be recognized"
	::= { envNode9Entry 16 }

envNode9InputResetTime	OBJECT-TYPE
	SYNTAX		INTEGER
	ACCESS		read-write
	STATUS		mandatory
	DESCRIPTION	"A value &gt;= 30 mins enables feature, 0 disables"
	::= { envNode9Entry 17 }

envNode9InputAlarmOnRTN	OBJECT-TYPE
	SYNTAX		INTEGER { false(1),true(2) }
	ACCESS		read-write
	STATUS		mandatory
	DESCRIPTION	"Allow an alarm to occur when a condition goes back to normal"
	::= { envNode9Entry 18 }

envNode9InputClass	OBJECT-TYPE
	SYNTAX		INTEGER
	ACCESS		read-write
	STATUS		mandatory
	DESCRIPTION	"Alarm class of Input (255 is none)"
	::= { envNode9Entry 19 }

envNode9InputDatalogEnable	OBJECT-TYPE
	SYNTAX		INTEGER { false(1),true(2) }
	ACCESS		read-write
	STATUS		mandatory
	DESCRIPTION	"Datalog input"
	::= { envNode9Entry 20 }

envNode9InputCustomVoice	OBJECT-TYPE
	SYNTAX		DisplayString
	ACCESS		read-write
	STATUS		mandatory
	DESCRIPTION	"WAV file for the custom voice message"
	::= { envNode9Entry 21 }

envNode9InputAck	OBJECT-TYPE
	SYNTAX		INTEGER { false(1),true(2) }
	ACCESS		read-write
	STATUS		mandatory
	DESCRIPTION	"Ack alarm"
	::= { envNode9Entry 22 }

envNode10Table	OBJECT-TYPE
	SYNTAX	SEQUENCE OF	EnvNode10Entry
	ACCESS not-accessible
	STATUS	mandatory
	DESCRIPTION
		"A List of Env entries"
	::= { node10Env	1 }

envNode10Entry	OBJECT-TYPE
	SYNTAX EnvNode10Entry
	ACCESS not-accessible
	STATUS	mandatory
	DESCRIPTION
		"A Env entry"
	INDEX { envNode10Index }
	::= { envNode10Table 1 }

EnvNode10Entry ::=
	SEQUENCE {
		envNode10Index
			INTEGER,
		envNode10InputName
			DisplayString,
		envNode10InputType
			INTEGER,
		envNode10InputInUse
			INTEGER,
		envNode10InputUserInUse
			INTEGER,
		envNode10InputEnable
			INTEGER,
		envNode10InputValue
			INTEGER,
		envNode10InputStatus
			INTEGER,
		envNode10InputMin
			INTEGER,
		envNode10InputMax
			INTEGER,
		envNode10InputLastAlarm
			DisplayString,
		envNode10InputLastAck
			DisplayString,
		envNode10InputLowLimit
			INTEGER,
		envNode10InputHighLimit
			INTEGER,
		envNode10InputCalib
			INTEGER,
		envNode10InputRecTime
			INTEGER,
		envNode10InputResetTime
			INTEGER,
		envNode10InputAlarmOnRTN
			INTEGER,
		envNode10InputClass
			INTEGER,
		envNode10InputDatalogEnable
			INTEGER,
		envNode10InputCustomVoice
			DisplayString,
		envNode10InputAck
			INTEGER
	}

envNode10Index				OBJECT-TYPE
	SYNTAX				INTEGER (1..11)
	ACCESS				read-write
	STATUS				mandatory
	DESCRIPTION	"The index of the env entry 1..11"
	::= { envNode10Entry 1 }

envNode10InputName		OBJECT-TYPE
	SYNTAX				DisplayString
	ACCESS				read-write
	STATUS				mandatory
	DESCRIPTION	"Name for Input"
	::= { envNode10Entry 2 }

envNode10InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode10Entry 3 }

envNode10InputInUse	OBJECT-TYPE
	SYNTAX		INTEGER {	false(1),true(2) }
	ACCESS		read-only
	STATUS		mandatory
	DESCRIPTION	"Sensor plugged in"
	::= { envNode10Entry 4 }

envNode10InputUserInUse	OBJECT-TYPE
	SYNTAX		INTEGER {	false(1),true(2) }
	ACCESS		read-write
	STATUS		mandatory
	DESCRIPTION	"Channel Enable"
	::= { envNode10Entry 5 }

envNode10InputEnable	OBJECT-TYPE
	SYNTAX		INTEGER { false(1),true(2) }
	ACCESS		read-only
	STATUS		mandatory
	DESCRIPTION	"Iput enabled by scheduler"
	::= { envNode10Entry 6 }

envNode10InputValue	OBJECT-TYPE
	SYNTAX		INTEGER
	ACCESS		read-only
	STATUS		mandatory
	DESCRIPTION	"Real time value of this input"
	::= { envNode10Entry 7 }

envNode10InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode10Entry 8 }

envNode10InputMin		OBJECT-TYPE
	SYNTAX		INTEGER
	ACCESS		read-only
	STATUS		mandatory
	DESCRIPTION	"The minimum value this input has reached"
	::= { envNode10Entry 9 }

envNode10InputMax		OBJECT-TYPE
	SYNTAX		INTEGER
	ACCESS		read-only
	STATUS		mandatory
	DESCRIPTION	"The maximum value this input has reached"
	::= { envNode10Entry 10}

envNode10InputLastAlarm	OBJECT-TYPE
	SYNTAX		DisplayString
	ACCESS		read-only
	STATUS		mandatory
	DESCRIPTION	"Timestamp of the last alarm"
	::= {  envNode10Entry 11 }

envNode10InputLastAck	OBJECT-TYPE
	SYNTAX		DisplayString
	ACCESS		read-only
	STATUS		mandatory
	DESCRIPTION	"Timestamp of the last alarm Ack"
	::= { envNode10Entry 12 }

envNode10InputLowLimit	OBJECT-TYPE
	SYNTAX		INTEGER
	ACCESS		read-write
	STATUS		mandatory
	DESCRIPTION	"The low alarm threshold"
	::= { envNode10Entry 13 }

envNode10InputHighLimit	OBJECT-TYPE
	SYNTAX		INTEGER
	ACCESS		read-write
	STATUS		mandatory
	DESCRIPTION	"The high alarm threshold"
	::= { envNode10Entry 14}

envNode10InputCalib	OBJECT-TYPE
	SYNTAX		INTEGER
	ACCESS		read-write
	STATUS		mandatory
	DESCRIPTION	"Calibration offset"
	::= { envNode10Entry 15 }

envNode10InputRecTime	OBJECT-TYPE
	SYNTAX		INTEGER
	ACCESS		read-write
	STATUS		mandatory
	DESCRIPTION	"Time in seconds for an alarm to be recognized"
	::= { envNode10Entry 16 }

envNode10InputResetTime	OBJECT-TYPE
	SYNTAX		INTEGER
	ACCESS		read-write
	STATUS		mandatory
	DESCRIPTION	"A value &gt;= 30 mins enables feature, 0 disables"
	::= { envNode10Entry 17 }

envNode10InputAlarmOnRTN	OBJECT-TYPE
	SYNTAX		INTEGER { false(1),true(2) }
	ACCESS		read-write
	STATUS		mandatory
	DESCRIPTION	"Allow an alarm to occur when a condition goes back to normal"
	::= { envNode10Entry 18 }

envNode10InputClass	OBJECT-TYPE
	SYNTAX		INTEGER
	ACCESS		read-write
	STATUS		mandatory
	DESCRIPTION	"Alarm class of Input (255 is none)"
	::= { envNode10Entry 19 }

envNode10InputDatalogEnable	OBJECT-TYPE
	SYNTAX		INTEGER { false(1),true(2) }
	ACCESS		read-write
	STATUS		mandatory
	DESCRIPTION	"Datalog Input"
	::= { envNode10Entry 20 }

envNode10InputCustomVoice	OBJECT-TYPE
	SYNTAX		DisplayString
	ACCESS		read-write
	STATUS		mandatory
	DESCRIPTION	"WAV file for the custom voice message"
	::= { envNode10Entry 21 }

envNode10InputAck	OBJECT-TYPE
	SYNTAX		INTEGER { false(1),true(2) }
	ACCESS		read-write
	STATUS		mandatory
	DESCRIPTION	"Ack alarm"
	::= { envNode10Entry 22 }

envNode11Table	OBJECT-TYPE
	SYNTAX	SEQUENCE OF	EnvNode11Entry
	ACCESS not-accessible
	STATUS	mandatory
	DESCRIPTION
		"A List of Env entries"
	::= { node11Env	1 }

envNode11Entry	OBJECT-TYPE
	SYNTAX EnvNode11Entry
	ACCESS not-accessible
	STATUS	mandatory
	DESCRIPTION
		"A Env entry"
	INDEX { envNode11Index }
	::= { envNode11Table 1 }

EnvNode11Entry ::=
	SEQUENCE {
		envNode11Index
			INTEGER,
		envNode11InputName
			DisplayString,
		envNode11InputType
			INTEGER,
		envNode11InputInUse
			INTEGER,
		envNode11InputUserInUse
			INTEGER,
		envNode11InputEnable
			INTEGER,
		envNode11InputValue
			INTEGER,
		envNode11InputStatus
			INTEGER,
		envNode11InputMin
			INTEGER,
		envNode11InputMax
			INTEGER,
		envNode11InputLastAlarm
			DisplayString,
		envNode11InputLastAck
			DisplayString,
		envNode11InputLowLimit
			INTEGER,
		envNode11InputHighLimit
			INTEGER,
		envNode11InputCalib
			INTEGER,
		envNode11InputRecTime
			INTEGER,
		envNode11InputResetTime
			INTEGER,
		envNode11InputAlarmOnRTN
			INTEGER,
		envNode11InputClass
			INTEGER,
		envNode11InputDatalogEnable
			INTEGER,
		envNode11InputCustomVoice
			DisplayString,
		envNode11InputAck
			INTEGER
	}

envNode11Index				OBJECT-TYPE
	SYNTAX				INTEGER (1..11)
	ACCESS				read-write
	STATUS				mandatory
	DESCRIPTION	"The index of the env entry 1..11"
	::= { envNode11Entry 1 }

envNode11InputName		OBJECT-TYPE
	SYNTAX				DisplayString
	ACCESS				read-write
	STATUS				mandatory
	DESCRIPTION	"Name for Input"
	::= { envNode11Entry 2 }

envNode11InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode11Entry 3 }

envNode11InputInUse	OBJECT-TYPE
	SYNTAX		INTEGER {	false(1),true(2) }
	ACCESS		read-only
	STATUS		mandatory
	DESCRIPTION	"Sensor plugged in"
	::= { envNode11Entry 4 }

envNode11InputUserInUse	OBJECT-TYPE
	SYNTAX		INTEGER {	false(1),true(2) }
	ACCESS		read-write
	STATUS		mandatory
	DESCRIPTION	"Channel Enable"
	::= { envNode11Entry 5 }

envNode11InputEnable	OBJECT-TYPE
	SYNTAX		INTEGER { false(1),true(2) }
	ACCESS		read-only
	STATUS		mandatory
	DESCRIPTION	"Input enabled by scheduler"
	::= { envNode11Entry 6 }

envNode11InputValue	OBJECT-TYPE
	SYNTAX		INTEGER
	ACCESS		read-only
	STATUS		mandatory
	DESCRIPTION	"Real time value of this input"
	::= { envNode11Entry 7 }

envNode11InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode11Entry 8 }

envNode11InputMin		OBJECT-TYPE
	SYNTAX		INTEGER
	ACCESS		read-only
	STATUS		mandatory
	DESCRIPTION	"The minimum value this input has reached"
	::= { envNode11Entry 9 }

envNode11InputMax		OBJECT-TYPE
	SYNTAX		INTEGER
	ACCESS		read-only
	STATUS		mandatory
	DESCRIPTION	"The maximum value this input has reached"
	::= { envNode11Entry 10}

envNode11InputLastAlarm	OBJECT-TYPE
	SYNTAX		DisplayString
	ACCESS		read-only
	STATUS		mandatory
	DESCRIPTION	"Timestamp of the last alarm"
	::= {  envNode11Entry 11 }

envNode11InputLastAck	OBJECT-TYPE
	SYNTAX		DisplayString
	ACCESS		read-only
	STATUS		mandatory
	DESCRIPTION	"Timestamp of the last alarm Ack"
	::= { envNode11Entry 12 }

envNode11InputLowLimit	OBJECT-TYPE
	SYNTAX		INTEGER
	ACCESS		read-write
	STATUS		mandatory
	DESCRIPTION	"The low alarm threshold"
	::= { envNode11Entry 13 }

envNode11InputHighLimit	OBJECT-TYPE
	SYNTAX		INTEGER
	ACCESS		read-write
	STATUS		mandatory
	DESCRIPTION	"The high alarm threshold"
	::= { envNode11Entry 14}

envNode11InputCalib	OBJECT-TYPE
	SYNTAX		INTEGER
	ACCESS		read-write
	STATUS		mandatory
	DESCRIPTION	"Calibration offset"
	::= { envNode11Entry 15 }

envNode11InputRecTime	OBJECT-TYPE
	SYNTAX		INTEGER
	ACCESS		read-write
	STATUS		mandatory
	DESCRIPTION	"Time in seconds for an alarm to be recognized"
	::= { envNode11Entry 16 }

envNode11InputResetTime	OBJECT-TYPE
	SYNTAX		INTEGER
	ACCESS		read-write
	STATUS		mandatory
	DESCRIPTION	"A value &gt;= 30 mins enables feature, 0 disables"
	::= { envNode11Entry 17 }

envNode11InputAlarmOnRTN	OBJECT-TYPE
	SYNTAX		INTEGER { false(1),true(2) }
	ACCESS		read-write
	STATUS		mandatory
	DESCRIPTION	"Allow an alarm to occur when a condition goes back to normal"
	::= { envNode11Entry 18 }

envNode11InputClass	OBJECT-TYPE
	SYNTAX		INTEGER
	ACCESS		read-write
	STATUS		mandatory
	DESCRIPTION	"Alarm class of Input (255 is none)"
	::= { envNode11Entry 19 }

envNode11InputDatalogEnable	OBJECT-TYPE
	SYNTAX		INTEGER { false(1),true(2) }
	ACCESS		read-write
	STATUS		mandatory
	DESCRIPTION	"Datalog Input"
	::= { envNode11Entry 20 }

envNode11InputCustomVoice	OBJECT-TYPE
	SYNTAX		DisplayString
	ACCESS		read-write
	STATUS		mandatory
	DESCRIPTION	"WAV file for the custom voice message"
	::= { envNode11Entry 21 }

envNode11InputAck	OBJECT-TYPE
	SYNTAX		INTEGER { false(1),true(2) }
	ACCESS		read-write
	STATUS		mandatory
	DESCRIPTION	"Ack alarm"
	::= { envNode11Entry 22 }

envNode12Table	OBJECT-TYPE
	SYNTAX	SEQUENCE OF	EnvNode12Entry
	ACCESS not-accessible
	STATUS	mandatory
	DESCRIPTION
		"A List of Env entries"
	::= { node12Env	1 }

envNode12Entry	OBJECT-TYPE
	SYNTAX EnvNode12Entry
	ACCESS not-accessible
	STATUS	mandatory
	DESCRIPTION
		"A Env entry"
	INDEX { envNode12Index }
	::= { envNode12Table 1 }

EnvNode12Entry ::=
	SEQUENCE {
		envNode12Index
			INTEGER,
		envNode12InputName
			DisplayString,
		envNode12InputType
			INTEGER,
		envNode12InputInUse
			INTEGER,
		envNode12InputUserInUse
			INTEGER,
		envNode12InputEnable
			INTEGER,
		envNode12InputValue
			INTEGER,
		envNode12InputStatus
			INTEGER,
		envNode12InputMin
			INTEGER,
		envNode12InputMax
			INTEGER,
		envNode12InputLastAlarm
			DisplayString,
		envNode12InputLastAck
			DisplayString,
		envNode12InputLowLimit
			INTEGER,
		envNode12InputHighLimit
			INTEGER,
		envNode12InputCalib
			INTEGER,
		envNode12InputRecTime
			INTEGER,
		envNode12InputResetTime
			INTEGER,
		envNode12InputAlarmOnRTN
			INTEGER,
		envNode12InputClass
			INTEGER,
		envNode12InputDatalogEnable
			INTEGER,
		envNode12InputCustomVoice
			DisplayString,
		envNode12InputAck
			INTEGER
	}

envNode12Index				OBJECT-TYPE
	SYNTAX				INTEGER (1..11)
	ACCESS				read-write
	STATUS				mandatory
	DESCRIPTION	"The index of the env entry 1..11"
	::= { envNode12Entry 1 }

envNode12InputName		OBJECT-TYPE
	SYNTAX				DisplayString
	ACCESS				read-write
	STATUS				mandatory
	DESCRIPTION	"Name for Input"
	::= { envNode12Entry 2 }

envNode12InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"The type of sensor attached to Input 1 on the host"
	::= { envNode12Entry 3 }

envNode12InputInUse	OBJECT-TYPE
	SYNTAX		INTEGER {	false(1),true(2) }
	ACCESS		read-only
	STATUS		mandatory
	DESCRIPTION	"Sensor plugged in"
	::= { envNode12Entry 4 }

envNode12InputUserInUse	OBJECT-TYPE
	SYNTAX		INTEGER {	false(1),true(2) }
	ACCESS		read-write
	STATUS		mandatory
	DESCRIPTION	"Channel Enable"
	::= { envNode12Entry 5 }

envNode12InputEnable	OBJECT-TYPE
	SYNTAX		INTEGER { false(1),true(2) }
	ACCESS		read-only
	STATUS		mandatory
	DESCRIPTION	"Input enabled by scheduler"
	::= { envNode12Entry 6 }

envNode12InputValue	OBJECT-TYPE
	SYNTAX		INTEGER
	ACCESS		read-only
	STATUS		mandatory
	DESCRIPTION	"Real time value of this input"
	::= { envNode12Entry 7 }

envNode12InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode12Entry 8 }

envNode12InputMin		OBJECT-TYPE
	SYNTAX		INTEGER
	ACCESS		read-only
	STATUS		mandatory
	DESCRIPTION	"The minimum value this input has reached"
	::= { envNode12Entry 9 }

envNode12InputMax		OBJECT-TYPE
	SYNTAX		INTEGER
	ACCESS		read-only
	STATUS		mandatory
	DESCRIPTION	"The maximum value this input has reached"
	::= { envNode12Entry 10}

envNode12InputLastAlarm	OBJECT-TYPE
	SYNTAX		DisplayString
	ACCESS		read-only
	STATUS		mandatory
	DESCRIPTION	"Timestamp of the last alarm"
	::= {  envNode12Entry 11 }

envNode12InputLastAck	OBJECT-TYPE
	SYNTAX		DisplayString
	ACCESS		read-only
	STATUS		mandatory
	DESCRIPTION	"Timestamp of the last alarm Ack"
	::= { envNode12Entry 12 }

envNode12InputLowLimit	OBJECT-TYPE
	SYNTAX		INTEGER
	ACCESS		read-write
	STATUS		mandatory
	DESCRIPTION	"The low alarm threshold"
	::= { envNode12Entry 13 }

envNode12InputHighLimit	OBJECT-TYPE
	SYNTAX		INTEGER
	ACCESS		read-write
	STATUS		mandatory
	DESCRIPTION	"The high alarm threshold"
	::= { envNode12Entry 14}

envNode12InputCalib	OBJECT-TYPE
	SYNTAX		INTEGER
	ACCESS		read-write
	STATUS		mandatory
	DESCRIPTION	"Calibration offset"
	::= { envNode12Entry 15 }

envNode12InputRecTime	OBJECT-TYPE
	SYNTAX		INTEGER
	ACCESS		read-write
	STATUS		mandatory
	DESCRIPTION	"Time in seconds for an alarm to be recognized"
	::= { envNode12Entry 16 }

envNode12InputResetTime	OBJECT-TYPE
	SYNTAX		INTEGER
	ACCESS		read-write
	STATUS		mandatory
	DESCRIPTION	"A value &gt;= 30 mins enables feature, 0 disables"
	::= { envNode12Entry 17 }

envNode12InputAlarmOnRTN	OBJECT-TYPE
	SYNTAX		INTEGER { false(1),true(2) }
	ACCESS		read-write
	STATUS		mandatory
	DESCRIPTION	"Allow an alarm to occur when a condition goes back to normal"
	::= { envNode12Entry 18}

envNode12InputClass	OBJECT-TYPE
	SYNTAX		INTEGER
	ACCESS		read-write
	STATUS		mandatory
	DESCRIPTION	"Alarm class of Input (255 is none)"
	::= { envNode12Entry 19 }

envNode12InputDatalogEnable	OBJECT-TYPE
	SYNTAX		INTEGER { false(1),true(2) }
	ACCESS		read-write
	STATUS		mandatory
	DESCRIPTION	"Datalog Input"
	::= { envNode12Entry 20 }

envNode12InputCustomVoice	OBJECT-TYPE
	SYNTAX		DisplayString
	ACCESS		read-write
	STATUS		mandatory
	DESCRIPTION	"WAV file for the custom voice message"
	::= { envNode12Entry 21 }

envNode12InputAck	OBJECT-TYPE
	SYNTAX		INTEGER { false(1),true(2) }
	ACCESS		read-write
	STATUS		mandatory
	DESCRIPTION	"Ack alarm"
	::= { envNode12Entry 22 }

envNode13Table	OBJECT-TYPE
	SYNTAX	SEQUENCE OF	EnvNode13Entry
	ACCESS not-accessible
	STATUS	mandatory
	DESCRIPTION
		"A List of Env entries"
	::= { node13Env	1 }

envNode13Entry	OBJECT-TYPE
	SYNTAX EnvNode13Entry
	ACCESS not-accessible
	STATUS	mandatory
	DESCRIPTION
		"A Env entry"
	INDEX { envNode13Index }
	::= { envNode13Table 1 }

EnvNode13Entry ::=
	SEQUENCE {
		envNode13Index
			INTEGER,
		envNode13InputName
			DisplayString,
		envNode13InputType
			INTEGER,
		envNode13InputInUse
			INTEGER,
		envNode13InputUserInUse
			INTEGER,
		envNode13InputEnable
			INTEGER,
		envNode13InputValue
			INTEGER,
		envNode13InputStatus
			INTEGER,
		envNode13InputMin
			INTEGER,
		envNode13InputMax
			INTEGER,
		envNode13InputLastAlarm
			DisplayString,
		envNode13InputLastAck
			DisplayString,
		envNode13InputLowLimit
			INTEGER,
		envNode13InputHighLimit
			INTEGER,
		envNode13InputCalib
			INTEGER,
		envNode13InputRecTime
			INTEGER,
		envNode13InputResetTime
			INTEGER,
		envNode13InputAlarmOnRTN
			INTEGER,
		envNode13InputClass
			INTEGER,
		envNode13InputDatalogEnable
			INTEGER,
		envNode13InputCustomVoice
			DisplayString,
		envNode13InputAck
			INTEGER
	}

envNode13Index				OBJECT-TYPE
	SYNTAX				INTEGER (1..11)
	ACCESS				read-write
	STATUS				mandatory
	DESCRIPTION	"The index of the env entry 1..11"
	::= { envNode13Entry 1 }

envNode13InputName		OBJECT-TYPE
	SYNTAX				DisplayString
	ACCESS				read-write
	STATUS				mandatory
	DESCRIPTION	"Name for Input"
	::= { envNode13Entry 2 }

envNode13InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode13Entry 3 }

envNode13InputInUse	OBJECT-TYPE
	SYNTAX		INTEGER {	false(1),true(2) }
	ACCESS		read-only
	STATUS		mandatory
	DESCRIPTION	"Sensor plugged in"
	::= { envNode13Entry 4 }

envNode13InputUserInUse	OBJECT-TYPE
	SYNTAX		INTEGER {	false(1),true(2) }
	ACCESS		read-write
	STATUS		mandatory
	DESCRIPTION	"Channel Enable"
	::= { envNode13Entry 5 }

envNode13InputEnable	OBJECT-TYPE
	SYNTAX		INTEGER { false(1),true(2) }
	ACCESS		read-only
	STATUS		mandatory
	DESCRIPTION	"Input enabled by scheduler"
	::= { envNode13Entry 6 }

envNode13InputValue	OBJECT-TYPE
	SYNTAX		INTEGER
	ACCESS		read-only
	STATUS		mandatory
	DESCRIPTION	"Real time value of this input"
	::= { envNode13Entry 7 }

envNode13InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode13Entry 8 }

envNode13InputMin		OBJECT-TYPE
	SYNTAX		INTEGER
	ACCESS		read-only
	STATUS		mandatory
	DESCRIPTION	"The minimum value this input has reached"
	::= { envNode13Entry 9 }

envNode13InputMax		OBJECT-TYPE
	SYNTAX		INTEGER
	ACCESS		read-only
	STATUS		mandatory
	DESCRIPTION	"The maximum value this input has reached"
	::= { envNode13Entry 10}

envNode13InputLastAlarm	OBJECT-TYPE
	SYNTAX		DisplayString
	ACCESS		read-only
	STATUS		mandatory
	DESCRIPTION	"Timestamp of the last alarm"
	::= {  envNode13Entry 11 }

envNode13InputLastAck	OBJECT-TYPE
	SYNTAX		DisplayString
	ACCESS		read-only
	STATUS		mandatory
	DESCRIPTION	"Timestamp of the last alarm Ack"
	::= { envNode13Entry 12 }

envNode13InputLowLimit	OBJECT-TYPE
	SYNTAX		INTEGER
	ACCESS		read-write
	STATUS		mandatory
	DESCRIPTION	"The low alarm threshold"
	::= { envNode13Entry 13 }

envNode13InputHighLimit	OBJECT-TYPE
	SYNTAX		INTEGER
	ACCESS		read-write
	STATUS		mandatory
	DESCRIPTION	"The high alarm threshold"
	::= { envNode13Entry 14}

envNode13InputCalib	OBJECT-TYPE
	SYNTAX		INTEGER
	ACCESS		read-write
	STATUS		mandatory
	DESCRIPTION	"Calibration offset"
	::= { envNode13Entry 15 }

envNode13InputRecTime	OBJECT-TYPE
	SYNTAX		INTEGER
	ACCESS		read-write
	STATUS		mandatory
	DESCRIPTION	"Time in seconds for an alarm to be recognized"
	::= { envNode13Entry 16 }

envNode13InputResetTime	OBJECT-TYPE
	SYNTAX		INTEGER
	ACCESS		read-write
	STATUS		mandatory
	DESCRIPTION	"A value &gt;= 30 mins enables feature, 0 disables"
	::= { envNode13Entry 17 }

envNode13InputAlarmOnRTN	OBJECT-TYPE
	SYNTAX		INTEGER { false(1),true(2) }
	ACCESS		read-write
	STATUS		mandatory
	DESCRIPTION	"Allow an alarm to occur when a condition goes back to normal"
	::= { envNode13Entry 18 }

envNode13InputClass	OBJECT-TYPE
	SYNTAX		INTEGER
	ACCESS		read-write
	STATUS		mandatory
	DESCRIPTION	"Alarm class of Input (255 is none)"
	::= { envNode13Entry 19 }

envNode13InputDatalogEnable	OBJECT-TYPE
	SYNTAX		INTEGER { false(1),true(2) }
	ACCESS		read-write
	STATUS		mandatory
	DESCRIPTION	"Datalog Input"
	::= { envNode13Entry 20 }

envNode13InputCustomVoice	OBJECT-TYPE
	SYNTAX		DisplayString
	ACCESS		read-write
	STATUS		mandatory
	DESCRIPTION	"WAV file for the custom voice message"
	::= { envNode13Entry 21 }

envNode13InputAck	OBJECT-TYPE
	SYNTAX		INTEGER { false(1),true(2) }
	ACCESS		read-write
	STATUS		mandatory
	DESCRIPTION	"Ack alarm"
	::= { envNode13Entry 22 }

envNode14Table	OBJECT-TYPE
	SYNTAX	SEQUENCE OF	EnvNode14Entry
	ACCESS not-accessible
	STATUS	mandatory
	DESCRIPTION
		"A List of Env entries"
	::= { node14Env	1 }

envNode14Entry	OBJECT-TYPE
	SYNTAX EnvNode14Entry
	ACCESS not-accessible
	STATUS	mandatory
	DESCRIPTION
		"A Env entry"
	INDEX { envNode14Index }
	::= { envNode14Table 1 }

EnvNode14Entry ::=
	SEQUENCE {
		envNode14Index
			INTEGER,
		envNode14InputName
			DisplayString,
		envNode14InputType
			INTEGER,
		envNode14InputInUse
			INTEGER,
		envNode14InputUserInUse
			INTEGER,
		envNode14InputEnable
			INTEGER,
		envNode14InputValue
			INTEGER,
		envNode14InputStatus
			INTEGER,
		envNode14InputMin
			INTEGER,
		envNode14InputMax
			INTEGER,
		envNode14InputLastAlarm
			DisplayString,
		envNode14InputLastAck
			DisplayString,
		envNode14InputLowLimit
			INTEGER,
		envNode14InputHighLimit
			INTEGER,
		envNode14InputCalib
			INTEGER,
		envNode14InputRecTime
			INTEGER,
		envNode14InputResetTime
			INTEGER,
		envNode14InputAlarmOnRTN
			INTEGER,
		envNode14InputClass
			INTEGER,
		envNode14InputDatalogEnable
			INTEGER,
		envNode14InputCustomVoice
			DisplayString,
		envNode14InputAck
			INTEGER
	}

envNode14Index				OBJECT-TYPE
	SYNTAX				INTEGER (1..11)
	ACCESS				read-write
	STATUS				mandatory
	DESCRIPTION	"The index of the env entry 1..11"
	::= { envNode14Entry 1 }

envNode14InputName		OBJECT-TYPE
	SYNTAX				DisplayString
	ACCESS				read-write
	STATUS				mandatory
	DESCRIPTION	"Name for Input"
	::= { envNode14Entry 2 }

envNode14InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode14Entry 3 }

envNode14InputInUse	OBJECT-TYPE
	SYNTAX		INTEGER {	false(1),true(2) }
	ACCESS		read-only
	STATUS		mandatory
	DESCRIPTION	"Sensor plugged in"
	::= { envNode14Entry 4 }

envNode14InputUserInUse	OBJECT-TYPE
	SYNTAX		INTEGER {	false(1),true(2) }
	ACCESS		read-write
	STATUS		mandatory
	DESCRIPTION	"Channel Enable"
	::= { envNode14Entry 5 }

envNode14InputEnable	OBJECT-TYPE
	SYNTAX		INTEGER { false(1),true(2) }
	ACCESS		read-only
	STATUS		mandatory
	DESCRIPTION	"True if this input is enabled by the scheduler"
	::= { envNode14Entry 6 }

envNode14InputValue	OBJECT-TYPE
	SYNTAX		INTEGER
	ACCESS		read-only
	STATUS		mandatory
	DESCRIPTION	"Real time value of this input"
	::= { envNode14Entry 7 }

envNode14InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode14Entry 8 }

envNode14InputMin		OBJECT-TYPE
	SYNTAX		INTEGER
	ACCESS		read-only
	STATUS		mandatory
	DESCRIPTION	"The minimum value this input has reached"
	::= { envNode14Entry 9 }

envNode14InputMax		OBJECT-TYPE
	SYNTAX		INTEGER
	ACCESS		read-only
	STATUS		mandatory
	DESCRIPTION	"The maximum value this input has reached"
	::= { envNode14Entry 10}

envNode14InputLastAlarm	OBJECT-TYPE
	SYNTAX		DisplayString
	ACCESS		read-only
	STATUS		mandatory
	DESCRIPTION	"Timestamp of the last alarm"
	::= {  envNode14Entry 11 }

envNode14InputLastAck	OBJECT-TYPE
	SYNTAX		DisplayString
	ACCESS		read-only
	STATUS		mandatory
	DESCRIPTION	"Timestamp of the last alarm Ack"
	::= { envNode14Entry 12 }

envNode14InputLowLimit	OBJECT-TYPE
	SYNTAX		INTEGER
	ACCESS		read-write
	STATUS		mandatory
	DESCRIPTION	"The low alarm threshold"
	::= { envNode14Entry 13 }

envNode14InputHighLimit	OBJECT-TYPE
	SYNTAX		INTEGER
	ACCESS		read-write
	STATUS		mandatory
	DESCRIPTION	"The high alarm threshold"
	::= { envNode14Entry 14}

envNode14InputCalib	OBJECT-TYPE
	SYNTAX		INTEGER
	ACCESS		read-write
	STATUS		mandatory
	DESCRIPTION	"Calibration offset"
	::= { envNode14Entry 15 }

envNode14InputRecTime	OBJECT-TYPE
	SYNTAX		INTEGER
	ACCESS		read-write
	STATUS		mandatory
	DESCRIPTION	"Time in seconds for an alarm to be recognized"
	::= { envNode14Entry 16 }

envNode14InputResetTime	OBJECT-TYPE
	SYNTAX		INTEGER
	ACCESS		read-write
	STATUS		mandatory
	DESCRIPTION	"A value &gt;= 30 mins enables feature, 0 disables"
	::= { envNode14Entry 17 }

envNode14InputAlarmOnRTN	OBJECT-TYPE
	SYNTAX		INTEGER { false(1),true(2) }
	ACCESS		read-write
	STATUS		mandatory
	DESCRIPTION	"Allow an alarm to occur when a condition goes back to normal"
	::= { envNode14Entry 18 }

envNode14InputClass	OBJECT-TYPE
	SYNTAX		INTEGER
	ACCESS		read-write
	STATUS		mandatory
	DESCRIPTION	"Alarm class of Input (255 is none)"
	::= { envNode14Entry 19 }

envNode14InputDatalogEnable	OBJECT-TYPE
	SYNTAX		INTEGER { false(1),true(2) }
	ACCESS		read-write
	STATUS		mandatory
	DESCRIPTION	"Datalog Input"
	::= { envNode14Entry 20 }

envNode14InputCustomVoice	OBJECT-TYPE
	SYNTAX		DisplayString
	ACCESS		read-write
	STATUS		mandatory
	DESCRIPTION	"WAV file for the custom voice message"
	::= { envNode14Entry 21 }

envNode14InputAck	OBJECT-TYPE
	SYNTAX		INTEGER { false(1),true(2) }
	ACCESS		read-write
	STATUS		mandatory
	DESCRIPTION	"Ack alarm"
	::= { envNode14Entry 22 }

envNode15Table	OBJECT-TYPE
	SYNTAX	SEQUENCE OF	EnvNode15Entry
	ACCESS not-accessible
	STATUS	mandatory
	DESCRIPTION
		"A List of Env entries"
	::= { node15Env	1 }

envNode15Entry	OBJECT-TYPE
	SYNTAX EnvNode15Entry
	ACCESS not-accessible
	STATUS	mandatory
	DESCRIPTION
		"A Env entry"
	INDEX { envNode15Index }
	::= { envNode15Table 1 }

EnvNode15Entry ::=
	SEQUENCE {
		envNode15Index
			INTEGER,
		envNode15InputName
			DisplayString,
		envNode15InputType
			INTEGER,
		envNode15InputInUse
			INTEGER,
		envNode15InputUserInUse
			INTEGER,
		envNode15InputEnable
			INTEGER,
		envNode15InputValue
			INTEGER,
		envNode15InputStatus
			INTEGER,
		envNode15InputMin
			INTEGER,
		envNode15InputMax
			INTEGER,
		envNode15InputLastAlarm
			DisplayString,
		envNode15InputLastAck
			DisplayString,
		envNode15InputLowLimit
			INTEGER,
		envNode15InputHighLimit
			INTEGER,
		envNode15InputCalib
			INTEGER,
		envNode15InputRecTime
			INTEGER,
		envNode15InputResetTime
			INTEGER,
		envNode15InputAlarmOnRTN
			INTEGER,
		envNode15InputClass
			INTEGER,
		envNode15InputDatalogEnable
			INTEGER,
		envNode15InputCustomVoice
			DisplayString,
		envNode15InputAck
			INTEGER
	}

envNode15Index				OBJECT-TYPE
	SYNTAX				INTEGER (1..11)
	ACCESS				read-write
	STATUS				mandatory
	DESCRIPTION	"The index of the env entry 1..11"
	::= { envNode15Entry 1 }

envNode15InputName		OBJECT-TYPE
	SYNTAX				DisplayString
	ACCESS				read-write
	STATUS				mandatory
	DESCRIPTION	"Name for Input"
	::= { envNode15Entry 2 }

envNode15InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode15Entry 3 }

envNode15InputInUse	OBJECT-TYPE
	SYNTAX		INTEGER {	false(1),true(2) }
	ACCESS		read-only
	STATUS		mandatory
	DESCRIPTION	"Sensor plugged in"
	::= { envNode15Entry 4 }

envNode15InputUserInUse	OBJECT-TYPE
	SYNTAX		INTEGER {	false(1),true(2) }
	ACCESS		read-write
	STATUS		mandatory
	DESCRIPTION	"Channel Enable"
	::= { envNode15Entry 5 }

envNode15InputEnable	OBJECT-TYPE
	SYNTAX		INTEGER { false(1),true(2) }
	ACCESS		read-only
	STATUS		mandatory
	DESCRIPTION	"Input enabled by scheduler"
	::= { envNode15Entry 6 }

envNode15InputValue	OBJECT-TYPE
	SYNTAX		INTEGER
	ACCESS		read-only
	STATUS		mandatory
	DESCRIPTION	"Real time value of this input"
	::= { envNode15Entry 7 }

envNode15InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode15Entry 8 }

envNode15InputMin		OBJECT-TYPE
	SYNTAX		INTEGER
	ACCESS		read-only
	STATUS		mandatory
	DESCRIPTION	"The minimum value this input has reached"
	::= { envNode15Entry 9 }

envNode15InputMax		OBJECT-TYPE
	SYNTAX		INTEGER
	ACCESS		read-only
	STATUS		mandatory
	DESCRIPTION	"The maximum value this input has reached"
	::= { envNode15Entry 10}

envNode15InputLastAlarm	OBJECT-TYPE
	SYNTAX		DisplayString
	ACCESS		read-only
	STATUS		mandatory
	DESCRIPTION	"Timestamp of the last alarm"
	::= {  envNode15Entry 11 }

envNode15InputLastAck	OBJECT-TYPE
	SYNTAX		DisplayString
	ACCESS		read-only
	STATUS		mandatory
	DESCRIPTION	"Timestamp of the last alarm Ack"
	::= { envNode15Entry 12 }

envNode15InputLowLimit	OBJECT-TYPE
	SYNTAX		INTEGER
	ACCESS		read-write
	STATUS		mandatory
	DESCRIPTION	"The low alarm threshold"
	::= { envNode15Entry 13 }

envNode15InputHighLimit	OBJECT-TYPE
	SYNTAX		INTEGER
	ACCESS		read-write
	STATUS		mandatory
	DESCRIPTION	"The high alarm threshold"
	::= { envNode15Entry 14}

envNode15InputCalib	OBJECT-TYPE
	SYNTAX		INTEGER
	ACCESS		read-write
	STATUS		mandatory
	DESCRIPTION	"Calibration offset"
	::= { envNode15Entry 15 }

envNode15InputRecTime	OBJECT-TYPE
	SYNTAX		INTEGER
	ACCESS		read-write
	STATUS		mandatory
	DESCRIPTION	"Time in seconds for an alarm to be recognized"
	::= { envNode15Entry 16 }

envNode15InputResetTime	OBJECT-TYPE
	SYNTAX		INTEGER
	ACCESS		read-write
	STATUS		mandatory
	DESCRIPTION	"A value &gt;= 30 mins enables feature, 0 disables"
	::= { envNode15Entry 17 }

envNode15InputAlarmOnRTN	OBJECT-TYPE
	SYNTAX		INTEGER { false(1),true(2) }
	ACCESS		read-write
	STATUS		mandatory
	DESCRIPTION	"Allow an alarm to occur when a condition goes back to normal"
	::= { envNode15Entry 18 }

envNode15InputClass	OBJECT-TYPE
	SYNTAX		INTEGER
	ACCESS		read-write
	STATUS		mandatory
	DESCRIPTION	"Alarm class of Input (255 is none)"
	::= { envNode15Entry 19 }

envNode15InputDatalogEnable	OBJECT-TYPE
	SYNTAX		INTEGER { false(1),true(2) }
	ACCESS		read-write
	STATUS		mandatory
	DESCRIPTION	"Datalog Input"
	::= { envNode15Entry 20 }

envNode15InputCustomVoice	OBJECT-TYPE
	SYNTAX		DisplayString
	ACCESS		read-write
	STATUS		mandatory
	DESCRIPTION	"WAV file for the custom voice message"
	::= { envNode15Entry 21 }

envNode15InputAck	OBJECT-TYPE
	SYNTAX		INTEGER { false(1),true(2) }
	ACCESS		read-write
	STATUS		mandatory
	DESCRIPTION	"Ack alarm"
	::= { envNode15Entry 22 }

envNode16Table	OBJECT-TYPE
	SYNTAX	SEQUENCE OF	EnvNode16Entry
	ACCESS not-accessible
	STATUS	mandatory
	DESCRIPTION
		"A List of Env entries"
	::= { node16Env	1 }

envNode16Entry	OBJECT-TYPE
	SYNTAX EnvNode16Entry
	ACCESS not-accessible
	STATUS	mandatory
	DESCRIPTION
		"A Env entry"
	INDEX { envNode16Index }
	::= { envNode16Table 1 }

EnvNode16Entry ::=
	SEQUENCE {
		envNode16Index
			INTEGER,
		envNode16InputName
			DisplayString,
		envNode16InputType
			INTEGER,
		envNode16InputInUse
			INTEGER,
		envNode16InputUserInUse
			INTEGER,
		envNode16InputEnable
			INTEGER,
		envNode16InputValue
			INTEGER,
		envNode16InputStatus
			INTEGER,
		envNode16InputMin
			INTEGER,
		envNode16InputMax
			INTEGER,
		envNode16InputLastAlarm
			DisplayString,
		envNode16InputLastAck
			DisplayString,
		envNode16InputLowLimit
			INTEGER,
		envNode16InputHighLimit
			INTEGER,
		envNode16InputCalib
			INTEGER,
		envNode16InputRecTime
			INTEGER,
		envNode16InputResetTime
			INTEGER,
		envNode16InputAlarmOnRTN
			INTEGER,
		envNode16InputClass
			INTEGER,
		envNode16InputDatalogEnable
			INTEGER,
		envNode16InputCustomVoice
			DisplayString,
		envNode16InputAck
			INTEGER
	}

envNode16Index				OBJECT-TYPE
	SYNTAX				INTEGER (1..11)
	ACCESS				read-write
	STATUS				mandatory
	DESCRIPTION	"The index of the env entry 1..11"
	::= { envNode16Entry 1 }

envNode16InputName		OBJECT-TYPE
	SYNTAX				DisplayString
	ACCESS				read-write
	STATUS				mandatory
	DESCRIPTION	"Name for Input"
	::= { envNode16Entry 2 }

envNode16InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),	undef1(14),undef2(15),none(16),hostPower(17),
		nodePower(18),battery(19),sound(20),ip(21)
	}
	ACCESS				read-only
	STATUS				mandatory
	DESCRIPTION	"Type of sensor"
	::= { envNode16Entry 3 }

envNode16InputInUse	OBJECT-TYPE
	SYNTAX		INTEGER {	false(1),true(2) }
	ACCESS		read-only
	STATUS		mandatory
	DESCRIPTION	"Sensor plugged in"
	::= { envNode16Entry 4 }

envNode16InputUserInUse	OBJECT-TYPE
	SYNTAX		INTEGER {	false(1),true(2) }
	ACCESS		read-write
	STATUS		mandatory
	DESCRIPTION	"Channel Enable"
	::= { envNode16Entry 5 }

envNode16InputEnable	OBJECT-TYPE
	SYNTAX		INTEGER { false(1),true(2) }
	ACCESS		read-only
	STATUS		mandatory
	DESCRIPTION	"Input enabled by scheduler"
	::= { envNode16Entry 6 }

envNode16InputValue	OBJECT-TYPE
	SYNTAX		INTEGER
	ACCESS		read-only
	STATUS		mandatory
	DESCRIPTION	"Real time value of this input"
	::= { envNode16Entry 7 }

envNode16InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode16Entry 8 }

envNode16InputMin		OBJECT-TYPE
	SYNTAX		INTEGER
	ACCESS		read-only
	STATUS		mandatory
	DESCRIPTION	"The minimum value this input has reached"
	::= { envNode16Entry 9 }

envNode16InputMax		OBJECT-TYPE
	SYNTAX		INTEGER
	ACCESS		read-only
	STATUS		mandatory
	DESCRIPTION	"The maximum value this input has reached"
	::= { envNode16Entry 10}

envNode16InputLastAlarm	OBJECT-TYPE
	SYNTAX		DisplayString
	ACCESS		read-only
	STATUS		mandatory
	DESCRIPTION	"Timestamp of the last alarm"
	::= {  envNode16Entry 11 }

envNode16InputLastAck	OBJECT-TYPE
	SYNTAX		DisplayString
	ACCESS		read-only
	STATUS		mandatory
	DESCRIPTION	"Timestamp of the last alarm Ack"
	::= { envNode16Entry 12 }

envNode16InputLowLimit	OBJECT-TYPE
	SYNTAX		INTEGER
	ACCESS		read-write
	STATUS		mandatory
	DESCRIPTION	"The low alarm threshold"
	::= { envNode16Entry 13 }

envNode16InputHighLimit	OBJECT-TYPE
	SYNTAX		INTEGER
	ACCESS		read-write
	STATUS		mandatory
	DESCRIPTION	"The high alarm threshold"
	::= { envNode16Entry 14}

envNode16InputCalib	OBJECT-TYPE
	SYNTAX		INTEGER
	ACCESS		read-write
	STATUS		mandatory
	DESCRIPTION	"Calibration offset"
	::= { envNode16Entry 15 }

envNode16InputRecTime	OBJECT-TYPE
	SYNTAX		INTEGER
	ACCESS		read-write
	STATUS		mandatory
	DESCRIPTION	"Time in seconds for an alarm to be recognized"
	::= { envNode16Entry 16 }

envNode16InputResetTime	OBJECT-TYPE
	SYNTAX		INTEGER
	ACCESS		read-write
	STATUS		mandatory
	DESCRIPTION	"A value &gt;= 30 mins enables feature, 0 disables"
	::= { envNode16Entry 17 }

envNode16InputAlarmOnRTN	OBJECT-TYPE
	SYNTAX		INTEGER { false(1),true(2) }
	ACCESS		read-write
	STATUS		mandatory
	DESCRIPTION	"Allow an alarm to occur when a condition goes back to normal"
	::= { envNode16Entry 18 }

envNode16InputClass	OBJECT-TYPE
	SYNTAX		INTEGER
	ACCESS		read-write
	STATUS		mandatory
	DESCRIPTION	"Alarm class of Input (255 is none)"
	::= { envNode16Entry 19 }

envNode16InputDatalogEnable	OBJECT-TYPE
	SYNTAX		INTEGER { false(1),true(2) }
	ACCESS		read-write
	STATUS		mandatory
	DESCRIPTION	"Datalog Input"
	::= { envNode16Entry 20 }

envNode16InputCustomVoice	OBJECT-TYPE
	SYNTAX		DisplayString
	ACCESS		read-write
	STATUS		mandatory
	DESCRIPTION	"WAV file for the custom voice message"
	::= { envNode16Entry 21 }

envNode16InputAck	OBJECT-TYPE
	SYNTAX		INTEGER { false(1),true(2) }
	ACCESS		read-write
	STATUS		mandatory
	DESCRIPTION	"Ack alarm"
	::= { envNode16Entry 22 }

envNode17Table	OBJECT-TYPE
	SYNTAX	SEQUENCE OF	EnvNode17Entry
	ACCESS not-accessible
	STATUS	mandatory
	DESCRIPTION
		"A List of Env entries"
	::= { node17Env	1 }

envNode17Entry	OBJECT-TYPE
	SYNTAX EnvNode17Entry
	ACCESS not-accessible
	STATUS	mandatory
	DESCRIPTION
		"A Env entry"
	INDEX { envNode17Index }
	::= { envNode17Table 1 }

EnvNode17Entry ::=
	SEQUENCE {
		envNode17Index
			INTEGER,
		envNode17InputName
			DisplayString,
		envNode17InputType
			INTEGER,
		envNode17InputInUse
			INTEGER,
		envNode17InputUserInUse
			INTEGER,
		envNode17InputEnable
			INTEGER,
		envNode17InputValue
			INTEGER,
		envNode17InputStatus
			INTEGER,
		envNode17InputMin
			INTEGER,
		envNode17InputMax
			INTEGER,
		envNode17InputLastAlarm
			DisplayString,
		envNode17InputLastAck
			DisplayString,
		envNode17InputLowLimit
			INTEGER,
		envNode17InputHighLimit
			INTEGER,
		envNode17InputCalib
			INTEGER,
		envNode17InputRecTime
			INTEGER,
		envNode17InputResetTime
			INTEGER,
		envNode17InputAlarmOnRTN
			INTEGER,
		envNode17InputClass
			INTEGER,
		envNode17InputDatalogEnable
			INTEGER,
		envNode17InputCustomVoice
			DisplayString,
		envNode17InputAck
			INTEGER
	}

envNode17Index				OBJECT-TYPE
	SYNTAX				INTEGER (1..11)
	ACCESS				read-write
	STATUS				mandatory
	DESCRIPTION	"The index of the env entry 1..11"
	::= { envNode17Entry 1 }

envNode17InputName		OBJECT-TYPE
	SYNTAX				DisplayString
	ACCESS				read-write
	STATUS				mandatory
	DESCRIPTION	"Name for Input"
	::= { envNode17Entry 2 }

envNode17InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode17Entry 3 }

envNode17InputInUse	OBJECT-TYPE
	SYNTAX		INTEGER {	false(1),true(2) }
	ACCESS		read-only
	STATUS		mandatory
	DESCRIPTION	"Sensor plugged in"
	::= { envNode17Entry 4 }

envNode17InputUserInUse	OBJECT-TYPE
	SYNTAX		INTEGER {	false(1),true(2) }
	ACCESS		read-write
	STATUS		mandatory
	DESCRIPTION	"Channel Enable"
	::= { envNode17Entry 5 }

envNode17InputEnable	OBJECT-TYPE
	SYNTAX		INTEGER { false(1),true(2) }
	ACCESS		read-only
	STATUS		mandatory
	DESCRIPTION	"Input enabled by scheduler"
	::= { envNode17Entry 6 }

envNode17InputValue	OBJECT-TYPE
	SYNTAX		INTEGER
	ACCESS		read-only
	STATUS		mandatory
	DESCRIPTION	"Real time value of this input"
	::= { envNode17Entry 7 }

envNode17InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode17Entry 8 }

envNode17InputMin		OBJECT-TYPE
	SYNTAX		INTEGER
	ACCESS		read-only
	STATUS		mandatory
	DESCRIPTION	"The minimum value this input has reached"
	::= { envNode17Entry 9 }

envNode17InputMax		OBJECT-TYPE
	SYNTAX		INTEGER
	ACCESS		read-only
	STATUS		mandatory
	DESCRIPTION	"The maximum value this input has reached"
	::= { envNode17Entry 10}

envNode17InputLastAlarm	OBJECT-TYPE
	SYNTAX		DisplayString
	ACCESS		read-only
	STATUS		mandatory
	DESCRIPTION	"Timestamp of the last alarm"
	::= {  envNode17Entry 11 }

envNode17InputLastAck	OBJECT-TYPE
	SYNTAX		DisplayString
	ACCESS		read-only
	STATUS		mandatory
	DESCRIPTION	"Timestamp of the last alarm Ack"
	::= { envNode17Entry 12 }

envNode17InputLowLimit	OBJECT-TYPE
	SYNTAX		INTEGER
	ACCESS		read-write
	STATUS		mandatory
	DESCRIPTION	"The low alarm threshold"
	::= { envNode17Entry 13 }

envNode17InputHighLimit	OBJECT-TYPE
	SYNTAX		INTEGER
	ACCESS		read-write
	STATUS		mandatory
	DESCRIPTION	"The high alarm threshold"
	::= { envNode17Entry 14}

envNode17InputCalib	OBJECT-TYPE
	SYNTAX		INTEGER
	ACCESS		read-write
	STATUS		mandatory
	DESCRIPTION	"Calibration offset"
	::= { envNode17Entry 15 }

envNode17InputRecTime	OBJECT-TYPE
	SYNTAX		INTEGER
	ACCESS		read-write
	STATUS		mandatory
	DESCRIPTION	"Time in seconds for an alarm to be recognized"
	::= { envNode17Entry 16 }

envNode17InputResetTime	OBJECT-TYPE
	SYNTAX		INTEGER
	ACCESS		read-write
	STATUS		mandatory
	DESCRIPTION	"A value &gt;= 30 mins enables feature, 0 disables"
	::= { envNode17Entry 17 }

envNode17InputAlarmOnRTN	OBJECT-TYPE
	SYNTAX		INTEGER { false(1),true(2) }
	ACCESS		read-write
	STATUS		mandatory
	DESCRIPTION	"Allow an alarm to occur when a condition goes back to normal"
	::= { envNode17Entry 18 }

envNode17InputClass	OBJECT-TYPE
	SYNTAX		INTEGER
	ACCESS		read-write
	STATUS		mandatory
	DESCRIPTION	"Alarm class of Input (255 is none)"
	::= { envNode17Entry 19 }

envNode17InputDatalogEnable	OBJECT-TYPE
	SYNTAX		INTEGER { false(1),true(2) }
	ACCESS		read-write
	STATUS		mandatory
	DESCRIPTION	"Datalog Input"
	::= { envNode17Entry 20 }

envNode17InputCustomVoice	OBJECT-TYPE
	SYNTAX		DisplayString
	ACCESS		read-write
	STATUS		mandatory
	DESCRIPTION	"WAV file for the custom voice message"
	::= { envNode17Entry 21 }

envNode17InputAck	OBJECT-TYPE
	SYNTAX		INTEGER { false(1),true(2) }
	ACCESS		read-write
	STATUS		mandatory
	DESCRIPTION	"Ack alarm"
	::= { envNode17Entry 22 }

envNode18Table	OBJECT-TYPE
	SYNTAX	SEQUENCE OF	EnvNode18Entry
	ACCESS not-accessible
	STATUS	mandatory
	DESCRIPTION
		"A List of Env entries"
	::= { node18Env	1 }

envNode18Entry	OBJECT-TYPE
	SYNTAX EnvNode18Entry
	ACCESS not-accessible
	STATUS	mandatory
	DESCRIPTION
		"A Env entry"
	INDEX { envNode18Index }
	::= { envNode18Table 1 }

EnvNode18Entry ::=
	SEQUENCE {
		envNode18Index
			INTEGER,
		envNode18InputName
			DisplayString,
		envNode18InputType
			INTEGER,
		envNode18InputInUse
			INTEGER,
		envNode18InputUserInUse
			INTEGER,
		envNode18InputEnable
			INTEGER,
		envNode18InputValue
			INTEGER,
		envNode18InputStatus
			INTEGER,
		envNode18InputMin
			INTEGER,
		envNode18InputMax
			INTEGER,
		envNode18InputLastAlarm
			DisplayString,
		envNode18InputLastAck
			DisplayString,
		envNode18InputLowLimit
			INTEGER,
		envNode18InputHighLimit
			INTEGER,
		envNode18InputCalib
			INTEGER,
		envNode18InputRecTime
			INTEGER,
		envNode18InputResetTime
			INTEGER,
		envNode18InputAlarmOnRTN
			INTEGER,
		envNode18InputClass
			INTEGER,
		envNode18InputDatalogEnable
			INTEGER,
		envNode18InputCustomVoice
			DisplayString,
		envNode18InputAck
			INTEGER
	}

envNode18Index				OBJECT-TYPE
	SYNTAX				INTEGER (1..11)
	ACCESS				read-write
	STATUS				mandatory
	DESCRIPTION	"The index of the env entry 1..11"
	::= { envNode18Entry 1 }

envNode18InputName		OBJECT-TYPE
	SYNTAX				DisplayString
	ACCESS				read-write
	STATUS				mandatory
	DESCRIPTION	"Name for Input"
	::= { envNode18Entry 2 }

envNode18InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode18Entry 3 }

envNode18InputInUse	OBJECT-TYPE
	SYNTAX		INTEGER {	false(1),true(2) }
	ACCESS		read-only
	STATUS		mandatory
	DESCRIPTION	"Sensor plugged in"
	::= { envNode18Entry 4 }

envNode18InputUserInUse	OBJECT-TYPE
	SYNTAX		INTEGER {	false(1),true(2) }
	ACCESS		read-write
	STATUS		mandatory
	DESCRIPTION	"Channel Enable"
	::= { envNode18Entry 5 }

envNode18InputEnable	OBJECT-TYPE
	SYNTAX		INTEGER { false(1),true(2) }
	ACCESS		read-only
	STATUS		mandatory
	DESCRIPTION	"Input enabled by scheduler"
	::= { envNode18Entry 6 }

envNode18InputValue	OBJECT-TYPE
	SYNTAX		INTEGER
	ACCESS		read-only
	STATUS		mandatory
	DESCRIPTION	"Real time value of this input"
	::= { envNode18Entry 7 }

envNode18InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode18Entry 8 }

envNode18InputMin		OBJECT-TYPE
	SYNTAX		INTEGER
	ACCESS		read-only
	STATUS		mandatory
	DESCRIPTION	"The minimum value this input has reached"
	::= { envNode18Entry 9 }

envNode18InputMax		OBJECT-TYPE
	SYNTAX		INTEGER
	ACCESS		read-only
	STATUS		mandatory
	DESCRIPTION	"The maximum value this input has reached"
	::= { envNode18Entry 10}

envNode18InputLastAlarm	OBJECT-TYPE
	SYNTAX		DisplayString
	ACCESS		read-only
	STATUS		mandatory
	DESCRIPTION	"Timestamp of the last alarm"
	::= {  envNode18Entry 11 }

envNode18InputLastAck	OBJECT-TYPE
	SYNTAX		DisplayString
	ACCESS		read-only
	STATUS		mandatory
	DESCRIPTION	"Timestamp of the last alarm Ack"
	::= { envNode18Entry 12 }

envNode18InputLowLimit	OBJECT-TYPE
	SYNTAX		INTEGER
	ACCESS		read-write
	STATUS		mandatory
	DESCRIPTION	"The low alarm threshold"
	::= { envNode18Entry 13 }

envNode18InputHighLimit	OBJECT-TYPE
	SYNTAX		INTEGER
	ACCESS		read-write
	STATUS		mandatory
	DESCRIPTION	"The high alarm threshold"
	::= { envNode18Entry 14}

envNode18InputCalib	OBJECT-TYPE
	SYNTAX		INTEGER
	ACCESS		read-write
	STATUS		mandatory
	DESCRIPTION	"Calibration offset"
	::= { envNode18Entry 15 }

envNode18InputRecTime	OBJECT-TYPE
	SYNTAX		INTEGER
	ACCESS		read-write
	STATUS		mandatory
	DESCRIPTION	"Time in seconds for an alarm to be recognized"
	::= { envNode18Entry 16 }

envNode18InputResetTime	OBJECT-TYPE
	SYNTAX		INTEGER
	ACCESS		read-write
	STATUS		mandatory
	DESCRIPTION	"A value &gt;= 30 mins enables feature, 0 disables"
	::= { envNode18Entry 17 }

envNode18InputAlarmOnRTN	OBJECT-TYPE
	SYNTAX		INTEGER { false(1),true(2) }
	ACCESS		read-write
	STATUS		mandatory
	DESCRIPTION	"Allow an alarm to occur when a condition goes back to normal"
	::= { envNode18Entry 18 }

envNode18InputClass	OBJECT-TYPE
	SYNTAX		INTEGER
	ACCESS		read-write
	STATUS		mandatory
	DESCRIPTION	"Alarm class of Input (255 is none)"
	::= { envNode18Entry 19 }

envNode18InputDatalogEnable	OBJECT-TYPE
	SYNTAX		INTEGER { false(1),true(2) }
	ACCESS		read-write
	STATUS		mandatory
	DESCRIPTION	"Datalog Input"
	::= { envNode18Entry 20 }

envNode18InputCustomVoice	OBJECT-TYPE
	SYNTAX		DisplayString
	ACCESS		read-write
	STATUS		mandatory
	DESCRIPTION	"WAV file for the custom voice message"
	::= { envNode18Entry 21 }

envNode18InputAck	OBJECT-TYPE
	SYNTAX		INTEGER { false(1),true(2) }
	ACCESS		read-write
	STATUS		mandatory
	DESCRIPTION	"Ack alarm"
	::= { envNode18Entry 22 }

envNode19Table	OBJECT-TYPE
	SYNTAX	SEQUENCE OF	EnvNode19Entry
	ACCESS not-accessible
	STATUS	mandatory
	DESCRIPTION
		"A List of Env entries"
	::= { node19Env	1 }

envNode19Entry	OBJECT-TYPE
	SYNTAX EnvNode19Entry
	ACCESS not-accessible
	STATUS	mandatory
	DESCRIPTION
		"A Env entry"
	INDEX { envNode19Index }
	::= { envNode19Table 1 }

EnvNode19Entry ::=
	SEQUENCE {
		envNode19Index
			INTEGER,
		envNode19InputName
			DisplayString,
		envNode19InputType
			INTEGER,
		envNode19InputInUse
			INTEGER,
		envNode19InputUserInUse
			INTEGER,
		envNode19InputEnable
			INTEGER,
		envNode19InputValue
			INTEGER,
		envNode19InputStatus
			INTEGER,
		envNode19InputMin
			INTEGER,
		envNode19InputMax
			INTEGER,
		envNode19InputLastAlarm
			DisplayString,
		envNode19InputLastAck
			DisplayString,
		envNode19InputLowLimit
			INTEGER,
		envNode19InputHighLimit
			INTEGER,
		envNode19InputCalib
			INTEGER,
		envNode19InputRecTime
			INTEGER,
		envNode19InputResetTime
			INTEGER,
		envNode19InputAlarmOnRTN
			INTEGER,
		envNode19InputClass
			INTEGER,
		envNode19InputDatalogEnable
			INTEGER,
		envNode19InputCustomVoice
			DisplayString,
		envNode19InputAck
			INTEGER
	}

envNode19Index				OBJECT-TYPE
	SYNTAX				INTEGER (1..11)
	ACCESS				read-write
	STATUS				mandatory
	DESCRIPTION	"The index of the env entry 1..11"
	::= { envNode19Entry 1 }

envNode19InputName		OBJECT-TYPE
	SYNTAX				DisplayString
	ACCESS				read-write
	STATUS				mandatory
	DESCRIPTION	"Name for Input"
	::= { envNode19Entry 2 }

envNode19InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode19Entry 3 }

envNode19InputInUse	OBJECT-TYPE
	SYNTAX		INTEGER {	false(1),true(2) }
	ACCESS		read-only
	STATUS		mandatory
	DESCRIPTION	"Sensor plugged in"
	::= { envNode19Entry 4 }

envNode19InputUserInUse	OBJECT-TYPE
	SYNTAX		INTEGER {	false(1),true(2) }
	ACCESS		read-write
	STATUS		mandatory
	DESCRIPTION	"Channel Enable"
	::= { envNode19Entry 5 }

envNode19InputEnable	OBJECT-TYPE
	SYNTAX		INTEGER { false(1),true(2) }
	ACCESS		read-only
	STATUS		mandatory
	DESCRIPTION	"Input enabled by scheduler"
	::= { envNode19Entry 6 }

envNode19InputValue	OBJECT-TYPE
	SYNTAX		INTEGER
	ACCESS		read-only
	STATUS		mandatory
	DESCRIPTION	"Real time value of this input"
	::= { envNode19Entry 7 }

envNode19InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode19Entry 8 }

envNode19InputMin		OBJECT-TYPE
	SYNTAX		INTEGER
	ACCESS		read-only
	STATUS		mandatory
	DESCRIPTION	"The minimum value this input has reached"
	::= { envNode19Entry 9 }

envNode19InputMax		OBJECT-TYPE
	SYNTAX		INTEGER
	ACCESS		read-only
	STATUS		mandatory
	DESCRIPTION	"The maximum value this input has reached"
	::= { envNode19Entry 10}

envNode19InputLastAlarm	OBJECT-TYPE
	SYNTAX		DisplayString
	ACCESS		read-only
	STATUS		mandatory
	DESCRIPTION	"Timestamp of the last alarm"
	::= {  envNode19Entry 11 }

envNode19InputLastAck	OBJECT-TYPE
	SYNTAX		DisplayString
	ACCESS		read-only
	STATUS		mandatory
	DESCRIPTION	"Timestamp of the last alarm Ack"
	::= { envNode19Entry 12 }

envNode19InputLowLimit	OBJECT-TYPE
	SYNTAX		INTEGER
	ACCESS		read-write
	STATUS		mandatory
	DESCRIPTION	"The low alarm threshold"
	::= { envNode19Entry 13 }

envNode19InputHighLimit	OBJECT-TYPE
	SYNTAX		INTEGER
	ACCESS		read-write
	STATUS		mandatory
	DESCRIPTION	"The high alarm threshold"
	::= { envNode19Entry 14}

envNode19InputCalib	OBJECT-TYPE
	SYNTAX		INTEGER
	ACCESS		read-write
	STATUS		mandatory
	DESCRIPTION	"Calibration offset"
	::= { envNode19Entry 15 }

envNode19InputRecTime	OBJECT-TYPE
	SYNTAX		INTEGER
	ACCESS		read-write
	STATUS		mandatory
	DESCRIPTION	"Time in seconds for an alarm to be recognized"
	::= { envNode19Entry 16 }

envNode19InputResetTime	OBJECT-TYPE
	SYNTAX		INTEGER
	ACCESS		read-write
	STATUS		mandatory
	DESCRIPTION	"A value &gt;= 30 mins enables feature, 0 disables"
	::= { envNode19Entry 17 }

envNode19InputAlarmOnRTN	OBJECT-TYPE
	SYNTAX		INTEGER { false(1),true(2) }
	ACCESS		read-write
	STATUS		mandatory
	DESCRIPTION	"Allow an alarm to occur when a condition goes back to normal"
	::= { envNode19Entry 18 }

envNode19InputClass	OBJECT-TYPE
	SYNTAX		INTEGER
	ACCESS		read-write
	STATUS		mandatory
	DESCRIPTION	"Alarm class of Input (255 is none)"
	::= { envNode19Entry 19 }

envNode19InputDatalogEnable	OBJECT-TYPE
	SYNTAX		INTEGER { false(1),true(2) }
	ACCESS		read-write
	STATUS		mandatory
	DESCRIPTION	"Datalog Input"
	::= { envNode19Entry 20 }

envNode19InputCustomVoice	OBJECT-TYPE
	SYNTAX		DisplayString
	ACCESS		read-write
	STATUS		mandatory
	DESCRIPTION	"WAV file for the custom voice message"
	::= { envNode19Entry 21 }

envNode19InputAck	OBJECT-TYPE
	SYNTAX		INTEGER { false(1),true(2) }
	ACCESS		read-write
	STATUS		mandatory
	DESCRIPTION	"Ack alarm"
	::= { envNode19Entry 22 }

envNode20Table	OBJECT-TYPE
	SYNTAX	SEQUENCE OF	EnvNode20Entry
	ACCESS not-accessible
	STATUS	mandatory
	DESCRIPTION
		"A List of Env entries"
	::= { node20Env	1 }

envNode20Entry	OBJECT-TYPE
	SYNTAX EnvNode20Entry
	ACCESS not-accessible
	STATUS	mandatory
	DESCRIPTION
		"A Env entry"
	INDEX { envNode20Index }
	::= { envNode20Table 1 }

EnvNode20Entry ::=
	SEQUENCE {
		envNode20Index
			INTEGER,
		envNode20InputName
			DisplayString,
		envNode20InputType
			INTEGER,
		envNode20InputInUse
			INTEGER,
		envNode20InputUserInUse
			INTEGER,
		envNode20InputEnable
			INTEGER,
		envNode20InputValue
			INTEGER,
		envNode20InputStatus
			INTEGER,
		envNode20InputMin
			INTEGER,
		envNode20InputMax
			INTEGER,
		envNode20InputLastAlarm
			DisplayString,
		envNode20InputLastAck
			DisplayString,
		envNode20InputLowLimit
			INTEGER,
		envNode20InputHighLimit
			INTEGER,
		envNode20InputCalib
			INTEGER,
		envNode20InputRecTime
			INTEGER,
		envNode20InputResetTime
			INTEGER,
		envNode20InputAlarmOnRTN
			INTEGER,
		envNode20InputClass
			INTEGER,
		envNode20InputDatalogEnable
			INTEGER,
		envNode20InputCustomVoice
			DisplayString,
		envNode20InputAck
			INTEGER
	}

envNode20Index				OBJECT-TYPE
	SYNTAX				INTEGER (1..11)
	ACCESS				read-write
	STATUS				mandatory
	DESCRIPTION	"The index of the env entry 1..11"
	::= { envNode20Entry 1 }

envNode20InputName		OBJECT-TYPE
	SYNTAX				DisplayString
	ACCESS				read-write
	STATUS				mandatory
	DESCRIPTION	"Name for Input"
	::= { envNode20Entry 2 }

envNode20InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode20Entry 3 }

envNode20InputInUse	OBJECT-TYPE
	SYNTAX		INTEGER {	false(1),true(2) }
	ACCESS		read-only
	STATUS		mandatory
	DESCRIPTION	"Sensor plugged in"
	::= { envNode20Entry 4 }

envNode20InputUserInUse	OBJECT-TYPE
	SYNTAX		INTEGER {	false(1),true(2) }
	ACCESS		read-write
	STATUS		mandatory
	DESCRIPTION	"Channel Enable"
	::= { envNode20Entry 5 }

envNode20InputEnable	OBJECT-TYPE
	SYNTAX		INTEGER { false(1),true(2) }
	ACCESS		read-only
	STATUS		mandatory
	DESCRIPTION	"Input enabled by scheduler"
	::= { envNode20Entry 6 }

envNode20InputValue	OBJECT-TYPE
	SYNTAX		INTEGER
	ACCESS		read-only
	STATUS		mandatory
	DESCRIPTION	"Real time value of this input"
	::= { envNode20Entry 7 }

envNode20InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode20Entry 8 }

envNode20InputMin		OBJECT-TYPE
	SYNTAX		INTEGER
	ACCESS		read-only
	STATUS		mandatory
	DESCRIPTION	"The minimum value this input has reached"
	::= { envNode20Entry 9 }

envNode20InputMax		OBJECT-TYPE
	SYNTAX		INTEGER
	ACCESS		read-only
	STATUS		mandatory
	DESCRIPTION	"The maximum value this input has reached"
	::= { envNode20Entry 10}

envNode20InputLastAlarm	OBJECT-TYPE
	SYNTAX		DisplayString
	ACCESS		read-only
	STATUS		mandatory
	DESCRIPTION	"Timestamp of the last alarm"
	::= {  envNode20Entry 11 }

envNode20InputLastAck	OBJECT-TYPE
	SYNTAX		DisplayString
	ACCESS		read-only
	STATUS		mandatory
	DESCRIPTION	"Timestamp of the last alarm Ack"
	::= { envNode20Entry 12 }

envNode20InputLowLimit	OBJECT-TYPE
	SYNTAX		INTEGER
	ACCESS		read-write
	STATUS		mandatory
	DESCRIPTION	"The low alarm threshold"
	::= { envNode20Entry 13 }

envNode20InputHighLimit	OBJECT-TYPE
	SYNTAX		INTEGER
	ACCESS		read-write
	STATUS		mandatory
	DESCRIPTION	"The high alarm threshold"
	::= { envNode20Entry 14}

envNode20InputCalib	OBJECT-TYPE
	SYNTAX		INTEGER
	ACCESS		read-write
	STATUS		mandatory
	DESCRIPTION	"Calibration offset"
	::= { envNode20Entry 15 }

envNode20InputRecTime	OBJECT-TYPE
	SYNTAX		INTEGER
	ACCESS		read-write
	STATUS		mandatory
	DESCRIPTION	"Time in seconds for an alarm to be recognized"
	::= { envNode20Entry 16 }

envNode20InputResetTime	OBJECT-TYPE
	SYNTAX		INTEGER
	ACCESS		read-write
	STATUS		mandatory
	DESCRIPTION	"A value &gt;= 30 mins enables feature, 0 disables"
	::= { envNode20Entry 17 }

envNode20InputAlarmOnRTN	OBJECT-TYPE
	SYNTAX		INTEGER { false(1),true(2) }
	ACCESS		read-write
	STATUS		mandatory
	DESCRIPTION	"Allow an alarm to occur when a condition goes back to normal"
	::= { envNode20Entry 18 }

envNode20InputClass	OBJECT-TYPE
	SYNTAX		INTEGER
	ACCESS		read-write
	STATUS		mandatory
	DESCRIPTION	"Alarm class of Input (255 is none)"
	::= { envNode20Entry 19 }

envNode20InputDatalogEnable	OBJECT-TYPE
	SYNTAX		INTEGER { false(1),true(2) }
	ACCESS		read-write
	STATUS		mandatory
	DESCRIPTION	"Datalog Input"
	::= { envNode20Entry 20 }

envNode20InputCustomVoice	OBJECT-TYPE
	SYNTAX		DisplayString
	ACCESS		read-write
	STATUS		mandatory
	DESCRIPTION	"WAV file for the custom voice message"
	::= { envNode20Entry 21}

envNode20InputAck	OBJECT-TYPE
	SYNTAX		INTEGER { false(1),true(2) }
	ACCESS		read-write
	STATUS		mandatory
	DESCRIPTION	"Ack alarm"
	::= { envNode20Entry 22 }

envNode21Table	OBJECT-TYPE
	SYNTAX	SEQUENCE OF	EnvNode21Entry
	ACCESS not-accessible
	STATUS	mandatory
	DESCRIPTION
		"A List of Env entries"
	::= { node21Env	1 }

envNode21Entry	OBJECT-TYPE
	SYNTAX EnvNode21Entry
	ACCESS not-accessible
	STATUS	mandatory
	DESCRIPTION
		"A Env entry"
	INDEX { envNode21Index }
	::= { envNode21Table 1 }

EnvNode21Entry ::=
	SEQUENCE {
		envNode21Index
			INTEGER,
		envNode21InputName
			DisplayString,
		envNode21InputType
			INTEGER,
		envNode21InputInUse
			INTEGER,
		envNode21InputUserInUse
			INTEGER,
		envNode21InputEnable
			INTEGER,
		envNode21InputValue
			INTEGER,
		envNode21InputStatus
			INTEGER,
		envNode21InputMin
			INTEGER,
		envNode21InputMax
			INTEGER,
		envNode21InputLastAlarm
			DisplayString,
		envNode21InputLastAck
			DisplayString,
		envNode21InputLowLimit
			INTEGER,
		envNode21InputHighLimit
			INTEGER,
		envNode21InputCalib
			INTEGER,
		envNode21InputRecTime
			INTEGER,
		envNode21InputResetTime
			INTEGER,
		envNode21InputAlarmOnRTN
			INTEGER,
		envNode21InputClass
			INTEGER,
		envNode21InputDatalogEnable
			INTEGER,
		envNode21InputCustomVoice
			DisplayString,
		envNode21InputAck
			INTEGER
	}

envNode21Index				OBJECT-TYPE
	SYNTAX				INTEGER (1..11)
	ACCESS				read-write
	STATUS				mandatory
	DESCRIPTION	"The index of the env entry 1..11"
	::= { envNode21Entry 1 }

envNode21InputName		OBJECT-TYPE
	SYNTAX				DisplayString
	ACCESS				read-write
	STATUS				mandatory
	DESCRIPTION	"Name for Input"
	::= { envNode21Entry 2 }

envNode21InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode21Entry 3 }

envNode21InputInUse	OBJECT-TYPE
	SYNTAX		INTEGER {	false(1),true(2) }
	ACCESS		read-only
	STATUS		mandatory
	DESCRIPTION	"Sensor plugged in"
	::= { envNode21Entry 4 }

envNode21InputUserInUse	OBJECT-TYPE
	SYNTAX		INTEGER {	false(1),true(2) }
	ACCESS		read-write
	STATUS		mandatory
	DESCRIPTION	"Channel Enable"
	::= { envNode21Entry 5 }

envNode21InputEnable	OBJECT-TYPE
	SYNTAX		INTEGER { false(1),true(2) }
	ACCESS		read-only
	STATUS		mandatory
	DESCRIPTION	"Input enabled by scheduler"
	::= { envNode21Entry 6 }

envNode21InputValue	OBJECT-TYPE
	SYNTAX		INTEGER
	ACCESS		read-only
	STATUS		mandatory
	DESCRIPTION	"Real time value of this input"
	::= { envNode21Entry 7 }

envNode21InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode21Entry 8 }

envNode21InputMin		OBJECT-TYPE
	SYNTAX		INTEGER
	ACCESS		read-only
	STATUS		mandatory
	DESCRIPTION	"The minimum value this input has reached"
	::= { envNode21Entry 9 }

envNode21InputMax		OBJECT-TYPE
	SYNTAX		INTEGER
	ACCESS		read-only
	STATUS		mandatory
	DESCRIPTION	"The maximum value this input has reached"
	::= { envNode21Entry 10}

envNode21InputLastAlarm	OBJECT-TYPE
	SYNTAX		DisplayString
	ACCESS		read-only
	STATUS		mandatory
	DESCRIPTION	"Timestamp of the last alarm"
	::= {  envNode21Entry 11 }

envNode21InputLastAck	OBJECT-TYPE
	SYNTAX		DisplayString
	ACCESS		read-only
	STATUS		mandatory
	DESCRIPTION	"Timestamp of the last alarm Ack"
	::= { envNode21Entry 12 }

envNode21InputLowLimit	OBJECT-TYPE
	SYNTAX		INTEGER
	ACCESS		read-write
	STATUS		mandatory
	DESCRIPTION	"The low alarm threshold"
	::= { envNode21Entry 13 }

envNode21InputHighLimit	OBJECT-TYPE
	SYNTAX		INTEGER
	ACCESS		read-write
	STATUS		mandatory
	DESCRIPTION	"The high alarm threshold"
	::= { envNode21Entry 14}

envNode21InputCalib	OBJECT-TYPE
	SYNTAX		INTEGER
	ACCESS		read-write
	STATUS		mandatory
	DESCRIPTION	"Calibration offset"
	::= { envNode21Entry 15 }

envNode21InputRecTime	OBJECT-TYPE
	SYNTAX		INTEGER
	ACCESS		read-write
	STATUS		mandatory
	DESCRIPTION	"Time in seconds for an alarm to be recognized"
	::= { envNode21Entry 16 }

envNode21InputResetTime	OBJECT-TYPE
	SYNTAX		INTEGER
	ACCESS		read-write
	STATUS		mandatory
	DESCRIPTION	"A value &gt;= 30 mins enables feature, 0 disables"
	::= { envNode21Entry 17 }

envNode21InputAlarmOnRTN	OBJECT-TYPE
	SYNTAX		INTEGER { false(1),true(2) }
	ACCESS		read-write
	STATUS		mandatory
	DESCRIPTION	"Allow an alarm to occur when a condition goes back to normal"
	::= { envNode21Entry 18 }

envNode21InputClass	OBJECT-TYPE
	SYNTAX		INTEGER
	ACCESS		read-write
	STATUS		mandatory
	DESCRIPTION	"Alarm class of Input (255 is none)"
	::= { envNode21Entry 19 }

envNode21InputDatalogEnable	OBJECT-TYPE
	SYNTAX		INTEGER { false(1),true(2) }
	ACCESS		read-write
	STATUS		mandatory
	DESCRIPTION	"Datalog Input"
	::= { envNode21Entry 20 }

envNode21InputCustomVoice	OBJECT-TYPE
	SYNTAX		DisplayString
	ACCESS		read-write
	STATUS		mandatory
	DESCRIPTION	"WAV file for the custom voice message"
	::= { envNode21Entry 21 }

envNode21InputAck	OBJECT-TYPE
	SYNTAX		INTEGER { false(1),true(2) }
	ACCESS		read-write
	STATUS		mandatory
	DESCRIPTION	"Ack alarm"
	::= { envNode21Entry 22 }

envNode22Table	OBJECT-TYPE
	SYNTAX	SEQUENCE OF	EnvNode22Entry
	ACCESS not-accessible
	STATUS	mandatory
	DESCRIPTION
		"A List of Env entries"
	::= { node22Env	1 }

envNode22Entry	OBJECT-TYPE
	SYNTAX EnvNode22Entry
	ACCESS not-accessible
	STATUS	mandatory
	DESCRIPTION
		"A Env entry"
	INDEX { envNode22Index }
	::= { envNode22Table 1 }

EnvNode22Entry ::=
	SEQUENCE {
		envNode22Index
			INTEGER,
		envNode22InputName
			DisplayString,
		envNode22InputType
			INTEGER,
		envNode22InputInUse
			INTEGER,
		envNode22InputUserInUse
			INTEGER,
		envNode22InputEnable
			INTEGER,
		envNode22InputValue
			INTEGER,
		envNode22InputStatus
			INTEGER,
		envNode22InputMin
			INTEGER,
		envNode22InputMax
			INTEGER,
		envNode22InputLastAlarm
			DisplayString,
		envNode22InputLastAck
			DisplayString,
		envNode22InputLowLimit
			INTEGER,
		envNode22InputHighLimit
			INTEGER,
		envNode22InputCalib
			INTEGER,
		envNode22InputRecTime
			INTEGER,
		envNode22InputResetTime
			INTEGER,
		envNode22InputAlarmOnRTN
			INTEGER,
		envNode22InputClass
			INTEGER,
		envNode22InputDatalogEnable
			INTEGER,
		envNode22InputCustomVoice
			DisplayString,
		envNode22InputAck
			INTEGER
	}

envNode22Index				OBJECT-TYPE
	SYNTAX				INTEGER (1..11)
	ACCESS				read-write
	STATUS				mandatory
	DESCRIPTION	"The index of the env entry 1..11"
	::= { envNode22Entry 1 }

envNode22InputName		OBJECT-TYPE
	SYNTAX				DisplayString
	ACCESS				read-write
	STATUS				mandatory
	DESCRIPTION	"Name for Input"
	::= { envNode22Entry 2 }

envNode22InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"The type of sensor attached to Input 1 on the host"
	::= { envNode22Entry 3 }

envNode22InputInUse	OBJECT-TYPE
	SYNTAX		INTEGER {	false(1),true(2) }
	ACCESS		read-only
	STATUS		mandatory
	DESCRIPTION	"Sensor plugged in"
	::= { envNode22Entry 4 }

envNode22InputUserInUse	OBJECT-TYPE
	SYNTAX		INTEGER {	false(1),true(2) }
	ACCESS		read-write
	STATUS		mandatory
	DESCRIPTION	"Channel Enable"
	::= { envNode22Entry 5 }

envNode22InputEnable	OBJECT-TYPE
	SYNTAX		INTEGER { false(1),true(2) }
	ACCESS		read-only
	STATUS		mandatory
	DESCRIPTION	"Input enabled by scheduler"
	::= { envNode22Entry 6 }

envNode22InputValue	OBJECT-TYPE
	SYNTAX		INTEGER
	ACCESS		read-only
	STATUS		mandatory
	DESCRIPTION	"Real time value of this input"
	::= { envNode22Entry 7 }

envNode22InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode22Entry 8 }

envNode22InputMin		OBJECT-TYPE
	SYNTAX		INTEGER
	ACCESS		read-only
	STATUS		mandatory
	DESCRIPTION	"The minimum value this input has reached"
	::= { envNode22Entry 9 }

envNode22InputMax		OBJECT-TYPE
	SYNTAX		INTEGER
	ACCESS		read-only
	STATUS		mandatory
	DESCRIPTION	"The maximum value this input has reached"
	::= { envNode22Entry 10}

envNode22InputLastAlarm	OBJECT-TYPE
	SYNTAX		DisplayString
	ACCESS		read-only
	STATUS		mandatory
	DESCRIPTION	"Timestamp of the last alarm"
	::= {  envNode22Entry 11 }

envNode22InputLastAck	OBJECT-TYPE
	SYNTAX		DisplayString
	ACCESS		read-only
	STATUS		mandatory
	DESCRIPTION	"Timestamp of the last alarm Ack"
	::= { envNode22Entry 12 }

envNode22InputLowLimit	OBJECT-TYPE
	SYNTAX		INTEGER
	ACCESS		read-write
	STATUS		mandatory
	DESCRIPTION	"The low alarm threshold"
	::= { envNode22Entry 13 }

envNode22InputHighLimit	OBJECT-TYPE
	SYNTAX		INTEGER
	ACCESS		read-write
	STATUS		mandatory
	DESCRIPTION	"The high alarm threshold"
	::= { envNode22Entry 14}

envNode22InputCalib	OBJECT-TYPE
	SYNTAX		INTEGER
	ACCESS		read-write
	STATUS		mandatory
	DESCRIPTION	"Calibration offset"
	::= { envNode22Entry 15 }

envNode22InputRecTime	OBJECT-TYPE
	SYNTAX		INTEGER
	ACCESS		read-write
	STATUS		mandatory
	DESCRIPTION	"Time in seconds for an alarm to be recognized"
	::= { envNode22Entry 16 }

envNode22InputResetTime	OBJECT-TYPE
	SYNTAX		INTEGER
	ACCESS		read-write
	STATUS		mandatory
	DESCRIPTION	"Time in minutes when an alarm will re-trip after Ack"
	::= { envNode22Entry 17 }

envNode22InputAlarmOnRTN	OBJECT-TYPE
	SYNTAX		INTEGER { false(1),true(2) }
	ACCESS		read-write
	STATUS		mandatory
	DESCRIPTION	"Allow an alarm to occur when a condition goes back to normal"
	::= { envNode22Entry 18 }

envNode22InputClass	OBJECT-TYPE
	SYNTAX		INTEGER
	ACCESS		read-write
	STATUS		mandatory
	DESCRIPTION	"Alarm class of Input (255 is none)"
	::= { envNode22Entry 19 }

envNode22InputDatalogEnable	OBJECT-TYPE
	SYNTAX		INTEGER { false(1),true(2) }
	ACCESS		read-write
	STATUS		mandatory
	DESCRIPTION	"Datalog Input"
	::= { envNode22Entry 20}

envNode22InputCustomVoice	OBJECT-TYPE
	SYNTAX		DisplayString
	ACCESS		read-write
	STATUS		mandatory
	DESCRIPTION	"WAV file for the custom voice message"
	::= { envNode22Entry 21 }

envNode22InputAck	OBJECT-TYPE
	SYNTAX		INTEGER { false(1),true(2) }
	ACCESS		read-write
	STATUS		mandatory
	DESCRIPTION	"Ack alarm"
	::= { envNode22Entry 22 }

envNode23Table	OBJECT-TYPE
	SYNTAX	SEQUENCE OF	EnvNode23Entry
	ACCESS not-accessible
	STATUS	mandatory
	DESCRIPTION
		"A List of Env entries"
	::= { node23Env	1 }

envNode23Entry	OBJECT-TYPE
	SYNTAX EnvNode23Entry
	ACCESS not-accessible
	STATUS	mandatory
	DESCRIPTION
		"A Env entry"
	INDEX { envNode23Index }
	::= { envNode23Table 1 }

EnvNode23Entry ::=
	SEQUENCE {
		envNode23Index
			INTEGER,
		envNode23InputName
			DisplayString,
		envNode23InputType
			INTEGER,
		envNode23InputInUse
			INTEGER,
		envNode23InputUserInUse
			INTEGER,
		envNode23InputEnable
			INTEGER,
		envNode23InputValue
			INTEGER,
		envNode23InputStatus
			INTEGER,
		envNode23InputMin
			INTEGER,
		envNode23InputMax
			INTEGER,
		envNode23InputLastAlarm
			DisplayString,
		envNode23InputLastAck
			DisplayString,
		envNode23InputLowLimit
			INTEGER,
		envNode23InputHighLimit
			INTEGER,
		envNode23InputCalib
			INTEGER,
		envNode23InputRecTime
			INTEGER,
		envNode23InputResetTime
			INTEGER,
		envNode23InputAlarmOnRTN
			INTEGER,
		envNode23InputClass
			INTEGER,
		envNode23InputDatalogEnable
			INTEGER,
		envNode23InputCustomVoice
			DisplayString,
		envNode23InputAck
			INTEGER
	}

envNode23Index				OBJECT-TYPE
	SYNTAX				INTEGER (1..11)
	ACCESS				read-write
	STATUS				mandatory
	DESCRIPTION	"The index of the env entry 1..11"
	::= { envNode23Entry 1 }

envNode23InputName		OBJECT-TYPE
	SYNTAX				DisplayString
	ACCESS				read-write
	STATUS				mandatory
	DESCRIPTION	"Name for Input"
	::= { envNode23Entry 2 }

envNode23InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode23Entry 3 }

envNode23InputInUse	OBJECT-TYPE
	SYNTAX		INTEGER {	false(1),true(2) }
	ACCESS		read-only
	STATUS		mandatory
	DESCRIPTION	"Sensor plugged in"
	::= { envNode23Entry 4 }

envNode23InputUserInUse	OBJECT-TYPE
	SYNTAX		INTEGER {	false(1),true(2) }
	ACCESS		read-write
	STATUS		mandatory
	DESCRIPTION	"Channel Enable"
	::= { envNode23Entry 5 }

envNode23InputEnable	OBJECT-TYPE
	SYNTAX		INTEGER { false(1),true(2) }
	ACCESS		read-only
	STATUS		mandatory
	DESCRIPTION	"Input enabled by scheduler"
	::= { envNode23Entry 6 }

envNode23InputValue	OBJECT-TYPE
	SYNTAX		INTEGER
	ACCESS		read-only
	STATUS		mandatory
	DESCRIPTION	"Real time value of this input"
	::= { envNode23Entry 7 }

envNode23InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode23Entry 8 }

envNode23InputMin		OBJECT-TYPE
	SYNTAX		INTEGER
	ACCESS		read-only
	STATUS		mandatory
	DESCRIPTION	"The minimum value this input has reached"
	::= { envNode23Entry 9 }

envNode23InputMax		OBJECT-TYPE
	SYNTAX		INTEGER
	ACCESS		read-only
	STATUS		mandatory
	DESCRIPTION	"The maximum value this input has reached"
	::= { envNode23Entry 10}

envNode23InputLastAlarm	OBJECT-TYPE
	SYNTAX		DisplayString
	ACCESS		read-only
	STATUS		mandatory
	DESCRIPTION	"Timestamp of the last alarm"
	::= {  envNode23Entry 11 }

envNode23InputLastAck	OBJECT-TYPE
	SYNTAX		DisplayString
	ACCESS		read-only
	STATUS		mandatory
	DESCRIPTION	"Timestamp of the last alarm Ack"
	::= { envNode23Entry 12 }

envNode23InputLowLimit	OBJECT-TYPE
	SYNTAX		INTEGER
	ACCESS		read-write
	STATUS		mandatory
	DESCRIPTION	"The low alarm threshold"
	::= { envNode23Entry 13 }

envNode23InputHighLimit	OBJECT-TYPE
	SYNTAX		INTEGER
	ACCESS		read-write
	STATUS		mandatory
	DESCRIPTION	"The high alarm threshold"
	::= { envNode23Entry 14}

envNode23InputCalib	OBJECT-TYPE
	SYNTAX		INTEGER
	ACCESS		read-write
	STATUS		mandatory
	DESCRIPTION	"Calibration offset"
	::= { envNode23Entry 15 }

envNode23InputRecTime	OBJECT-TYPE
	SYNTAX		INTEGER
	ACCESS		read-write
	STATUS		mandatory
	DESCRIPTION	"Time in seconds for an alarm to be recognized"
	::= { envNode23Entry 16 }

envNode23InputResetTime	OBJECT-TYPE
	SYNTAX		INTEGER
	ACCESS		read-write
	STATUS		mandatory
	DESCRIPTION	"A value &gt;= 30 mins enables feature, 0 disables"
	::= { envNode23Entry 17 }

envNode23InputAlarmOnRTN	OBJECT-TYPE
	SYNTAX		INTEGER { false(1),true(2) }
	ACCESS		read-write
	STATUS		mandatory
	DESCRIPTION	"Allow an alarm to occur when a condition goes back to normal"
	::= { envNode23Entry 18 }

envNode23InputClass	OBJECT-TYPE
	SYNTAX		INTEGER
	ACCESS		read-write
	STATUS		mandatory
	DESCRIPTION	"Alarm class of Input (255 is none)"
	::= { envNode23Entry 19 }

envNode23InputDatalogEnable	OBJECT-TYPE
	SYNTAX		INTEGER { false(1),true(2) }
	ACCESS		read-write
	STATUS		mandatory
	DESCRIPTION	"Datalog Input"
	::= { envNode23Entry 20 }

envNode23InputCustomVoice	OBJECT-TYPE
	SYNTAX		DisplayString
	ACCESS		read-write
	STATUS		mandatory
	DESCRIPTION	"WAV file for the custom voice message"
	::= { envNode23Entry 21 }

envNode23InputAck	OBJECT-TYPE
	SYNTAX		INTEGER { false(1),true(2) }
	ACCESS		read-write
	STATUS		mandatory
	DESCRIPTION	"Ack alarm"
	::= { envNode23Entry 22 }

envNode24Table	OBJECT-TYPE
	SYNTAX	SEQUENCE OF	EnvNode24Entry
	ACCESS not-accessible
	STATUS	mandatory
	DESCRIPTION
		"A List of Env entries"
	::= { node24Env	1 }

envNode24Entry	OBJECT-TYPE
	SYNTAX EnvNode24Entry
	ACCESS not-accessible
	STATUS	mandatory
	DESCRIPTION
		"A Env entry"
	INDEX { envNode24Index }
	::= { envNode24Table 1 }

EnvNode24Entry ::=
	SEQUENCE {
		envNode24Index
			INTEGER,
		envNode24InputName
			DisplayString,
		envNode24InputType
			INTEGER,
		envNode24InputInUse
			INTEGER,
		envNode24InputUserInUse
			INTEGER,
		envNode24InputEnable
			INTEGER,
		envNode24InputValue
			INTEGER,
		envNode24InputStatus
			INTEGER,
		envNode24InputMin
			INTEGER,
		envNode24InputMax
			INTEGER,
		envNode24InputLastAlarm
			DisplayString,
		envNode24InputLastAck
			DisplayString,
		envNode24InputLowLimit
			INTEGER,
		envNode24InputHighLimit
			INTEGER,
		envNode24InputCalib
			INTEGER,
		envNode24InputRecTime
			INTEGER,
		envNode24InputResetTime
			INTEGER,
		envNode24InputAlarmOnRTN
			INTEGER,
		envNode24InputClass
			INTEGER,
		envNode24InputDatalogEnable
			INTEGER,
		envNode24InputCustomVoice
			DisplayString,
		envNode24InputAck
			INTEGER
	}

envNode24Index				OBJECT-TYPE
	SYNTAX				INTEGER (1..11)
	ACCESS				read-write
	STATUS				mandatory
	DESCRIPTION	"The index of the env entry 1..11"
	::= { envNode24Entry 1 }

envNode24InputName		OBJECT-TYPE
	SYNTAX				DisplayString
	ACCESS				read-write
	STATUS				mandatory
	DESCRIPTION	"Name for Input"
	::= { envNode24Entry 2 }

envNode24InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode24Entry 3 }

envNode24InputInUse	OBJECT-TYPE
	SYNTAX		INTEGER {	false(1),true(2) }
	ACCESS		read-only
	STATUS		mandatory
	DESCRIPTION	"Sensor plugged in"
	::= { envNode24Entry 4 }

envNode24InputUserInUse	OBJECT-TYPE
	SYNTAX		INTEGER {	false(1),true(2) }
	ACCESS		read-write
	STATUS		mandatory
	DESCRIPTION	"Channel Enable"
	::= { envNode24Entry 5 }

envNode24InputEnable	OBJECT-TYPE
	SYNTAX		INTEGER { false(1),true(2) }
	ACCESS		read-only
	STATUS		mandatory
	DESCRIPTION	"True if this input is enabled by the scheduler"
	::= { envNode24Entry 6 }

envNode24InputValue	OBJECT-TYPE
	SYNTAX		INTEGER
	ACCESS		read-only
	STATUS		mandatory
	DESCRIPTION	"Real time value of this input"
	::= { envNode24Entry 7 }

envNode24InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode24Entry 8 }

envNode24InputMin		OBJECT-TYPE
	SYNTAX		INTEGER
	ACCESS		read-only
	STATUS		mandatory
	DESCRIPTION	"The minimum value this input has reached"
	::= { envNode24Entry 9 }

envNode24InputMax		OBJECT-TYPE
	SYNTAX		INTEGER
	ACCESS		read-only
	STATUS		mandatory
	DESCRIPTION	"The maximum value this input has reached"
	::= { envNode24Entry 10}

envNode24InputLastAlarm	OBJECT-TYPE
	SYNTAX		DisplayString
	ACCESS		read-only
	STATUS		mandatory
	DESCRIPTION	"Timestamp of the last alarm"
	::= {  envNode24Entry 11 }

envNode24InputLastAck	OBJECT-TYPE
	SYNTAX		DisplayString
	ACCESS		read-only
	STATUS		mandatory
	DESCRIPTION	"Timestamp of the last alarm Ack"
	::= { envNode24Entry 12 }

envNode24InputLowLimit	OBJECT-TYPE
	SYNTAX		INTEGER
	ACCESS		read-write
	STATUS		mandatory
	DESCRIPTION	"The low alarm threshold"
	::= { envNode24Entry 13 }

envNode24InputHighLimit	OBJECT-TYPE
	SYNTAX		INTEGER
	ACCESS		read-write
	STATUS		mandatory
	DESCRIPTION	"The high alarm threshold"
	::= { envNode24Entry 14}

envNode24InputCalib	OBJECT-TYPE
	SYNTAX		INTEGER
	ACCESS		read-write
	STATUS		mandatory
	DESCRIPTION	"Calibration offset"
	::= { envNode24Entry 15 }

envNode24InputRecTime	OBJECT-TYPE
	SYNTAX		INTEGER
	ACCESS		read-write
	STATUS		mandatory
	DESCRIPTION	"Time in seconds for an alarm to be recognized"
	::= { envNode24Entry 16 }

envNode24InputResetTime	OBJECT-TYPE
	SYNTAX		INTEGER
	ACCESS		read-write
	STATUS		mandatory
	DESCRIPTION	"A value &gt;= 30 mins enables feature, 0 disables"
	::= { envNode24Entry 17 }

envNode24InputAlarmOnRTN	OBJECT-TYPE
	SYNTAX		INTEGER { false(1),true(2) }
	ACCESS		read-write
	STATUS		mandatory
	DESCRIPTION	"Allow an alarm to occur when a condition goes back to normal"
	::= { envNode24Entry 18 }

envNode24InputClass	OBJECT-TYPE
	SYNTAX		INTEGER
	ACCESS		read-write
	STATUS		mandatory
	DESCRIPTION	"Alarm class of Input (255 is none)"
	::= { envNode24Entry 19 }

envNode24InputDatalogEnable	OBJECT-TYPE
	SYNTAX		INTEGER { false(1),true(2) }
	ACCESS		read-write
	STATUS		mandatory
	DESCRIPTION	"Datalog Input"
	::= { envNode24Entry 20 }

envNode24InputCustomVoice	OBJECT-TYPE
	SYNTAX		DisplayString
	ACCESS		read-write
	STATUS		mandatory
	DESCRIPTION	"WAV file for the custom voice message"
	::= { envNode24Entry 21 }

envNode24InputAck	OBJECT-TYPE
	SYNTAX		INTEGER { false(1),true(2) }
	ACCESS		read-write
	STATUS		mandatory
	DESCRIPTION	"Ack alarm"
	::= { envNode24Entry 22 }

envNode25Table	OBJECT-TYPE
	SYNTAX	SEQUENCE OF	EnvNode25Entry
	ACCESS not-accessible
	STATUS	mandatory
	DESCRIPTION
		"A List of Env entries"
	::= { node25Env	1 }

envNode25Entry	OBJECT-TYPE
	SYNTAX EnvNode25Entry
	ACCESS not-accessible
	STATUS	mandatory
	DESCRIPTION
		"A Env entry"
	INDEX { envNode25Index }
	::= { envNode25Table 1 }

EnvNode25Entry ::=
	SEQUENCE {
		envNode25Index
			INTEGER,
		envNode25InputName
			DisplayString,
		envNode25InputType
			INTEGER,
		envNode25InputInUse
			INTEGER,
		envNode25InputUserInUse
			INTEGER,
		envNode25InputEnable
			INTEGER,
		envNode25InputValue
			INTEGER,
		envNode25InputStatus
			INTEGER,
		envNode25InputMin
			INTEGER,
		envNode25InputMax
			INTEGER,
		envNode25InputLastAlarm
			DisplayString,
		envNode25InputLastAck
			DisplayString,
		envNode25InputLowLimit
			INTEGER,
		envNode25InputHighLimit
			INTEGER,
		envNode25InputCalib
			INTEGER,
		envNode25InputRecTime
			INTEGER,
		envNode25InputResetTime
			INTEGER,
		envNode25InputAlarmOnRTN
			INTEGER,
		envNode25InputClass
			INTEGER,
		envNode25InputDatalogEnable
			INTEGER,
		envNode25InputCustomVoice
			DisplayString,
		envNode25InputAck
			INTEGER
	}

envNode25Index				OBJECT-TYPE
	SYNTAX				INTEGER (1..11)
	ACCESS				read-write
	STATUS				mandatory
	DESCRIPTION	"The index of the env entry 1..11"
	::= { envNode25Entry 1 }

envNode25InputName		OBJECT-TYPE
	SYNTAX				DisplayString
	ACCESS				read-write
	STATUS				mandatory
	DESCRIPTION	"Name for Input"
	::= { envNode25Entry 2 }

envNode25InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode25Entry 3 }

envNode25InputInUse	OBJECT-TYPE
	SYNTAX		INTEGER {	false(1),true(2) }
	ACCESS		read-only
	STATUS		mandatory
	DESCRIPTION	"Sensor plugged in"
	::= { envNode25Entry 4 }

envNode25InputUserInUse	OBJECT-TYPE
	SYNTAX		INTEGER {	false(1),true(2) }
	ACCESS		read-write
	STATUS		mandatory
	DESCRIPTION	"Channel Enable"
	::= { envNode25Entry 5 }

envNode25InputEnable	OBJECT-TYPE
	SYNTAX		INTEGER { false(1),true(2) }
	ACCESS		read-only
	STATUS		mandatory
	DESCRIPTION	"Input enabled by scheduler"
	::= { envNode25Entry 6 }

envNode25InputValue	OBJECT-TYPE
	SYNTAX		INTEGER
	ACCESS		read-only
	STATUS		mandatory
	DESCRIPTION	"Real time value of this input"
	::= { envNode25Entry 7 }

envNode25InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode25Entry 8 }

envNode25InputMin		OBJECT-TYPE
	SYNTAX		INTEGER
	ACCESS		read-only
	STATUS		mandatory
	DESCRIPTION	"The minimum value this input has reached"
	::= { envNode25Entry 9 }

envNode25InputMax		OBJECT-TYPE
	SYNTAX		INTEGER
	ACCESS		read-only
	STATUS		mandatory
	DESCRIPTION	"The maximum value this input has reached"
	::= { envNode25Entry 10}

envNode25InputLastAlarm	OBJECT-TYPE
	SYNTAX		DisplayString
	ACCESS		read-only
	STATUS		mandatory
	DESCRIPTION	"Timestamp of the last alarm"
	::= {  envNode25Entry 11 }

envNode25InputLastAck	OBJECT-TYPE
	SYNTAX		DisplayString
	ACCESS		read-only
	STATUS		mandatory
	DESCRIPTION	"Timestamp of the last alarm Ack"
	::= { envNode25Entry 12 }

envNode25InputLowLimit	OBJECT-TYPE
	SYNTAX		INTEGER
	ACCESS		read-write
	STATUS		mandatory
	DESCRIPTION	"The low alarm threshold"
	::= { envNode25Entry 13 }

envNode25InputHighLimit	OBJECT-TYPE
	SYNTAX		INTEGER
	ACCESS		read-write
	STATUS		mandatory
	DESCRIPTION	"The high alarm threshold"
	::= { envNode25Entry 14}

envNode25InputCalib	OBJECT-TYPE
	SYNTAX		INTEGER
	ACCESS		read-write
	STATUS		mandatory
	DESCRIPTION	"Calibration offset"
	::= { envNode25Entry 15 }

envNode25InputRecTime	OBJECT-TYPE
	SYNTAX		INTEGER
	ACCESS		read-write
	STATUS		mandatory
	DESCRIPTION	"Time in seconds for an alarm to be recognized"
	::= { envNode25Entry 16 }

envNode25InputResetTime	OBJECT-TYPE
	SYNTAX		INTEGER
	ACCESS		read-write
	STATUS		mandatory
	DESCRIPTION	"A value &gt;= 30 mins enables feature, 0 disables"
	::= { envNode25Entry 17 }

envNode25InputAlarmOnRTN	OBJECT-TYPE
	SYNTAX		INTEGER { false(1),true(2) }
	ACCESS		read-write
	STATUS		mandatory
	DESCRIPTION	"Allow an alarm to occur when a condition goes back to normal"
	::= { envNode25Entry 18 }

envNode25InputClass	OBJECT-TYPE
	SYNTAX		INTEGER
	ACCESS		read-write
	STATUS		mandatory
	DESCRIPTION	"Alarm class of Input (255 is none)"
	::= { envNode25Entry 19 }

envNode25InputDatalogEnable	OBJECT-TYPE
	SYNTAX		INTEGER { false(1),true(2) }
	ACCESS		read-write
	STATUS		mandatory
	DESCRIPTION	"Datalog Input"
	::= { envNode25Entry 20 }

envNode25InputCustomVoice	OBJECT-TYPE
	SYNTAX		DisplayString
	ACCESS		read-write
	STATUS		mandatory
	DESCRIPTION	"WAV file for the custom voice message"
	::= { envNode25Entry 21 }

envNode25InputAck	OBJECT-TYPE
	SYNTAX		INTEGER { false(1),true(2) }
	ACCESS		read-write
	STATUS		mandatory
	DESCRIPTION	"Ack alarm"
	::= { envNode25Entry 22 }

envNode26Table	OBJECT-TYPE
	SYNTAX	SEQUENCE OF	EnvNode26Entry
	ACCESS not-accessible
	STATUS	mandatory
	DESCRIPTION
		"A List of Env entries"
	::= { node26Env	1 }

envNode26Entry	OBJECT-TYPE
	SYNTAX EnvNode26Entry
	ACCESS not-accessible
	STATUS	mandatory
	DESCRIPTION
		"A Env entry"
	INDEX { envNode26Index }
	::= { envNode26Table 1 }

EnvNode26Entry ::=
	SEQUENCE {
		envNode26Index
			INTEGER,
		envNode26InputName
			DisplayString,
		envNode26InputType
			INTEGER,
		envNode26InputInUse
			INTEGER,
		envNode26InputUserInUse
			INTEGER,
		envNode26InputEnable
			INTEGER,
		envNode26InputValue
			INTEGER,
		envNode26InputStatus
			INTEGER,
		envNode26InputMin
			INTEGER,
		envNode26InputMax
			INTEGER,
		envNode26InputLastAlarm
			DisplayString,
		envNode26InputLastAck
			DisplayString,
		envNode26InputLowLimit
			INTEGER,
		envNode26InputHighLimit
			INTEGER,
		envNode26InputCalib
			INTEGER,
		envNode26InputRecTime
			INTEGER,
		envNode26InputResetTime
			INTEGER,
		envNode26InputAlarmOnRTN
			INTEGER,
		envNode26InputClass
			INTEGER,
		envNode26InputDatalogEnable
			INTEGER,
		envNode26InputCustomVoice
			DisplayString,
		envNode26InputAck
			INTEGER
	}

envNode26Index				OBJECT-TYPE
	SYNTAX				INTEGER (1..11)
	ACCESS				read-write
	STATUS				mandatory
	DESCRIPTION	"The index of the env entry 1..11"
	::= { envNode26Entry 1 }

envNode26InputName		OBJECT-TYPE
	SYNTAX				DisplayString
	ACCESS				read-write
	STATUS				mandatory
	DESCRIPTION	"Name for Input"
	::= { envNode26Entry 2 }

envNode26InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode26Entry 3 }

envNode26InputInUse	OBJECT-TYPE
	SYNTAX		INTEGER {	false(1),true(2) }
	ACCESS		read-only
	STATUS		mandatory
	DESCRIPTION	"Sensor plugged in"
	::= { envNode26Entry 4 }

envNode26InputUserInUse	OBJECT-TYPE
	SYNTAX		INTEGER {	false(1),true(2) }
	ACCESS		read-write
	STATUS		mandatory
	DESCRIPTION	"Channel Enable"
	::= { envNode26Entry 5 }

envNode26InputEnable	OBJECT-TYPE
	SYNTAX		INTEGER { false(1),true(2) }
	ACCESS		read-only
	STATUS		mandatory
	DESCRIPTION	"Input enabled by scheduler"
	::= { envNode26Entry 6 }

envNode26InputValue	OBJECT-TYPE
	SYNTAX		INTEGER
	ACCESS		read-only
	STATUS		mandatory
	DESCRIPTION	"Real time value of this input"
	::= { envNode26Entry 7 }

envNode26InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode26Entry 8 }

envNode26InputMin		OBJECT-TYPE
	SYNTAX		INTEGER
	ACCESS		read-only
	STATUS		mandatory
	DESCRIPTION	"The minimum value this input has reached"
	::= { envNode26Entry 9 }

envNode26InputMax		OBJECT-TYPE
	SYNTAX		INTEGER
	ACCESS		read-only
	STATUS		mandatory
	DESCRIPTION	"The maximum value this input has reached"
	::= { envNode26Entry 10}

envNode26InputLastAlarm	OBJECT-TYPE
	SYNTAX		DisplayString
	ACCESS		read-only
	STATUS		mandatory
	DESCRIPTION	"Timestamp of the last alarm"
	::= {  envNode26Entry 11 }

envNode26InputLastAck	OBJECT-TYPE
	SYNTAX		DisplayString
	ACCESS		read-only
	STATUS		mandatory
	DESCRIPTION	"Timestamp of the last alarm Ack"
	::= { envNode26Entry 12 }

envNode26InputLowLimit	OBJECT-TYPE
	SYNTAX		INTEGER
	ACCESS		read-write
	STATUS		mandatory
	DESCRIPTION	"The low alarm threshold"
	::= { envNode26Entry 13 }

envNode26InputHighLimit	OBJECT-TYPE
	SYNTAX		INTEGER
	ACCESS		read-write
	STATUS		mandatory
	DESCRIPTION	"The high alarm threshold"
	::= { envNode26Entry 14}

envNode26InputCalib	OBJECT-TYPE
	SYNTAX		INTEGER
	ACCESS		read-write
	STATUS		mandatory
	DESCRIPTION	"Calibration offset"
	::= { envNode26Entry 15 }

envNode26InputRecTime	OBJECT-TYPE
	SYNTAX		INTEGER
	ACCESS		read-write
	STATUS		mandatory
	DESCRIPTION	"Time in seconds for an alarm to be recognized"
	::= { envNode26Entry 16 }

envNode26InputResetTime	OBJECT-TYPE
	SYNTAX		INTEGER
	ACCESS		read-write
	STATUS		mandatory
	DESCRIPTION	"A value &gt;= 30 mins enables feature, 0 disables"
	::= { envNode26Entry 17 }

envNode26InputAlarmOnRTN	OBJECT-TYPE
	SYNTAX		INTEGER { false(1),true(2) }
	ACCESS		read-write
	STATUS		mandatory
	DESCRIPTION	"Allow an alarm to occur when a condition goes back to normal"
	::= { envNode26Entry 18 }

envNode26InputClass	OBJECT-TYPE
	SYNTAX		INTEGER
	ACCESS		read-write
	STATUS		mandatory
	DESCRIPTION	"Alarm class of Input (255 is none)"
	::= { envNode26Entry 19 }

envNode26InputDatalogEnable	OBJECT-TYPE
	SYNTAX		INTEGER { false(1),true(2) }
	ACCESS		read-write
	STATUS		mandatory
	DESCRIPTION	"Datalog Input"
	::= { envNode26Entry 20 }

envNode26InputCustomVoice	OBJECT-TYPE
	SYNTAX		DisplayString
	ACCESS		read-write
	STATUS		mandatory
	DESCRIPTION	"WAV file for the custom voice message"
	::= { envNode26Entry 21 }

envNode26InputAck	OBJECT-TYPE
	SYNTAX		INTEGER { false(1),true(2) }
	ACCESS		read-write
	STATUS		mandatory
	DESCRIPTION	"Ack alarm"
	::= { envNode26Entry 22 }

envNode27Table	OBJECT-TYPE
	SYNTAX	SEQUENCE OF	EnvNode27Entry
	ACCESS not-accessible
	STATUS	mandatory
	DESCRIPTION
		"A List of Env entries"
	::= { node27Env	1 }

envNode27Entry	OBJECT-TYPE
	SYNTAX EnvNode27Entry
	ACCESS not-accessible
	STATUS	mandatory
	DESCRIPTION
		"A Env entry"
	INDEX { envNode27Index }
	::= { envNode27Table 1 }

EnvNode27Entry ::=
	SEQUENCE {
		envNode27Index
			INTEGER,
		envNode27InputName
			DisplayString,
		envNode27InputType
			INTEGER,
		envNode27InputInUse
			INTEGER,
		envNode27InputUserInUse
			INTEGER,
		envNode27InputEnable
			INTEGER,
		envNode27InputValue
			INTEGER,
		envNode27InputStatus
			INTEGER,
		envNode27InputMin
			INTEGER,
		envNode27InputMax
			INTEGER,
		envNode27InputLastAlarm
			DisplayString,
		envNode27InputLastAck
			DisplayString,
		envNode27InputLowLimit
			INTEGER,
		envNode27InputHighLimit
			INTEGER,
		envNode27InputCalib
			INTEGER,
		envNode27InputRecTime
			INTEGER,
		envNode27InputResetTime
			INTEGER,
		envNode27InputAlarmOnRTN
			INTEGER,
		envNode27InputClass
			INTEGER,
		envNode27InputDatalogEnable
			INTEGER,
		envNode27InputCustomVoice
			DisplayString,
		envNode27InputAck
			INTEGER
	}

envNode27Index				OBJECT-TYPE
	SYNTAX				INTEGER (1..11)
	ACCESS				read-write
	STATUS				mandatory
	DESCRIPTION	"The index of the env entry 1..11"
	::= { envNode27Entry 1 }

envNode27InputName		OBJECT-TYPE
	SYNTAX				DisplayString
	ACCESS				read-write
	STATUS				mandatory
	DESCRIPTION	"Name for Input"
	::= { envNode27Entry 2 }

envNode27InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode27Entry 3 }

envNode27InputInUse	OBJECT-TYPE
	SYNTAX		INTEGER {	false(1),true(2) }
	ACCESS		read-only
	STATUS		mandatory
	DESCRIPTION	"Sensor plugged in"
	::= { envNode27Entry 4 }

envNode27InputUserInUse	OBJECT-TYPE
	SYNTAX		INTEGER {	false(1),true(2) }
	ACCESS		read-write
	STATUS		mandatory
	DESCRIPTION	"Channel Enable"
	::= { envNode27Entry 5 }

envNode27InputEnable	OBJECT-TYPE
	SYNTAX		INTEGER { false(1),true(2) }
	ACCESS		read-only
	STATUS		mandatory
	DESCRIPTION	"Input enabled by scheduler"
	::= { envNode27Entry 6 }

envNode27InputValue	OBJECT-TYPE
	SYNTAX		INTEGER
	ACCESS		read-only
	STATUS		mandatory
	DESCRIPTION	"Real time value of this input"
	::= { envNode27Entry 7 }

envNode27InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode27Entry 8 }

envNode27InputMin		OBJECT-TYPE
	SYNTAX		INTEGER
	ACCESS		read-only
	STATUS		mandatory
	DESCRIPTION	"The minimum value this input has reached"
	::= { envNode27Entry 9 }

envNode27InputMax		OBJECT-TYPE
	SYNTAX		INTEGER
	ACCESS		read-only
	STATUS		mandatory
	DESCRIPTION	"The maximum value this input has reached"
	::= { envNode27Entry 10}

envNode27InputLastAlarm	OBJECT-TYPE
	SYNTAX		DisplayString
	ACCESS		read-only
	STATUS		mandatory
	DESCRIPTION	"Timestamp of the last alarm"
	::= {  envNode27Entry 11 }

envNode27InputLastAck	OBJECT-TYPE
	SYNTAX		DisplayString
	ACCESS		read-only
	STATUS		mandatory
	DESCRIPTION	"Timestamp of the last alarm Ack"
	::= { envNode27Entry 12 }

envNode27InputLowLimit	OBJECT-TYPE
	SYNTAX		INTEGER
	ACCESS		read-write
	STATUS		mandatory
	DESCRIPTION	"The low alarm threshold"
	::= { envNode27Entry 13 }

envNode27InputHighLimit	OBJECT-TYPE
	SYNTAX		INTEGER
	ACCESS		read-write
	STATUS		mandatory
	DESCRIPTION	"The high alarm threshold"
	::= { envNode27Entry 14}

envNode27InputCalib	OBJECT-TYPE
	SYNTAX		INTEGER
	ACCESS		read-write
	STATUS		mandatory
	DESCRIPTION	"Calibration offset"
	::= { envNode27Entry 15 }

envNode27InputRecTime	OBJECT-TYPE
	SYNTAX		INTEGER
	ACCESS		read-write
	STATUS		mandatory
	DESCRIPTION	"Time in seconds for an alarm to be recognized"
	::= { envNode27Entry 16 }

envNode27InputResetTime	OBJECT-TYPE
	SYNTAX		INTEGER
	ACCESS		read-write
	STATUS		mandatory
	DESCRIPTION	"A value &gt;= 30 mins enables feature, 0 disables"
	::= { envNode27Entry 17 }

envNode27InputAlarmOnRTN	OBJECT-TYPE
	SYNTAX		INTEGER { false(1),true(2) }
	ACCESS		read-write
	STATUS		mandatory
	DESCRIPTION	"Allow an alarm to occur when a condition goes back to normal"
	::= { envNode27Entry 18 }

envNode27InputClass	OBJECT-TYPE
	SYNTAX		INTEGER
	ACCESS		read-write
	STATUS		mandatory
	DESCRIPTION	"Alarm class of Input (255 is none)"
	::= { envNode27Entry 19 }

envNode27InputDatalogEnable	OBJECT-TYPE
	SYNTAX		INTEGER { false(1),true(2) }
	ACCESS		read-write
	STATUS		mandatory
	DESCRIPTION	"Datalog Input"
	::= { envNode27Entry 20 }

envNode27InputCustomVoice	OBJECT-TYPE
	SYNTAX		DisplayString
	ACCESS		read-write
	STATUS		mandatory
	DESCRIPTION	"WAV file for the custom voice message"
	::= { envNode27Entry 21 }

envNode27InputAck	OBJECT-TYPE
	SYNTAX		INTEGER { false(1),true(2) }
	ACCESS		read-write
	STATUS		mandatory
	DESCRIPTION	"Ack alarm"
	::= { envNode27Entry 22 }

envNode28Table	OBJECT-TYPE
	SYNTAX	SEQUENCE OF	EnvNode28Entry
	ACCESS not-accessible
	STATUS	mandatory
	DESCRIPTION
		"A List of Env entries"
	::= { node28Env	1 }

envNode28Entry	OBJECT-TYPE
	SYNTAX EnvNode28Entry
	ACCESS not-accessible
	STATUS	mandatory
	DESCRIPTION
		"A Env entry"
	INDEX { envNode28Index }
	::= { envNode28Table 1 }

EnvNode28Entry ::=
	SEQUENCE {
		envNode28Index
			INTEGER,
		envNode28InputName
			DisplayString,
		envNode28InputType
			INTEGER,
		envNode28InputInUse
			INTEGER,
		envNode28InputUserInUse
			INTEGER,
		envNode28InputEnable
			INTEGER,
		envNode28InputValue
			INTEGER,
		envNode28InputStatus
			INTEGER,
		envNode28InputMin
			INTEGER,
		envNode28InputMax
			INTEGER,
		envNode28InputLastAlarm
			DisplayString,
		envNode28InputLastAck
			DisplayString,
		envNode28InputLowLimit
			INTEGER,
		envNode28InputHighLimit
			INTEGER,
		envNode28InputCalib
			INTEGER,
		envNode28InputRecTime
			INTEGER,
		envNode28InputResetTime
			INTEGER,
		envNode28InputAlarmOnRTN
			INTEGER,
		envNode28InputClass
			INTEGER,
		envNode28InputDatalogEnable
			INTEGER,
		envNode28InputCustomVoice
			DisplayString,
		envNode28InputAck
			INTEGER
	}

envNode28Index				OBJECT-TYPE
	SYNTAX				INTEGER (1..11)
	ACCESS				read-write
	STATUS				mandatory
	DESCRIPTION	"The index of the env entry 1..11"
	::= { envNode28Entry 1 }

envNode28InputName		OBJECT-TYPE
	SYNTAX				DisplayString
	ACCESS				read-write
	STATUS				mandatory
	DESCRIPTION	"Name for Input"
	::= { envNode28Entry 2 }

envNode28InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode28Entry 3 }

envNode28InputInUse	OBJECT-TYPE
	SYNTAX		INTEGER {	false(1),true(2) }
	ACCESS		read-only
	STATUS		mandatory
	DESCRIPTION	"Sensor plugged in"
	::= { envNode28Entry 4 }

envNode28InputUserInUse	OBJECT-TYPE
	SYNTAX		INTEGER {	false(1),true(2) }
	ACCESS		read-write
	STATUS		mandatory
	DESCRIPTION	"Channel Enable"
	::= { envNode28Entry 5 }

envNode28InputEnable	OBJECT-TYPE
	SYNTAX		INTEGER { false(1),true(2) }
	ACCESS		read-only
	STATUS		mandatory
	DESCRIPTION	"Input enabled by scheduler"
	::= { envNode28Entry 6 }

envNode28InputValue	OBJECT-TYPE
	SYNTAX		INTEGER
	ACCESS		read-only
	STATUS		mandatory
	DESCRIPTION	"Real time value of this input"
	::= { envNode28Entry 7 }

envNode28InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode28Entry 8 }

envNode28InputMin		OBJECT-TYPE
	SYNTAX		INTEGER
	ACCESS		read-only
	STATUS		mandatory
	DESCRIPTION	"The minimum value this input has reached"
	::= { envNode28Entry 9 }

envNode28InputMax		OBJECT-TYPE
	SYNTAX		INTEGER
	ACCESS		read-only
	STATUS		mandatory
	DESCRIPTION	"The maximum value this input has reached"
	::= { envNode28Entry 10}

envNode28InputLastAlarm	OBJECT-TYPE
	SYNTAX		DisplayString
	ACCESS		read-only
	STATUS		mandatory
	DESCRIPTION	"Timestamp of the last alarm"
	::= {  envNode28Entry 11 }

envNode28InputLastAck	OBJECT-TYPE
	SYNTAX		DisplayString
	ACCESS		read-only
	STATUS		mandatory
	DESCRIPTION	"Timestamp of the last alarm Ack"
	::= { envNode28Entry 12 }

envNode28InputLowLimit	OBJECT-TYPE
	SYNTAX		INTEGER
	ACCESS		read-write
	STATUS		mandatory
	DESCRIPTION	"The low alarm threshold"
	::= { envNode28Entry 13 }

envNode28InputHighLimit	OBJECT-TYPE
	SYNTAX		INTEGER
	ACCESS		read-write
	STATUS		mandatory
	DESCRIPTION	"The high alarm threshold"
	::= { envNode28Entry 14}

envNode28InputCalib	OBJECT-TYPE
	SYNTAX		INTEGER
	ACCESS		read-write
	STATUS		mandatory
	DESCRIPTION	"Calibration offset"
	::= { envNode28Entry 15 }

envNode28InputRecTime	OBJECT-TYPE
	SYNTAX		INTEGER
	ACCESS		read-write
	STATUS		mandatory
	DESCRIPTION	"Time in seconds for an alarm to be recognized"
	::= { envNode28Entry 16 }

envNode28InputResetTime	OBJECT-TYPE
	SYNTAX		INTEGER
	ACCESS		read-write
	STATUS		mandatory
	DESCRIPTION	"A value &gt;= 30 mins enables feature, 0 disables"
	::= { envNode28Entry 17 }

envNode28InputAlarmOnRTN	OBJECT-TYPE
	SYNTAX		INTEGER { false(1),true(2) }
	ACCESS		read-write
	STATUS		mandatory
	DESCRIPTION	"Allow an alarm to occur when a condition goes back to normal"
	::= { envNode28Entry 18 }

envNode28InputClass	OBJECT-TYPE
	SYNTAX		INTEGER
	ACCESS		read-write
	STATUS		mandatory
	DESCRIPTION	"Alarm class of Input (255 is none)"
	::= { envNode28Entry 19 }

envNode28InputDatalogEnable	OBJECT-TYPE
	SYNTAX		INTEGER { false(1),true(2) }
	ACCESS		read-write
	STATUS		mandatory
	DESCRIPTION	"Datalog Input"
	::= { envNode28Entry 20 }

envNode28InputCustomVoice	OBJECT-TYPE
	SYNTAX		DisplayString
	ACCESS		read-write
	STATUS		mandatory
	DESCRIPTION	"WAV file for the custom voice message"
	::= { envNode28Entry 21 }

envNode28InputAck	OBJECT-TYPE
	SYNTAX		INTEGER { false(1),true(2) }
	ACCESS		read-write
	STATUS		mandatory
	DESCRIPTION	"Ack alarm"
	::= { envNode28Entry 22 }

envNode29Table	OBJECT-TYPE
	SYNTAX	SEQUENCE OF	EnvNode29Entry
	ACCESS not-accessible
	STATUS	mandatory
	DESCRIPTION
		"A List of Env entries"
	::= { node29Env	1 }

envNode29Entry	OBJECT-TYPE
	SYNTAX EnvNode29Entry
	ACCESS not-accessible
	STATUS	mandatory
	DESCRIPTION
		"A Env entry"
	INDEX { envNode29Index }
	::= { envNode29Table 1 }

EnvNode29Entry ::=
	SEQUENCE {
		envNode29Index
			INTEGER,
		envNode29InputName
			DisplayString,
		envNode29InputType
			INTEGER,
		envNode29InputInUse
			INTEGER,
		envNode29InputUserInUse
			INTEGER,
		envNode29InputEnable
			INTEGER,
		envNode29InputValue
			INTEGER,
		envNode29InputStatus
			INTEGER,
		envNode29InputMin
			INTEGER,
		envNode29InputMax
			INTEGER,
		envNode29InputLastAlarm
			DisplayString,
		envNode29InputLastAck
			DisplayString,
		envNode29InputLowLimit
			INTEGER,
		envNode29InputHighLimit
			INTEGER,
		envNode29InputCalib
			INTEGER,
		envNode29InputRecTime
			INTEGER,
		envNode29InputResetTime
			INTEGER,
		envNode29InputAlarmOnRTN
			INTEGER,
		envNode29InputClass
			INTEGER,
		envNode29InputDatalogEnable
			INTEGER,
		envNode29InputCustomVoice
			DisplayString,
		envNode29InputAck
			INTEGER
	}

envNode29Index				OBJECT-TYPE
	SYNTAX				INTEGER (1..11)
	ACCESS				read-write
	STATUS				mandatory
	DESCRIPTION	"The index of the env entry 1..11"
	::= { envNode29Entry 1 }

envNode29InputName		OBJECT-TYPE
	SYNTAX				DisplayString
	ACCESS				read-write
	STATUS				mandatory
	DESCRIPTION	"Name for Input"
	::= { envNode29Entry 2 }

envNode29InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode29Entry 3 }

envNode29InputInUse	OBJECT-TYPE
	SYNTAX		INTEGER {	false(1),true(2) }
	ACCESS		read-only
	STATUS		mandatory
	DESCRIPTION	"Sensor plugged in"
	::= { envNode29Entry 4 }

envNode29InputUserInUse	OBJECT-TYPE
	SYNTAX		INTEGER {	false(1),true(2) }
	ACCESS		read-write
	STATUS		mandatory
	DESCRIPTION	"Channel Enable"
	::= { envNode29Entry 5 }

envNode29InputEnable	OBJECT-TYPE
	SYNTAX		INTEGER { false(1),true(2) }
	ACCESS		read-only
	STATUS		mandatory
	DESCRIPTION	"Input enabled by scheduler"
	::= { envNode29Entry 6 }

envNode29InputValue	OBJECT-TYPE
	SYNTAX		INTEGER
	ACCESS		read-only
	STATUS		mandatory
	DESCRIPTION	"Real time value of this input"
	::= { envNode29Entry 7 }

envNode29InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode29Entry 8 }

envNode29InputMin		OBJECT-TYPE
	SYNTAX		INTEGER
	ACCESS		read-only
	STATUS		mandatory
	DESCRIPTION	"The minimum value this input has reached"
	::= { envNode29Entry 9 }

envNode29InputMax		OBJECT-TYPE
	SYNTAX		INTEGER
	ACCESS		read-only
	STATUS		mandatory
	DESCRIPTION	"The maximum value this input has reached"
	::= { envNode29Entry 10}

envNode29InputLastAlarm	OBJECT-TYPE
	SYNTAX		DisplayString
	ACCESS		read-only
	STATUS		mandatory
	DESCRIPTION	"Timestamp of the last alarm"
	::= {  envNode29Entry 11 }

envNode29InputLastAck	OBJECT-TYPE
	SYNTAX		DisplayString
	ACCESS		read-only
	STATUS		mandatory
	DESCRIPTION	"Timestamp of the last alarm Ack"
	::= { envNode29Entry 12 }

envNode29InputLowLimit	OBJECT-TYPE
	SYNTAX		INTEGER
	ACCESS		read-write
	STATUS		mandatory
	DESCRIPTION	"The low alarm threshold"
	::= { envNode29Entry 13 }

envNode29InputHighLimit	OBJECT-TYPE
	SYNTAX		INTEGER
	ACCESS		read-write
	STATUS		mandatory
	DESCRIPTION	"The high alarm threshold"
	::= { envNode29Entry 14}

envNode29InputCalib	OBJECT-TYPE
	SYNTAX		INTEGER
	ACCESS		read-write
	STATUS		mandatory
	DESCRIPTION	"Calibration offset"
	::= { envNode29Entry 15 }

envNode29InputRecTime	OBJECT-TYPE
	SYNTAX		INTEGER
	ACCESS		read-write
	STATUS		mandatory
	DESCRIPTION	"Time in seconds for an alarm to be recognized"
	::= { envNode29Entry 16 }

envNode29InputResetTime	OBJECT-TYPE
	SYNTAX		INTEGER
	ACCESS		read-write
	STATUS		mandatory
	DESCRIPTION	"A value &gt;= 30 mins enables feature, 0 disables"
	::= { envNode29Entry 17 }

envNode29InputAlarmOnRTN	OBJECT-TYPE
	SYNTAX		INTEGER { false(1),true(2) }
	ACCESS		read-write
	STATUS		mandatory
	DESCRIPTION	"Allow an alarm to occur when a condition goes back to normal"
	::= { envNode29Entry 18 }

envNode29InputClass	OBJECT-TYPE
	SYNTAX		INTEGER
	ACCESS		read-write
	STATUS		mandatory
	DESCRIPTION	"Alarm class of Input (255 is none)"
	::= { envNode29Entry 19 }

envNode29InputDatalogEnable	OBJECT-TYPE
	SYNTAX		INTEGER { false(1),true(2) }
	ACCESS		read-write
	STATUS		mandatory
	DESCRIPTION	"Datalog Input"
	::= { envNode29Entry 20 }

envNode29InputCustomVoice	OBJECT-TYPE
	SYNTAX		DisplayString
	ACCESS		read-write
	STATUS		mandatory
	DESCRIPTION	"WAV file for the custom voice message"
	::= { envNode29Entry 21 }

envNode29InputAck	OBJECT-TYPE
	SYNTAX		INTEGER { false(1),true(2) }
	ACCESS		read-write
	STATUS		mandatory
	DESCRIPTION	"Ack alarm"
	::= { envNode29Entry 22 }

envNode30Table	OBJECT-TYPE
	SYNTAX	SEQUENCE OF	EnvNode30Entry
	ACCESS not-accessible
	STATUS	mandatory
	DESCRIPTION
		"A List of Env entries"
	::= { node30Env	1 }

envNode30Entry	OBJECT-TYPE
	SYNTAX EnvNode30Entry
	ACCESS not-accessible
	STATUS	mandatory
	DESCRIPTION
		"A Env entry"
	INDEX { envNode30Index }
	::= { envNode30Table 1 }

EnvNode30Entry ::=
	SEQUENCE {
		envNode30Index
			INTEGER,
		envNode30InputName
			DisplayString,
		envNode30InputType
			INTEGER,
		envNode30InputInUse
			INTEGER,
		envNode30InputUserInUse
			INTEGER,
		envNode30InputEnable
			INTEGER,
		envNode30InputValue
			INTEGER,
		envNode30InputStatus
			INTEGER,
		envNode30InputMin
			INTEGER,
		envNode30InputMax
			INTEGER,
		envNode30InputLastAlarm
			DisplayString,
		envNode30InputLastAck
			DisplayString,
		envNode30InputLowLimit
			INTEGER,
		envNode30InputHighLimit
			INTEGER,
		envNode30InputCalib
			INTEGER,
		envNode30InputRecTime
			INTEGER,
		envNode30InputResetTime
			INTEGER,
		envNode30InputAlarmOnRTN
			INTEGER,
		envNode30InputClass
			INTEGER,
		envNode30InputDatalogEnable
			INTEGER,
		envNode30InputCustomVoice
			DisplayString,
		envNode30InputAck
			INTEGER
	}

envNode30Index				OBJECT-TYPE
	SYNTAX				INTEGER (1..11)
	ACCESS				read-write
	STATUS				mandatory
	DESCRIPTION	"The index of the env entry 1..11"
	::= { envNode30Entry 1 }

envNode30InputName		OBJECT-TYPE
	SYNTAX				DisplayString
	ACCESS				read-write
	STATUS				mandatory
	DESCRIPTION	"Name for Input"
	::= { envNode30Entry 2 }

envNode30InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode30Entry 3 }

envNode30InputInUse	OBJECT-TYPE
	SYNTAX		INTEGER {	false(1),true(2) }
	ACCESS		read-only
	STATUS		mandatory
	DESCRIPTION	"Sensor plugged in"
	::= { envNode30Entry 4 }

envNode30InputUserInUse	OBJECT-TYPE
	SYNTAX		INTEGER {	false(1),true(2) }
	ACCESS		read-write
	STATUS		mandatory
	DESCRIPTION	"Channel Enable"
	::= { envNode30Entry 5 }

envNode30InputEnable	OBJECT-TYPE
	SYNTAX		INTEGER { false(1),true(2) }
	ACCESS		read-only
	STATUS		mandatory
	DESCRIPTION	"Input enabled by scheduler"
	::= { envNode30Entry 6 }

envNode30InputValue	OBJECT-TYPE
	SYNTAX		INTEGER
	ACCESS		read-only
	STATUS		mandatory
	DESCRIPTION	"Real time value of this input"
	::= { envNode30Entry 7 }

envNode30InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode30Entry 8 }

envNode30InputMin		OBJECT-TYPE
	SYNTAX		INTEGER
	ACCESS		read-only
	STATUS		mandatory
	DESCRIPTION	"The minimum value this input has reached"
	::= { envNode30Entry 9 }

envNode30InputMax		OBJECT-TYPE
	SYNTAX		INTEGER
	ACCESS		read-only
	STATUS		mandatory
	DESCRIPTION	"The maximum value this input has reached"
	::= { envNode30Entry 10}

envNode30InputLastAlarm	OBJECT-TYPE
	SYNTAX		DisplayString
	ACCESS		read-only
	STATUS		mandatory
	DESCRIPTION	"Timestamp of the last alarm"
	::= {  envNode30Entry 11 }

envNode30InputLastAck	OBJECT-TYPE
	SYNTAX		DisplayString
	ACCESS		read-only
	STATUS		mandatory
	DESCRIPTION	"Timestamp of the last alarm Ack"
	::= { envNode30Entry 12 }

envNode30InputLowLimit	OBJECT-TYPE
	SYNTAX		INTEGER
	ACCESS		read-write
	STATUS		mandatory
	DESCRIPTION	"The low alarm threshold"
	::= { envNode30Entry 13 }

envNode30InputHighLimit	OBJECT-TYPE
	SYNTAX		INTEGER
	ACCESS		read-write
	STATUS		mandatory
	DESCRIPTION	"The high alarm threshold"
	::= { envNode30Entry 14}

envNode30InputCalib	OBJECT-TYPE
	SYNTAX		INTEGER
	ACCESS		read-write
	STATUS		mandatory
	DESCRIPTION	"Calibration offset"
	::= { envNode30Entry 15 }

envNode30InputRecTime	OBJECT-TYPE
	SYNTAX		INTEGER
	ACCESS		read-write
	STATUS		mandatory
	DESCRIPTION	"Time in seconds for an alarm to be recognized"
	::= { envNode30Entry 16 }

envNode30InputResetTime	OBJECT-TYPE
	SYNTAX		INTEGER
	ACCESS		read-write
	STATUS		mandatory
	DESCRIPTION	"A value &gt;= 30 mins enables feature, 0 disables"
	::= { envNode30Entry 17 }

envNode30InputAlarmOnRTN	OBJECT-TYPE
	SYNTAX		INTEGER { false(1),true(2) }
	ACCESS		read-write
	STATUS		mandatory
	DESCRIPTION	"Allow an alarm to occur when a condition goes back to normal"
	::= { envNode30Entry 18 }

envNode30InputClass	OBJECT-TYPE
	SYNTAX		INTEGER
	ACCESS		read-write
	STATUS		mandatory
	DESCRIPTION	"Alarm class of Input (255 is none)"
	::= { envNode30Entry 19 }

envNode30InputDatalogEnable	OBJECT-TYPE
	SYNTAX		INTEGER { false(1),true(2) }
	ACCESS		read-write
	STATUS		mandatory
	DESCRIPTION	"Datalog Input"
	::= { envNode30Entry 20 }

envNode30InputCustomVoice	OBJECT-TYPE
	SYNTAX		DisplayString
	ACCESS		read-write
	STATUS		mandatory
	DESCRIPTION	"WAV file for the custom voice message"
	::= { envNode30Entry 21 }

envNode30InputAck	OBJECT-TYPE
	SYNTAX		INTEGER { false(1),true(2) }
	ACCESS		read-write
	STATUS		mandatory
	DESCRIPTION	"Ack alarm"
	::= { envNode30Entry 22 }

envNode31Table	OBJECT-TYPE
	SYNTAX	SEQUENCE OF	EnvNode31Entry
	ACCESS not-accessible
	STATUS	mandatory
	DESCRIPTION
		"A List of Env entries"
	::= { node31Env	1 }

envNode31Entry	OBJECT-TYPE
	SYNTAX EnvNode31Entry
	ACCESS not-accessible
	STATUS	mandatory
	DESCRIPTION
		"A Env entry"
	INDEX { envNode31Index }
	::= { envNode31Table 1 }

EnvNode31Entry ::=
	SEQUENCE {
		envNode31Index
			INTEGER,
		envNode31InputName
			DisplayString,
		envNode31InputType
			INTEGER,
		envNode31InputInUse
			INTEGER,
		envNode31InputUserInUse
			INTEGER,
		envNode31InputEnable
			INTEGER,
		envNode31InputValue
			INTEGER,
		envNode31InputStatus
			INTEGER,
		envNode31InputMin
			INTEGER,
		envNode31InputMax
			INTEGER,
		envNode31InputLastAlarm
			DisplayString,
		envNode31InputLastAck
			DisplayString,
		envNode31InputLowLimit
			INTEGER,
		envNode31InputHighLimit
			INTEGER,
		envNode31InputCalib
			INTEGER,
		envNode31InputRecTime
			INTEGER,
		envNode31InputResetTime
			INTEGER,
		envNode31InputAlarmOnRTN
			INTEGER,
		envNode31InputClass
			INTEGER,
		envNode31InputDatalogEnable
			INTEGER,
		envNode31InputCustomVoice
			DisplayString,
		envNode31InputAck
			INTEGER
	}

envNode31Index				OBJECT-TYPE
	SYNTAX				INTEGER (1..11)
	ACCESS				read-write
	STATUS				mandatory
	DESCRIPTION	"The index of the env entry 1..11"
	::= { envNode31Entry 1 }

envNode31InputName		OBJECT-TYPE
	SYNTAX				DisplayString
	ACCESS				read-write
	STATUS				mandatory
	DESCRIPTION	"Name for Input"
	::= { envNode31Entry 2 }

envNode31InputType			OBJECT-TYPE
	SYNTAX				INTEGER {
		temp-F(1),temp-C(2),hum(3),water(4),extPower(5),nc(6),no(7),
		smoke(8),irMotion(9),humLCD(10),temp-F-LCD(11),temp-C-LCD(12),
		trans40-20ma(13),undef1(14),undef2(15),none(16),hostPower(17),
		nodePower(18),battery(19),sound(20),ip(21)
	}
	ACCESS				read-only
	STATUS				mandatory
	DESCRIPTION	"Type of sensor"
	::= { envNode31Entry 3 }

envNode31InputInUse	OBJECT-TYPE
	SYNTAX		INTEGER {	false(1),true(2) }
	ACCESS		read-only
	STATUS		mandatory
	DESCRIPTION	"Sensor plugged in"
	::= { envNode31Entry 4 }

envNode31InputUserInUse	OBJECT-TYPE
	SYNTAX		INTEGER {	false(1),true(2) }
	ACCESS		read-write
	STATUS		mandatory
	DESCRIPTION	"Channel Enable"
	::= { envNode31Entry 5 }

envNode31InputEnable	OBJECT-TYPE
	SYNTAX		INTEGER { false(1),true(2) }
	ACCESS		read-only
	STATUS		mandatory
	DESCRIPTION	"Input enabled by scheduler"
	::= { envNode31Entry 6 }

envNode31InputValue	OBJECT-TYPE
	SYNTAX		INTEGER
	ACCESS		read-only
	STATUS		mandatory
	DESCRIPTION	"Real time value of this input"
	::= { envNode31Entry 7 }

envNode31InputStatus	OBJECT-TYPE
	SYNTAX				INTEGER	{
		ok(1),waiting(2),openSensorClosed(3),
		closedSensorOpened(4),low(5),high(6),pingTO(7),retToNorm(8),
		sensorTrouble(9),routeDown(10),nodeTrouble(11),pGTrouble(12)
	}
	ACCESS		read-only
	STATUS		mandatory
	DESCRIPTION	"Alarm status code"
	::= { envNode31Entry 8 }

envNode31InputMin		OBJECT-TYPE
	SYNTAX		INTEGER
	ACCESS		read-only
	STATUS		mandatory
	DESCRIPTION	"The minimum value this input has reached"
	::= { envNode31Entry 9 }

envNode31InputMax		OBJECT-TYPE
	SYNTAX		INTEGER
	ACCESS		read-only
	STATUS		mandatory
	DESCRIPTION	"The maximum value this input has reached"
	::= { envNode31Entry 10}

envNode31InputLastAlarm	OBJECT-TYPE
	SYNTAX		DisplayString
	ACCESS		read-only
	STATUS		mandatory
	DESCRIPTION	"Timestamp of the last alarm"
	::= {  envNode31Entry 11 }

envNode31InputLastAck	OBJECT-TYPE
	SYNTAX		DisplayString
	ACCESS		read-only
	STATUS		mandatory
	DESCRIPTION	"Timestamp of the last alarm Ack"
	::= { envNode31Entry 12 }

envNode31InputLowLimit	OBJECT-TYPE
	SYNTAX		INTEGER
	ACCESS		read-write
	STATUS		mandatory
	DESCRIPTION	"The low alarm threshold"
	::= { envNode31Entry 13 }

envNode31InputHighLimit	OBJECT-TYPE
	SYNTAX		INTEGER
	ACCESS		read-write
	STATUS		mandatory
	DESCRIPTION	"The high alarm threshold"
	::= { envNode31Entry 14}

envNode31InputCalib	OBJECT-TYPE
	SYNTAX		INTEGER
	ACCESS		read-write
	STATUS		mandatory
	DESCRIPTION	"Calibration offset"
	::= { envNode31Entry 15 }

envNode31InputRecTime	OBJECT-TYPE
	SYNTAX		INTEGER
	ACCESS		read-write
	STATUS		mandatory
	DESCRIPTION	"Time in seconds for an alarm to be recognized"
	::= { envNode31Entry 16 }

envNode31InputResetTime	OBJECT-TYPE
	SYNTAX		INTEGER
	ACCESS		read-write
	STATUS		mandatory
	DESCRIPTION	"A value &gt;= 30 mins enables feature, 0 disables"
	::= { envNode31Entry 17 }

envNode31InputAlarmOnRTN	OBJECT-TYPE
	SYNTAX		INTEGER { false(1),true(2) }
	ACCESS		read-write
	STATUS		mandatory
	DESCRIPTION	"Allow an alarm to occur when a condition goes back to normal"
	::= { envNode31Entry 18 }

envNode31InputClass	OBJECT-TYPE
	SYNTAX		INTEGER
	ACCESS		read-write
	STATUS		mandatory
	DESCRIPTION	"Alarm class of Input (255 is none)"
	::= { envNode31Entry 19 }

envNode31InputDatalogEnable	OBJECT-TYPE
	SYNTAX		INTEGER { false(1),true(2) }
	ACCESS		read-write
	STATUS		mandatory
	DESCRIPTION	"Datalog Input"
	::= { envNode31Entry 20 }

envNode31InputCustomVoice	OBJECT-TYPE
	SYNTAX		DisplayString
	ACCESS		read-write
	STATUS		mandatory
	DESCRIPTION	"WAV file for the custom voice message"
	::= { envNode31Entry 21 }

envNode31InputAck	OBJECT-TYPE
	SYNTAX		INTEGER { false(1),true(2) }
	ACCESS		read-write
	STATUS		mandatory
	DESCRIPTION	"Ack alarm"
	::= { envNode31Entry 22 }


-- IP tables

ipHostTable	OBJECT-TYPE
	SYNTAX	SEQUENCE OF	IpHostEntry
	ACCESS not-accessible
	STATUS	mandatory
	DESCRIPTION
		"A List of IP entries"
	::= { hostIP	1 }

ipHostEntry	OBJECT-TYPE
	SYNTAX IpHostEntry
	ACCESS not-accessible
	STATUS	mandatory
	DESCRIPTION
		"An IP entry"
	INDEX { ipHostIndex }
	::= { ipHostTable 1 }

IpHostEntry ::=
	SEQUENCE {
		ipHostIndex
			INTEGER,
		ipHostAlarmIPnum
			DisplayString,
		ipHostAlarmPort
			INTEGER,
		ipHostAlarmIPvalid
			INTEGER,
		ipHostAlarmStatus
			INTEGER,
		ipHostAlarmLastResponse
			DisplayString,
		ipHostAlarmDependency
			INTEGER,
		ipHostAlarmRetries
			INTEGER,
		ipHostAlarmTimeout
			INTEGER,
		ipHostAlarmResetTime
			INTEGER,
		ipHostAlarmAlarmOnRTN
			INTEGER,
		ipHostAlarmInUse
			INTEGER,
		ipHostAlarmLastAlarm
			DisplayString,
		ipHostAlarmLastAck
			DisplayString,
		ipHostAlarmName
			DisplayString,
		ipHostAlarmClass
			INTEGER,
		ipHostAlarmEnable
			INTEGER,
		ipHostAlarmDatalog
			INTEGER,
		ipHostAlarmCustomVoice
			DisplayString,
		ipHostAlarmAck
			INTEGER
	}

ipHostIndex					OBJECT-TYPE
	SYNTAX				INTEGER (1..64)
	ACCESS				read-write
	STATUS				mandatory
	DESCRIPTION "The index of the IP (1..64)"
	::= { ipHostEntry 1 }

ipHostAlarmIPnum		OBJECT-TYPE
	SYNTAX				DisplayString
	ACCESS				read-write
	STATUS				mandatory
	DESCRIPTION "The numeric IP address"
	::= { ipHostEntry 2 }

ipHostAlarmPort			OBJECT-TYPE
	SYNTAX				INTEGER
	ACCESS				read-write
	STATUS				mandatory
	DESCRIPTION "The IP port to check for service"
	::= { ipHostEntry 3 }

ipHostAlarmIPvalid		OBJECT-TYPE
	SYNTAX				INTEGER { false(1), true(2) }
	ACCESS				read-only
	STATUS				mandatory
	DESCRIPTION "IP valid"
	::= { ipHostEntry 4 }

ipHostAlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipHostEntry 5 }

ipHostAlarmLastResponse	OBJECT-TYPE
	SYNTAX				DisplayString
	ACCESS				read-only
	STATUS				mandatory
	DESCRIPTION "Last time that this IP device responsed"
	::= { ipHostEntry 6 }

ipHostAlarmDependency		OBJECT-TYPE
	SYNTAX				INTEGER
	ACCESS				read-write
	STATUS				mandatory
	DESCRIPTION "Other IP that this one is dependent upon (255 is none)"
	::= { ipHostEntry 7 }

ipHostAlarmRetries		OBJECT-TYPE
	SYNTAX				INTEGER
	ACCESS				read-write
	STATUS				mandatory
	DESCRIPTION "Number of time to retry this device before failing it"
	::= { ipHostEntry 8 }

ipHostAlarmTimeout		OBJECT-TYPE
	SYNTAX				INTEGER
	ACCESS				read-write
	STATUS				mandatory
	DESCRIPTION "Time in seconds to wait for a response"
	::= { ipHostEntry 9 }

ipHostAlarmResetTime		OBJECT-TYPE
	SYNTAX				INTEGER
	ACCESS				read-write
	STATUS				mandatory
	DESCRIPTION "A value &gt;= 30 mins enables feature, 0 disables"
	::= { ipHostEntry 10 }

ipHostAlarmAlarmOnRTN	OBJECT-TYPE
	SYNTAX		INTEGER {	false(1),true(2) }
	ACCESS				read-write
	STATUS				mandatory
	DESCRIPTION "Allow an alarm to occur when this device starts responding again"
	::= { ipHostEntry 11 }

ipHostAlarmInUse		OBJECT-TYPE
	SYNTAX		INTEGER { false(1),true(2) }
	ACCESS				read-write
	STATUS				mandatory
	DESCRIPTION "True if this IP alarm is active"
	::= { ipHostEntry 12 }

ipHostAlarmLastAlarm		OBJECT-TYPE
	SYNTAX				DisplayString
	ACCESS				read-only
	STATUS				mandatory
	DESCRIPTION "Timestamp of the last alarm"
	::= { ipHostEntry 13 }

ipHostAlarmLastAck		OBJECT-TYPE
	SYNTAX				DisplayString
	ACCESS				read-only
	STATUS				mandatory
	DESCRIPTION "Timestamp of the last alarm Ack"
	::= { ipHostEntry 14 }

ipHostAlarmName			OBJECT-TYPE
	SYNTAX				DisplayString
	ACCESS				read-write
	STATUS				mandatory
	DESCRIPTION "Reference name for this IP device"
	::= { ipHostEntry 15 }

ipHostAlarmClass		OBJECT-TYPE
	SYNTAX				INTEGER
	ACCESS				read-write
	STATUS				mandatory
	DESCRIPTION "The alarm class that is assigned (255 is none)"
	::= { ipHostEntry 16 }

ipHostAlarmEnable		OBJECT-TYPE
	SYNTAX		INTEGER { false(1),true(2) }
	ACCESS				read-only
	STATUS				mandatory
	DESCRIPTION "IP enabled by scheduler"
	::= { ipHostEntry 17 }

ipHostAlarmDatalog		OBJECT-TYPE
	SYNTAX		INTEGER { false(1),true(2) }
	ACCESS				read-write
	STATUS				mandatory
	DESCRIPTION "Datalog IP"
	::= { ipHostEntry 18 }

ipHostAlarmCustomVoice	OBJECT-TYPE
	SYNTAX				DisplayString
	ACCESS				read-write
	STATUS				mandatory
	DESCRIPTION 	"WAV file for the custom voice message"
	::= { ipHostEntry 19 }

ipHostAlarmAck			OBJECT-TYPE
	SYNTAX				INTEGER { false(1),true(2) }
	ACCESS				read-write
	STATUS				mandatory
	DESCRIPTION 	"Ack Alarm"
	::= { ipHostEntry 20 }

ipNode1Table	OBJECT-TYPE
	SYNTAX	SEQUENCE OF	IpNode1Entry
	ACCESS not-accessible
	STATUS	mandatory
	DESCRIPTION
		"A List of IP entries"
	::= { node1IP	1 }

ipNode1Entry	OBJECT-TYPE
	SYNTAX IpNode1Entry
	ACCESS not-accessible
	STATUS	mandatory
	DESCRIPTION
		"An IP entry"
	INDEX { ipNode1Index }
	::= { ipNode1Table 1 }

IpNode1Entry ::=
	SEQUENCE {
		ipNode1Index
			INTEGER,
		ipNode1AlarmIPnum
			DisplayString,
		ipNode1AlarmPort
			INTEGER,
		ipNode1AlarmIPvalid
			INTEGER,
		ipNode1AlarmStatus
			INTEGER,
		ipNode1AlarmLastResponse
			DisplayString,
		ipNode1AlarmDependency
			INTEGER,
		ipNode1AlarmRetries
			INTEGER,
		ipNode1AlarmTimeout
			INTEGER,
		ipNode1AlarmResetTime
			INTEGER,
		ipNode1AlarmAlarmOnRTN
			INTEGER,
		ipNode1AlarmInUse
			INTEGER,
		ipNode1AlarmLastAlarm
			DisplayString,
		ipNode1AlarmLastAck
			DisplayString,
		ipNode1AlarmName
			DisplayString,
		ipNode1AlarmClass
			INTEGER,
		ipNode1AlarmEnable
			INTEGER,
		ipNode1AlarmDatalog
			INTEGER,
		ipNode1AlarmCustomVoice
			DisplayString,
		ipNode1AlarmAck
			INTEGER
	}

ipNode1Index					OBJECT-TYPE
	SYNTAX				INTEGER (1..64)
	ACCESS				read-write
	STATUS				mandatory
	DESCRIPTION "The index of the IP (1..64)"
	::= { ipNode1Entry 1 }

ipNode1AlarmIPnum		OBJECT-TYPE
	SYNTAX				DisplayString
	ACCESS				read-write
	STATUS				mandatory
	DESCRIPTION "The numeric IP address"
	::= { ipNode1Entry 2 }

ipNode1AlarmPort			OBJECT-TYPE
	SYNTAX				INTEGER
	ACCESS				read-write
	STATUS				mandatory
	DESCRIPTION "The IP port to check for service"
	::= { ipNode1Entry 3 }

ipNode1AlarmIPvalid		OBJECT-TYPE
	SYNTAX				INTEGER { false(1), true(2) }
	ACCESS				read-only
	STATUS				mandatory
	DESCRIPTION "IP valid"
	::= { ipNode1Entry 4 }


ipNode1AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode1Entry 5 }

ipNode1AlarmLastResponse	OBJECT-TYPE
	SYNTAX				DisplayString
	ACCESS				read-only
	STATUS				mandatory
	DESCRIPTION "Last time that this IP device responsed"
	::= { ipNode1Entry 6 }

ipNode1AlarmDependency		OBJECT-TYPE
	SYNTAX				INTEGER
	ACCESS				read-write
	STATUS				mandatory
	DESCRIPTION "Other IP that this one is dependent upon (255 is none)"
	::= { ipNode1Entry 7 }

ipNode1AlarmRetries		OBJECT-TYPE
	SYNTAX				INTEGER
	ACCESS				read-write
	STATUS				mandatory
	DESCRIPTION "Number of time to retry this device before failing it"
	::= { ipNode1Entry 8 }

ipNode1AlarmTimeout		OBJECT-TYPE
	SYNTAX				INTEGER
	ACCESS				read-write
	STATUS				mandatory
	DESCRIPTION "Time in seconds to wait for a response"
	::= { ipNode1Entry 9 }

ipNode1AlarmResetTime		OBJECT-TYPE
	SYNTAX				INTEGER
	ACCESS				read-write
	STATUS				mandatory
	DESCRIPTION "A value &gt;= 30 mins enables feature, 0 disables"
	::= { ipNode1Entry 10 }

ipNode1AlarmAlarmOnRTN	OBJECT-TYPE
	SYNTAX		INTEGER {	false(1),true(2) }
	ACCESS				read-write
	STATUS				mandatory
	DESCRIPTION "Allow an alarm to occur when this device starts responding again"
	::= { ipNode1Entry 11 }

ipNode1AlarmInUse		OBJECT-TYPE
	SYNTAX		INTEGER { false(1),true(2) }
	ACCESS				read-write
	STATUS				mandatory
	DESCRIPTION "True if this IP alarm is active"
	::= { ipNode1Entry 12 }

ipNode1AlarmLastAlarm		OBJECT-TYPE
	SYNTAX				DisplayString
	ACCESS				read-only
	STATUS				mandatory
	DESCRIPTION "Timestamp of the last alarm"
	::= { ipNode1Entry 13 }

ipNode1AlarmLastAck		OBJECT-TYPE
	SYNTAX				DisplayString
	ACCESS				read-only
	STATUS				mandatory
	DESCRIPTION "Timestamp of the last alarm Ack"
	::= { ipNode1Entry 14 }

ipNode1AlarmName			OBJECT-TYPE
	SYNTAX				DisplayString
	ACCESS				read-write
	STATUS				mandatory
	DESCRIPTION "Reference name for this IP device"
	::= { ipNode1Entry 15 }

ipNode1AlarmClass		OBJECT-TYPE
	SYNTAX				INTEGER
	ACCESS				read-write
	STATUS				mandatory
	DESCRIPTION "Alarm class of IP (255 is none)"
	::= { ipNode1Entry 16 }

ipNode1AlarmEnable		OBJECT-TYPE
	SYNTAX		INTEGER { false(1),true(2) }
	ACCESS				read-only
	STATUS				mandatory
	DESCRIPTION "IP enabled by the scheduler"
	::= { ipNode1Entry 17 }

ipNode1AlarmDatalog		OBJECT-TYPE
	SYNTAX		INTEGER { false(1),true(2) }
	ACCESS				read-write
	STATUS				mandatory
	DESCRIPTION "Datalog IP"
	::= { ipNode1Entry 18 }

ipNode1AlarmCustomVoice	OBJECT-TYPE
	SYNTAX				DisplayString
	ACCESS				read-write
	STATUS				mandatory
	DESCRIPTION "WAV file for the custom voice message"
	::= { ipNode1Entry 19 }

ipNode1AlarmAck			OBJECT-TYPE
	SYNTAX				INTEGER { false(1),true(2) }
	ACCESS				read-write
	STATUS				mandatory
	DESCRIPTION 	"Ack Alarm"
	::= { ipNode1Entry 20 }

ipNode2Table	OBJECT-TYPE
	SYNTAX	SEQUENCE OF	IpNode2Entry
	ACCESS not-accessible
	STATUS	mandatory
	DESCRIPTION
		"A List of IP entries"
	::= { node2IP	1 }

ipNode2Entry	OBJECT-TYPE
	SYNTAX IpNode2Entry
	ACCESS not-accessible
	STATUS	mandatory
	DESCRIPTION
		"An IP entry"
	INDEX { ipNode2Index }
	::= { ipNode2Table 1 }

IpNode2Entry ::=
	SEQUENCE {
		ipNode2Index
			INTEGER,
		ipNode2AlarmIPnum
			DisplayString,
		ipNode2AlarmPort
			INTEGER,
		ipNode2AlarmIPvalid
			INTEGER,
		ipNode2AlarmStatus
			INTEGER,
		ipNode2AlarmLastResponse
			DisplayString,
		ipNode2AlarmDependency
			INTEGER,
		ipNode2AlarmRetries
			INTEGER,
		ipNode2AlarmTimeout
			INTEGER,
		ipNode2AlarmResetTime
			INTEGER,
		ipNode2AlarmAlarmOnRTN
			INTEGER,
		ipNode2AlarmInUse
			INTEGER,
		ipNode2AlarmLastAlarm
			DisplayString,
		ipNode2AlarmLastAck
			DisplayString,
		ipNode2AlarmName
			DisplayString,
		ipNode2AlarmClass
			INTEGER,
		ipNode2AlarmEnable
			INTEGER,
		ipNode2AlarmDatalog
			INTEGER,
		ipNode2AlarmCustomVoice
			DisplayString,
		ipNode2AlarmAck
			INTEGER
	}

ipNode2Index					OBJECT-TYPE
	SYNTAX				INTEGER (1..64)
	ACCESS				read-write
	STATUS				mandatory
	DESCRIPTION "The index of the IP (1..64)"
	::= { ipNode2Entry 1 }

ipNode2AlarmIPnum		OBJECT-TYPE
	SYNTAX				DisplayString
	ACCESS				read-write
	STATUS				mandatory
	DESCRIPTION "The numeric IP address"
	::= { ipNode2Entry 2 }

ipNode2AlarmPort			OBJECT-TYPE
	SYNTAX				INTEGER
	ACCESS				read-write
	STATUS				mandatory
	DESCRIPTION "The IP port to check for service"
	::= { ipNode2Entry 3 }

ipNode2AlarmIPvalid		OBJECT-TYPE
	SYNTAX				INTEGER { false(1), true(2) }
	ACCESS				read-only
	STATUS				mandatory
	DESCRIPTION		"IP valid"
	::= { ipNode2Entry 4 }

ipNode2AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode2Entry 5 }

ipNode2AlarmLastResponse	OBJECT-TYPE
	SYNTAX				DisplayString
	ACCESS				read-only
	STATUS				mandatory
	DESCRIPTION "Last time that this IP device responsed"
	::= { ipNode2Entry 6 }

ipNode2AlarmDependency		OBJECT-TYPE
	SYNTAX				INTEGER
	ACCESS				read-write
	STATUS				mandatory
	DESCRIPTION "Other IP that this one is dependent upon (255 is none)"
	::= { ipNode2Entry 7 }

ipNode2AlarmRetries		OBJECT-TYPE
	SYNTAX				INTEGER
	ACCESS				read-write
	STATUS				mandatory
	DESCRIPTION "Number of time to retry this device before failing it"
	::= { ipNode2Entry 8 }

ipNode2AlarmTimeout		OBJECT-TYPE
	SYNTAX				INTEGER
	ACCESS				read-write
	STATUS				mandatory
	DESCRIPTION "Time in seconds to wait for a response"
	::= { ipNode2Entry 9 }

ipNode2AlarmResetTime		OBJECT-TYPE
	SYNTAX				INTEGER
	ACCESS				read-write
	STATUS				mandatory
	DESCRIPTION "A value &gt;= 30 mins enables feature, 0 disables"
	::= { ipNode2Entry 10 }

ipNode2AlarmAlarmOnRTN	OBJECT-TYPE
	SYNTAX		INTEGER {	false(1),true(2) }
	ACCESS				read-write
	STATUS				mandatory
	DESCRIPTION "Allow an alarm to occur when this device starts responding again"
	::= { ipNode2Entry 11 }

ipNode2AlarmInUse		OBJECT-TYPE
	SYNTAX		INTEGER { false(1),true(2) }
	ACCESS				read-write
	STATUS				mandatory
	DESCRIPTION "True if this IP alarm is active"
	::= { ipNode2Entry 12 }

ipNode2AlarmLastAlarm		OBJECT-TYPE
	SYNTAX				DisplayString
	ACCESS				read-only
	STATUS				mandatory
	DESCRIPTION "Timestamp of the last alarm"
	::= { ipNode2Entry 13 }

ipNode2AlarmLastAck		OBJECT-TYPE
	SYNTAX				DisplayString
	ACCESS				read-only
	STATUS				mandatory
	DESCRIPTION "Timestamp of the last alarm Ack"
	::= { ipNode2Entry 14 }

ipNode2AlarmName			OBJECT-TYPE
	SYNTAX				DisplayString
	ACCESS				read-write
	STATUS				mandatory
	DESCRIPTION "Reference name for this IP device"
	::= { ipNode2Entry 15 }

ipNode2AlarmClass		OBJECT-TYPE
	SYNTAX				INTEGER
	ACCESS				read-write
	STATUS				mandatory
	DESCRIPTION "Alarm class of IP (255 is none)"
	::= { ipNode2Entry 16 }

ipNode2AlarmEnable		OBJECT-TYPE
	SYNTAX		INTEGER { false(1),true(2) }
	ACCESS				read-only
	STATUS				mandatory
	DESCRIPTION "IP enabled by scheduler"
	::= { ipNode2Entry 17 }

ipNode2AlarmDatalog		OBJECT-TYPE
	SYNTAX		INTEGER { false(1),true(2) }
	ACCESS				read-write
	STATUS				mandatory
	DESCRIPTION "Datalog IP"
	::= { ipNode2Entry 18 }

ipNode2AlarmCustomVoice	OBJECT-TYPE
	SYNTAX				DisplayString
	ACCESS				read-write
	STATUS				mandatory
	DESCRIPTION "WAV file for the custom voice message"
	::= { ipNode2Entry 19 }

ipNode2AlarmAck			OBJECT-TYPE
	SYNTAX				INTEGER { false(1),true(2) }
	ACCESS				read-write
	STATUS				mandatory
	DESCRIPTION 	"Ack Alarm"
	::= { ipNode2Entry 20 }

ipNode3Table	OBJECT-TYPE
	SYNTAX	SEQUENCE OF	IpNode3Entry
	ACCESS not-accessible
	STATUS	mandatory
	DESCRIPTION
		"A List of IP entries"
	::= { node3IP	1 }

ipNode3Entry	OBJECT-TYPE
	SYNTAX IpNode3Entry
	ACCESS not-accessible
	STATUS	mandatory
	DESCRIPTION
		"An IP entry"
	INDEX { ipNode3Index }
	::= { ipNode3Table 1 }

IpNode3Entry ::=
	SEQUENCE {
		ipNode3Index
			INTEGER,
		ipNode3AlarmIPnum
			DisplayString,
		ipNode3AlarmPort
			INTEGER,
		ipNode3AlarmIPvalid
			INTEGER,
		ipNode3AlarmStatus
			INTEGER,
		ipNode3AlarmLastResponse
			DisplayString,
		ipNode3AlarmDependency
			INTEGER,
		ipNode3AlarmRetries
			INTEGER,
		ipNode3AlarmTimeout
			INTEGER,
		ipNode3AlarmResetTime
			INTEGER,
		ipNode3AlarmAlarmOnRTN
			INTEGER,
		ipNode3AlarmInUse
			INTEGER,
		ipNode3AlarmLastAlarm
			DisplayString,
		ipNode3AlarmLastAck
			DisplayString,
		ipNode3AlarmName
			DisplayString,
		ipNode3AlarmClass
			INTEGER,
		ipNode3AlarmEnable
			INTEGER,
		ipNode3AlarmDatalog
			INTEGER,
		ipNode3AlarmCustomVoice
			DisplayString,
		ipNode3AlarmAck
			INTEGER
	}

ipNode3Index					OBJECT-TYPE
	SYNTAX				INTEGER (1..64)
	ACCESS				read-write
	STATUS				mandatory
	DESCRIPTION "The index of the IP (1..64)"
	::= { ipNode3Entry 1 }

ipNode3AlarmIPnum		OBJECT-TYPE
	SYNTAX				DisplayString
	ACCESS				read-write
	STATUS				mandatory
	DESCRIPTION "The numeric IP address"
	::= { ipNode3Entry 2 }

ipNode3AlarmPort			OBJECT-TYPE
	SYNTAX				INTEGER
	ACCESS				read-write
	STATUS				mandatory
	DESCRIPTION "The IP port to check for service"
	::= { ipNode3Entry 3 }

ipNode3AlarmIPvalid		OBJECT-TYPE
	SYNTAX				INTEGER { false(1), true(2) }
	ACCESS				read-only
	STATUS				mandatory
	DESCRIPTION "IP valid"
	::= { ipNode3Entry 4 }

ipNode3AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode3Entry 5 }

ipNode3AlarmLastResponse	OBJECT-TYPE
	SYNTAX				DisplayString
	ACCESS				read-only
	STATUS				mandatory
	DESCRIPTION "Last time that this IP device responsed"
	::= { ipNode3Entry 6 }

ipNode3AlarmDependency		OBJECT-TYPE
	SYNTAX				INTEGER
	ACCESS				read-write
	STATUS				mandatory
	DESCRIPTION "Other IP that this one is dependent upon (255 is none)"
	::= { ipNode3Entry 7 }

ipNode3AlarmRetries		OBJECT-TYPE
	SYNTAX				INTEGER
	ACCESS				read-write
	STATUS				mandatory
	DESCRIPTION "Number of time to retry this device before failing it"
	::= { ipNode3Entry 8 }

ipNode3AlarmTimeout		OBJECT-TYPE
	SYNTAX				INTEGER
	ACCESS				read-write
	STATUS				mandatory
	DESCRIPTION "Time in seconds to wait for a response"
	::= { ipNode3Entry 9 }

ipNode3AlarmResetTime		OBJECT-TYPE
	SYNTAX				INTEGER
	ACCESS				read-write
	STATUS				mandatory
	DESCRIPTION "A value &gt;= 30 mins enables feature, 0 disables"
	::= { ipNode3Entry 10 }

ipNode3AlarmAlarmOnRTN	OBJECT-TYPE
	SYNTAX		INTEGER {	false(1),true(2) }
	ACCESS				read-write
	STATUS				mandatory
	DESCRIPTION "Allow an alarm to occur when this device starts responding again"
	::= { ipNode3Entry 11 }

ipNode3AlarmInUse		OBJECT-TYPE
	SYNTAX		INTEGER { false(1),true(2) }
	ACCESS				read-write
	STATUS				mandatory
	DESCRIPTION "True if this IP alarm is active"
	::= { ipNode3Entry 12 }

ipNode3AlarmLastAlarm		OBJECT-TYPE
	SYNTAX				DisplayString
	ACCESS				read-only
	STATUS				mandatory
	DESCRIPTION "Timestamp of the last alarm"
	::= { ipNode3Entry 13 }

ipNode3AlarmLastAck		OBJECT-TYPE
	SYNTAX				DisplayString
	ACCESS				read-only
	STATUS				mandatory
	DESCRIPTION "Timestamp of the last alarm Ack"
	::= { ipNode3Entry 14 }

ipNode3AlarmName			OBJECT-TYPE
	SYNTAX				DisplayString
	ACCESS				read-write
	STATUS				mandatory
	DESCRIPTION "Reference name for this IP device"
	::= { ipNode3Entry 15 }

ipNode3AlarmClass		OBJECT-TYPE
	SYNTAX				INTEGER
	ACCESS				read-write
	STATUS				mandatory
	DESCRIPTION "Alarm class of IP (255 is none)"
	::= { ipNode3Entry 16 }

ipNode3AlarmEnable		OBJECT-TYPE
	SYNTAX		INTEGER { false(1),true(2) }
	ACCESS				read-only
	STATUS				mandatory
	DESCRIPTION "IP enabled by scheduler"
	::= { ipNode3Entry 17 }

ipNode3AlarmDatalog		OBJECT-TYPE
	SYNTAX		INTEGER { false(1),true(2) }
	ACCESS				read-write
	STATUS				mandatory
	DESCRIPTION "Datalog IP"
	::= { ipNode3Entry 18 }

ipNode3AlarmCustomVoice	OBJECT-TYPE
	SYNTAX				DisplayString
	ACCESS				read-write
	STATUS				mandatory
	DESCRIPTION "WAV file for the custom voice message"
	::= { ipNode3Entry 19 }

ipNode3AlarmAck			OBJECT-TYPE
	SYNTAX				INTEGER { false(1),true(2) }
	ACCESS				read-write
	STATUS				mandatory
	DESCRIPTION 	"Ack Alarm"
	::= { ipNode3Entry 20 }

ipNode4Table	OBJECT-TYPE
	SYNTAX	SEQUENCE OF	IpNode4Entry
	ACCESS not-accessible
	STATUS	mandatory
	DESCRIPTION
		"A List of IP entries"
	::= { node4IP	1 }

ipNode4Entry	OBJECT-TYPE
	SYNTAX IpNode4Entry
	ACCESS not-accessible
	STATUS	mandatory
	DESCRIPTION
		"An IP entry"
	INDEX { ipNode4Index }
	::= { ipNode4Table 1 }

IpNode4Entry ::=
	SEQUENCE {
		ipNode4Index
			INTEGER,
		ipNode4AlarmIPnum
			DisplayString,
		ipNode4AlarmPort
			INTEGER,
		ipNode4AlarmIPvalid
			INTEGER,
		ipNode4AlarmStatus
			INTEGER,
		ipNode4AlarmLastResponse
			DisplayString,
		ipNode4AlarmDependency
			INTEGER,
		ipNode4AlarmRetries
			INTEGER,
		ipNode4AlarmTimeout
			INTEGER,
		ipNode4AlarmResetTime
			INTEGER,
		ipNode4AlarmAlarmOnRTN
			INTEGER,
		ipNode4AlarmInUse
			INTEGER,
		ipNode4AlarmLastAlarm
			DisplayString,
		ipNode4AlarmLastAck
			DisplayString,
		ipNode4AlarmName
			DisplayString,
		ipNode4AlarmClass
			INTEGER,
		ipNode4AlarmEnable
			INTEGER,
		ipNode4AlarmDatalog
			INTEGER,
		ipNode4AlarmCustomVoice
			DisplayString,
		ipNode4AlarmAck
			INTEGER
	}

ipNode4Index					OBJECT-TYPE
	SYNTAX				INTEGER (1..64)
	ACCESS				read-write
	STATUS				mandatory
	DESCRIPTION "The index of the IP (1..64)"
	::= { ipNode4Entry 1 }

ipNode4AlarmIPnum		OBJECT-TYPE
	SYNTAX				DisplayString
	ACCESS				read-write
	STATUS				mandatory
	DESCRIPTION "The numeric IP address"
	::= { ipNode4Entry 2 }

ipNode4AlarmPort			OBJECT-TYPE
	SYNTAX				INTEGER
	ACCESS				read-write
	STATUS				mandatory
	DESCRIPTION "The IP port to check for service"
	::= { ipNode4Entry 3 }

ipNode4AlarmIPvalid		OBJECT-TYPE
	SYNTAX				INTEGER { false(1), true(2) }
	ACCESS				read-only
	STATUS				mandatory
	DESCRIPTION "IP valid"
	::= { ipNode4Entry 4 }

ipNode4AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode4Entry 5 }

ipNode4AlarmLastResponse	OBJECT-TYPE
	SYNTAX				DisplayString
	ACCESS				read-only
	STATUS				mandatory
	DESCRIPTION "Last time that this IP device responsed"
	::= { ipNode4Entry 6 }

ipNode4AlarmDependency		OBJECT-TYPE
	SYNTAX				INTEGER
	ACCESS				read-write
	STATUS				mandatory
	DESCRIPTION "Other IP that this one is dependent upon (255 is none)"
	::= { ipNode4Entry 7 }

ipNode4AlarmRetries		OBJECT-TYPE
	SYNTAX				INTEGER
	ACCESS				read-write
	STATUS				mandatory
	DESCRIPTION "Number of time to retry this device before failing it"
	::= { ipNode4Entry 8 }

ipNode4AlarmTimeout		OBJECT-TYPE
	SYNTAX				INTEGER
	ACCESS				read-write
	STATUS				mandatory
	DESCRIPTION "Time in seconds to wait for a response"
	::= { ipNode4Entry 9 }

ipNode4AlarmResetTime		OBJECT-TYPE
	SYNTAX				INTEGER
	ACCESS				read-write
	STATUS				mandatory
	DESCRIPTION "A value &gt;= 30 mins enables feature, 0 disables"
	::= { ipNode4Entry 10 }

ipNode4AlarmAlarmOnRTN	OBJECT-TYPE
	SYNTAX		INTEGER {	false(1),true(2) }
	ACCESS				read-write
	STATUS				mandatory
	DESCRIPTION "Allow an alarm to occur when this device starts responding again"
	::= { ipNode4Entry 11 }

ipNode4AlarmInUse		OBJECT-TYPE
	SYNTAX		INTEGER { false(1),true(2) }
	ACCESS				read-write
	STATUS				mandatory
	DESCRIPTION "True if this IP alarm is active"
	::= { ipNode4Entry 12 }

ipNode4AlarmLastAlarm		OBJECT-TYPE
	SYNTAX				DisplayString
	ACCESS				read-only
	STATUS				mandatory
	DESCRIPTION "Timestamp of the last alarm"
	::= { ipNode4Entry 13 }

ipNode4AlarmLastAck		OBJECT-TYPE
	SYNTAX				DisplayString
	ACCESS				read-only
	STATUS				mandatory
	DESCRIPTION "Timestamp of the last alarm Ack"
	::= { ipNode4Entry 14 }

ipNode4AlarmName			OBJECT-TYPE
	SYNTAX				DisplayString
	ACCESS				read-write
	STATUS				mandatory
	DESCRIPTION "Reference name for this IP device"
	::= { ipNode4Entry 15 }

ipNode4AlarmClass		OBJECT-TYPE
	SYNTAX				INTEGER
	ACCESS				read-write
	STATUS				mandatory
	DESCRIPTION "Alarm class of IP (255 is none)"
	::= { ipNode4Entry 16 }

ipNode4AlarmEnable		OBJECT-TYPE
	SYNTAX		INTEGER { false(1),true(2) }
	ACCESS				read-only
	STATUS				mandatory
	DESCRIPTION "IP enabled by scheduler"
	::= { ipNode4Entry 17 }

ipNode4AlarmDatalog		OBJECT-TYPE
	SYNTAX		INTEGER { false(1),true(2) }
	ACCESS				read-write
	STATUS				mandatory
	DESCRIPTION "Datalog IP"
	::= { ipNode4Entry 18 }

ipNode4AlarmCustomVoice	OBJECT-TYPE
	SYNTAX				DisplayString
	ACCESS				read-write
	STATUS				mandatory
	DESCRIPTION "WAV file for the custom voice message"
	::= { ipNode4Entry 19 }


ipNode4AlarmAck			OBJECT-TYPE
	SYNTAX				INTEGER { false(1),true(2) }
	ACCESS				read-write
	STATUS				mandatory
	DESCRIPTION 	"Ack Alarm"
	::= { ipNode4Entry 20 }

ipNode5Table	OBJECT-TYPE
	SYNTAX	SEQUENCE OF	IpNode5Entry
	ACCESS not-accessible
	STATUS	mandatory
	DESCRIPTION
		"A List of IP entries"
	::= { node5IP	1 }

ipNode5Entry	OBJECT-TYPE
	SYNTAX IpNode5Entry
	ACCESS not-accessible
	STATUS	mandatory
	DESCRIPTION
		"An IP entry"
	INDEX { ipNode5Index }
	::= { ipNode5Table 1 }

IpNode5Entry ::=
	SEQUENCE {
		ipNode5Index
			INTEGER,
		ipNode5AlarmIPnum
			DisplayString,
		ipNode5AlarmPort
			INTEGER,
		ipNode5AlarmIPvalid
			INTEGER,
		ipNode5AlarmStatus
			INTEGER,
		ipNode5AlarmLastResponse
			DisplayString,
		ipNode5AlarmDependency
			INTEGER,
		ipNode5AlarmRetries
			INTEGER,
		ipNode5AlarmTimeout
			INTEGER,
		ipNode5AlarmResetTime
			INTEGER,
		ipNode5AlarmAlarmOnRTN
			INTEGER,
		ipNode5AlarmInUse
			INTEGER,
		ipNode5AlarmLastAlarm
			DisplayString,
		ipNode5AlarmLastAck
			DisplayString,
		ipNode5AlarmName
			DisplayString,
		ipNode5AlarmClass
			INTEGER,
		ipNode5AlarmEnable
			INTEGER,
		ipNode5AlarmDatalog
			INTEGER,
		ipNode5AlarmCustomVoice
			DisplayString,
		ipNode5AlarmAck
			INTEGER
	}

ipNode5Index					OBJECT-TYPE
	SYNTAX				INTEGER (1..64)
	ACCESS				read-write
	STATUS				mandatory
	DESCRIPTION "The index of the IP (1..64)"
	::= { ipNode5Entry 1 }

ipNode5AlarmIPnum		OBJECT-TYPE
	SYNTAX				DisplayString
	ACCESS				read-write
	STATUS				mandatory
	DESCRIPTION "The numeric IP address"
	::= { ipNode5Entry 2 }

ipNode5AlarmPort			OBJECT-TYPE
	SYNTAX				INTEGER
	ACCESS				read-write
	STATUS				mandatory
	DESCRIPTION "The IP port to check for service"
	::= { ipNode5Entry 3 }

ipNode5AlarmIPvalid		OBJECT-TYPE
	SYNTAX				INTEGER { false(1), true(2) }
	ACCESS				read-only
	STATUS				mandatory
	DESCRIPTION "IP valid"
	::= { ipNode5Entry 4 }

ipNode5AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode5Entry 5 }

ipNode5AlarmLastResponse	OBJECT-TYPE
	SYNTAX				DisplayString
	ACCESS				read-only
	STATUS				mandatory
	DESCRIPTION "Last time that this IP device responsed"
	::= { ipNode5Entry 6 }

ipNode5AlarmDependency		OBJECT-TYPE
	SYNTAX				INTEGER
	ACCESS				read-write
	STATUS				mandatory
	DESCRIPTION "Other IP that this one is dependent upon (255 is none)"
	::= { ipNode5Entry 7 }

ipNode5AlarmRetries		OBJECT-TYPE
	SYNTAX				INTEGER
	ACCESS				read-write
	STATUS				mandatory
	DESCRIPTION "Number of time to retry this device before failing it"
	::= { ipNode5Entry 8 }

ipNode5AlarmTimeout		OBJECT-TYPE
	SYNTAX				INTEGER
	ACCESS				read-write
	STATUS				mandatory
	DESCRIPTION "Time in seconds to wait for a response"
	::= { ipNode5Entry 9 }

ipNode5AlarmResetTime		OBJECT-TYPE
	SYNTAX				INTEGER
	ACCESS				read-write
	STATUS				mandatory
	DESCRIPTION "A value &gt;= 30 mins enables feature, 0 disables"
	::= { ipNode5Entry 10 }

ipNode5AlarmAlarmOnRTN	OBJECT-TYPE
	SYNTAX		INTEGER {	false(1),true(2) }
	ACCESS				read-write
	STATUS				mandatory
	DESCRIPTION "Allow an alarm to occur when this device starts responding again"
	::= { ipNode5Entry 11 }

ipNode5AlarmInUse		OBJECT-TYPE
	SYNTAX		INTEGER { false(1),true(2) }
	ACCESS				read-write
	STATUS				mandatory
	DESCRIPTION "True if this IP alarm is active"
	::= { ipNode5Entry 12 }

ipNode5AlarmLastAlarm		OBJECT-TYPE
	SYNTAX				DisplayString
	ACCESS				read-only
	STATUS				mandatory
	DESCRIPTION "Timestamp of the last alarm"
	::= { ipNode5Entry 13 }

ipNode5AlarmLastAck		OBJECT-TYPE
	SYNTAX				DisplayString
	ACCESS				read-only
	STATUS				mandatory
	DESCRIPTION "Timestamp of the last alarm Ack"
	::= { ipNode5Entry 14 }

ipNode5AlarmName			OBJECT-TYPE
	SYNTAX				DisplayString
	ACCESS				read-write
	STATUS				mandatory
	DESCRIPTION "Reference name for this IP device"
	::= { ipNode5Entry 15 }

ipNode5AlarmClass		OBJECT-TYPE
	SYNTAX				INTEGER
	ACCESS				read-write
	STATUS				mandatory
	DESCRIPTION "Alarm class of IP (255 is none)"
	::= { ipNode5Entry 16 }

ipNode5AlarmEnable		OBJECT-TYPE
	SYNTAX		INTEGER { false(1),true(2) }
	ACCESS				read-only
	STATUS				mandatory
	DESCRIPTION "IP enabled by the scheduler"
	::= { ipNode5Entry 17 }

ipNode5AlarmDatalog		OBJECT-TYPE
	SYNTAX		INTEGER { false(1),true(2) }
	ACCESS				read-write
	STATUS				mandatory
	DESCRIPTION "Datalog IP"
	::= { ipNode5Entry 18 }

ipNode5AlarmCustomVoice	OBJECT-TYPE
	SYNTAX				DisplayString
	ACCESS				read-write
	STATUS				mandatory
	DESCRIPTION "WAV file for the custom voice message"
	::= { ipNode5Entry 19 }

ipNode5AlarmAck			OBJECT-TYPE
	SYNTAX				INTEGER { false(1),true(2) }
	ACCESS				read-write
	STATUS				mandatory
	DESCRIPTION 	"Ack Alarm"
	::= { ipNode5Entry 20 }

ipNode6Table	OBJECT-TYPE
	SYNTAX	SEQUENCE OF	IpNode6Entry
	ACCESS not-accessible
	STATUS	mandatory
	DESCRIPTION
		"A List of IP entries"
	::= { node6IP	1 }

ipNode6Entry	OBJECT-TYPE
	SYNTAX IpNode6Entry
	ACCESS not-accessible
	STATUS	mandatory
	DESCRIPTION
		"An IP entry"
	INDEX { ipNode6Index }
	::= { ipNode6Table 1 }

IpNode6Entry ::=
	SEQUENCE {
		ipNode6Index
			INTEGER,
		ipNode6AlarmIPnum
			DisplayString,
		ipNode6AlarmPort
			INTEGER,
		ipNode6AlarmIPvalid
			INTEGER,
		ipNode6AlarmStatus
			INTEGER,
		ipNode6AlarmLastResponse
			DisplayString,
		ipNode6AlarmDependency
			INTEGER,
		ipNode6AlarmRetries
			INTEGER,
		ipNode6AlarmTimeout
			INTEGER,
		ipNode6AlarmResetTime
			INTEGER,
		ipNode6AlarmAlarmOnRTN
			INTEGER,
		ipNode6AlarmInUse
			INTEGER,
		ipNode6AlarmLastAlarm
			DisplayString,
		ipNode6AlarmLastAck
			DisplayString,
		ipNode6AlarmName
			DisplayString,
		ipNode6AlarmClass
			INTEGER,
		ipNode6AlarmEnable
			INTEGER,
		ipNode6AlarmDatalog
			INTEGER,
		ipNode6AlarmCustomVoice
			DisplayString,
		ipNode6AlarmAck
			INTEGER
	}

ipNode6Index					OBJECT-TYPE
	SYNTAX				INTEGER (1..64)
	ACCESS				read-write
	STATUS				mandatory
	DESCRIPTION "The index of the IP (1..64)"
	::= { ipNode6Entry 1 }

ipNode6AlarmIPnum		OBJECT-TYPE
	SYNTAX				DisplayString
	ACCESS				read-write
	STATUS				mandatory
	DESCRIPTION "The numeric IP address"
	::= { ipNode6Entry 2 }

ipNode6AlarmPort			OBJECT-TYPE
	SYNTAX				INTEGER
	ACCESS				read-write
	STATUS				mandatory
	DESCRIPTION "The IP port to check for service"
	::= { ipNode6Entry 3 }

ipNode6AlarmIPvalid		OBJECT-TYPE
	SYNTAX				INTEGER { false(1), true(2) }
	ACCESS				read-only
	STATUS				mandatory
	DESCRIPTION "IP valid"
	::= { ipNode6Entry 4 }

ipNode6AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode6Entry 5 }

ipNode6AlarmLastResponse	OBJECT-TYPE
	SYNTAX				DisplayString
	ACCESS				read-only
	STATUS				mandatory
	DESCRIPTION "Last time that this IP device responsed"
	::= { ipNode6Entry 6 }

ipNode6AlarmDependency		OBJECT-TYPE
	SYNTAX				INTEGER
	ACCESS				read-write
	STATUS				mandatory
	DESCRIPTION "Other IP that this one is dependent upon (255 is none)"
	::= { ipNode6Entry 7 }

ipNode6AlarmRetries		OBJECT-TYPE
	SYNTAX				INTEGER
	ACCESS				read-write
	STATUS				mandatory
	DESCRIPTION "Number of time to retry this device before failing it"
	::= { ipNode6Entry 8 }

ipNode6AlarmTimeout		OBJECT-TYPE
	SYNTAX				INTEGER
	ACCESS				read-write
	STATUS				mandatory
	DESCRIPTION "Time in seconds to wait for a response"
	::= { ipNode6Entry 9 }

ipNode6AlarmResetTime		OBJECT-TYPE
	SYNTAX				INTEGER
	ACCESS				read-write
	STATUS				mandatory
	DESCRIPTION "A value &gt;= 30 mins enables feature, 0 disables"
	::= { ipNode6Entry 10 }

ipNode6AlarmAlarmOnRTN	OBJECT-TYPE
	SYNTAX		INTEGER {	false(1),true(2) }
	ACCESS				read-write
	STATUS				mandatory
	DESCRIPTION "Allow an alarm to occur when this device starts responding again"
	::= { ipNode6Entry 11 }

ipNode6AlarmInUse		OBJECT-TYPE
	SYNTAX		INTEGER { false(1),true(2) }
	ACCESS				read-write
	STATUS				mandatory
	DESCRIPTION "True if this IP alarm is active"
	::= { ipNode6Entry 12 }

ipNode6AlarmLastAlarm		OBJECT-TYPE
	SYNTAX				DisplayString
	ACCESS				read-only
	STATUS				mandatory
	DESCRIPTION "Timestamp of the last alarm"
	::= { ipNode6Entry 13 }

ipNode6AlarmLastAck		OBJECT-TYPE
	SYNTAX				DisplayString
	ACCESS				read-only
	STATUS				mandatory
	DESCRIPTION "Timestamp of the last alarm Ack"
	::= { ipNode6Entry 14 }

ipNode6AlarmName			OBJECT-TYPE
	SYNTAX				DisplayString
	ACCESS				read-write
	STATUS				mandatory
	DESCRIPTION "Reference name for this IP device"
	::= { ipNode6Entry 15 }

ipNode6AlarmClass		OBJECT-TYPE
	SYNTAX				INTEGER
	ACCESS				read-write
	STATUS				mandatory
	DESCRIPTION "Alarm class of IP (255 is none)"
	::= { ipNode6Entry 16 }

ipNode6AlarmEnable		OBJECT-TYPE
	SYNTAX		INTEGER { false(1),true(2) }
	ACCESS				read-only
	STATUS				mandatory
	DESCRIPTION "IP enabled by scheduler"
	::= { ipNode6Entry 17 }

ipNode6AlarmDatalog		OBJECT-TYPE
	SYNTAX		INTEGER { false(1),true(2) }
	ACCESS				read-write
	STATUS				mandatory
	DESCRIPTION "Datalog IP"
	::= { ipNode6Entry 18 }

ipNode6AlarmCustomVoice	OBJECT-TYPE
	SYNTAX				DisplayString
	ACCESS				read-write
	STATUS				mandatory
	DESCRIPTION "WAV file for the custom voice message"
	::= { ipNode6Entry 19 }

ipNode6AlarmAck			OBJECT-TYPE
	SYNTAX				INTEGER { false(1),true(2) }
	ACCESS				read-write
	STATUS				mandatory
	DESCRIPTION 	"Ack Alarm"
	::= { ipNode6Entry 20 }

ipNode7Table	OBJECT-TYPE
	SYNTAX	SEQUENCE OF	IpNode7Entry
	ACCESS not-accessible
	STATUS	mandatory
	DESCRIPTION
		"A List of IP entries"
	::= { node7IP	1 }

ipNode7Entry	OBJECT-TYPE
	SYNTAX IpNode7Entry
	ACCESS not-accessible
	STATUS	mandatory
	DESCRIPTION
		"An IP entry"
	INDEX { ipNode7Index }
	::= { ipNode7Table 1 }

IpNode7Entry ::=
	SEQUENCE {
		ipNode7Index
			INTEGER,
		ipNode7AlarmIPnum
			DisplayString,
		ipNode7AlarmPort
			INTEGER,
		ipNode7AlarmIPvalid
			INTEGER,
		ipNode7AlarmStatus
			INTEGER,
		ipNode7AlarmLastResponse
			DisplayString,
		ipNode7AlarmDependency
			INTEGER,
		ipNode7AlarmRetries
			INTEGER,
		ipNode7AlarmTimeout
			INTEGER,
		ipNode7AlarmResetTime
			INTEGER,
		ipNode7AlarmAlarmOnRTN
			INTEGER,
		ipNode7AlarmInUse
			INTEGER,
		ipNode7AlarmLastAlarm
			DisplayString,
		ipNode7AlarmLastAck
			DisplayString,
		ipNode7AlarmName
			DisplayString,
		ipNode7AlarmClass
			INTEGER,
		ipNode7AlarmEnable
			INTEGER,
		ipNode7AlarmDatalog
			INTEGER,
		ipNode7AlarmCustomVoice
			DisplayString,
		ipNode7AlarmAck
			INTEGER
	}

ipNode7Index					OBJECT-TYPE
	SYNTAX				INTEGER (1..64)
	ACCESS				read-write
	STATUS				mandatory
	DESCRIPTION "The index of the IP (1..64)"
	::= { ipNode7Entry 1 }

ipNode7AlarmIPnum		OBJECT-TYPE
	SYNTAX				DisplayString
	ACCESS				read-write
	STATUS				mandatory
	DESCRIPTION "The numeric IP address"
	::= { ipNode7Entry 2 }

ipNode7AlarmPort			OBJECT-TYPE
	SYNTAX				INTEGER
	ACCESS				read-write
	STATUS				mandatory
	DESCRIPTION "The IP port to check for service"
	::= { ipNode7Entry 3 }

ipNode7AlarmIPvalid		OBJECT-TYPE
	SYNTAX				INTEGER { false(1), true(2) }
	ACCESS				read-only
	STATUS				mandatory
	DESCRIPTION "IP valid"
	::= { ipNode7Entry 4 }

ipNode7AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode7Entry 5 }

ipNode7AlarmLastResponse	OBJECT-TYPE
	SYNTAX				DisplayString
	ACCESS				read-only
	STATUS				mandatory
	DESCRIPTION "Last time that this IP device responsed"
	::= { ipNode7Entry 6 }

ipNode7AlarmDependency		OBJECT-TYPE
	SYNTAX				INTEGER
	ACCESS				read-write
	STATUS				mandatory
	DESCRIPTION "Other IP that this one is dependent upon (255 is none)"
	::= { ipNode7Entry 7 }

ipNode7AlarmRetries		OBJECT-TYPE
	SYNTAX				INTEGER
	ACCESS				read-write
	STATUS				mandatory
	DESCRIPTION "Number of time to retry this device before failing it"
	::= { ipNode7Entry 8 }

ipNode7AlarmTimeout		OBJECT-TYPE
	SYNTAX				INTEGER
	ACCESS				read-write
	STATUS				mandatory
	DESCRIPTION "Time in seconds to wait for a response"
	::= { ipNode7Entry 9 }

ipNode7AlarmResetTime		OBJECT-TYPE
	SYNTAX				INTEGER
	ACCESS				read-write
	STATUS				mandatory
	DESCRIPTION "A value &gt;= 30 mins enables feature, 0 disables"
	::= { ipNode7Entry 10 }

ipNode7AlarmAlarmOnRTN	OBJECT-TYPE
	SYNTAX		INTEGER {	false(1),true(2) }
	ACCESS				read-write
	STATUS				mandatory
	DESCRIPTION "Allow an alarm to occur when this device starts responding again"
	::= { ipNode7Entry 11 }

ipNode7AlarmInUse		OBJECT-TYPE
	SYNTAX		INTEGER { false(1),true(2) }
	ACCESS				read-write
	STATUS				mandatory
	DESCRIPTION "True if this IP alarm is active"
	::= { ipNode7Entry 12 }

ipNode7AlarmLastAlarm		OBJECT-TYPE
	SYNTAX				DisplayString
	ACCESS				read-only
	STATUS				mandatory
	DESCRIPTION "Timestamp of the last alarm"
	::= { ipNode7Entry 13 }

ipNode7AlarmLastAck		OBJECT-TYPE
	SYNTAX				DisplayString
	ACCESS				read-only
	STATUS				mandatory
	DESCRIPTION "Timestamp of the last alarm Ack"
	::= { ipNode7Entry 14 }

ipNode7AlarmName			OBJECT-TYPE
	SYNTAX				DisplayString
	ACCESS				read-write
	STATUS				mandatory
	DESCRIPTION "Reference name for this IP device"
	::= { ipNode7Entry 15 }

ipNode7AlarmClass		OBJECT-TYPE
	SYNTAX				INTEGER
	ACCESS				read-write
	STATUS				mandatory
	DESCRIPTION "Alarm class of IP (255 is none)"
	::= { ipNode7Entry 16 }

ipNode7AlarmEnable		OBJECT-TYPE
	SYNTAX		INTEGER { false(1),true(2) }
	ACCESS				read-only
	STATUS				mandatory
	DESCRIPTION "IP enabled by scheduler"
	::= { ipNode7Entry 17 }

ipNode7AlarmDatalog		OBJECT-TYPE
	SYNTAX		INTEGER { false(1),true(2) }
	ACCESS				read-write
	STATUS				mandatory
	DESCRIPTION "Datalog IP"
	::= { ipNode7Entry 18 }

ipNode7AlarmCustomVoice	OBJECT-TYPE
	SYNTAX				DisplayString
	ACCESS				read-write
	STATUS				mandatory
	DESCRIPTION "WAV file for the custom voice message"
	::= { ipNode7Entry 19 }

ipNode7AlarmAck			OBJECT-TYPE
	SYNTAX				INTEGER { false(1),true(2) }
	ACCESS				read-write
	STATUS				mandatory
	DESCRIPTION 	"Ack Alarm"
	::= { ipNode7Entry 20 }

ipNode8Table	OBJECT-TYPE
	SYNTAX	SEQUENCE OF	IpNode8Entry
	ACCESS not-accessible
	STATUS	mandatory
	DESCRIPTION
		"A List of IP entries"
	::= { node8IP	1 }

ipNode8Entry	OBJECT-TYPE
	SYNTAX IpNode8Entry
	ACCESS not-accessible
	STATUS	mandatory
	DESCRIPTION
		"An IP entry"
	INDEX { ipNode8Index }
	::= { ipNode8Table 1 }

IpNode8Entry ::=
	SEQUENCE {
		ipNode8Index
			INTEGER,
		ipNode8AlarmIPnum
			DisplayString,
		ipNode8AlarmPort
			INTEGER,
		ipNode8AlarmIPvalid
			INTEGER,
		ipNode8AlarmStatus
			INTEGER,
		ipNode8AlarmLastResponse
			DisplayString,
		ipNode8AlarmDependency
			INTEGER,
		ipNode8AlarmRetries
			INTEGER,
		ipNode8AlarmTimeout
			INTEGER,
		ipNode8AlarmResetTime
			INTEGER,
		ipNode8AlarmAlarmOnRTN
			INTEGER,
		ipNode8AlarmInUse
			INTEGER,
		ipNode8AlarmLastAlarm
			DisplayString,
		ipNode8AlarmLastAck
			DisplayString,
		ipNode8AlarmName
			DisplayString,
		ipNode8AlarmClass
			INTEGER,
		ipNode8AlarmEnable
			INTEGER,
		ipNode8AlarmDatalog
			INTEGER,
		ipNode8AlarmCustomVoice
			DisplayString,
		ipNode8AlarmAck
			INTEGER
	}

ipNode8Index					OBJECT-TYPE
	SYNTAX				INTEGER (1..64)
	ACCESS				read-write
	STATUS				mandatory
	DESCRIPTION "The index of the IP (1..64)"
	::= { ipNode8Entry 1 }

ipNode8AlarmIPnum		OBJECT-TYPE
	SYNTAX				DisplayString
	ACCESS				read-write
	STATUS				mandatory
	DESCRIPTION "The numeric IP address"
	::= { ipNode8Entry 2 }

ipNode8AlarmPort			OBJECT-TYPE
	SYNTAX				INTEGER
	ACCESS				read-write
	STATUS				mandatory
	DESCRIPTION "The IP port to check for service"
	::= { ipNode8Entry 3 }

ipNode8AlarmIPvalid		OBJECT-TYPE
	SYNTAX				INTEGER { false(1), true(2) }
	ACCESS				read-only
	STATUS				mandatory
	DESCRIPTION "IP valid"
	::= { ipNode8Entry 4 }

ipNode8AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode8Entry 5 }

ipNode8AlarmLastResponse	OBJECT-TYPE
	SYNTAX				DisplayString
	ACCESS				read-only
	STATUS				mandatory
	DESCRIPTION "Last time that this IP device responsed"
	::= { ipNode8Entry 6 }

ipNode8AlarmDependency		OBJECT-TYPE
	SYNTAX				INTEGER
	ACCESS				read-write
	STATUS				mandatory
	DESCRIPTION "Other IP that this one is dependent upon (255 is none)"
	::= { ipNode8Entry 7 }

ipNode8AlarmRetries		OBJECT-TYPE
	SYNTAX				INTEGER
	ACCESS				read-write
	STATUS				mandatory
	DESCRIPTION "Number of time to retry this device before failing it"
	::= { ipNode8Entry 8 }

ipNode8AlarmTimeout		OBJECT-TYPE
	SYNTAX				INTEGER
	ACCESS				read-write
	STATUS				mandatory
	DESCRIPTION "Time in seconds to wait for a response"
	::= { ipNode8Entry 9 }

ipNode8AlarmResetTime		OBJECT-TYPE
	SYNTAX				INTEGER
	ACCESS				read-write
	STATUS				mandatory
	DESCRIPTION "A value &gt;= 30 mins enables feature, 0 disables"
	::= { ipNode8Entry 10 }

ipNode8AlarmAlarmOnRTN	OBJECT-TYPE
	SYNTAX		INTEGER {	false(1),true(2) }
	ACCESS				read-write
	STATUS				mandatory
	DESCRIPTION "Allow an alarm to occur when this device starts responding again"
	::= { ipNode8Entry 11 }

ipNode8AlarmInUse		OBJECT-TYPE
	SYNTAX		INTEGER { false(1),true(2) }
	ACCESS				read-write
	STATUS				mandatory
	DESCRIPTION "True if this IP alarm is active"
	::= { ipNode8Entry 12 }

ipNode8AlarmLastAlarm		OBJECT-TYPE
	SYNTAX				DisplayString
	ACCESS				read-only
	STATUS				mandatory
	DESCRIPTION "Timestamp of the last alarm"
	::= { ipNode8Entry 13 }

ipNode8AlarmLastAck		OBJECT-TYPE
	SYNTAX				DisplayString
	ACCESS				read-only
	STATUS				mandatory
	DESCRIPTION "Timestamp of the last alarm Ack"
	::= { ipNode8Entry 14 }

ipNode8AlarmName			OBJECT-TYPE
	SYNTAX				DisplayString
	ACCESS				read-write
	STATUS				mandatory
	DESCRIPTION "Reference name for this IP device"
	::= { ipNode8Entry 15 }

ipNode8AlarmClass		OBJECT-TYPE
	SYNTAX				INTEGER
	ACCESS				read-write
	STATUS				mandatory
	DESCRIPTION "Alarm class of IP (255 is none)"
	::= { ipNode8Entry 16 }

ipNode8AlarmEnable		OBJECT-TYPE
	SYNTAX		INTEGER { false(1),true(2) }
	ACCESS				read-only
	STATUS				mandatory
	DESCRIPTION "IP enabled by scheduler"
	::= { ipNode8Entry 17 }

ipNode8AlarmDatalog		OBJECT-TYPE
	SYNTAX		INTEGER { false(1),true(2) }
	ACCESS				read-write
	STATUS				mandatory
	DESCRIPTION "Datalog IP"
	::= { ipNode8Entry 18 }

ipNode8AlarmCustomVoice	OBJECT-TYPE
	SYNTAX				DisplayString
	ACCESS				read-write
	STATUS				mandatory
	DESCRIPTION "WAV file for the custom voice message"
	::= { ipNode8Entry 19 }

ipNode8AlarmAck			OBJECT-TYPE
	SYNTAX				INTEGER { false(1),true(2) }
	ACCESS				read-write
	STATUS				mandatory
	DESCRIPTION 	"Ack Alarm"
	::= { ipNode8Entry 20 }

ipNode9Table	OBJECT-TYPE
	SYNTAX	SEQUENCE OF	IpNode9Entry
	ACCESS not-accessible
	STATUS	mandatory
	DESCRIPTION
		"A List of IP entries"
	::= { node9IP	1 }

ipNode9Entry	OBJECT-TYPE
	SYNTAX IpNode9Entry
	ACCESS not-accessible
	STATUS	mandatory
	DESCRIPTION
		"An IP entry"
	INDEX { ipNode9Index }
	::= { ipNode9Table 1 }

IpNode9Entry ::=
	SEQUENCE {
		ipNode9Index
			INTEGER,
		ipNode9AlarmIPnum
			DisplayString,
		ipNode9AlarmPort
			INTEGER,
		ipNode9AlarmIPvalid
			INTEGER,
		ipNode9AlarmStatus
			INTEGER,
		ipNode9AlarmLastResponse
			DisplayString,
		ipNode9AlarmDependency
			INTEGER,
		ipNode9AlarmRetries
			INTEGER,
		ipNode9AlarmTimeout
			INTEGER,
		ipNode9AlarmResetTime
			INTEGER,
		ipNode9AlarmAlarmOnRTN
			INTEGER,
		ipNode9AlarmInUse
			INTEGER,
		ipNode9AlarmLastAlarm
			DisplayString,
		ipNode9AlarmLastAck
			DisplayString,
		ipNode9AlarmName
			DisplayString,
		ipNode9AlarmClass
			INTEGER,
		ipNode9AlarmEnable
			INTEGER,
		ipNode9AlarmDatalog
			INTEGER,
		ipNode9AlarmCustomVoice
			DisplayString,
		ipNode9AlarmAck
			INTEGER
	}

ipNode9Index					OBJECT-TYPE
	SYNTAX				INTEGER (1..64)
	ACCESS				read-write
	STATUS				mandatory
	DESCRIPTION "The index of the IP (1..64)"
	::= { ipNode9Entry 1 }

ipNode9AlarmIPnum		OBJECT-TYPE
	SYNTAX				DisplayString
	ACCESS				read-write
	STATUS				mandatory
	DESCRIPTION "The numeric IP address"
	::= { ipNode9Entry 2 }

ipNode9AlarmPort			OBJECT-TYPE
	SYNTAX				INTEGER
	ACCESS				read-write
	STATUS				mandatory
	DESCRIPTION "The IP port to check for service"
	::= { ipNode9Entry 3 }

ipNode9AlarmIPvalid		OBJECT-TYPE
	SYNTAX				INTEGER { false(1), true(2) }
	ACCESS				read-only
	STATUS				mandatory
	DESCRIPTION "IP valid"
	::= { ipNode9Entry 4 }

ipNode9AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode9Entry 5 }

ipNode9AlarmLastResponse	OBJECT-TYPE
	SYNTAX				DisplayString
	ACCESS				read-only
	STATUS				mandatory
	DESCRIPTION "Last time that this IP device responsed"
	::= { ipNode9Entry 6 }

ipNode9AlarmDependency		OBJECT-TYPE
	SYNTAX				INTEGER
	ACCESS				read-write
	STATUS				mandatory
	DESCRIPTION "Other IP that this one is dependent upon (255 is none)"
	::= { ipNode9Entry 7 }

ipNode9AlarmRetries		OBJECT-TYPE
	SYNTAX				INTEGER
	ACCESS				read-write
	STATUS				mandatory
	DESCRIPTION "Number of time to retry this device before failing it"
	::= { ipNode9Entry 8 }

ipNode9AlarmTimeout		OBJECT-TYPE
	SYNTAX				INTEGER
	ACCESS				read-write
	STATUS				mandatory
	DESCRIPTION "Time in seconds to wait for a response"
	::= { ipNode9Entry 9 }

ipNode9AlarmResetTime		OBJECT-TYPE
	SYNTAX				INTEGER
	ACCESS				read-write
	STATUS				mandatory
	DESCRIPTION "A value &gt;= 30 mins enables feature, 0 disables"
	::= { ipNode9Entry 10 }

ipNode9AlarmAlarmOnRTN	OBJECT-TYPE
	SYNTAX		INTEGER {	false(1),true(2) }
	ACCESS				read-write
	STATUS				mandatory
	DESCRIPTION "Allow an alarm to occur when this device starts responding again"
	::= { ipNode9Entry 11 }

ipNode9AlarmInUse		OBJECT-TYPE
	SYNTAX		INTEGER { false(1),true(2) }
	ACCESS				read-write
	STATUS				mandatory
	DESCRIPTION "True if this IP alarm is active"
	::= { ipNode9Entry 12 }

ipNode9AlarmLastAlarm		OBJECT-TYPE
	SYNTAX				DisplayString
	ACCESS				read-only
	STATUS				mandatory
	DESCRIPTION "Timestamp of the last alarm"
	::= { ipNode9Entry 13 }

ipNode9AlarmLastAck		OBJECT-TYPE
	SYNTAX				DisplayString
	ACCESS				read-only
	STATUS				mandatory
	DESCRIPTION "Timestamp of the last alarm Ack"
	::= { ipNode9Entry 14 }

ipNode9AlarmName			OBJECT-TYPE
	SYNTAX				DisplayString
	ACCESS				read-write
	STATUS				mandatory
	DESCRIPTION "Reference name for this IP device"
	::= { ipNode9Entry 15 }

ipNode9AlarmClass		OBJECT-TYPE
	SYNTAX				INTEGER
	ACCESS				read-write
	STATUS				mandatory
	DESCRIPTION "Alarm class of IP (255 is none)"
	::= { ipNode9Entry 16 }

ipNode9AlarmEnable		OBJECT-TYPE
	SYNTAX		INTEGER { false(1),true(2) }
	ACCESS				read-only
	STATUS				mandatory
	DESCRIPTION "IP enabled by scheduler"
	::= { ipNode9Entry 17 }

ipNode9AlarmDatalog		OBJECT-TYPE
	SYNTAX		INTEGER { false(1),true(2) }
	ACCESS				read-write
	STATUS				mandatory
	DESCRIPTION "Datalog IP"
	::= { ipNode9Entry 18 }

ipNode9AlarmCustomVoice	OBJECT-TYPE
	SYNTAX				DisplayString
	ACCESS				read-write
	STATUS				mandatory
	DESCRIPTION "WAV file for the custom voice message"
	::= { ipNode9Entry 19 }

ipNode9AlarmAck		OBJECT-TYPE
	SYNTAX				INTEGER { false(1),true(2) }
	ACCESS				read-write
	STATUS				mandatory
	DESCRIPTION 	"Ack Alarm"
	::= { ipNode9Entry 20 }

ipNode10Table	OBJECT-TYPE
	SYNTAX	SEQUENCE OF	IpNode10Entry
	ACCESS not-accessible
	STATUS	mandatory
	DESCRIPTION
		"A List of IP entries"
	::= { node10IP	1 }

ipNode10Entry	OBJECT-TYPE
	SYNTAX IpNode10Entry
	ACCESS not-accessible
	STATUS	mandatory
	DESCRIPTION
		"An IP entry"
	INDEX { ipNode10Index }
	::= { ipNode10Table 1 }

IpNode10Entry ::=
	SEQUENCE {
		ipNode10Index
			INTEGER,
		ipNode10AlarmIPnum
			DisplayString,
		ipNode10AlarmPort
			INTEGER,
		ipNode10AlarmIPvalid
			INTEGER,
		ipNode10AlarmStatus
			INTEGER,
		ipNode10AlarmLastResponse
			DisplayString,
		ipNode10AlarmDependency
			INTEGER,
		ipNode10AlarmRetries
			INTEGER,
		ipNode10AlarmTimeout
			INTEGER,
		ipNode10AlarmResetTime
			INTEGER,
		ipNode10AlarmAlarmOnRTN
			INTEGER,
		ipNode10AlarmInUse
			INTEGER,
		ipNode10AlarmLastAlarm
			DisplayString,
		ipNode10AlarmLastAck
			DisplayString,
		ipNode10AlarmName
			DisplayString,
		ipNode10AlarmClass
			INTEGER,
		ipNode10AlarmEnable
			INTEGER,
		ipNode10AlarmDatalog
			INTEGER,
		ipNode10AlarmCustomVoice
			DisplayString,
		ipNode10AlarmAck
			INTEGER
	}

ipNode10Index					OBJECT-TYPE
	SYNTAX				INTEGER (1..64)
	ACCESS				read-write
	STATUS				mandatory
	DESCRIPTION "The index of the IP (1..64)"
	::= { ipNode10Entry 1 }

ipNode10AlarmIPnum		OBJECT-TYPE
	SYNTAX				DisplayString
	ACCESS				read-write
	STATUS				mandatory
	DESCRIPTION "The numeric IP address"
	::= { ipNode10Entry 2 }

ipNode10AlarmPort			OBJECT-TYPE
	SYNTAX				INTEGER
	ACCESS				read-write
	STATUS				mandatory
	DESCRIPTION "The IP port to check for service"
	::= { ipNode10Entry 3 }

ipNode10AlarmIPvalid		OBJECT-TYPE
	SYNTAX				INTEGER { false(1), true(2) }
	ACCESS				read-only
	STATUS				mandatory
	DESCRIPTION "IP valid"
	::= { ipNode10Entry 4 }

ipNode10AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode10Entry 5 }

ipNode10AlarmLastResponse	OBJECT-TYPE
	SYNTAX				DisplayString
	ACCESS				read-only
	STATUS				mandatory
	DESCRIPTION "Last time that this IP device responsed"
	::= { ipNode10Entry 6 }

ipNode10AlarmDependency		OBJECT-TYPE
	SYNTAX				INTEGER
	ACCESS				read-write
	STATUS				mandatory
	DESCRIPTION "Other IP that this one is dependent upon (255 is none)"
	::= { ipNode10Entry 7 }

ipNode10AlarmRetries		OBJECT-TYPE
	SYNTAX				INTEGER
	ACCESS				read-write
	STATUS				mandatory
	DESCRIPTION "Number of time to retry this device before failing it"
	::= { ipNode10Entry 8 }

ipNode10AlarmTimeout		OBJECT-TYPE
	SYNTAX				INTEGER
	ACCESS				read-write
	STATUS				mandatory
	DESCRIPTION "Time in seconds to wait for a response"
	::= { ipNode10Entry 9 }

ipNode10AlarmResetTime		OBJECT-TYPE
	SYNTAX				INTEGER
	ACCESS				read-write
	STATUS				mandatory
	DESCRIPTION "A value &gt;= 30 mins enables feature, 0 disables"
	::= { ipNode10Entry 10 }

ipNode10AlarmAlarmOnRTN	OBJECT-TYPE
	SYNTAX		INTEGER {	false(1),true(2) }
	ACCESS				read-write
	STATUS				mandatory
	DESCRIPTION "Allow an alarm to occur when this device starts responding again"
	::= { ipNode10Entry 11 }

ipNode10AlarmInUse		OBJECT-TYPE
	SYNTAX		INTEGER { false(1),true(2) }
	ACCESS				read-write
	STATUS				mandatory
	DESCRIPTION "True if this IP alarm is active"
	::= { ipNode10Entry 12 }

ipNode10AlarmLastAlarm		OBJECT-TYPE
	SYNTAX				DisplayString
	ACCESS				read-only
	STATUS				mandatory
	DESCRIPTION "Timestamp of the last alarm"
	::= { ipNode10Entry 13 }

ipNode10AlarmLastAck		OBJECT-TYPE
	SYNTAX				DisplayString
	ACCESS				read-only
	STATUS				mandatory
	DESCRIPTION "Timestamp of the last alarm Ack"
	::= { ipNode10Entry 14 }

ipNode10AlarmName			OBJECT-TYPE
	SYNTAX				DisplayString
	ACCESS				read-write
	STATUS				mandatory
	DESCRIPTION "Reference name for this IP device"
	::= { ipNode10Entry 15 }

ipNode10AlarmClass		OBJECT-TYPE
	SYNTAX				INTEGER
	ACCESS				read-write
	STATUS				mandatory
	DESCRIPTION "Alarm class of IP (255 is none)"
	::= { ipNode10Entry 16 }

ipNode10AlarmEnable		OBJECT-TYPE
	SYNTAX		INTEGER { false(1),true(2) }
	ACCESS				read-only
	STATUS				mandatory
	DESCRIPTION "IP enabled by scheduler"
	::= { ipNode10Entry 17 }

ipNode10AlarmDatalog		OBJECT-TYPE
	SYNTAX		INTEGER { false(1),true(2) }
	ACCESS				read-write
	STATUS				mandatory
	DESCRIPTION "Datalog IP"
	::= { ipNode10Entry 18 }

ipNode10AlarmCustomVoice	OBJECT-TYPE
	SYNTAX				DisplayString
	ACCESS				read-write
	STATUS				mandatory
	DESCRIPTION "WAV file for the custom voice message"
	::= { ipNode10Entry 19 }

ipNode10AlarmAck		OBJECT-TYPE
	SYNTAX				INTEGER { false(1),true(2) }
	ACCESS				read-write
	STATUS				mandatory
	DESCRIPTION 	"Ack Alarm"
	::= { ipNode10Entry 20 }

ipNode11Table	OBJECT-TYPE
	SYNTAX	SEQUENCE OF	IpNode11Entry
	ACCESS not-accessible
	STATUS	mandatory
	DESCRIPTION
		"A List of IP entries"
	::= { node11IP	1 }

ipNode11Entry	OBJECT-TYPE
	SYNTAX IpNode11Entry
	ACCESS not-accessible
	STATUS	mandatory
	DESCRIPTION
		"An IP entry"
	INDEX { ipNode11Index }
	::= { ipNode11Table 1 }

IpNode11Entry ::=
	SEQUENCE {
		ipNode11Index
			INTEGER,
		ipNode11AlarmIPnum
			DisplayString,
		ipNode11AlarmPort
			INTEGER,
		ipNode11AlarmIPvalid
			INTEGER,
		ipNode11AlarmStatus
			INTEGER,
		ipNode11AlarmLastResponse
			DisplayString,
		ipNode11AlarmDependency
			INTEGER,
		ipNode11AlarmRetries
			INTEGER,
		ipNode11AlarmTimeout
			INTEGER,
		ipNode11AlarmResetTime
			INTEGER,
		ipNode11AlarmAlarmOnRTN
			INTEGER,
		ipNode11AlarmInUse
			INTEGER,
		ipNode11AlarmLastAlarm
			DisplayString,
		ipNode11AlarmLastAck
			DisplayString,
		ipNode11AlarmName
			DisplayString,
		ipNode11AlarmClass
			INTEGER,
		ipNode11AlarmEnable
			INTEGER,
		ipNode11AlarmDatalog
			INTEGER,
		ipNode11AlarmCustomVoice
			DisplayString,
		ipNode11AlarmAck
			INTEGER
	}

ipNode11Index					OBJECT-TYPE
	SYNTAX				INTEGER (1..64)
	ACCESS				read-write
	STATUS				mandatory
	DESCRIPTION "The index of the IP (1..64)"
	::= { ipNode11Entry 1 }

ipNode11AlarmIPnum		OBJECT-TYPE
	SYNTAX				DisplayString
	ACCESS				read-write
	STATUS				mandatory
	DESCRIPTION "The numeric IP address"
	::= { ipNode11Entry 2 }

ipNode11AlarmPort			OBJECT-TYPE
	SYNTAX				INTEGER
	ACCESS				read-write
	STATUS				mandatory
	DESCRIPTION "The IP port to check for service"
	::= { ipNode11Entry 3 }

ipNode11AlarmIPvalid		OBJECT-TYPE
	SYNTAX				INTEGER { false(1), true(2) }
	ACCESS				read-only
	STATUS				mandatory
	DESCRIPTION "IP valid"
	::= { ipNode11Entry 4 }

ipNode11AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode11Entry 5 }

ipNode11AlarmLastResponse	OBJECT-TYPE
	SYNTAX				DisplayString
	ACCESS				read-only
	STATUS				mandatory
	DESCRIPTION "Last time that this IP device responsed"
	::= { ipNode11Entry 6 }

ipNode11AlarmDependency		OBJECT-TYPE
	SYNTAX				INTEGER
	ACCESS				read-write
	STATUS				mandatory
	DESCRIPTION "Other IP that this one is dependent upon (255 is none)"
	::= { ipNode11Entry 7 }

ipNode11AlarmRetries		OBJECT-TYPE
	SYNTAX				INTEGER
	ACCESS				read-write
	STATUS				mandatory
	DESCRIPTION "Number of time to retry this device before failing it"
	::= { ipNode11Entry 8 }

ipNode11AlarmTimeout		OBJECT-TYPE
	SYNTAX				INTEGER
	ACCESS				read-write
	STATUS				mandatory
	DESCRIPTION "Time in seconds to wait for a response"
	::= { ipNode11Entry 9 }

ipNode11AlarmResetTime		OBJECT-TYPE
	SYNTAX				INTEGER
	ACCESS				read-write
	STATUS				mandatory
	DESCRIPTION "A value &gt;= 30 mins enables feature, 0 disables"
	::= { ipNode11Entry 10 }

ipNode11AlarmAlarmOnRTN	OBJECT-TYPE
	SYNTAX		INTEGER {	false(1),true(2) }
	ACCESS				read-write
	STATUS				mandatory
	DESCRIPTION "Allow an alarm to occur when this device starts responding again"
	::= { ipNode11Entry 11 }

ipNode11AlarmInUse		OBJECT-TYPE
	SYNTAX		INTEGER { false(1),true(2) }
	ACCESS				read-write
	STATUS				mandatory
	DESCRIPTION "True if this IP alarm is active"
	::= { ipNode11Entry 12 }

ipNode11AlarmLastAlarm		OBJECT-TYPE
	SYNTAX				DisplayString
	ACCESS				read-only
	STATUS				mandatory
	DESCRIPTION "Timestamp of the last alarm"
	::= { ipNode11Entry 13 }

ipNode11AlarmLastAck		OBJECT-TYPE
	SYNTAX				DisplayString
	ACCESS				read-only
	STATUS				mandatory
	DESCRIPTION "Timestamp of the last alarm Ack"
	::= { ipNode11Entry 14 }

ipNode11AlarmName			OBJECT-TYPE
	SYNTAX				DisplayString
	ACCESS				read-write
	STATUS				mandatory
	DESCRIPTION "Reference name for this IP device"
	::= { ipNode11Entry 15 }

ipNode11AlarmClass		OBJECT-TYPE
	SYNTAX				INTEGER
	ACCESS				read-write
	STATUS				mandatory
	DESCRIPTION "Alarm class of IP (255 is none)"
	::= { ipNode11Entry 16 }

ipNode11AlarmEnable		OBJECT-TYPE
	SYNTAX		INTEGER { false(1),true(2) }
	ACCESS				read-only
	STATUS				mandatory
	DESCRIPTION "IP enabled by scheduler"
	::= { ipNode11Entry 17 }

ipNode11AlarmDatalog		OBJECT-TYPE
	SYNTAX		INTEGER { false(1),true(2) }
	ACCESS				read-write
	STATUS				mandatory
	DESCRIPTION "Datalog IP"
	::= { ipNode11Entry 18 }

ipNode11AlarmCustomVoice	OBJECT-TYPE
	SYNTAX				DisplayString
	ACCESS				read-write
	STATUS				mandatory
	DESCRIPTION "WAV file for the custom voice message"
	::= { ipNode11Entry 19 }

ipNode11AlarmAck		OBJECT-TYPE
	SYNTAX				INTEGER { false(1),true(2) }
	ACCESS				read-write
	STATUS				mandatory
	DESCRIPTION 	"Ack Alarm"
	::= { ipNode11Entry 20 }

ipNode12Table	OBJECT-TYPE
	SYNTAX	SEQUENCE OF	IpNode12Entry
	ACCESS not-accessible
	STATUS	mandatory
	DESCRIPTION
		"A List of IP entries"
	::= { node12IP	1 }

ipNode12Entry	OBJECT-TYPE
	SYNTAX IpNode12Entry
	ACCESS not-accessible
	STATUS	mandatory
	DESCRIPTION
		"An IP entry"
	INDEX { ipNode12Index }
	::= { ipNode12Table 1 }

IpNode12Entry ::=
	SEQUENCE {
		ipNode12Index
			INTEGER,
		ipNode12AlarmIPnum
			DisplayString,
		ipNode12AlarmPort
			INTEGER,
		ipNode12AlarmIPvalid
			INTEGER,
		ipNode12AlarmStatus
			INTEGER,
		ipNode12AlarmLastResponse
			DisplayString,
		ipNode12AlarmDependency
			INTEGER,
		ipNode12AlarmRetries
			INTEGER,
		ipNode12AlarmTimeout
			INTEGER,
		ipNode12AlarmResetTime
			INTEGER,
		ipNode12AlarmAlarmOnRTN
			INTEGER,
		ipNode12AlarmInUse
			INTEGER,
		ipNode12AlarmLastAlarm
			DisplayString,
		ipNode12AlarmLastAck
			DisplayString,
		ipNode12AlarmName
			DisplayString,
		ipNode12AlarmClass
			INTEGER,
		ipNode12AlarmEnable
			INTEGER,
		ipNode12AlarmDatalog
			INTEGER,
		ipNode12AlarmCustomVoice
			DisplayString,
		ipNode12AlarmAck
			INTEGER
	}

ipNode12Index					OBJECT-TYPE
	SYNTAX				INTEGER (1..64)
	ACCESS				read-write
	STATUS				mandatory
	DESCRIPTION "The index of the IP (1..64)"
	::= { ipNode12Entry 1 }

ipNode12AlarmIPnum		OBJECT-TYPE
	SYNTAX				DisplayString
	ACCESS				read-write
	STATUS				mandatory
	DESCRIPTION "The numeric IP address"
	::= { ipNode12Entry 2 }

ipNode12AlarmPort			OBJECT-TYPE
	SYNTAX				INTEGER
	ACCESS				read-write
	STATUS				mandatory
	DESCRIPTION "The IP port to check for service"
	::= { ipNode12Entry 3 }

ipNode12AlarmIPvalid		OBJECT-TYPE
	SYNTAX				INTEGER { false(1), true(2) }
	ACCESS				read-only
	STATUS				mandatory
	DESCRIPTION "IP valid"
	::= { ipNode12Entry 4 }

ipNode12AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode12Entry 5 }

ipNode12AlarmLastResponse	OBJECT-TYPE
	SYNTAX				DisplayString
	ACCESS				read-only
	STATUS				mandatory
	DESCRIPTION "Last time that this IP device responsed"
	::= { ipNode12Entry 6 }

ipNode12AlarmDependency		OBJECT-TYPE
	SYNTAX				INTEGER
	ACCESS				read-write
	STATUS				mandatory
	DESCRIPTION "Other IP that this one is dependent upon (255 is none)"
	::= { ipNode12Entry 7 }

ipNode12AlarmRetries		OBJECT-TYPE
	SYNTAX				INTEGER
	ACCESS				read-write
	STATUS				mandatory
	DESCRIPTION "Number of time to retry this device before failing it"
	::= { ipNode12Entry 8 }

ipNode12AlarmTimeout		OBJECT-TYPE
	SYNTAX				INTEGER
	ACCESS				read-write
	STATUS				mandatory
	DESCRIPTION "Time in seconds to wait for a response"
	::= { ipNode12Entry 9 }

ipNode12AlarmResetTime		OBJECT-TYPE
	SYNTAX				INTEGER
	ACCESS				read-write
	STATUS				mandatory
	DESCRIPTION "A value &gt;= 30 mins enables feature, 0 disables"
	::= { ipNode12Entry 10 }

ipNode12AlarmAlarmOnRTN	OBJECT-TYPE
	SYNTAX		INTEGER {	false(1),true(2) }
	ACCESS				read-write
	STATUS				mandatory
	DESCRIPTION "Allow an alarm to occur when this device starts responding again"
	::= { ipNode12Entry 11 }

ipNode12AlarmInUse		OBJECT-TYPE
	SYNTAX		INTEGER { false(1),true(2) }
	ACCESS				read-write
	STATUS				mandatory
	DESCRIPTION "True if this IP alarm is active"
	::= { ipNode12Entry 12 }

ipNode12AlarmLastAlarm		OBJECT-TYPE
	SYNTAX				DisplayString
	ACCESS				read-only
	STATUS				mandatory
	DESCRIPTION "Timestamp of the last alarm"
	::= { ipNode12Entry 13 }

ipNode12AlarmLastAck		OBJECT-TYPE
	SYNTAX				DisplayString
	ACCESS				read-only
	STATUS				mandatory
	DESCRIPTION "Timestamp of the last alarm Ack"
	::= { ipNode12Entry 14 }

ipNode12AlarmName			OBJECT-TYPE
	SYNTAX				DisplayString
	ACCESS				read-write
	STATUS				mandatory
	DESCRIPTION "Reference name for this IP device"
	::= { ipNode12Entry 15 }

ipNode12AlarmClass		OBJECT-TYPE
	SYNTAX				INTEGER
	ACCESS				read-write
	STATUS				mandatory
	DESCRIPTION "Alarm class of IP (255 is none)"
	::= { ipNode12Entry 16 }

ipNode12AlarmEnable		OBJECT-TYPE
	SYNTAX		INTEGER { false(1),true(2) }
	ACCESS				read-only
	STATUS				mandatory
	DESCRIPTION "IP enabled by scheduler"
	::= { ipNode12Entry 17 }

ipNode12AlarmDatalog		OBJECT-TYPE
	SYNTAX		INTEGER { false(1),true(2) }
	ACCESS				read-write
	STATUS				mandatory
	DESCRIPTION "Datalog IP"
	::= { ipNode12Entry 18 }

ipNode12AlarmCustomVoice	OBJECT-TYPE
	SYNTAX				DisplayString
	ACCESS				read-write
	STATUS				mandatory
	DESCRIPTION "WAV file for the custom voice message"
	::= { ipNode12Entry 19 }

ipNode12AlarmAck		OBJECT-TYPE
	SYNTAX				INTEGER { false(1),true(2) }
	ACCESS				read-write
	STATUS				mandatory
	DESCRIPTION 	"Ack Alarm"
	::= { ipNode12Entry 20 }

ipNode13Table	OBJECT-TYPE
	SYNTAX	SEQUENCE OF	IpNode13Entry
	ACCESS not-accessible
	STATUS	mandatory
	DESCRIPTION
		"A List of IP entries"
	::= { node13IP	1 }

ipNode13Entry	OBJECT-TYPE
	SYNTAX IpNode13Entry
	ACCESS not-accessible
	STATUS	mandatory
	DESCRIPTION
		"An IP entry"
	INDEX { ipNode13Index }
	::= { ipNode13Table 1 }

IpNode13Entry ::=
	SEQUENCE {
		ipNode13Index
			INTEGER,
		ipNode13AlarmIPnum
			DisplayString,
		ipNode13AlarmPort
			INTEGER,
		ipNode13AlarmIPvalid
			INTEGER,
		ipNode13AlarmStatus
			INTEGER,
		ipNode13AlarmLastResponse
			DisplayString,
		ipNode13AlarmDependency
			INTEGER,
		ipNode13AlarmRetries
			INTEGER,
		ipNode13AlarmTimeout
			INTEGER,
		ipNode13AlarmResetTime
			INTEGER,
		ipNode13AlarmAlarmOnRTN
			INTEGER,
		ipNode13AlarmInUse
			INTEGER,
		ipNode13AlarmLastAlarm
			DisplayString,
		ipNode13AlarmLastAck
			DisplayString,
		ipNode13AlarmName
			DisplayString,
		ipNode13AlarmClass
			INTEGER,
		ipNode13AlarmEnable
			INTEGER,
		ipNode13AlarmDatalog
			INTEGER,
		ipNode13AlarmCustomVoice
			DisplayString,
		ipNode13AlarmAck
			INTEGER
	}

ipNode13Index					OBJECT-TYPE
	SYNTAX				INTEGER (1..64)
	ACCESS				read-write
	STATUS				mandatory
	DESCRIPTION "The index of the IP (1..64)"
	::= { ipNode13Entry 1 }

ipNode13AlarmIPnum		OBJECT-TYPE
	SYNTAX				DisplayString
	ACCESS				read-write
	STATUS				mandatory
	DESCRIPTION "The numeric IP address"
	::= { ipNode13Entry 2 }

ipNode13AlarmPort			OBJECT-TYPE
	SYNTAX				INTEGER
	ACCESS				read-write
	STATUS				mandatory
	DESCRIPTION "The IP port to check for service"
	::= { ipNode13Entry 3 }

ipNode13AlarmIPvalid		OBJECT-TYPE
	SYNTAX				INTEGER { false(1), true(2) }
	ACCESS				read-only
	STATUS				mandatory
	DESCRIPTION "IP valid"
	::= { ipNode13Entry 4 }

ipNode13AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode13Entry 5 }

ipNode13AlarmLastResponse	OBJECT-TYPE
	SYNTAX				DisplayString
	ACCESS				read-only
	STATUS				mandatory
	DESCRIPTION "Last time that this IP device responsed"
	::= { ipNode13Entry 6 }

ipNode13AlarmDependency		OBJECT-TYPE
	SYNTAX				INTEGER
	ACCESS				read-write
	STATUS				mandatory
	DESCRIPTION "Other IP that this one is dependent upon (255 is none)"
	::= { ipNode13Entry 7 }

ipNode13AlarmRetries		OBJECT-TYPE
	SYNTAX				INTEGER
	ACCESS				read-write
	STATUS				mandatory
	DESCRIPTION "Number of time to retry this device before failing it"
	::= { ipNode13Entry 8 }

ipNode13AlarmTimeout		OBJECT-TYPE
	SYNTAX				INTEGER
	ACCESS				read-write
	STATUS				mandatory
	DESCRIPTION "Time in seconds to wait for a response"
	::= { ipNode13Entry 9 }

ipNode13AlarmResetTime		OBJECT-TYPE
	SYNTAX				INTEGER
	ACCESS				read-write
	STATUS				mandatory
	DESCRIPTION "A value &gt;= 30 mins enables feature, 0 disables"
	::= { ipNode13Entry 10 }

ipNode13AlarmAlarmOnRTN	OBJECT-TYPE
	SYNTAX		INTEGER {	false(1),true(2) }
	ACCESS				read-write
	STATUS				mandatory
	DESCRIPTION "Allow an alarm to occur when this device starts responding again"
	::= { ipNode13Entry 11 }

ipNode13AlarmInUse		OBJECT-TYPE
	SYNTAX		INTEGER { false(1),true(2) }
	ACCESS				read-write
	STATUS				mandatory
	DESCRIPTION "True if this IP alarm is active"
	::= { ipNode13Entry 12 }

ipNode13AlarmLastAlarm		OBJECT-TYPE
	SYNTAX				DisplayString
	ACCESS				read-only
	STATUS				mandatory
	DESCRIPTION "Timestamp of the last alarm"
	::= { ipNode13Entry 13 }

ipNode13AlarmLastAck		OBJECT-TYPE
	SYNTAX				DisplayString
	ACCESS				read-only
	STATUS				mandatory
	DESCRIPTION "Timestamp of the last alarm Ack"
	::= { ipNode13Entry 14 }

ipNode13AlarmName			OBJECT-TYPE
	SYNTAX				DisplayString
	ACCESS				read-write
	STATUS				mandatory
	DESCRIPTION "Reference name for this IP device"
	::= { ipNode13Entry 15 }

ipNode13AlarmClass		OBJECT-TYPE
	SYNTAX				INTEGER
	ACCESS				read-write
	STATUS				mandatory
	DESCRIPTION "Alarm class of IP (255 is none)"
	::= { ipNode13Entry 16 }

ipNode13AlarmEnable		OBJECT-TYPE
	SYNTAX		INTEGER { false(1),true(2) }
	ACCESS				read-only
	STATUS				mandatory
	DESCRIPTION "IP enabled by scheduler"
	::= { ipNode13Entry 17 }

ipNode13AlarmDatalog		OBJECT-TYPE
	SYNTAX		INTEGER { false(1),true(2) }
	ACCESS				read-write
	STATUS				mandatory
	DESCRIPTION "Datalog IP"
	::= { ipNode13Entry 18 }

ipNode13AlarmCustomVoice	OBJECT-TYPE
	SYNTAX				DisplayString
	ACCESS				read-write
	STATUS				mandatory
	DESCRIPTION "WAV file for the custom voice message"
	::= { ipNode13Entry 19 }

ipNode13AlarmAck		OBJECT-TYPE
	SYNTAX				INTEGER { false(1),true(2) }
	ACCESS				read-write
	STATUS				mandatory
	DESCRIPTION 	"Ack Alarm"
	::= { ipNode13Entry 20 }

ipNode14Table	OBJECT-TYPE
	SYNTAX	SEQUENCE OF	IpNode14Entry
	ACCESS not-accessible
	STATUS	mandatory
	DESCRIPTION
		"A List of IP entries"
	::= { node14IP	1 }

ipNode14Entry	OBJECT-TYPE
	SYNTAX IpNode14Entry
	ACCESS not-accessible
	STATUS	mandatory
	DESCRIPTION
		"An IP entry"
	INDEX { ipNode14Index }
	::= { ipNode14Table 1 }

IpNode14Entry ::=
	SEQUENCE {
		ipNode14Index
			INTEGER,
		ipNode14AlarmIPnum
			DisplayString,
		ipNode14AlarmPort
			INTEGER,
		ipNode14AlarmIPvalid
			INTEGER,
		ipNode14AlarmStatus
			INTEGER,
		ipNode14AlarmLastResponse
			DisplayString,
		ipNode14AlarmDependency
			INTEGER,
		ipNode14AlarmRetries
			INTEGER,
		ipNode14AlarmTimeout
			INTEGER,
		ipNode14AlarmResetTime
			INTEGER,
		ipNode14AlarmAlarmOnRTN
			INTEGER,
		ipNode14AlarmInUse
			INTEGER,
		ipNode14AlarmLastAlarm
			DisplayString,
		ipNode14AlarmLastAck
			DisplayString,
		ipNode14AlarmName
			DisplayString,
		ipNode14AlarmClass
			INTEGER,
		ipNode14AlarmEnable
			INTEGER,
		ipNode14AlarmDatalog
			INTEGER,
		ipNode14AlarmCustomVoice
			DisplayString,
		ipNode14AlarmAck
			INTEGER
	}

ipNode14Index					OBJECT-TYPE
	SYNTAX				INTEGER (1..64)
	ACCESS				read-write
	STATUS				mandatory
	DESCRIPTION "The index of the IP (1..64)"
	::= { ipNode14Entry 1 }

ipNode14AlarmIPnum		OBJECT-TYPE
	SYNTAX				DisplayString
	ACCESS				read-write
	STATUS				mandatory
	DESCRIPTION "The numeric IP address"
	::= { ipNode14Entry 2 }

ipNode14AlarmPort			OBJECT-TYPE
	SYNTAX				INTEGER
	ACCESS				read-write
	STATUS				mandatory
	DESCRIPTION "The IP port to check for service"
	::= { ipNode14Entry 3 }

ipNode14AlarmIPvalid		OBJECT-TYPE
	SYNTAX				INTEGER { false(1), true(2) }
	ACCESS				read-only
	STATUS				mandatory
	DESCRIPTION "IP valid"
	::= { ipNode14Entry 4 }

ipNode14AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode14Entry 5 }

ipNode14AlarmLastResponse	OBJECT-TYPE
	SYNTAX				DisplayString
	ACCESS				read-only
	STATUS				mandatory
	DESCRIPTION "Last time that this IP device responsed"
	::= { ipNode14Entry 6 }

ipNode14AlarmDependency		OBJECT-TYPE
	SYNTAX				INTEGER
	ACCESS				read-write
	STATUS				mandatory
	DESCRIPTION "Other IP that this one is dependent upon (255 is none)"
	::= { ipNode14Entry 7 }

ipNode14AlarmRetries		OBJECT-TYPE
	SYNTAX				INTEGER
	ACCESS				read-write
	STATUS				mandatory
	DESCRIPTION "Number of time to retry this device before failing it"
	::= { ipNode14Entry 8 }

ipNode14AlarmTimeout		OBJECT-TYPE
	SYNTAX				INTEGER
	ACCESS				read-write
	STATUS				mandatory
	DESCRIPTION "Time in seconds to wait for a response"
	::= { ipNode14Entry 9 }

ipNode14AlarmResetTime		OBJECT-TYPE
	SYNTAX				INTEGER
	ACCESS				read-write
	STATUS				mandatory
	DESCRIPTION "A value &gt;= 30 mins enables feature, 0 disables"
	::= { ipNode14Entry 10 }

ipNode14AlarmAlarmOnRTN	OBJECT-TYPE
	SYNTAX		INTEGER {	false(1),true(2) }
	ACCESS				read-write
	STATUS				mandatory
	DESCRIPTION "Allow an alarm to occur when this device starts responding again"
	::= { ipNode14Entry 11 }

ipNode14AlarmInUse		OBJECT-TYPE
	SYNTAX		INTEGER { false(1),true(2) }
	ACCESS				read-write
	STATUS				mandatory
	DESCRIPTION "True if this IP alarm is active"
	::= { ipNode14Entry 12 }

ipNode14AlarmLastAlarm		OBJECT-TYPE
	SYNTAX				DisplayString
	ACCESS				read-only
	STATUS				mandatory
	DESCRIPTION "Timestamp of the last alarm"
	::= { ipNode14Entry 13 }

ipNode14AlarmLastAck		OBJECT-TYPE
	SYNTAX				DisplayString
	ACCESS				read-only
	STATUS				mandatory
	DESCRIPTION "Timestamp of the last alarm Ack"
	::= { ipNode14Entry 14 }

ipNode14AlarmName			OBJECT-TYPE
	SYNTAX				DisplayString
	ACCESS				read-write
	STATUS				mandatory
	DESCRIPTION "Reference name for this IP device"
	::= { ipNode14Entry 15 }

ipNode14AlarmClass		OBJECT-TYPE
	SYNTAX				INTEGER
	ACCESS				read-write
	STATUS				mandatory
	DESCRIPTION "Alarm class of IP (255 is none)"
	::= { ipNode14Entry 16 }

ipNode14AlarmEnable		OBJECT-TYPE
	SYNTAX		INTEGER { false(1),true(2) }
	ACCESS				read-only
	STATUS				mandatory
	DESCRIPTION "IP enabled by scheduler"
	::= { ipNode14Entry 17 }

ipNode14AlarmDatalog		OBJECT-TYPE
	SYNTAX		INTEGER { false(1),true(2) }
	ACCESS				read-write
	STATUS				mandatory
	DESCRIPTION "Datalog IP"
	::= { ipNode14Entry 18 }

ipNode14AlarmCustomVoice	OBJECT-TYPE
	SYNTAX				DisplayString
	ACCESS				read-write
	STATUS				mandatory
	DESCRIPTION "WAV file for the custom voice message"
	::= { ipNode14Entry 19 }

ipNode14AlarmAck		OBJECT-TYPE
	SYNTAX				INTEGER { false(1),true(2) }
	ACCESS				read-write
	STATUS				mandatory
	DESCRIPTION 	"Ack Alarm"
	::= { ipNode14Entry 20 }

ipNode15Table	OBJECT-TYPE
	SYNTAX	SEQUENCE OF	IpNode15Entry
	ACCESS not-accessible
	STATUS	mandatory
	DESCRIPTION
		"A List of IP entries"
	::= { node15IP	1 }

ipNode15Entry	OBJECT-TYPE
	SYNTAX IpNode15Entry
	ACCESS not-accessible
	STATUS	mandatory
	DESCRIPTION
		"An IP entry"
	INDEX { ipNode15Index }
	::= { ipNode15Table 1 }

IpNode15Entry ::=
	SEQUENCE {
		ipNode15Index
			INTEGER,
		ipNode15AlarmIPnum
			DisplayString,
		ipNode15AlarmPort
			INTEGER,
		ipNode15AlarmIPvalid
			INTEGER,
		ipNode15AlarmStatus
			INTEGER,
		ipNode15AlarmLastResponse
			DisplayString,
		ipNode15AlarmDependency
			INTEGER,
		ipNode15AlarmRetries
			INTEGER,
		ipNode15AlarmTimeout
			INTEGER,
		ipNode15AlarmResetTime
			INTEGER,
		ipNode15AlarmAlarmOnRTN
			INTEGER,
		ipNode15AlarmInUse
			INTEGER,
		ipNode15AlarmLastAlarm
			DisplayString,
		ipNode15AlarmLastAck
			DisplayString,
		ipNode15AlarmName
			DisplayString,
		ipNode15AlarmClass
			INTEGER,
		ipNode15AlarmEnable
			INTEGER,
		ipNode15AlarmDatalog
			INTEGER,
		ipNode15AlarmCustomVoice
			DisplayString,
		ipNode15AlarmAck
			INTEGER
	}

ipNode15Index					OBJECT-TYPE
	SYNTAX				INTEGER (1..64)
	ACCESS				read-write
	STATUS				mandatory
	DESCRIPTION "The index of the IP (1..64)"
	::= { ipNode15Entry 1 }

ipNode15AlarmIPnum		OBJECT-TYPE
	SYNTAX				DisplayString
	ACCESS				read-write
	STATUS				mandatory
	DESCRIPTION "The numeric IP address"
	::= { ipNode15Entry 2 }

ipNode15AlarmPort			OBJECT-TYPE
	SYNTAX				INTEGER
	ACCESS				read-write
	STATUS				mandatory
	DESCRIPTION "The IP port to check for service"
	::= { ipNode15Entry 3 }

ipNode15AlarmIPvalid		OBJECT-TYPE
	SYNTAX				INTEGER { false(1), true(2) }
	ACCESS				read-only
	STATUS				mandatory
	DESCRIPTION "IP valid"
	::= { ipNode15Entry 4 }

ipNode15AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode15Entry 5 }

ipNode15AlarmLastResponse	OBJECT-TYPE
	SYNTAX				DisplayString
	ACCESS				read-only
	STATUS				mandatory
	DESCRIPTION "Last time that this IP device responsed"
	::= { ipNode15Entry 6 }

ipNode15AlarmDependency		OBJECT-TYPE
	SYNTAX				INTEGER
	ACCESS				read-write
	STATUS				mandatory
	DESCRIPTION "Other IP that this one is dependent upon (255 is none)"
	::= { ipNode15Entry 7 }

ipNode15AlarmRetries		OBJECT-TYPE
	SYNTAX				INTEGER
	ACCESS				read-write
	STATUS				mandatory
	DESCRIPTION "Number of time to retry this device before failing it"
	::= { ipNode15Entry 8 }

ipNode15AlarmTimeout		OBJECT-TYPE
	SYNTAX				INTEGER
	ACCESS				read-write
	STATUS				mandatory
	DESCRIPTION "Time in seconds to wait for a response"
	::= { ipNode15Entry 9 }

ipNode15AlarmResetTime		OBJECT-TYPE
	SYNTAX				INTEGER
	ACCESS				read-write
	STATUS				mandatory
	DESCRIPTION "A value &gt;= 30 mins enables feature, 0 disables"
	::= { ipNode15Entry 10 }

ipNode15AlarmAlarmOnRTN	OBJECT-TYPE
	SYNTAX		INTEGER {	false(1),true(2) }
	ACCESS				read-write
	STATUS				mandatory
	DESCRIPTION "Allow an alarm to occur when this device starts responding again"
	::= { ipNode15Entry 11 }

ipNode15AlarmInUse		OBJECT-TYPE
	SYNTAX		INTEGER { false(1),true(2) }
	ACCESS				read-write
	STATUS				mandatory
	DESCRIPTION "True if this IP alarm is active"
	::= { ipNode15Entry 12 }

ipNode15AlarmLastAlarm		OBJECT-TYPE
	SYNTAX				DisplayString
	ACCESS				read-only
	STATUS				mandatory
	DESCRIPTION "Timestamp of the last alarm"
	::= { ipNode15Entry 13 }

ipNode15AlarmLastAck		OBJECT-TYPE
	SYNTAX				DisplayString
	ACCESS				read-only
	STATUS				mandatory
	DESCRIPTION "Timestamp of the last alarm Ack"
	::= { ipNode15Entry 14 }

ipNode15AlarmName			OBJECT-TYPE
	SYNTAX				DisplayString
	ACCESS				read-write
	STATUS				mandatory
	DESCRIPTION "Reference name for this IP device"
	::= { ipNode15Entry 15 }

ipNode15AlarmClass		OBJECT-TYPE
	SYNTAX				INTEGER
	ACCESS				read-write
	STATUS				mandatory
	DESCRIPTION "Alarm class of IP (255 is none)"
	::= { ipNode15Entry 16 }

ipNode15AlarmEnable		OBJECT-TYPE
	SYNTAX		INTEGER { false(1),true(2) }
	ACCESS				read-only
	STATUS				mandatory
	DESCRIPTION "IP enabled by scheduler"
	::= { ipNode15Entry 17 }

ipNode15AlarmDatalog		OBJECT-TYPE
	SYNTAX		INTEGER { false(1),true(2) }
	ACCESS				read-write
	STATUS				mandatory
	DESCRIPTION "Datalog IP"
	::= { ipNode15Entry 18 }

ipNode15AlarmCustomVoice	OBJECT-TYPE
	SYNTAX				DisplayString
	ACCESS				read-write
	STATUS				mandatory
	DESCRIPTION "WAV file for the custom voice message"
	::= { ipNode15Entry 19 }

ipNode15AlarmAck		OBJECT-TYPE
	SYNTAX				INTEGER { false(1),true(2) }
	ACCESS				read-write
	STATUS				mandatory
	DESCRIPTION 	"Ack Alarm"
	::= { ipNode15Entry 20 }

ipNode16Table	OBJECT-TYPE
	SYNTAX	SEQUENCE OF	IpNode16Entry
	ACCESS not-accessible
	STATUS	mandatory
	DESCRIPTION
		"A List of IP entries"
	::= { node16IP	1 }

ipNode16Entry	OBJECT-TYPE
	SYNTAX IpNode16Entry
	ACCESS not-accessible
	STATUS	mandatory
	DESCRIPTION
		"An IP entry"
	INDEX { ipNode16Index }
	::= { ipNode16Table 1 }

IpNode16Entry ::=
	SEQUENCE {
		ipNode16Index
			INTEGER,
		ipNode16AlarmIPnum
			DisplayString,
		ipNode16AlarmPort
			INTEGER,
		ipNode16AlarmIPvalid
			INTEGER,
		ipNode16AlarmStatus
			INTEGER,
		ipNode16AlarmLastResponse
			DisplayString,
		ipNode16AlarmDependency
			INTEGER,
		ipNode16AlarmRetries
			INTEGER,
		ipNode16AlarmTimeout
			INTEGER,
		ipNode16AlarmResetTime
			INTEGER,
		ipNode16AlarmAlarmOnRTN
			INTEGER,
		ipNode16AlarmInUse
			INTEGER,
		ipNode16AlarmLastAlarm
			DisplayString,
		ipNode16AlarmLastAck
			DisplayString,
		ipNode16AlarmName
			DisplayString,
		ipNode16AlarmClass
			INTEGER,
		ipNode16AlarmEnable
			INTEGER,
		ipNode16AlarmDatalog
			INTEGER,
		ipNode16AlarmCustomVoice
			DisplayString,
		ipNode16AlarmAck
			INTEGER
	}

ipNode16Index					OBJECT-TYPE
	SYNTAX				INTEGER (1..64)
	ACCESS				read-write
	STATUS				mandatory
	DESCRIPTION "The index of the IP (1..64)"
	::= { ipNode16Entry 1 }

ipNode16AlarmIPnum		OBJECT-TYPE
	SYNTAX				DisplayString
	ACCESS				read-write
	STATUS				mandatory
	DESCRIPTION "The numeric IP address"
	::= { ipNode16Entry 2 }

ipNode16AlarmPort			OBJECT-TYPE
	SYNTAX				INTEGER
	ACCESS				read-write
	STATUS				mandatory
	DESCRIPTION "The IP port to check for service"
	::= { ipNode16Entry 3 }

ipNode16AlarmIPvalid		OBJECT-TYPE
	SYNTAX				INTEGER { false(1), true(2) }
	ACCESS				read-only
	STATUS				mandatory
	DESCRIPTION "IP valid"
	::= { ipNode16Entry 4 }

ipNode16AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode16Entry 5 }

ipNode16AlarmLastResponse	OBJECT-TYPE
	SYNTAX				DisplayString
	ACCESS				read-only
	STATUS				mandatory
	DESCRIPTION "Last time that this IP device responsed"
	::= { ipNode16Entry 6 }

ipNode16AlarmDependency		OBJECT-TYPE
	SYNTAX				INTEGER
	ACCESS				read-write
	STATUS				mandatory
	DESCRIPTION "Other IP that this one is dependent upon (255 is none)"
	::= { ipNode16Entry 7 }

ipNode16AlarmRetries		OBJECT-TYPE
	SYNTAX				INTEGER
	ACCESS				read-write
	STATUS				mandatory
	DESCRIPTION "Number of time to retry this device before failing it"
	::= { ipNode16Entry 8 }

ipNode16AlarmTimeout		OBJECT-TYPE
	SYNTAX				INTEGER
	ACCESS				read-write
	STATUS				mandatory
	DESCRIPTION "Time in seconds to wait for a response"
	::= { ipNode16Entry 9 }

ipNode16AlarmResetTime		OBJECT-TYPE
	SYNTAX				INTEGER
	ACCESS				read-write
	STATUS				mandatory
	DESCRIPTION "A value &gt;= 30 mins enables feature, 0 disables"
	::= { ipNode16Entry 10 }

ipNode16AlarmAlarmOnRTN	OBJECT-TYPE
	SYNTAX		INTEGER {	false(1),true(2) }
	ACCESS				read-write
	STATUS				mandatory
	DESCRIPTION "Allow an alarm to occur when this device starts responding again"
	::= { ipNode16Entry 11 }

ipNode16AlarmInUse		OBJECT-TYPE
	SYNTAX		INTEGER { false(1),true(2) }
	ACCESS				read-write
	STATUS				mandatory
	DESCRIPTION "True if this IP alarm is active"
	::= { ipNode16Entry 12 }

ipNode16AlarmLastAlarm		OBJECT-TYPE
	SYNTAX				DisplayString
	ACCESS				read-only
	STATUS				mandatory
	DESCRIPTION "Timestamp of the last alarm"
	::= { ipNode16Entry 13 }

ipNode16AlarmLastAck		OBJECT-TYPE
	SYNTAX				DisplayString
	ACCESS				read-only
	STATUS				mandatory
	DESCRIPTION "Timestamp of the last alarm Ack"
	::= { ipNode16Entry 14 }

ipNode16AlarmName			OBJECT-TYPE
	SYNTAX				DisplayString
	ACCESS				read-write
	STATUS				mandatory
	DESCRIPTION "Reference name for this IP device"
	::= { ipNode16Entry 15 }

ipNode16AlarmClass		OBJECT-TYPE
	SYNTAX				INTEGER
	ACCESS				read-write
	STATUS				mandatory
	DESCRIPTION "Alarm class of IP (255 is none)"
	::= { ipNode16Entry 16 }

ipNode16AlarmEnable		OBJECT-TYPE
	SYNTAX		INTEGER { false(1),true(2) }
	ACCESS				read-only
	STATUS				mandatory
	DESCRIPTION "IP enabled by scheduler"
	::= { ipNode16Entry 17 }

ipNode16AlarmDatalog		OBJECT-TYPE
	SYNTAX		INTEGER { false(1),true(2) }
	ACCESS				read-write
	STATUS				mandatory
	DESCRIPTION "Datalog IP"
	::= { ipNode16Entry 18 }

ipNode16AlarmCustomVoice	OBJECT-TYPE
	SYNTAX				DisplayString
	ACCESS				read-write
	STATUS				mandatory
	DESCRIPTION "WAV file for the custom voice message"
	::= { ipNode16Entry 19 }

ipNode16AlarmAck		OBJECT-TYPE
	SYNTAX				INTEGER { false(1),true(2) }
	ACCESS				read-write
	STATUS				mandatory
	DESCRIPTION 	"Ack Alarm"
	::= { ipNode16Entry 20 }

ipNode17Table	OBJECT-TYPE
	SYNTAX	SEQUENCE OF	IpNode17Entry
	ACCESS not-accessible
	STATUS	mandatory
	DESCRIPTION
		"A List of IP entries"
	::= { node17IP	1 }

ipNode17Entry	OBJECT-TYPE
	SYNTAX IpNode17Entry
	ACCESS not-accessible
	STATUS	mandatory
	DESCRIPTION
		"An IP entry"
	INDEX { ipNode17Index }
	::= { ipNode17Table 1 }

IpNode17Entry ::=
	SEQUENCE {
		ipNode17Index
			INTEGER,
		ipNode17AlarmIPnum
			DisplayString,
		ipNode17AlarmPort
			INTEGER,
		ipNode17AlarmIPvalid
			INTEGER,
		ipNode17AlarmStatus
			INTEGER,
		ipNode17AlarmLastResponse
			DisplayString,
		ipNode17AlarmDependency
			INTEGER,
		ipNode17AlarmRetries
			INTEGER,
		ipNode17AlarmTimeout
			INTEGER,
		ipNode17AlarmResetTime
			INTEGER,
		ipNode17AlarmAlarmOnRTN
			INTEGER,
		ipNode17AlarmInUse
			INTEGER,
		ipNode17AlarmLastAlarm
			DisplayString,
		ipNode17AlarmLastAck
			DisplayString,
		ipNode17AlarmName
			DisplayString,
		ipNode17AlarmClass
			INTEGER,
		ipNode17AlarmEnable
			INTEGER,
		ipNode17AlarmDatalog
			INTEGER,
		ipNode17AlarmCustomVoice
			DisplayString,
		ipNode17AlarmAck
			INTEGER
	}

ipNode17Index					OBJECT-TYPE
	SYNTAX				INTEGER (1..64)
	ACCESS				read-write
	STATUS				mandatory
	DESCRIPTION "The index of the IP (1..64)"
	::= { ipNode17Entry 1 }

ipNode17AlarmIPnum		OBJECT-TYPE
	SYNTAX				DisplayString
	ACCESS				read-write
	STATUS				mandatory
	DESCRIPTION "The numeric IP address"
	::= { ipNode17Entry 2 }

ipNode17AlarmPort			OBJECT-TYPE
	SYNTAX				INTEGER
	ACCESS				read-write
	STATUS				mandatory
	DESCRIPTION "The IP port to check for service"
	::= { ipNode17Entry 3 }

ipNode17AlarmIPvalid		OBJECT-TYPE
	SYNTAX				INTEGER { false(1), true(2) }
	ACCESS				read-only
	STATUS				mandatory
	DESCRIPTION "IP valid"
	::= { ipNode17Entry 4 }

ipNode17AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode17Entry 5 }

ipNode17AlarmLastResponse	OBJECT-TYPE
	SYNTAX				DisplayString
	ACCESS				read-only
	STATUS				mandatory
	DESCRIPTION "Last time that this IP device responsed"
	::= { ipNode17Entry 6 }

ipNode17AlarmDependency		OBJECT-TYPE
	SYNTAX				INTEGER
	ACCESS				read-write
	STATUS				mandatory
	DESCRIPTION "Other IP that this one is dependent upon (255 is none)"
	::= { ipNode17Entry 7 }

ipNode17AlarmRetries		OBJECT-TYPE
	SYNTAX				INTEGER
	ACCESS				read-write
	STATUS				mandatory
	DESCRIPTION "Number of time to retry this device before failing it"
	::= { ipNode17Entry 8 }

ipNode17AlarmTimeout		OBJECT-TYPE
	SYNTAX				INTEGER
	ACCESS				read-write
	STATUS				mandatory
	DESCRIPTION "Time in seconds to wait for a response"
	::= { ipNode17Entry 9 }

ipNode17AlarmResetTime		OBJECT-TYPE
	SYNTAX				INTEGER
	ACCESS				read-write
	STATUS				mandatory
	DESCRIPTION "A value &gt;= 30 mins enables feature, 0 disables"
	::= { ipNode17Entry 10 }

ipNode17AlarmAlarmOnRTN	OBJECT-TYPE
	SYNTAX		INTEGER {	false(1),true(2) }
	ACCESS				read-write
	STATUS				mandatory
	DESCRIPTION "Allow an alarm to occur when this device starts responding again"
	::= { ipNode17Entry 11 }

ipNode17AlarmInUse		OBJECT-TYPE
	SYNTAX		INTEGER { false(1),true(2) }
	ACCESS				read-write
	STATUS				mandatory
	DESCRIPTION "True if this IP alarm is active"
	::= { ipNode17Entry 12 }

ipNode17AlarmLastAlarm		OBJECT-TYPE
	SYNTAX				DisplayString
	ACCESS				read-only
	STATUS				mandatory
	DESCRIPTION "Timestamp of the last alarm"
	::= { ipNode17Entry 13 }

ipNode17AlarmLastAck		OBJECT-TYPE
	SYNTAX				DisplayString
	ACCESS				read-only
	STATUS				mandatory
	DESCRIPTION "Timestamp of the last alarm Ack"
	::= { ipNode17Entry 14 }

ipNode17AlarmName			OBJECT-TYPE
	SYNTAX				DisplayString
	ACCESS				read-write
	STATUS				mandatory
	DESCRIPTION "Reference name for this IP device"
	::= { ipNode17Entry 15 }

ipNode17AlarmClass		OBJECT-TYPE
	SYNTAX				INTEGER
	ACCESS				read-write
	STATUS				mandatory
	DESCRIPTION "Alarm class of IP (255 is none)"
	::= { ipNode17Entry 16 }

ipNode17AlarmEnable		OBJECT-TYPE
	SYNTAX		INTEGER { false(1),true(2) }
	ACCESS				read-only
	STATUS				mandatory
	DESCRIPTION "IP enabled by scheduler"
	::= { ipNode17Entry 17 }

ipNode17AlarmDatalog		OBJECT-TYPE
	SYNTAX		INTEGER { false(1),true(2) }
	ACCESS				read-write
	STATUS				mandatory
	DESCRIPTION "Datalog IP"
	::= { ipNode17Entry 18 }

ipNode17AlarmCustomVoice	OBJECT-TYPE
	SYNTAX				DisplayString
	ACCESS				read-write
	STATUS				mandatory
	DESCRIPTION "WAV file for the custom voice message"
	::= { ipNode17Entry 19 }

ipNode17AlarmAck		OBJECT-TYPE
	SYNTAX				INTEGER { false(1),true(2) }
	ACCESS				read-write
	STATUS				mandatory
	DESCRIPTION 	"Ack Alarm"
	::= { ipNode17Entry 20 }

ipNode18Table	OBJECT-TYPE
	SYNTAX	SEQUENCE OF	IpNode18Entry
	ACCESS not-accessible
	STATUS	mandatory
	DESCRIPTION
		"A List of IP entries"
	::= { node18IP	1 }

ipNode18Entry	OBJECT-TYPE
	SYNTAX IpNode18Entry
	ACCESS not-accessible
	STATUS	mandatory
	DESCRIPTION
		"An IP entry"
	INDEX { ipNode18Index }
	::= { ipNode18Table 1 }

IpNode18Entry ::=
	SEQUENCE {
		ipNode18Index
			INTEGER,
		ipNode18AlarmIPnum
			DisplayString,
		ipNode18AlarmPort
			INTEGER,
		ipNode18AlarmIPvalid
			INTEGER,
		ipNode18AlarmStatus
			INTEGER,
		ipNode18AlarmLastResponse
			DisplayString,
		ipNode18AlarmDependency
			INTEGER,
		ipNode18AlarmRetries
			INTEGER,
		ipNode18AlarmTimeout
			INTEGER,
		ipNode18AlarmResetTime
			INTEGER,
		ipNode18AlarmAlarmOnRTN
			INTEGER,
		ipNode18AlarmInUse
			INTEGER,
		ipNode18AlarmLastAlarm
			DisplayString,
		ipNode18AlarmLastAck
			DisplayString,
		ipNode18AlarmName
			DisplayString,
		ipNode18AlarmClass
			INTEGER,
		ipNode18AlarmEnable
			INTEGER,
		ipNode18AlarmDatalog
			INTEGER,
		ipNode18AlarmCustomVoice
			DisplayString,
		ipNode18AlarmAck
			INTEGER
	}

ipNode18Index					OBJECT-TYPE
	SYNTAX				INTEGER (1..64)
	ACCESS				read-write
	STATUS				mandatory
	DESCRIPTION "The index of the IP (1..64)"
	::= { ipNode18Entry 1 }

ipNode18AlarmIPnum		OBJECT-TYPE
	SYNTAX				DisplayString
	ACCESS				read-write
	STATUS				mandatory
	DESCRIPTION "The numeric IP address"
	::= { ipNode18Entry 2 }

ipNode18AlarmPort			OBJECT-TYPE
	SYNTAX				INTEGER
	ACCESS				read-write
	STATUS				mandatory
	DESCRIPTION "The IP port to check for service"
	::= { ipNode18Entry 3 }

ipNode18AlarmIPvalid		OBJECT-TYPE
	SYNTAX				INTEGER { false(1), true(2) }
	ACCESS				read-only
	STATUS				mandatory
	DESCRIPTION "IP valid"
	::= { ipNode18Entry 4 }

ipNode18AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode18Entry 5 }

ipNode18AlarmLastResponse	OBJECT-TYPE
	SYNTAX				DisplayString
	ACCESS				read-only
	STATUS				mandatory
	DESCRIPTION "Last time that this IP device responsed"
	::= { ipNode18Entry 6 }

ipNode18AlarmDependency		OBJECT-TYPE
	SYNTAX				INTEGER
	ACCESS				read-write
	STATUS				mandatory
	DESCRIPTION "Other IP that this one is dependent upon (255 is none)"
	::= { ipNode18Entry 7 }

ipNode18AlarmRetries		OBJECT-TYPE
	SYNTAX				INTEGER
	ACCESS				read-write
	STATUS				mandatory
	DESCRIPTION "Number of time to retry this device before failing it"
	::= { ipNode18Entry 8 }

ipNode18AlarmTimeout		OBJECT-TYPE
	SYNTAX				INTEGER
	ACCESS				read-write
	STATUS				mandatory
	DESCRIPTION "Time in seconds to wait for a response"
	::= { ipNode18Entry 9 }

ipNode18AlarmResetTime		OBJECT-TYPE
	SYNTAX				INTEGER
	ACCESS				read-write
	STATUS				mandatory
	DESCRIPTION "A value &gt;= 30 mins enables feature, 0 disables"
	::= { ipNode18Entry 10 }

ipNode18AlarmAlarmOnRTN	OBJECT-TYPE
	SYNTAX		INTEGER {	false(1),true(2) }
	ACCESS				read-write
	STATUS				mandatory
	DESCRIPTION "Allow an alarm to occur when this device starts responding again"
	::= { ipNode18Entry 11 }

ipNode18AlarmInUse		OBJECT-TYPE
	SYNTAX		INTEGER { false(1),true(2) }
	ACCESS				read-write
	STATUS				mandatory
	DESCRIPTION "True if this IP alarm is active"
	::= { ipNode18Entry 12 }

ipNode18AlarmLastAlarm		OBJECT-TYPE
	SYNTAX				DisplayString
	ACCESS				read-only
	STATUS				mandatory
	DESCRIPTION "Timestamp of the last alarm"
	::= { ipNode18Entry 13 }

ipNode18AlarmLastAck		OBJECT-TYPE
	SYNTAX				DisplayString
	ACCESS				read-only
	STATUS				mandatory
	DESCRIPTION "Timestamp of the last alarm Ack"
	::= { ipNode18Entry 14 }

ipNode18AlarmName			OBJECT-TYPE
	SYNTAX				DisplayString
	ACCESS				read-write
	STATUS				mandatory
	DESCRIPTION "Reference name for this IP device"
	::= { ipNode18Entry 15 }

ipNode18AlarmClass		OBJECT-TYPE
	SYNTAX				INTEGER
	ACCESS				read-write
	STATUS				mandatory
	DESCRIPTION "Alarm class of IP (255 is none)"
	::= { ipNode18Entry 16 }

ipNode18AlarmEnable		OBJECT-TYPE
	SYNTAX		INTEGER { false(1),true(2) }
	ACCESS				read-only
	STATUS				mandatory
	DESCRIPTION "IP enabled by scheduler"
	::= { ipNode18Entry 17 }

ipNode18AlarmDatalog		OBJECT-TYPE
	SYNTAX		INTEGER { false(1),true(2) }
	ACCESS				read-write
	STATUS				mandatory
	DESCRIPTION "Datalog IP"
	::= { ipNode18Entry 18 }

ipNode18AlarmCustomVoice	OBJECT-TYPE
	SYNTAX				DisplayString
	ACCESS				read-write
	STATUS				mandatory
	DESCRIPTION "WAV file for the custom voice message"
	::= { ipNode18Entry 19 }

ipNode18AlarmAck		OBJECT-TYPE
	SYNTAX				INTEGER { false(1),true(2) }
	ACCESS				read-write
	STATUS				mandatory
	DESCRIPTION 	"Ack Alarm"
	::= { ipNode18Entry 20 }

ipNode19Table	OBJECT-TYPE
	SYNTAX	SEQUENCE OF	IpNode19Entry
	ACCESS not-accessible
	STATUS	mandatory
	DESCRIPTION
		"A List of IP entries"
	::= { node19IP	1 }

ipNode19Entry	OBJECT-TYPE
	SYNTAX IpNode19Entry
	ACCESS not-accessible
	STATUS	mandatory
	DESCRIPTION
		"An IP entry"
	INDEX { ipNode19Index }
	::= { ipNode19Table 1 }

IpNode19Entry ::=
	SEQUENCE {
		ipNode19Index
			INTEGER,
		ipNode19AlarmIPnum
			DisplayString,
		ipNode19AlarmPort
			INTEGER,
		ipNode19AlarmIPvalid
			INTEGER,
		ipNode19AlarmStatus
			INTEGER,
		ipNode19AlarmLastResponse
			DisplayString,
		ipNode19AlarmDependency
			INTEGER,
		ipNode19AlarmRetries
			INTEGER,
		ipNode19AlarmTimeout
			INTEGER,
		ipNode19AlarmResetTime
			INTEGER,
		ipNode19AlarmAlarmOnRTN
			INTEGER,
		ipNode19AlarmInUse
			INTEGER,
		ipNode19AlarmLastAlarm
			DisplayString,
		ipNode19AlarmLastAck
			DisplayString,
		ipNode19AlarmName
			DisplayString,
		ipNode19AlarmClass
			INTEGER,
		ipNode19AlarmEnable
			INTEGER,
		ipNode19AlarmDatalog
			INTEGER,
		ipNode19AlarmCustomVoice
			DisplayString,
		ipNode19AlarmAck
			INTEGER
	}

ipNode19Index					OBJECT-TYPE
	SYNTAX				INTEGER (1..64)
	ACCESS				read-write
	STATUS				mandatory
	DESCRIPTION "The index of the IP (1..64)"
	::= { ipNode19Entry 1 }

ipNode19AlarmIPnum		OBJECT-TYPE
	SYNTAX				DisplayString
	ACCESS				read-write
	STATUS				mandatory
	DESCRIPTION "The numeric IP address"
	::= { ipNode19Entry 2 }

ipNode19AlarmPort			OBJECT-TYPE
	SYNTAX				INTEGER
	ACCESS				read-write
	STATUS				mandatory
	DESCRIPTION "The IP port to check for service"
	::= { ipNode19Entry 3 }

ipNode19AlarmIPvalid		OBJECT-TYPE
	SYNTAX				INTEGER { false(1), true(2) }
	ACCESS				read-only
	STATUS				mandatory
	DESCRIPTION "IP valid"
	::= { ipNode19Entry 4 }

ipNode19AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode19Entry 5 }

ipNode19AlarmLastResponse	OBJECT-TYPE
	SYNTAX				DisplayString
	ACCESS				read-only
	STATUS				mandatory
	DESCRIPTION "Last time that this IP device responsed"
	::= { ipNode19Entry 6 }

ipNode19AlarmDependency		OBJECT-TYPE
	SYNTAX				INTEGER
	ACCESS				read-write
	STATUS				mandatory
	DESCRIPTION "Other IP that this one is dependent upon (255 is none)"
	::= { ipNode19Entry 7 }

ipNode19AlarmRetries		OBJECT-TYPE
	SYNTAX				INTEGER
	ACCESS				read-write
	STATUS				mandatory
	DESCRIPTION "Number of time to retry this device before failing it"
	::= { ipNode19Entry 8 }

ipNode19AlarmTimeout		OBJECT-TYPE
	SYNTAX				INTEGER
	ACCESS				read-write
	STATUS				mandatory
	DESCRIPTION "Time in seconds to wait for a response"
	::= { ipNode19Entry 9 }

ipNode19AlarmResetTime		OBJECT-TYPE
	SYNTAX				INTEGER
	ACCESS				read-write
	STATUS				mandatory
	DESCRIPTION "A value &gt;= 30 mins enables feature, 0 disables"
	::= { ipNode19Entry 10 }

ipNode19AlarmAlarmOnRTN	OBJECT-TYPE
	SYNTAX		INTEGER {	false(1),true(2) }
	ACCESS				read-write
	STATUS				mandatory
	DESCRIPTION "Allow an alarm to occur when this device starts responding again"
	::= { ipNode19Entry 11 }

ipNode19AlarmInUse		OBJECT-TYPE
	SYNTAX		INTEGER { false(1),true(2) }
	ACCESS				read-write
	STATUS				mandatory
	DESCRIPTION "True if this IP alarm is active"
	::= { ipNode19Entry 12 }

ipNode19AlarmLastAlarm		OBJECT-TYPE
	SYNTAX				DisplayString
	ACCESS				read-only
	STATUS				mandatory
	DESCRIPTION "Timestamp of the last alarm"
	::= { ipNode19Entry 13 }

ipNode19AlarmLastAck		OBJECT-TYPE
	SYNTAX				DisplayString
	ACCESS				read-only
	STATUS				mandatory
	DESCRIPTION "Timestamp of the last alarm Ack"
	::= { ipNode19Entry 14 }

ipNode19AlarmName			OBJECT-TYPE
	SYNTAX				DisplayString
	ACCESS				read-write
	STATUS				mandatory
	DESCRIPTION "Reference name for this IP device"
	::= { ipNode19Entry 15 }

ipNode19AlarmClass		OBJECT-TYPE
	SYNTAX				INTEGER
	ACCESS				read-write
	STATUS				mandatory
	DESCRIPTION "Alarm class of IP (255 is none)"
	::= { ipNode19Entry 16 }

ipNode19AlarmEnable		OBJECT-TYPE
	SYNTAX		INTEGER { false(1),true(2) }
	ACCESS				read-only
	STATUS				mandatory
	DESCRIPTION "IP enabled by scheduler"
	::= { ipNode19Entry 17 }

ipNode19AlarmDatalog		OBJECT-TYPE
	SYNTAX		INTEGER { false(1),true(2) }
	ACCESS				read-write
	STATUS				mandatory
	DESCRIPTION "Datalog IP"
	::= { ipNode19Entry 18 }

ipNode19AlarmCustomVoice	OBJECT-TYPE
	SYNTAX				DisplayString
	ACCESS				read-write
	STATUS				mandatory
	DESCRIPTION "WAV file for the custom voice message"
	::= { ipNode19Entry 19 }

ipNode19AlarmAck		OBJECT-TYPE
	SYNTAX				INTEGER { false(1),true(2) }
	ACCESS				read-write
	STATUS				mandatory
	DESCRIPTION 	"Ack Alarm"
	::= { ipNode19Entry 20 }

ipNode20Table	OBJECT-TYPE
	SYNTAX	SEQUENCE OF	IpNode20Entry
	ACCESS not-accessible
	STATUS	mandatory
	DESCRIPTION
		"A List of IP entries"
	::= { node20IP	1 }

ipNode20Entry	OBJECT-TYPE
	SYNTAX IpNode20Entry
	ACCESS not-accessible
	STATUS	mandatory
	DESCRIPTION
		"An IP entry"
	INDEX { ipNode20Index }
	::= { ipNode20Table 1 }

IpNode20Entry ::=
	SEQUENCE {
		ipNode20Index
			INTEGER,
		ipNode20AlarmIPnum
			DisplayString,
		ipNode20AlarmPort
			INTEGER,
		ipNode20AlarmIPvalid
			INTEGER,
		ipNode20AlarmStatus
			INTEGER,
		ipNode20AlarmLastResponse
			DisplayString,
		ipNode20AlarmDependency
			INTEGER,
		ipNode20AlarmRetries
			INTEGER,
		ipNode20AlarmTimeout
			INTEGER,
		ipNode20AlarmResetTime
			INTEGER,
		ipNode20AlarmAlarmOnRTN
			INTEGER,
		ipNode20AlarmInUse
			INTEGER,
		ipNode20AlarmLastAlarm
			DisplayString,
		ipNode20AlarmLastAck
			DisplayString,
		ipNode20AlarmName
			DisplayString,
		ipNode20AlarmClass
			INTEGER,
		ipNode20AlarmEnable
			INTEGER,
		ipNode20AlarmDatalog
			INTEGER,
		ipNode20AlarmCustomVoice
			DisplayString,
		ipNode20AlarmAck
			INTEGER
	}

ipNode20Index					OBJECT-TYPE
	SYNTAX				INTEGER (1..64)
	ACCESS				read-write
	STATUS				mandatory
	DESCRIPTION "The index of the IP (1..64)"
	::= { ipNode20Entry 1 }

ipNode20AlarmIPnum		OBJECT-TYPE
	SYNTAX				DisplayString
	ACCESS				read-write
	STATUS				mandatory
	DESCRIPTION "The numeric IP address"
	::= { ipNode20Entry 2 }

ipNode20AlarmPort			OBJECT-TYPE
	SYNTAX				INTEGER
	ACCESS				read-write
	STATUS				mandatory
	DESCRIPTION "The IP port to check for service"
	::= { ipNode20Entry 3 }

ipNode20AlarmIPvalid		OBJECT-TYPE
	SYNTAX				INTEGER { false(1), true(2) }
	ACCESS				read-only
	STATUS				mandatory
	DESCRIPTION "IP valid"
	::= { ipNode20Entry 4 }

ipNode20AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode20Entry 5 }

ipNode20AlarmLastResponse	OBJECT-TYPE
	SYNTAX				DisplayString
	ACCESS				read-only
	STATUS				mandatory
	DESCRIPTION "Last time that this IP device responsed"
	::= { ipNode20Entry 6 }

ipNode20AlarmDependency		OBJECT-TYPE
	SYNTAX				INTEGER
	ACCESS				read-write
	STATUS				mandatory
	DESCRIPTION "Other IP that this one is dependent upon (255 is none)"
	::= { ipNode20Entry 7 }

ipNode20AlarmRetries		OBJECT-TYPE
	SYNTAX				INTEGER
	ACCESS				read-write
	STATUS				mandatory
	DESCRIPTION "Number of time to retry this device before failing it"
	::= { ipNode20Entry 8 }

ipNode20AlarmTimeout		OBJECT-TYPE
	SYNTAX				INTEGER
	ACCESS				read-write
	STATUS				mandatory
	DESCRIPTION "Time in seconds to wait for a response"
	::= { ipNode20Entry 9 }

ipNode20AlarmResetTime		OBJECT-TYPE
	SYNTAX				INTEGER
	ACCESS				read-write
	STATUS				mandatory
	DESCRIPTION "A value &gt;= 30 mins enables feature, 0 disables"
	::= { ipNode20Entry 10 }

ipNode20AlarmAlarmOnRTN	OBJECT-TYPE
	SYNTAX		INTEGER {	false(1),true(2) }
	ACCESS				read-write
	STATUS				mandatory
	DESCRIPTION "Allow an alarm to occur when this device starts responding again"
	::= { ipNode20Entry 11 }

ipNode20AlarmInUse		OBJECT-TYPE
	SYNTAX		INTEGER { false(1),true(2) }
	ACCESS				read-write
	STATUS				mandatory
	DESCRIPTION "True if this IP alarm is active"
	::= { ipNode20Entry 12 }

ipNode20AlarmLastAlarm		OBJECT-TYPE
	SYNTAX				DisplayString
	ACCESS				read-only
	STATUS				mandatory
	DESCRIPTION "Timestamp of the last alarm"
	::= { ipNode20Entry 13 }

ipNode20AlarmLastAck		OBJECT-TYPE
	SYNTAX				DisplayString
	ACCESS				read-only
	STATUS				mandatory
	DESCRIPTION "Timestamp of the last alarm Ack"
	::= { ipNode20Entry 14 }

ipNode20AlarmName			OBJECT-TYPE
	SYNTAX				DisplayString
	ACCESS				read-write
	STATUS				mandatory
	DESCRIPTION "Reference name for this IP device"
	::= { ipNode20Entry 15 }

ipNode20AlarmClass		OBJECT-TYPE
	SYNTAX				INTEGER
	ACCESS				read-write
	STATUS				mandatory
	DESCRIPTION "Alarm class of IP (255 is none)"
	::= { ipNode20Entry 16 }

ipNode20AlarmEnable		OBJECT-TYPE
	SYNTAX		INTEGER { false(1),true(2) }
	ACCESS				read-only
	STATUS				mandatory
	DESCRIPTION "IP enabled by scheduler"
	::= { ipNode20Entry 17 }

ipNode20AlarmDatalog		OBJECT-TYPE
	SYNTAX		INTEGER { false(1),true(2) }
	ACCESS				read-write
	STATUS				mandatory
	DESCRIPTION "Datalog IP"
	::= { ipNode20Entry 18 }

ipNode20AlarmCustomVoice	OBJECT-TYPE
	SYNTAX				DisplayString
	ACCESS				read-write
	STATUS				mandatory
	DESCRIPTION "WAV file for the custom voice message"
	::= { ipNode20Entry 19 }

ipNode20AlarmAck		OBJECT-TYPE
	SYNTAX				INTEGER { false(1),true(2) }
	ACCESS				read-write
	STATUS				mandatory
	DESCRIPTION 	"Ack Alarm"
	::= { ipNode20Entry 20 }

ipNode21Table	OBJECT-TYPE
	SYNTAX	SEQUENCE OF	IpNode21Entry
	ACCESS not-accessible
	STATUS	mandatory
	DESCRIPTION
		"A List of IP entries"
	::= { node21IP	1 }

ipNode21Entry	OBJECT-TYPE
	SYNTAX IpNode21Entry
	ACCESS not-accessible
	STATUS	mandatory
	DESCRIPTION
		"An IP entry"
	INDEX { ipNode21Index }
	::= { ipNode21Table 1 }

IpNode21Entry ::=
	SEQUENCE {
		ipNode21Index
			INTEGER,
		ipNode21AlarmIPnum
			DisplayString,
		ipNode21AlarmPort
			INTEGER,
		ipNode21AlarmIPvalid
			INTEGER,
		ipNode21AlarmStatus
			INTEGER,
		ipNode21AlarmLastResponse
			DisplayString,
		ipNode21AlarmDependency
			INTEGER,
		ipNode21AlarmRetries
			INTEGER,
		ipNode21AlarmTimeout
			INTEGER,
		ipNode21AlarmResetTime
			INTEGER,
		ipNode21AlarmAlarmOnRTN
			INTEGER,
		ipNode21AlarmInUse
			INTEGER,
		ipNode21AlarmLastAlarm
			DisplayString,
		ipNode21AlarmLastAck
			DisplayString,
		ipNode21AlarmName
			DisplayString,
		ipNode21AlarmClass
			INTEGER,
		ipNode21AlarmEnable
			INTEGER,
		ipNode21AlarmDatalog
			INTEGER,
		ipNode21AlarmCustomVoice
			DisplayString,
		ipNode21AlarmAck
			INTEGER
	}

ipNode21Index					OBJECT-TYPE
	SYNTAX				INTEGER (1..64)
	ACCESS				read-write
	STATUS				mandatory
	DESCRIPTION "The index of the IP (1..64)"
	::= { ipNode21Entry 1 }

ipNode21AlarmIPnum		OBJECT-TYPE
	SYNTAX				DisplayString
	ACCESS				read-write
	STATUS				mandatory
	DESCRIPTION "The numeric IP address"
	::= { ipNode21Entry 2 }

ipNode21AlarmPort			OBJECT-TYPE
	SYNTAX				INTEGER
	ACCESS				read-write
	STATUS				mandatory
	DESCRIPTION "The IP port to check for service"
	::= { ipNode21Entry 3 }

ipNode21AlarmIPvalid		OBJECT-TYPE
	SYNTAX				INTEGER { false(1), true(2) }
	ACCESS				read-only
	STATUS				mandatory
	DESCRIPTION "IP valid"
	::= { ipNode21Entry 4 }

ipNode21AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode21Entry 5 }

ipNode21AlarmLastResponse	OBJECT-TYPE
	SYNTAX				DisplayString
	ACCESS				read-only
	STATUS				mandatory
	DESCRIPTION "Last time that this IP device responsed"
	::= { ipNode21Entry 6 }

ipNode21AlarmDependency		OBJECT-TYPE
	SYNTAX				INTEGER
	ACCESS				read-write
	STATUS				mandatory
	DESCRIPTION "Other IP that this one is dependent upon (255 is none)"
	::= { ipNode21Entry 7 }

ipNode21AlarmRetries		OBJECT-TYPE
	SYNTAX				INTEGER
	ACCESS				read-write
	STATUS				mandatory
	DESCRIPTION "Number of time to retry this device before failing it"
	::= { ipNode21Entry 8 }

ipNode21AlarmTimeout		OBJECT-TYPE
	SYNTAX				INTEGER
	ACCESS				read-write
	STATUS				mandatory
	DESCRIPTION "Time in seconds to wait for a response"
	::= { ipNode21Entry 9 }

ipNode21AlarmResetTime		OBJECT-TYPE
	SYNTAX				INTEGER
	ACCESS				read-write
	STATUS				mandatory
	DESCRIPTION "A value &gt;= 30 mins enables feature, 0 disables"
	::= { ipNode21Entry 10 }

ipNode21AlarmAlarmOnRTN	OBJECT-TYPE
	SYNTAX		INTEGER {	false(1),true(2) }
	ACCESS				read-write
	STATUS				mandatory
	DESCRIPTION "Allow an alarm to occur when this device starts responding again"
	::= { ipNode21Entry 11 }

ipNode21AlarmInUse		OBJECT-TYPE
	SYNTAX		INTEGER { false(1),true(2) }
	ACCESS				read-write
	STATUS				mandatory
	DESCRIPTION "True if this IP alarm is active"
	::= { ipNode21Entry 12 }

ipNode21AlarmLastAlarm		OBJECT-TYPE
	SYNTAX				DisplayString
	ACCESS				read-only
	STATUS				mandatory
	DESCRIPTION "Timestamp of the last alarm"
	::= { ipNode21Entry 13 }

ipNode21AlarmLastAck		OBJECT-TYPE
	SYNTAX				DisplayString
	ACCESS				read-only
	STATUS				mandatory
	DESCRIPTION "Timestamp of the last alarm Ack"
	::= { ipNode21Entry 14 }

ipNode21AlarmName			OBJECT-TYPE
	SYNTAX				DisplayString
	ACCESS				read-write
	STATUS				mandatory
	DESCRIPTION "Reference name for this IP device"
	::= { ipNode21Entry 15 }

ipNode21AlarmClass		OBJECT-TYPE
	SYNTAX				INTEGER
	ACCESS				read-write
	STATUS				mandatory
	DESCRIPTION "Alarm class of IP (255 is none)"
	::= { ipNode21Entry 16 }

ipNode21AlarmEnable		OBJECT-TYPE
	SYNTAX		INTEGER { false(1),true(2) }
	ACCESS				read-only
	STATUS				mandatory
	DESCRIPTION "IP enabled by scheduler"
	::= { ipNode21Entry 17 }

ipNode21AlarmDatalog		OBJECT-TYPE
	SYNTAX		INTEGER { false(1),true(2) }
	ACCESS				read-write
	STATUS				mandatory
	DESCRIPTION "Datalog IP"
	::= { ipNode21Entry 18 }

ipNode21AlarmCustomVoice	OBJECT-TYPE
	SYNTAX				DisplayString
	ACCESS				read-write
	STATUS				mandatory
	DESCRIPTION "WAV file for the custom voice message"
	::= { ipNode21Entry 19 }

ipNode21AlarmAck		OBJECT-TYPE
	SYNTAX				INTEGER { false(1),true(2) }
	ACCESS				read-write
	STATUS				mandatory
	DESCRIPTION 	"Ack Alarm"
	::= { ipNode21Entry 20 }

ipNode22Table	OBJECT-TYPE
	SYNTAX	SEQUENCE OF	IpNode22Entry
	ACCESS not-accessible
	STATUS	mandatory
	DESCRIPTION
		"A List of IP entries"
	::= { node22IP	1 }

ipNode22Entry	OBJECT-TYPE
	SYNTAX IpNode22Entry
	ACCESS not-accessible
	STATUS	mandatory
	DESCRIPTION
		"An IP entry"
	INDEX { ipNode22Index }
	::= { ipNode22Table 1 }

IpNode22Entry ::=
	SEQUENCE {
		ipNode22Index
			INTEGER,
		ipNode22AlarmIPnum
			DisplayString,
		ipNode22AlarmPort
			INTEGER,
		ipNode22AlarmIPvalid
			INTEGER,
		ipNode22AlarmStatus
			INTEGER,
		ipNode22AlarmLastResponse
			DisplayString,
		ipNode22AlarmDependency
			INTEGER,
		ipNode22AlarmRetries
			INTEGER,
		ipNode22AlarmTimeout
			INTEGER,
		ipNode22AlarmResetTime
			INTEGER,
		ipNode22AlarmAlarmOnRTN
			INTEGER,
		ipNode22AlarmInUse
			INTEGER,
		ipNode22AlarmLastAlarm
			DisplayString,
		ipNode22AlarmLastAck
			DisplayString,
		ipNode22AlarmName
			DisplayString,
		ipNode22AlarmClass
			INTEGER,
		ipNode22AlarmEnable
			INTEGER,
		ipNode22AlarmDatalog
			INTEGER,
		ipNode22AlarmCustomVoice
			DisplayString,
		ipNode22AlarmAck
			INTEGER
	}

ipNode22Index					OBJECT-TYPE
	SYNTAX				INTEGER (1..64)
	ACCESS				read-write
	STATUS				mandatory
	DESCRIPTION "The index of the IP (1..64)"
	::= { ipNode22Entry 1 }

ipNode22AlarmIPnum		OBJECT-TYPE
	SYNTAX				DisplayString
	ACCESS				read-write
	STATUS				mandatory
	DESCRIPTION "The numeric IP address"
	::= { ipNode22Entry 2 }

ipNode22AlarmPort			OBJECT-TYPE
	SYNTAX				INTEGER
	ACCESS				read-write
	STATUS				mandatory
	DESCRIPTION "The IP port to check for service"
	::= { ipNode22Entry 3 }

ipNode22AlarmIPvalid		OBJECT-TYPE
	SYNTAX				INTEGER { false(1), true(2) }
	ACCESS				read-only
	STATUS				mandatory
	DESCRIPTION "IP valid"
	::= { ipNode22Entry 4 }

ipNode22AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode22Entry 5 }

ipNode22AlarmLastResponse	OBJECT-TYPE
	SYNTAX				DisplayString
	ACCESS				read-only
	STATUS				mandatory
	DESCRIPTION "Last time that this IP device responsed"
	::= { ipNode22Entry 6 }

ipNode22AlarmDependency		OBJECT-TYPE
	SYNTAX				INTEGER
	ACCESS				read-write
	STATUS				mandatory
	DESCRIPTION "Other IP that this one is dependent upon (255 is none)"
	::= { ipNode22Entry 7 }

ipNode22AlarmRetries		OBJECT-TYPE
	SYNTAX				INTEGER
	ACCESS				read-write
	STATUS				mandatory
	DESCRIPTION "Number of time to retry this device before failing it"
	::= { ipNode22Entry 8 }

ipNode22AlarmTimeout		OBJECT-TYPE
	SYNTAX				INTEGER
	ACCESS				read-write
	STATUS				mandatory
	DESCRIPTION "Time in seconds to wait for a response"
	::= { ipNode22Entry 9 }

ipNode22AlarmResetTime		OBJECT-TYPE
	SYNTAX				INTEGER
	ACCESS				read-write
	STATUS				mandatory
	DESCRIPTION "A value &gt;= 30 mins enables feature, 0 disables"
	::= { ipNode22Entry 10 }

ipNode22AlarmAlarmOnRTN	OBJECT-TYPE
	SYNTAX		INTEGER {	false(1),true(2) }
	ACCESS				read-write
	STATUS				mandatory
	DESCRIPTION "Allow an alarm to occur when this device starts responding again"
	::= { ipNode22Entry 11 }

ipNode22AlarmInUse		OBJECT-TYPE
	SYNTAX		INTEGER { false(1),true(2) }
	ACCESS				read-write
	STATUS				mandatory
	DESCRIPTION "True if this IP alarm is active"
	::= { ipNode22Entry 12 }

ipNode22AlarmLastAlarm		OBJECT-TYPE
	SYNTAX				DisplayString
	ACCESS				read-only
	STATUS				mandatory
	DESCRIPTION "Timestamp of the last alarm"
	::= { ipNode22Entry 13 }

ipNode22AlarmLastAck		OBJECT-TYPE
	SYNTAX				DisplayString
	ACCESS				read-only
	STATUS				mandatory
	DESCRIPTION "Timestamp of the last alarm Ack"
	::= { ipNode22Entry 14 }

ipNode22AlarmName			OBJECT-TYPE
	SYNTAX				DisplayString
	ACCESS				read-write
	STATUS				mandatory
	DESCRIPTION "Reference name for this IP device"
	::= { ipNode22Entry 15 }

ipNode22AlarmClass		OBJECT-TYPE
	SYNTAX				INTEGER
	ACCESS				read-write
	STATUS				mandatory
	DESCRIPTION "Alarm class of IP (255 is none)"
	::= { ipNode22Entry 16 }

ipNode22AlarmEnable		OBJECT-TYPE
	SYNTAX		INTEGER { false(1),true(2) }
	ACCESS				read-only
	STATUS				mandatory
	DESCRIPTION "IP enabled by scheduler"
	::= { ipNode22Entry 17 }

ipNode22AlarmDatalog		OBJECT-TYPE
	SYNTAX		INTEGER { false(1),true(2) }
	ACCESS				read-write
	STATUS				mandatory
	DESCRIPTION "Datalog IP"
	::= { ipNode22Entry 18 }

ipNode22AlarmCustomVoice	OBJECT-TYPE
	SYNTAX				DisplayString
	ACCESS				read-write
	STATUS				mandatory
	DESCRIPTION "WAV file for the custom voice message"
	::= { ipNode22Entry 19 }

ipNode22AlarmAck		OBJECT-TYPE
	SYNTAX				INTEGER { false(1),true(2) }
	ACCESS				read-write
	STATUS				mandatory
	DESCRIPTION 	"Ack Alarm"
	::= { ipNode22Entry 20 }

ipNode23Table	OBJECT-TYPE
	SYNTAX	SEQUENCE OF	IpNode23Entry
	ACCESS not-accessible
	STATUS	mandatory
	DESCRIPTION
		"A List of IP entries"
	::= { node23IP	1 }

ipNode23Entry	OBJECT-TYPE
	SYNTAX IpNode23Entry
	ACCESS not-accessible
	STATUS	mandatory
	DESCRIPTION
		"An IP entry"
	INDEX { ipNode23Index }
	::= { ipNode23Table 1 }

IpNode23Entry ::=
	SEQUENCE {
		ipNode23Index
			INTEGER,
		ipNode23AlarmIPnum
			DisplayString,
		ipNode23AlarmPort
			INTEGER,
		ipNode23AlarmIPvalid
			INTEGER,
		ipNode23AlarmStatus
			INTEGER,
		ipNode23AlarmLastResponse
			DisplayString,
		ipNode23AlarmDependency
			INTEGER,
		ipNode23AlarmRetries
			INTEGER,
		ipNode23AlarmTimeout
			INTEGER,
		ipNode23AlarmResetTime
			INTEGER,
		ipNode23AlarmAlarmOnRTN
			INTEGER,
		ipNode23AlarmInUse
			INTEGER,
		ipNode23AlarmLastAlarm
			DisplayString,
		ipNode23AlarmLastAck
			DisplayString,
		ipNode23AlarmName
			DisplayString,
		ipNode23AlarmClass
			INTEGER,
		ipNode23AlarmEnable
			INTEGER,
		ipNode23AlarmDatalog
			INTEGER,
		ipNode23AlarmCustomVoice
			DisplayString,
		ipNode23AlarmAck
			INTEGER
	}

ipNode23Index					OBJECT-TYPE
	SYNTAX				INTEGER (1..64)
	ACCESS				read-write
	STATUS				mandatory
	DESCRIPTION "The index of the IP (1..64)"
	::= { ipNode23Entry 1 }

ipNode23AlarmIPnum		OBJECT-TYPE
	SYNTAX				DisplayString
	ACCESS				read-write
	STATUS				mandatory
	DESCRIPTION "The numeric IP address"
	::= { ipNode23Entry 2 }

ipNode23AlarmPort			OBJECT-TYPE
	SYNTAX				INTEGER
	ACCESS				read-write
	STATUS				mandatory
	DESCRIPTION "The IP port to check for service"
	::= { ipNode23Entry 3 }

ipNode23AlarmIPvalid		OBJECT-TYPE
	SYNTAX				INTEGER { false(1), true(2) }
	ACCESS				read-only
	STATUS				mandatory
	DESCRIPTION "IP valid"
	::= { ipNode23Entry 4 }

ipNode23AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode23Entry 5 }

ipNode23AlarmLastResponse	OBJECT-TYPE
	SYNTAX				DisplayString
	ACCESS				read-only
	STATUS				mandatory
	DESCRIPTION "Last time that this IP device responsed"
	::= { ipNode23Entry 6 }

ipNode23AlarmDependency		OBJECT-TYPE
	SYNTAX				INTEGER
	ACCESS				read-write
	STATUS				mandatory
	DESCRIPTION "Other IP that this one is dependent upon (255 is none)"
	::= { ipNode23Entry 7 }

ipNode23AlarmRetries		OBJECT-TYPE
	SYNTAX				INTEGER
	ACCESS				read-write
	STATUS				mandatory
	DESCRIPTION "Number of time to retry this device before failing it"
	::= { ipNode23Entry 8 }

ipNode23AlarmTimeout		OBJECT-TYPE
	SYNTAX				INTEGER
	ACCESS				read-write
	STATUS				mandatory
	DESCRIPTION "Time in seconds to wait for a response"
	::= { ipNode23Entry 9 }

ipNode23AlarmResetTime		OBJECT-TYPE
	SYNTAX				INTEGER
	ACCESS				read-write
	STATUS				mandatory
	DESCRIPTION "A value &gt;= 30 mins enables feature, 0 disables"
	::= { ipNode23Entry 10 }

ipNode23AlarmAlarmOnRTN	OBJECT-TYPE
	SYNTAX		INTEGER {	false(1),true(2) }
	ACCESS				read-write
	STATUS				mandatory
	DESCRIPTION "Allow an alarm to occur when this device starts responding again"
	::= { ipNode23Entry 11 }

ipNode23AlarmInUse		OBJECT-TYPE
	SYNTAX		INTEGER { false(1),true(2) }
	ACCESS				read-write
	STATUS				mandatory
	DESCRIPTION "True if this IP alarm is active"
	::= { ipNode23Entry 12 }

ipNode23AlarmLastAlarm		OBJECT-TYPE
	SYNTAX				DisplayString
	ACCESS				read-only
	STATUS				mandatory
	DESCRIPTION "Timestamp of the last alarm"
	::= { ipNode23Entry 13 }

ipNode23AlarmLastAck		OBJECT-TYPE
	SYNTAX				DisplayString
	ACCESS				read-only
	STATUS				mandatory
	DESCRIPTION "Timestamp of the last alarm Ack"
	::= { ipNode23Entry 14 }

ipNode23AlarmName			OBJECT-TYPE
	SYNTAX				DisplayString
	ACCESS				read-write
	STATUS				mandatory
	DESCRIPTION "Reference name for this IP device"
	::= { ipNode23Entry 15 }

ipNode23AlarmClass		OBJECT-TYPE
	SYNTAX				INTEGER
	ACCESS				read-write
	STATUS				mandatory
	DESCRIPTION "Alarm class of IP (255 is none)"
	::= { ipNode23Entry 16 }

ipNode23AlarmEnable		OBJECT-TYPE
	SYNTAX		INTEGER { false(1),true(2) }
	ACCESS				read-only
	STATUS				mandatory
	DESCRIPTION "IP enabled by scheduler"
	::= { ipNode23Entry 17 }

ipNode23AlarmDatalog		OBJECT-TYPE
	SYNTAX		INTEGER { false(1),true(2) }
	ACCESS				read-write
	STATUS				mandatory
	DESCRIPTION "Datalog IP"
	::= { ipNode23Entry 18 }

ipNode23AlarmCustomVoice	OBJECT-TYPE
	SYNTAX				DisplayString
	ACCESS				read-write
	STATUS				mandatory
	DESCRIPTION "WAV file for the custom voice message"
	::= { ipNode23Entry 19 }

ipNode23AlarmAck		OBJECT-TYPE
	SYNTAX				INTEGER { false(1),true(2) }
	ACCESS				read-write
	STATUS				mandatory
	DESCRIPTION 	"Ack Alarm"
	::= { ipNode23Entry 20 }

ipNode24Table	OBJECT-TYPE
	SYNTAX	SEQUENCE OF	IpNode24Entry
	ACCESS not-accessible
	STATUS	mandatory
	DESCRIPTION
		"A List of IP entries"
	::= { node24IP	1 }

ipNode24Entry	OBJECT-TYPE
	SYNTAX IpNode24Entry
	ACCESS not-accessible
	STATUS	mandatory
	DESCRIPTION
		"An IP entry"
	INDEX { ipNode24Index }
	::= { ipNode24Table 1 }

IpNode24Entry ::=
	SEQUENCE {
		ipNode24Index
			INTEGER,
		ipNode24AlarmIPnum
			DisplayString,
		ipNode24AlarmPort
			INTEGER,
		ipNode24AlarmIPvalid
			INTEGER,
		ipNode24AlarmStatus
			INTEGER,
		ipNode24AlarmLastResponse
			DisplayString,
		ipNode24AlarmDependency
			INTEGER,
		ipNode24AlarmRetries
			INTEGER,
		ipNode24AlarmTimeout
			INTEGER,
		ipNode24AlarmResetTime
			INTEGER,
		ipNode24AlarmAlarmOnRTN
			INTEGER,
		ipNode24AlarmInUse
			INTEGER,
		ipNode24AlarmLastAlarm
			DisplayString,
		ipNode24AlarmLastAck
			DisplayString,
		ipNode24AlarmName
			DisplayString,
		ipNode24AlarmClass
			INTEGER,
		ipNode24AlarmEnable
			INTEGER,
		ipNode24AlarmDatalog
			INTEGER,
		ipNode24AlarmCustomVoice
			DisplayString,
		ipNode24AlarmAck
			INTEGER
	}

ipNode24Index					OBJECT-TYPE
	SYNTAX				INTEGER (1..64)
	ACCESS				read-write
	STATUS				mandatory
	DESCRIPTION "The index of the IP (1..64)"
	::= { ipNode24Entry 1 }

ipNode24AlarmIPnum		OBJECT-TYPE
	SYNTAX				DisplayString
	ACCESS				read-write
	STATUS				mandatory
	DESCRIPTION "The numeric IP address"
	::= { ipNode24Entry 2 }

ipNode24AlarmPort			OBJECT-TYPE
	SYNTAX				INTEGER
	ACCESS				read-write
	STATUS				mandatory
	DESCRIPTION "The IP port to check for service"
	::= { ipNode24Entry 3 }

ipNode24AlarmIPvalid		OBJECT-TYPE
	SYNTAX				INTEGER { false(1), true(2) }
	ACCESS				read-only
	STATUS				mandatory
	DESCRIPTION "IP valid"
	::= { ipNode24Entry 4 }

ipNode24AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode24Entry 5 }

ipNode24AlarmLastResponse	OBJECT-TYPE
	SYNTAX				DisplayString
	ACCESS				read-only
	STATUS				mandatory
	DESCRIPTION "Last time that this IP device responsed"
	::= { ipNode24Entry 6 }

ipNode24AlarmDependency		OBJECT-TYPE
	SYNTAX				INTEGER
	ACCESS				read-write
	STATUS				mandatory
	DESCRIPTION "Other IP that this one is dependent upon (255 is none)"
	::= { ipNode24Entry 7 }

ipNode24AlarmRetries		OBJECT-TYPE
	SYNTAX				INTEGER
	ACCESS				read-write
	STATUS				mandatory
	DESCRIPTION "Number of time to retry this device before failing it"
	::= { ipNode24Entry 8 }

ipNode24AlarmTimeout		OBJECT-TYPE
	SYNTAX				INTEGER
	ACCESS				read-write
	STATUS				mandatory
	DESCRIPTION "Time in seconds to wait for a response"
	::= { ipNode24Entry 9 }

ipNode24AlarmResetTime		OBJECT-TYPE
	SYNTAX				INTEGER
	ACCESS				read-write
	STATUS				mandatory
	DESCRIPTION "A value &gt;= 30 mins enables feature, 0 disables"
	::= { ipNode24Entry 10 }

ipNode24AlarmAlarmOnRTN	OBJECT-TYPE
	SYNTAX		INTEGER {	false(1),true(2) }
	ACCESS				read-write
	STATUS				mandatory
	DESCRIPTION "Allow an alarm to occur when this device starts responding again"
	::= { ipNode24Entry 11 }

ipNode24AlarmInUse		OBJECT-TYPE
	SYNTAX		INTEGER { false(1),true(2) }
	ACCESS				read-write
	STATUS				mandatory
	DESCRIPTION "True if this IP alarm is active"
	::= { ipNode24Entry 12 }

ipNode24AlarmLastAlarm		OBJECT-TYPE
	SYNTAX				DisplayString
	ACCESS				read-only
	STATUS				mandatory
	DESCRIPTION "Timestamp of the last alarm"
	::= { ipNode24Entry 13 }

ipNode24AlarmLastAck		OBJECT-TYPE
	SYNTAX				DisplayString
	ACCESS				read-only
	STATUS				mandatory
	DESCRIPTION "Timestamp of the last alarm Ack"
	::= { ipNode24Entry 14 }

ipNode24AlarmName			OBJECT-TYPE
	SYNTAX				DisplayString
	ACCESS				read-write
	STATUS				mandatory
	DESCRIPTION "Reference name for this IP device"
	::= { ipNode24Entry 15 }

ipNode24AlarmClass		OBJECT-TYPE
	SYNTAX				INTEGER
	ACCESS				read-write
	STATUS				mandatory
	DESCRIPTION "Alarm class of IP (255 is none)"
	::= { ipNode24Entry 16 }

ipNode24AlarmEnable		OBJECT-TYPE
	SYNTAX		INTEGER { false(1),true(2) }
	ACCESS				read-only
	STATUS				mandatory
	DESCRIPTION "IP enabled by scheduler"
	::= { ipNode24Entry 17 }

ipNode24AlarmDatalog		OBJECT-TYPE
	SYNTAX		INTEGER { false(1),true(2) }
	ACCESS				read-write
	STATUS				mandatory
	DESCRIPTION "Datalog IP"
	::= { ipNode24Entry 18 }

ipNode24AlarmCustomVoice	OBJECT-TYPE
	SYNTAX				DisplayString
	ACCESS				read-write
	STATUS				mandatory
	DESCRIPTION "WAV file for the custom voice message"
	::= { ipNode24Entry 19 }

ipNode24AlarmAck		OBJECT-TYPE
	SYNTAX				INTEGER { false(1),true(2) }
	ACCESS				read-write
	STATUS				mandatory
	DESCRIPTION 	"Ack Alarm"
	::= { ipNode24Entry 20 }

ipNode25Table	OBJECT-TYPE
	SYNTAX	SEQUENCE OF	IpNode25Entry
	ACCESS not-accessible
	STATUS	mandatory
	DESCRIPTION
		"A List of IP entries"
	::= { node25IP	1 }

ipNode25Entry	OBJECT-TYPE
	SYNTAX IpNode25Entry
	ACCESS not-accessible
	STATUS	mandatory
	DESCRIPTION
		"An IP entry"
	INDEX { ipNode25Index }
	::= { ipNode25Table 1 }

IpNode25Entry ::=
	SEQUENCE {
		ipNode25Index
			INTEGER,
		ipNode25AlarmIPnum
			DisplayString,
		ipNode25AlarmPort
			INTEGER,
		ipNode25AlarmIPvalid
			INTEGER,
		ipNode25AlarmStatus
			INTEGER,
		ipNode25AlarmLastResponse
			DisplayString,
		ipNode25AlarmDependency
			INTEGER,
		ipNode25AlarmRetries
			INTEGER,
		ipNode25AlarmTimeout
			INTEGER,
		ipNode25AlarmResetTime
			INTEGER,
		ipNode25AlarmAlarmOnRTN
			INTEGER,
		ipNode25AlarmInUse
			INTEGER,
		ipNode25AlarmLastAlarm
			DisplayString,
		ipNode25AlarmLastAck
			DisplayString,
		ipNode25AlarmName
			DisplayString,
		ipNode25AlarmClass
			INTEGER,
		ipNode25AlarmEnable
			INTEGER,
		ipNode25AlarmDatalog
			INTEGER,
		ipNode25AlarmCustomVoice
			DisplayString,
		ipNode25AlarmAck
			INTEGER
	}

ipNode25Index					OBJECT-TYPE
	SYNTAX				INTEGER (1..64)
	ACCESS				read-write
	STATUS				mandatory
	DESCRIPTION "The index of the IP (1..64)"
	::= { ipNode25Entry 1 }

ipNode25AlarmIPnum		OBJECT-TYPE
	SYNTAX				DisplayString
	ACCESS				read-write
	STATUS				mandatory
	DESCRIPTION "The numeric IP address"
	::= { ipNode25Entry 2 }

ipNode25AlarmPort			OBJECT-TYPE
	SYNTAX				INTEGER
	ACCESS				read-write
	STATUS				mandatory
	DESCRIPTION "The IP port to check for service"
	::= { ipNode25Entry 3 }

ipNode25AlarmIPvalid		OBJECT-TYPE
	SYNTAX				INTEGER { false(1), true(2) }
	ACCESS				read-only
	STATUS				mandatory
	DESCRIPTION "IP valid"
	::= { ipNode25Entry 4 }

ipNode25AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode25Entry 5 }

ipNode25AlarmLastResponse	OBJECT-TYPE
	SYNTAX				DisplayString
	ACCESS				read-only
	STATUS				mandatory
	DESCRIPTION "Last time that this IP device responsed"
	::= { ipNode25Entry 6 }

ipNode25AlarmDependency		OBJECT-TYPE
	SYNTAX				INTEGER
	ACCESS				read-write
	STATUS				mandatory
	DESCRIPTION "Other IP that this one is dependent upon (255 is none)"
	::= { ipNode25Entry 7 }

ipNode25AlarmRetries		OBJECT-TYPE
	SYNTAX				INTEGER
	ACCESS				read-write
	STATUS				mandatory
	DESCRIPTION "Number of time to retry this device before failing it"
	::= { ipNode25Entry 8 }

ipNode25AlarmTimeout		OBJECT-TYPE
	SYNTAX				INTEGER
	ACCESS				read-write
	STATUS				mandatory
	DESCRIPTION "Time in seconds to wait for a response"
	::= { ipNode25Entry 9 }

ipNode25AlarmResetTime		OBJECT-TYPE
	SYNTAX				INTEGER
	ACCESS				read-write
	STATUS				mandatory
	DESCRIPTION "A value &gt;= 30 mins enables feature, 0 disables"
	::= { ipNode25Entry 10 }

ipNode25AlarmAlarmOnRTN	OBJECT-TYPE
	SYNTAX		INTEGER {	false(1),true(2) }
	ACCESS				read-write
	STATUS				mandatory
	DESCRIPTION "Allow an alarm to occur when this device starts responding again"
	::= { ipNode25Entry 11 }

ipNode25AlarmInUse		OBJECT-TYPE
	SYNTAX		INTEGER { false(1),true(2) }
	ACCESS				read-write
	STATUS				mandatory
	DESCRIPTION "True if this IP alarm is active"
	::= { ipNode25Entry 12 }

ipNode25AlarmLastAlarm		OBJECT-TYPE
	SYNTAX				DisplayString
	ACCESS				read-only
	STATUS				mandatory
	DESCRIPTION "Timestamp of the last alarm"
	::= { ipNode25Entry 13 }

ipNode25AlarmLastAck		OBJECT-TYPE
	SYNTAX				DisplayString
	ACCESS				read-only
	STATUS				mandatory
	DESCRIPTION "Timestamp of the last alarm Ack"
	::= { ipNode25Entry 14 }

ipNode25AlarmName			OBJECT-TYPE
	SYNTAX				DisplayString
	ACCESS				read-write
	STATUS				mandatory
	DESCRIPTION "Reference name for this IP device"
	::= { ipNode25Entry 15 }

ipNode25AlarmClass		OBJECT-TYPE
	SYNTAX				INTEGER
	ACCESS				read-write
	STATUS				mandatory
	DESCRIPTION "Alarm class of IP (255 is none)"
	::= { ipNode25Entry 16 }

ipNode25AlarmEnable		OBJECT-TYPE
	SYNTAX		INTEGER { false(1),true(2) }
	ACCESS				read-only
	STATUS				mandatory
	DESCRIPTION "IP enabled by scheduler"
	::= { ipNode25Entry 17 }

ipNode25AlarmDatalog		OBJECT-TYPE
	SYNTAX		INTEGER { false(1),true(2) }
	ACCESS				read-write
	STATUS				mandatory
	DESCRIPTION "Datalog IP"
	::= { ipNode25Entry 18 }

ipNode25AlarmCustomVoice	OBJECT-TYPE
	SYNTAX				DisplayString
	ACCESS				read-write
	STATUS				mandatory
	DESCRIPTION "WAV file for the custom voice message"
	::= { ipNode25Entry 19 }

ipNode25AlarmAck		OBJECT-TYPE
	SYNTAX				INTEGER { false(1),true(2) }
	ACCESS				read-write
	STATUS				mandatory
	DESCRIPTION 	"Ack Alarm"
	::= { ipNode25Entry 20 }

ipNode26Table	OBJECT-TYPE
	SYNTAX	SEQUENCE OF	IpNode26Entry
	ACCESS not-accessible
	STATUS	mandatory
	DESCRIPTION
		"A List of IP entries"
	::= { node26IP	1 }

ipNode26Entry	OBJECT-TYPE
	SYNTAX IpNode26Entry
	ACCESS not-accessible
	STATUS	mandatory
	DESCRIPTION
		"An IP entry"
	INDEX { ipNode26Index }
	::= { ipNode26Table 1 }

IpNode26Entry ::=
	SEQUENCE {
		ipNode26Index
			INTEGER,
		ipNode26AlarmIPnum
			DisplayString,
		ipNode26AlarmPort
			INTEGER,
		ipNode26AlarmIPvalid
			INTEGER,
		ipNode26AlarmStatus
			INTEGER,
		ipNode26AlarmLastResponse
			DisplayString,
		ipNode26AlarmDependency
			INTEGER,
		ipNode26AlarmRetries
			INTEGER,
		ipNode26AlarmTimeout
			INTEGER,
		ipNode26AlarmResetTime
			INTEGER,
		ipNode26AlarmAlarmOnRTN
			INTEGER,
		ipNode26AlarmInUse
			INTEGER,
		ipNode26AlarmLastAlarm
			DisplayString,
		ipNode26AlarmLastAck
			DisplayString,
		ipNode26AlarmName
			DisplayString,
		ipNode26AlarmClass
			INTEGER,
		ipNode26AlarmEnable
			INTEGER,
		ipNode26AlarmDatalog
			INTEGER,
		ipNode26AlarmCustomVoice
			DisplayString,
		ipNode26AlarmAck
			INTEGER
	}

ipNode26Index					OBJECT-TYPE
	SYNTAX				INTEGER (1..64)
	ACCESS				read-write
	STATUS				mandatory
	DESCRIPTION "The index of the IP (1..64)"
	::= { ipNode26Entry 1 }

ipNode26AlarmIPnum		OBJECT-TYPE
	SYNTAX				DisplayString
	ACCESS				read-write
	STATUS				mandatory
	DESCRIPTION "The numeric IP address"
	::= { ipNode26Entry 2 }

ipNode26AlarmPort			OBJECT-TYPE
	SYNTAX				INTEGER
	ACCESS				read-write
	STATUS				mandatory
	DESCRIPTION "The IP port to check for service"
	::= { ipNode26Entry 3 }

ipNode26AlarmIPvalid		OBJECT-TYPE
	SYNTAX				INTEGER { false(1), true(2) }
	ACCESS				read-only
	STATUS				mandatory
	DESCRIPTION "IP valid"
	::= { ipNode26Entry 4 }

ipNode26AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode26Entry 5 }

ipNode26AlarmLastResponse	OBJECT-TYPE
	SYNTAX				DisplayString
	ACCESS				read-only
	STATUS				mandatory
	DESCRIPTION "Last time that this IP device responsed"
	::= { ipNode26Entry 6 }

ipNode26AlarmDependency		OBJECT-TYPE
	SYNTAX				INTEGER
	ACCESS				read-write
	STATUS				mandatory
	DESCRIPTION "Other IP that this one is dependent upon (255 is none)"
	::= { ipNode26Entry 7 }

ipNode26AlarmRetries		OBJECT-TYPE
	SYNTAX				INTEGER
	ACCESS				read-write
	STATUS				mandatory
	DESCRIPTION "Number of time to retry this device before failing it"
	::= { ipNode26Entry 8 }

ipNode26AlarmTimeout		OBJECT-TYPE
	SYNTAX				INTEGER
	ACCESS				read-write
	STATUS				mandatory
	DESCRIPTION "Time in seconds to wait for a response"
	::= { ipNode26Entry 9 }

ipNode26AlarmResetTime		OBJECT-TYPE
	SYNTAX				INTEGER
	ACCESS				read-write
	STATUS				mandatory
	DESCRIPTION "A value &gt;= 30 mins enables feature, 0 disables"
	::= { ipNode26Entry 10 }

ipNode26AlarmAlarmOnRTN	OBJECT-TYPE
	SYNTAX		INTEGER {	false(1),true(2) }
	ACCESS				read-write
	STATUS				mandatory
	DESCRIPTION "Allow an alarm to occur when this device starts responding again"
	::= { ipNode26Entry 11 }

ipNode26AlarmInUse		OBJECT-TYPE
	SYNTAX		INTEGER { false(1),true(2) }
	ACCESS				read-write
	STATUS				mandatory
	DESCRIPTION "True if this IP alarm is active"
	::= { ipNode26Entry 12 }

ipNode26AlarmLastAlarm		OBJECT-TYPE
	SYNTAX				DisplayString
	ACCESS				read-only
	STATUS				mandatory
	DESCRIPTION "Timestamp of the last alarm"
	::= { ipNode26Entry 13 }

ipNode26AlarmLastAck		OBJECT-TYPE
	SYNTAX				DisplayString
	ACCESS				read-only
	STATUS				mandatory
	DESCRIPTION "Timestamp of the last alarm Ack"
	::= { ipNode26Entry 14 }

ipNode26AlarmName			OBJECT-TYPE
	SYNTAX				DisplayString
	ACCESS				read-write
	STATUS				mandatory
	DESCRIPTION "Reference name for this IP device"
	::= { ipNode26Entry 15 }

ipNode26AlarmClass		OBJECT-TYPE
	SYNTAX				INTEGER
	ACCESS				read-write
	STATUS				mandatory
	DESCRIPTION "Alarm class of IP (255 is none)"
	::= { ipNode26Entry 16 }

ipNode26AlarmEnable		OBJECT-TYPE
	SYNTAX		INTEGER { false(1),true(2) }
	ACCESS				read-only
	STATUS				mandatory
	DESCRIPTION "IP enabled by scheduler"
	::= { ipNode26Entry 17 }

ipNode26AlarmDatalog		OBJECT-TYPE
	SYNTAX		INTEGER { false(1),true(2) }
	ACCESS				read-write
	STATUS				mandatory
	DESCRIPTION "Datalog IP"
	::= { ipNode26Entry 18 }

ipNode26AlarmCustomVoice	OBJECT-TYPE
	SYNTAX				DisplayString
	ACCESS				read-write
	STATUS				mandatory
	DESCRIPTION "WAV file for the custom voice message"
	::= { ipNode26Entry 19 }

ipNode26AlarmAck		OBJECT-TYPE
	SYNTAX				INTEGER { false(1),true(2) }
	ACCESS				read-write
	STATUS				mandatory
	DESCRIPTION 	"Ack Alarm"
	::= { ipNode26Entry 20 }

ipNode27Table	OBJECT-TYPE
	SYNTAX	SEQUENCE OF	IpNode27Entry
	ACCESS not-accessible
	STATUS	mandatory
	DESCRIPTION
		"A List of IP entries"
	::= { node27IP	1 }

ipNode27Entry	OBJECT-TYPE
	SYNTAX IpNode27Entry
	ACCESS not-accessible
	STATUS	mandatory
	DESCRIPTION
		"An IP entry"
	INDEX { ipNode27Index }
	::= { ipNode27Table 1 }

IpNode27Entry ::=
	SEQUENCE {
		ipNode27Index
			INTEGER,
		ipNode27AlarmIPnum
			DisplayString,
		ipNode27AlarmPort
			INTEGER,
		ipNode27AlarmIPvalid
			INTEGER,
		ipNode27AlarmStatus
			INTEGER,
		ipNode27AlarmLastResponse
			DisplayString,
		ipNode27AlarmDependency
			INTEGER,
		ipNode27AlarmRetries
			INTEGER,
		ipNode27AlarmTimeout
			INTEGER,
		ipNode27AlarmResetTime
			INTEGER,
		ipNode27AlarmAlarmOnRTN
			INTEGER,
		ipNode27AlarmInUse
			INTEGER,
		ipNode27AlarmLastAlarm
			DisplayString,
		ipNode27AlarmLastAck
			DisplayString,
		ipNode27AlarmName
			DisplayString,
		ipNode27AlarmClass
			INTEGER,
		ipNode27AlarmEnable
			INTEGER,
		ipNode27AlarmDatalog
			INTEGER,
		ipNode27AlarmCustomVoice
			DisplayString,
		ipNode27AlarmAck
			INTEGER
	}

ipNode27Index					OBJECT-TYPE
	SYNTAX				INTEGER (1..64)
	ACCESS				read-write
	STATUS				mandatory
	DESCRIPTION "The index of the IP (1..64)"
	::= { ipNode27Entry 1 }

ipNode27AlarmIPnum		OBJECT-TYPE
	SYNTAX				DisplayString
	ACCESS				read-write
	STATUS				mandatory
	DESCRIPTION "The numeric IP address"
	::= { ipNode27Entry 2 }

ipNode27AlarmPort			OBJECT-TYPE
	SYNTAX				INTEGER
	ACCESS				read-write
	STATUS				mandatory
	DESCRIPTION "The IP port to check for service"
	::= { ipNode27Entry 3 }

ipNode27AlarmIPvalid		OBJECT-TYPE
	SYNTAX				INTEGER { false(1), true(2) }
	ACCESS				read-only
	STATUS				mandatory
	DESCRIPTION "IP valid"
	::= { ipNode27Entry 4 }


ipNode27AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode27Entry 5 }

ipNode27AlarmLastResponse	OBJECT-TYPE
	SYNTAX				DisplayString
	ACCESS				read-only
	STATUS				mandatory
	DESCRIPTION "Last time that this IP device responsed"
	::= { ipNode27Entry 6 }

ipNode27AlarmDependency		OBJECT-TYPE
	SYNTAX				INTEGER
	ACCESS				read-write
	STATUS				mandatory
	DESCRIPTION "Other IP that this one is dependent upon (255 is none)"
	::= { ipNode27Entry 7 }

ipNode27AlarmRetries		OBJECT-TYPE
	SYNTAX				INTEGER
	ACCESS				read-write
	STATUS				mandatory
	DESCRIPTION "Number of time to retry this device before failing it"
	::= { ipNode27Entry 8 }

ipNode27AlarmTimeout		OBJECT-TYPE
	SYNTAX				INTEGER
	ACCESS				read-write
	STATUS				mandatory
	DESCRIPTION "Time in seconds to wait for a response"
	::= { ipNode27Entry 9 }

ipNode27AlarmResetTime		OBJECT-TYPE
	SYNTAX				INTEGER
	ACCESS				read-write
	STATUS				mandatory
	DESCRIPTION "A value &gt;= 30 mins enables feature, 0 disables"
	::= { ipNode27Entry 10 }

ipNode27AlarmAlarmOnRTN	OBJECT-TYPE
	SYNTAX		INTEGER {	false(1),true(2) }
	ACCESS				read-write
	STATUS				mandatory
	DESCRIPTION "Allow an alarm to occur when this device starts responding again"
	::= { ipNode27Entry 11 }

ipNode27AlarmInUse		OBJECT-TYPE
	SYNTAX		INTEGER { false(1),true(2) }
	ACCESS				read-write
	STATUS				mandatory
	DESCRIPTION "True if this IP alarm is active"
	::= { ipNode27Entry 12 }

ipNode27AlarmLastAlarm		OBJECT-TYPE
	SYNTAX				DisplayString
	ACCESS				read-only
	STATUS				mandatory
	DESCRIPTION "Timestamp of the last alarm"
	::= { ipNode27Entry 13 }

ipNode27AlarmLastAck		OBJECT-TYPE
	SYNTAX				DisplayString
	ACCESS				read-only
	STATUS				mandatory
	DESCRIPTION "Timestamp of the last alarm Ack"
	::= { ipNode27Entry 14 }

ipNode27AlarmName			OBJECT-TYPE
	SYNTAX				DisplayString
	ACCESS				read-write
	STATUS				mandatory
	DESCRIPTION "Reference name for this IP device"
	::= { ipNode27Entry 15 }

ipNode27AlarmClass		OBJECT-TYPE
	SYNTAX				INTEGER
	ACCESS				read-write
	STATUS				mandatory
	DESCRIPTION "Alarm class of IP (255 is none)"
	::= { ipNode27Entry 16 }

ipNode27AlarmEnable		OBJECT-TYPE
	SYNTAX		INTEGER { false(1),true(2) }
	ACCESS				read-only
	STATUS				mandatory
	DESCRIPTION "IP enabled by the scheduler"
	::= { ipNode27Entry 17 }

ipNode27AlarmDatalog		OBJECT-TYPE
	SYNTAX		INTEGER { false(1),true(2) }
	ACCESS				read-write
	STATUS				mandatory
	DESCRIPTION "Datalog IP"
	::= { ipNode27Entry 18 }

ipNode27AlarmCustomVoice	OBJECT-TYPE
	SYNTAX				DisplayString
	ACCESS				read-write
	STATUS				mandatory
	DESCRIPTION "WAV file for the custom voice message"
	::= { ipNode27Entry 19 }

ipNode27AlarmAck		OBJECT-TYPE
	SYNTAX				INTEGER { false(1),true(2) }
	ACCESS				read-write
	STATUS				mandatory
	DESCRIPTION 	"Ack Alarm"
	::= { ipNode27Entry 20 }

ipNode28Table	OBJECT-TYPE
	SYNTAX	SEQUENCE OF	IpNode28Entry
	ACCESS not-accessible
	STATUS	mandatory
	DESCRIPTION
		"A List of IP entries"
	::= { node28IP	1 }

ipNode28Entry	OBJECT-TYPE
	SYNTAX IpNode28Entry
	ACCESS not-accessible
	STATUS	mandatory
	DESCRIPTION
		"An IP entry"
	INDEX { ipNode28Index }
	::= { ipNode28Table 1 }

IpNode28Entry ::=
	SEQUENCE {
		ipNode28Index
			INTEGER,
		ipNode28AlarmIPnum
			DisplayString,
		ipNode28AlarmPort
			INTEGER,
		ipNode28AlarmIPvalid
			INTEGER,
		ipNode28AlarmStatus
			INTEGER,
		ipNode28AlarmLastResponse
			DisplayString,
		ipNode28AlarmDependency
			INTEGER,
		ipNode28AlarmRetries
			INTEGER,
		ipNode28AlarmTimeout
			INTEGER,
		ipNode28AlarmResetTime
			INTEGER,
		ipNode28AlarmAlarmOnRTN
			INTEGER,
		ipNode28AlarmInUse
			INTEGER,
		ipNode28AlarmLastAlarm
			DisplayString,
		ipNode28AlarmLastAck
			DisplayString,
		ipNode28AlarmName
			DisplayString,
		ipNode28AlarmClass
			INTEGER,
		ipNode28AlarmEnable
			INTEGER,
		ipNode28AlarmDatalog
			INTEGER,
		ipNode28AlarmCustomVoice
			DisplayString,
		ipNode28AlarmAck
			INTEGER
	}

ipNode28Index					OBJECT-TYPE
	SYNTAX				INTEGER (1..64)
	ACCESS				read-write
	STATUS				mandatory
	DESCRIPTION "The index of the IP (1..64)"
	::= { ipNode28Entry 1 }

ipNode28AlarmIPnum		OBJECT-TYPE
	SYNTAX				DisplayString
	ACCESS				read-write
	STATUS				mandatory
	DESCRIPTION "The numeric IP address"
	::= { ipNode28Entry 2 }

ipNode28AlarmPort			OBJECT-TYPE
	SYNTAX				INTEGER
	ACCESS				read-write
	STATUS				mandatory
	DESCRIPTION "The IP port to check for service"
	::= { ipNode28Entry 3 }

ipNode28AlarmIPvalid		OBJECT-TYPE
	SYNTAX				INTEGER { false(1), true(2) }
	ACCESS				read-only
	STATUS				mandatory
	DESCRIPTION "IP valid"
	::= { ipNode28Entry 4 }


ipNode28AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode28Entry 5 }

ipNode28AlarmLastResponse	OBJECT-TYPE
	SYNTAX				DisplayString
	ACCESS				read-only
	STATUS				mandatory
	DESCRIPTION "Last time that this IP device responsed"
	::= { ipNode28Entry 6 }

ipNode28AlarmDependency		OBJECT-TYPE
	SYNTAX				INTEGER
	ACCESS				read-write
	STATUS				mandatory
	DESCRIPTION "Other IP that this one is dependent upon (255 is none)"
	::= { ipNode28Entry 7 }

ipNode28AlarmRetries		OBJECT-TYPE
	SYNTAX				INTEGER
	ACCESS				read-write
	STATUS				mandatory
	DESCRIPTION "Number of time to retry this device before failing it"
	::= { ipNode28Entry 8 }

ipNode28AlarmTimeout		OBJECT-TYPE
	SYNTAX				INTEGER
	ACCESS				read-write
	STATUS				mandatory
	DESCRIPTION "Time in seconds to wait for a response"
	::= { ipNode28Entry 9 }

ipNode28AlarmResetTime		OBJECT-TYPE
	SYNTAX				INTEGER
	ACCESS				read-write
	STATUS				mandatory
	DESCRIPTION "A value &gt;= 30 mins enables feature, 0 disables"
	::= { ipNode28Entry 10 }

ipNode28AlarmAlarmOnRTN	OBJECT-TYPE
	SYNTAX		INTEGER {	false(1),true(2) }
	ACCESS				read-write
	STATUS				mandatory
	DESCRIPTION "Allow an alarm to occur when this device starts responding again"
	::= { ipNode28Entry 11 }

ipNode28AlarmInUse		OBJECT-TYPE
	SYNTAX		INTEGER { false(1),true(2) }
	ACCESS				read-write
	STATUS				mandatory
	DESCRIPTION "True if this IP alarm is active"
	::= { ipNode28Entry 12 }

ipNode28AlarmLastAlarm		OBJECT-TYPE
	SYNTAX				DisplayString
	ACCESS				read-only
	STATUS				mandatory
	DESCRIPTION "Timestamp of the last alarm"
	::= { ipNode28Entry 13 }

ipNode28AlarmLastAck		OBJECT-TYPE
	SYNTAX				DisplayString
	ACCESS				read-only
	STATUS				mandatory
	DESCRIPTION "Timestamp of the last alarm Ack"
	::= { ipNode28Entry 14 }

ipNode28AlarmName			OBJECT-TYPE
	SYNTAX				DisplayString
	ACCESS				read-write
	STATUS				mandatory
	DESCRIPTION "Reference name for this IP device"
	::= { ipNode28Entry 15 }

ipNode28AlarmClass		OBJECT-TYPE
	SYNTAX				INTEGER
	ACCESS				read-write
	STATUS				mandatory
	DESCRIPTION "Alarm class of IP (255 is none)"
	::= { ipNode28Entry 16 }

ipNode28AlarmEnable		OBJECT-TYPE
	SYNTAX		INTEGER { false(1),true(2) }
	ACCESS				read-only
	STATUS				mandatory
	DESCRIPTION "IP enabled by scheduler"
	::= { ipNode28Entry 17 }

ipNode28AlarmDatalog		OBJECT-TYPE
	SYNTAX		INTEGER { false(1),true(2) }
	ACCESS				read-write
	STATUS				mandatory
	DESCRIPTION "Datalog IP"
	::= { ipNode28Entry 18 }

ipNode28AlarmCustomVoice	OBJECT-TYPE
	SYNTAX				DisplayString
	ACCESS				read-write
	STATUS				mandatory
	DESCRIPTION "WAV file for the custom voice message"
	::= { ipNode28Entry 19 }

ipNode28AlarmAck		OBJECT-TYPE
	SYNTAX				INTEGER { false(1),true(2) }
	ACCESS				read-write
	STATUS				mandatory
	DESCRIPTION 	"Ack Alarm"
	::= { ipNode28Entry 20 }

ipNode29Table	OBJECT-TYPE
	SYNTAX	SEQUENCE OF	IpNode29Entry
	ACCESS not-accessible
	STATUS	mandatory
	DESCRIPTION
		"A List of IP entries"
	::= { node29IP	1 }

ipNode29Entry	OBJECT-TYPE
	SYNTAX IpNode29Entry
	ACCESS not-accessible
	STATUS	mandatory
	DESCRIPTION
		"An IP entry"
	INDEX { ipNode29Index }
	::= { ipNode29Table 1 }

IpNode29Entry ::=
	SEQUENCE {
		ipNode29Index
			INTEGER,
		ipNode29AlarmIPnum
			DisplayString,
		ipNode29AlarmPort
			INTEGER,
		ipNode29AlarmIPvalid
			INTEGER,
		ipNode29AlarmStatus
			INTEGER,
		ipNode29AlarmLastResponse
			DisplayString,
		ipNode29AlarmDependency
			INTEGER,
		ipNode29AlarmRetries
			INTEGER,
		ipNode29AlarmTimeout
			INTEGER,
		ipNode29AlarmResetTime
			INTEGER,
		ipNode29AlarmAlarmOnRTN
			INTEGER,
		ipNode29AlarmInUse
			INTEGER,
		ipNode29AlarmLastAlarm
			DisplayString,
		ipNode29AlarmLastAck
			DisplayString,
		ipNode29AlarmName
			DisplayString,
		ipNode29AlarmClass
			INTEGER,
		ipNode29AlarmEnable
			INTEGER,
		ipNode29AlarmDatalog
			INTEGER,
		ipNode29AlarmCustomVoice
			DisplayString,
		ipNode29AlarmAck
			INTEGER
	}

ipNode29Index					OBJECT-TYPE
	SYNTAX				INTEGER (1..64)
	ACCESS				read-write
	STATUS				mandatory
	DESCRIPTION "The index of the IP (1..64)"
	::= { ipNode29Entry 1 }

ipNode29AlarmIPnum		OBJECT-TYPE
	SYNTAX				DisplayString
	ACCESS				read-write
	STATUS				mandatory
	DESCRIPTION "The numeric IP address"
	::= { ipNode29Entry 2 }

ipNode29AlarmPort			OBJECT-TYPE
	SYNTAX				INTEGER
	ACCESS				read-write
	STATUS				mandatory
	DESCRIPTION "The IP port to check for service"
	::= { ipNode29Entry 3 }

ipNode29AlarmIPvalid		OBJECT-TYPE
	SYNTAX				INTEGER { false(1), true(2) }
	ACCESS				read-only
	STATUS				mandatory
	DESCRIPTION "IP valid"
	::= { ipNode29Entry 4 }

ipNode29AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode29Entry 5 }

ipNode29AlarmLastResponse	OBJECT-TYPE
	SYNTAX				DisplayString
	ACCESS				read-only
	STATUS				mandatory
	DESCRIPTION "Last time that this IP device responsed"
	::= { ipNode29Entry 6 }

ipNode29AlarmDependency		OBJECT-TYPE
	SYNTAX				INTEGER
	ACCESS				read-write
	STATUS				mandatory
	DESCRIPTION "Other IP that this one is dependent upon (255 is none)"
	::= { ipNode29Entry 7 }

ipNode29AlarmRetries		OBJECT-TYPE
	SYNTAX				INTEGER
	ACCESS				read-write
	STATUS				mandatory
	DESCRIPTION "Number of time to retry this device before failing it"
	::= { ipNode29Entry 8 }

ipNode29AlarmTimeout		OBJECT-TYPE
	SYNTAX				INTEGER
	ACCESS				read-write
	STATUS				mandatory
	DESCRIPTION "Time in seconds to wait for a response"
	::= { ipNode29Entry 9 }

ipNode29AlarmResetTime		OBJECT-TYPE
	SYNTAX				INTEGER
	ACCESS				read-write
	STATUS				mandatory
	DESCRIPTION "A value &gt;= 30 mins enables feature, 0 disables"
	::= { ipNode29Entry 10 }

ipNode29AlarmAlarmOnRTN	OBJECT-TYPE
	SYNTAX		INTEGER {	false(1),true(2) }
	ACCESS				read-write
	STATUS				mandatory
	DESCRIPTION "Allow an alarm to occur when this device starts responding again"
	::= { ipNode29Entry 11 }

ipNode29AlarmInUse		OBJECT-TYPE
	SYNTAX		INTEGER { false(1),true(2) }
	ACCESS				read-write
	STATUS				mandatory
	DESCRIPTION "True if this IP alarm is active"
	::= { ipNode29Entry 12 }

ipNode29AlarmLastAlarm		OBJECT-TYPE
	SYNTAX				DisplayString
	ACCESS				read-only
	STATUS				mandatory
	DESCRIPTION "Timestamp of the last alarm"
	::= { ipNode29Entry 13 }

ipNode29AlarmLastAck		OBJECT-TYPE
	SYNTAX				DisplayString
	ACCESS				read-only
	STATUS				mandatory
	DESCRIPTION "Timestamp of the last alarm Ack"
	::= { ipNode29Entry 14 }

ipNode29AlarmName			OBJECT-TYPE
	SYNTAX				DisplayString
	ACCESS				read-write
	STATUS				mandatory
	DESCRIPTION "Reference name for this IP device"
	::= { ipNode29Entry 15 }

ipNode29AlarmClass		OBJECT-TYPE
	SYNTAX				INTEGER
	ACCESS				read-write
	STATUS				mandatory
	DESCRIPTION "Alarm class of IP (255 is none)"
	::= { ipNode29Entry 16 }

ipNode29AlarmEnable		OBJECT-TYPE
	SYNTAX		INTEGER { false(1),true(2) }
	ACCESS				read-only
	STATUS				mandatory
	DESCRIPTION "IP enabled by scheduler"
	::= { ipNode29Entry 17 }

ipNode29AlarmDatalog		OBJECT-TYPE
	SYNTAX		INTEGER { false(1),true(2) }
	ACCESS				read-write
	STATUS				mandatory
	DESCRIPTION "Datalog IP"
	::= { ipNode29Entry 18 }

ipNode29AlarmCustomVoice	OBJECT-TYPE
	SYNTAX				DisplayString
	ACCESS				read-write
	STATUS				mandatory
	DESCRIPTION "WAV file for the custom voice message"
	::= { ipNode29Entry 19 }

ipNode29AlarmAck		OBJECT-TYPE
	SYNTAX				INTEGER { false(1),true(2) }
	ACCESS				read-write
	STATUS				mandatory
	DESCRIPTION 	"Ack Alarm"
	::= { ipNode29Entry 20 }

ipNode30Table	OBJECT-TYPE
	SYNTAX	SEQUENCE OF	IpNode30Entry
	ACCESS not-accessible
	STATUS	mandatory
	DESCRIPTION
		"A List of IP entries"
	::= { node30IP	1 }

ipNode30Entry	OBJECT-TYPE
	SYNTAX IpNode30Entry
	ACCESS not-accessible
	STATUS	mandatory
	DESCRIPTION
		"An IP entry"
	INDEX { ipNode30Index }
	::= { ipNode30Table 1 }

IpNode30Entry ::=
	SEQUENCE {
		ipNode30Index
			INTEGER,
		ipNode30AlarmIPnum
			DisplayString,
		ipNode30AlarmPort
			INTEGER,
		ipNode30AlarmIPvalid
			INTEGER,
		ipNode30AlarmStatus
			INTEGER,
		ipNode30AlarmLastResponse
			DisplayString,
		ipNode30AlarmDependency
			INTEGER,
		ipNode30AlarmRetries
			INTEGER,
		ipNode30AlarmTimeout
			INTEGER,
		ipNode30AlarmResetTime
			INTEGER,
		ipNode30AlarmAlarmOnRTN
			INTEGER,
		ipNode30AlarmInUse
			INTEGER,
		ipNode30AlarmLastAlarm
			DisplayString,
		ipNode30AlarmLastAck
			DisplayString,
		ipNode30AlarmName
			DisplayString,
		ipNode30AlarmClass
			INTEGER,
		ipNode30AlarmEnable
			INTEGER,
		ipNode30AlarmDatalog
			INTEGER,
		ipNode30AlarmCustomVoice
			DisplayString,
		ipNode30AlarmAck
			INTEGER
	}

ipNode30Index					OBJECT-TYPE
	SYNTAX				INTEGER (1..64)
	ACCESS				read-write
	STATUS				mandatory
	DESCRIPTION "The index of the IP (1..64)"
	::= { ipNode30Entry 1 }

ipNode30AlarmIPnum		OBJECT-TYPE
	SYNTAX				DisplayString
	ACCESS				read-write
	STATUS				mandatory
	DESCRIPTION "The numeric IP address"
	::= { ipNode30Entry 2 }

ipNode30AlarmPort			OBJECT-TYPE
	SYNTAX				INTEGER
	ACCESS				read-write
	STATUS				mandatory
	DESCRIPTION "The IP port to check for service"
	::= { ipNode30Entry 3 }

ipNode30AlarmIPvalid		OBJECT-TYPE
	SYNTAX				INTEGER { false(1), true(2) }
	ACCESS				read-only
	STATUS				mandatory
	DESCRIPTION "IP valid"
	::= { ipNode30Entry 4 }

ipNode30AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode30Entry 5 }

ipNode30AlarmLastResponse	OBJECT-TYPE
	SYNTAX				DisplayString
	ACCESS				read-only
	STATUS				mandatory
	DESCRIPTION "Last time that this IP device responsed"
	::= { ipNode30Entry 6 }

ipNode30AlarmDependency		OBJECT-TYPE
	SYNTAX				INTEGER
	ACCESS				read-write
	STATUS				mandatory
	DESCRIPTION "Other IP that this one is dependent upon (255 is none)"
	::= { ipNode30Entry 7 }

ipNode30AlarmRetries		OBJECT-TYPE
	SYNTAX				INTEGER
	ACCESS				read-write
	STATUS				mandatory
	DESCRIPTION "Number of time to retry this device before failing it"
	::= { ipNode30Entry 8 }

ipNode30AlarmTimeout		OBJECT-TYPE
	SYNTAX				INTEGER
	ACCESS				read-write
	STATUS				mandatory
	DESCRIPTION "Time in seconds to wait for a response"
	::= { ipNode30Entry 9 }

ipNode30AlarmResetTime		OBJECT-TYPE
	SYNTAX				INTEGER
	ACCESS				read-write
	STATUS				mandatory
	DESCRIPTION "A value &gt;= 30 mins enables feature, 0 disables"
	::= { ipNode30Entry 10 }

ipNode30AlarmAlarmOnRTN	OBJECT-TYPE
	SYNTAX		INTEGER {	false(1),true(2) }
	ACCESS				read-write
	STATUS				mandatory
	DESCRIPTION "Allow an alarm to occur when this device starts responding again"
	::= { ipNode30Entry 11 }

ipNode30AlarmInUse		OBJECT-TYPE
	SYNTAX		INTEGER { false(1),true(2) }
	ACCESS				read-write
	STATUS				mandatory
	DESCRIPTION "IP alarm is active"
	::= { ipNode30Entry 12 }

ipNode30AlarmLastAlarm		OBJECT-TYPE
	SYNTAX				DisplayString
	ACCESS				read-only
	STATUS				mandatory
	DESCRIPTION "Timestamp of the last alarm"
	::= { ipNode30Entry 13 }

ipNode30AlarmLastAck		OBJECT-TYPE
	SYNTAX				DisplayString
	ACCESS				read-only
	STATUS				mandatory
	DESCRIPTION "Timestamp of the last alarm Ack"
	::= { ipNode30Entry 14 }

ipNode30AlarmName			OBJECT-TYPE
	SYNTAX				DisplayString
	ACCESS				read-write
	STATUS				mandatory
	DESCRIPTION "Reference name for this IP device"
	::= { ipNode30Entry 15 }

ipNode30AlarmClass		OBJECT-TYPE
	SYNTAX				INTEGER
	ACCESS				read-write
	STATUS				mandatory
	DESCRIPTION "Alarm class of IP (255 is none)"
	::= { ipNode30Entry 16 }

ipNode30AlarmEnable		OBJECT-TYPE
	SYNTAX		INTEGER { false(1),true(2) }
	ACCESS				read-only
	STATUS				mandatory
	DESCRIPTION "IP enabled by scheduler"
	::= { ipNode30Entry 17 }

ipNode30AlarmDatalog		OBJECT-TYPE
	SYNTAX		INTEGER { false(1),true(2) }
	ACCESS				read-write
	STATUS				mandatory
	DESCRIPTION "Datalog IP"
	::= { ipNode30Entry 18 }

ipNode30AlarmCustomVoice	OBJECT-TYPE
	SYNTAX				DisplayString
	ACCESS				read-write
	STATUS				mandatory
	DESCRIPTION "WAV file for the custom voice message"
	::= { ipNode30Entry 19 }

ipNode30AlarmAck		OBJECT-TYPE
	SYNTAX				INTEGER { false(1),true(2) }
	ACCESS				read-write
	STATUS				mandatory
	DESCRIPTION 	"Ack Alarm"
	::= { ipNode30Entry 20 }

ipNode32Table	OBJECT-TYPE
	SYNTAX	SEQUENCE OF	IpNode32Entry
	ACCESS not-accessible
	STATUS	mandatory
	DESCRIPTION
		"A List of IP entries"
	::= { node31IP	1 }

ipNode32Entry	OBJECT-TYPE
	SYNTAX IpNode32Entry
	ACCESS not-accessible
	STATUS	mandatory
	DESCRIPTION
		"An IP entry"
	INDEX { ipNode32Index }
	::= { ipNode32Table 1 }

IpNode32Entry ::=
	SEQUENCE {
		ipNode32Index
			INTEGER,
		ipNode32AlarmIPnum
			DisplayString,
		ipNode32AlarmPort
			INTEGER,
		ipNode32AlarmIPvalid
			INTEGER,
		ipNode32AlarmStatus
			INTEGER,
		ipNode32AlarmLastResponse
			DisplayString,
		ipNode32AlarmDependency
			INTEGER,
		ipNode32AlarmRetries
			INTEGER,
		ipNode32AlarmTimeout
			INTEGER,
		ipNode32AlarmResetTime
			INTEGER,
		ipNode32AlarmAlarmOnRTN
			INTEGER,
		ipNode32AlarmInUse
			INTEGER,
		ipNode32AlarmLastAlarm
			DisplayString,
		ipNode32AlarmLastAck
			DisplayString,
		ipNode32AlarmName
			DisplayString,
		ipNode32AlarmClass
			INTEGER,
		ipNode32AlarmEnable
			INTEGER,
		ipNode32AlarmDatalog
			INTEGER,
		ipNode32AlarmCustomVoice
			DisplayString,
		ipNode32AlarmAck
			INTEGER
	}

ipNode32Index					OBJECT-TYPE
	SYNTAX				INTEGER (1..64)
	ACCESS				read-write
	STATUS				mandatory
	DESCRIPTION "The index of the IP (1..64)"
	::= { ipNode32Entry 1 }

ipNode32AlarmIPnum		OBJECT-TYPE
	SYNTAX				DisplayString
	ACCESS				read-write
	STATUS				mandatory
	DESCRIPTION "The numeric IP address"
	::= { ipNode32Entry 2 }

ipNode32AlarmPort			OBJECT-TYPE
	SYNTAX				INTEGER
	ACCESS				read-write
	STATUS				mandatory
	DESCRIPTION "The IP port to check for service"
	::= { ipNode32Entry 3 }

ipNode32AlarmIPvalid		OBJECT-TYPE
	SYNTAX				INTEGER { false(1), true(2) }
	ACCESS				read-only
	STATUS				mandatory
	DESCRIPTION "IP valid"
	::= { ipNode32Entry 4 }

ipNode32AlarmStatus		OBJECT-TYPE
	SYNTAX				INTEGER	{
		ok(1),waiting(2),openSensorClosed(3),closedSensorOpened(4),
		low(5),high(6),pingTO(7),retToNorm(8),sensorTrouble(9),
		routeDown(10),nodeTrouble(11),pGTrouble(12)
	}
	ACCESS				read-only
	STATUS				mandatory
	DESCRIPTION "Alarm status code"
	::= { ipNode32Entry 5 }

ipNode32AlarmLastResponse	OBJECT-TYPE
	SYNTAX				DisplayString
	ACCESS				read-only
	STATUS				mandatory
	DESCRIPTION "Last time that this IP device responsed"
	::= { ipNode32Entry 6 }

ipNode32AlarmDependency		OBJECT-TYPE
	SYNTAX				INTEGER
	ACCESS				read-write
	STATUS				mandatory
	DESCRIPTION "Other IP that this one is dependent upon (255 is none)"
	::= { ipNode32Entry 7 }

ipNode32AlarmRetries		OBJECT-TYPE
	SYNTAX				INTEGER
	ACCESS				read-write
	STATUS				mandatory
	DESCRIPTION "Number of time to retry this device before failing it"
	::= { ipNode32Entry 8 }

ipNode32AlarmTimeout		OBJECT-TYPE
	SYNTAX				INTEGER
	ACCESS				read-write
	STATUS				mandatory
	DESCRIPTION "Time in seconds to wait for a response"
	::= { ipNode32Entry 9 }

ipNode32AlarmResetTime		OBJECT-TYPE
	SYNTAX				INTEGER
	ACCESS				read-write
	STATUS				mandatory
	DESCRIPTION "A value &gt;= 30 mins enables feature, 0 disables"
	::= { ipNode32Entry 10 }

ipNode32AlarmAlarmOnRTN	OBJECT-TYPE
	SYNTAX		INTEGER {	false(1),true(2) }
	ACCESS				read-write
	STATUS				mandatory
	DESCRIPTION "Allow an alarm to occur when this device starts responding again"
	::= { ipNode32Entry 11 }

ipNode32AlarmInUse		OBJECT-TYPE
	SYNTAX		INTEGER { false(1),true(2) }
	ACCESS				read-write
	STATUS				mandatory
	DESCRIPTION "IP alarm is active"
	::= { ipNode32Entry 12 }

ipNode32AlarmLastAlarm		OBJECT-TYPE
	SYNTAX				DisplayString
	ACCESS				read-only
	STATUS				mandatory
	DESCRIPTION "Timestamp of the last alarm"
	::= { ipNode32Entry 13 }

ipNode32AlarmLastAck		OBJECT-TYPE
	SYNTAX				DisplayString
	ACCESS				read-only
	STATUS				mandatory
	DESCRIPTION "Timestamp of the last alarm Ack"
	::= { ipNode32Entry 14 }

ipNode32AlarmName			OBJECT-TYPE
	SYNTAX				DisplayString
	ACCESS				read-write
	STATUS				mandatory
	DESCRIPTION "Reference name for this IP device"
	::= { ipNode32Entry 15 }

ipNode32AlarmClass		OBJECT-TYPE
	SYNTAX				INTEGER
	ACCESS				read-write
	STATUS				mandatory
	DESCRIPTION "Alarm class of IP (255 is none)"
	::= { ipNode32Entry 16 }

ipNode32AlarmEnable		OBJECT-TYPE
	SYNTAX		INTEGER { false(1),true(2) }
	ACCESS				read-only
	STATUS				mandatory
	DESCRIPTION "IP enabled by scheduler"
	::= { ipNode32Entry 17 }

ipNode32AlarmDatalog		OBJECT-TYPE
	SYNTAX		INTEGER { false(1),true(2) }
	ACCESS				read-write
	STATUS				mandatory
	DESCRIPTION "Datalog IP"
	::= { ipNode32Entry 18 }

ipNode32AlarmCustomVoice	OBJECT-TYPE
	SYNTAX				DisplayString
	ACCESS				read-write
	STATUS				mandatory
	DESCRIPTION "WAV file for the custom voice message"
	::= { ipNode32Entry 19 }

ipNode32AlarmAck		OBJECT-TYPE
	SYNTAX				INTEGER { false(1),true(2) }
	ACCESS				read-write
	STATUS				mandatory
	DESCRIPTION 	"Ack Alarm"
	::= { ipNode32Entry 20 }

-- System

sysTime					OBJECT-TYPE
	SYNTAX				DisplayString
	ACCESS				read-only
	STATUS				mandatory
	DESCRIPTION		"System time"
	::= { hostSystem 1}

sysEnterpriseName			OBJECT-TYPE
	SYNTAX				DisplayString
	ACCESS				read-only
	STATUS				mandatory
	DESCRIPTION		"EnterpriseName"
	::= { hostSystem 2}

sysMask			OBJECT-TYPE
	SYNTAX				DisplayString
	ACCESS				read-only
	STATUS				mandatory
	DESCRIPTION		"Network IP mask"
	::= { hostSystem 3}

sysGateway	OBJECT-TYPE
	SYNTAX				DisplayString
	ACCESS				read-only
	STATUS				mandatory
	DESCRIPTION		"Network gateway"
	::= { hostSystem 4}

sysDNS			OBJECT-TYPE
	SYNTAX				DisplayString
	ACCESS				read-only
	STATUS				mandatory
	DESCRIPTION		"Network domain server"
	::= { hostSystem 5}

sysPOP			OBJECT-TYPE
	SYNTAX				DisplayString
	ACCESS				read-write
	STATUS				mandatory
	DESCRIPTION		"Incoming Email server"
	::= { hostSystem 6}

sysSMTP			OBJECT-TYPE
	SYNTAX				DisplayString
	ACCESS				read-write
	STATUS				mandatory
	DESCRIPTION		"Outgoing Email server"
	::= { hostSystem 7}

sysSMTPUsername			OBJECT-TYPE
	SYNTAX				DisplayString
	ACCESS				read-write
	STATUS				mandatory
	DESCRIPTION		"SMTP Email username"
	::= { hostSystem 8}

sysSMTPpassword			OBJECT-TYPE
	SYNTAX				DisplayString
	ACCESS				read-write
	STATUS				mandatory
	DESCRIPTION		"SMTP Email password"
	::= { hostSystem 9}

sysPOPUsername			OBJECT-TYPE
	SYNTAX				DisplayString
	ACCESS				read-write
	STATUS				mandatory
	DESCRIPTION		"POP Email username"
	::= { hostSystem 10}

sysPOPpassword			OBJECT-TYPE
	SYNTAX				DisplayString
	ACCESS				read-write
	STATUS				mandatory
	DESCRIPTION		"POP Email password"
	::= { hostSystem 11}

sysMailReturn			OBJECT-TYPE
	SYNTAX				DisplayString
	ACCESS				read-write
	STATUS				mandatory
	DESCRIPTION		"SMTP return address"
	::= { hostSystem 12}

sysNumericID			OBJECT-TYPE
	SYNTAX				DisplayString
	ACCESS				read-write
	STATUS				mandatory
	DESCRIPTION		"Numeric Unit ID"
	::= { hostSystem 13}

sysTimeServer			OBJECT-TYPE
	SYNTAX				DisplayString
	ACCESS				read-write
	STATUS				mandatory
	DESCRIPTION		"Internet time server"
	::= { hostSystem 14}

sysMailCheck			OBJECT-TYPE
	SYNTAX				INTEGER
	ACCESS				read-write
	STATUS				mandatory
	DESCRIPTION		"POP Interval check"
	::= { hostSystem 15}

sysPagerSpeed			OBJECT-TYPE
	SYNTAX				INTEGER { ps1200(1), ps2400(2) }
	ACCESS				read-write
	STATUS				mandatory
	DESCRIPTION		"Alphnum pager speed"
	::= { hostSystem 16}

sysWebFTPenable	OBJECT-TYPE
	SYNTAX				INTEGER { false(1) , true(2) }
	ACCESS				read-write
	STATUS				mandatory
	DESCRIPTION		"Enable FTP delivery of web pages"
	::= { hostSystem 17}

sysCheckForDialtone			OBJECT-TYPE
	SYNTAX				INTEGER { true(1), false(2) }
	ACCESS				read-write
	STATUS				mandatory
	DESCRIPTION		"Check for Dialtone"
	::= { hostSystem 18}

sysRingsToAns			OBJECT-TYPE
	SYNTAX				INTEGER
	ACCESS				read-write
	STATUS				mandatory
	DESCRIPTION		"Rings to answer"
	::= { hostSystem 19}

sysPhoneAttempts			OBJECT-TYPE
	SYNTAX				INTEGER (1..10)
	ACCESS				read-write
	STATUS				mandatory
	DESCRIPTION		"PhoneAttempts"
	::= { hostSystem 20}

sysWebFTPtime		OBJECT-TYPE
	SYNTAX				INTEGER
	ACCESS				read-write
	STATUS				mandatory
	DESCRIPTION		"Web FTP time"
	::= { hostSystem 21}

sysWebFTPHost		OBJECT-TYPE
	SYNTAX				DisplayString
	ACCESS				read-write
	STATUS				mandatory
	DESCRIPTION		"Web FTP host"
	::= { hostSystem 22}

sysWebFTPusername		OBJECT-TYPE
	SYNTAX				DisplayString
	ACCESS				read-write
	STATUS				mandatory
	DESCRIPTION		"Web FTP username"
	::= { hostSystem 23}

sysWebFTPpassword		OBJECT-TYPE
	SYNTAX				DisplayString
	ACCESS				read-write
	STATUS				mandatory
	DESCRIPTION		"Web FTP password"
	::= { hostSystem 24}

sysWebFTPfolder		OBJECT-TYPE
	SYNTAX				DisplayString
	ACCESS				read-write
	STATUS				mandatory
	DESCRIPTION		"Web FTP folder"
	::= { hostSystem 25}

sysWebFTPhtmlfile		OBJECT-TYPE
	SYNTAX				DisplayString
	ACCESS				read-write
	STATUS				mandatory
	DESCRIPTION		"Web FTP html file"
	::= { hostSystem 26}

sysWebFTPwmlfile		OBJECT-TYPE
	SYNTAX				DisplayString
	ACCESS				read-write
	STATUS				mandatory
	DESCRIPTION		"Web FTP wml file"
	::= { hostSystem 27}

sysWebrefresh		OBJECT-TYPE
	SYNTAX				INTEGER
	ACCESS				read-write
	STATUS				mandatory
	DESCRIPTION		"Web refresh time (minutes)"
	::= { hostSystem 28}


-- Security

secEnableWeb			OBJECT-TYPE
	SYNTAX				INTEGER { false(1) , true(2) }
	ACCESS				read-only
	STATUS				mandatory
	DESCRIPTION		"Enable Web access"
	::= { hostSecurity 1}

secWebPassword	OBJECT-TYPE
	SYNTAX				INTEGER { false(1) , true(2) }
	ACCESS				read-only
	STATUS				mandatory
	DESCRIPTION		"Enable Web password"
	::= { hostSecurity 2}

secEnableListen	OBJECT-TYPE
	SYNTAX				INTEGER { false(1) , true(2) }
	ACCESS				read-only
	STATUS				mandatory
	DESCRIPTION		"Enable voice listen"
	::= { hostSecurity 3}

secEnableRAS		OBJECT-TYPE
	SYNTAX				INTEGER { false(1) , true(2) }
	ACCESS				read-only
	STATUS				mandatory
	DESCRIPTION		"Enable RAS"
	::= { hostSecurity 4}

secEnable2Way		OBJECT-TYPE
	SYNTAX				INTEGER { false(1) , true(2) }
	ACCESS				read-only
	STATUS				mandatory
	DESCRIPTION		"Enable 2 way email"
	::= { hostSecurity 5}

secEnableDatamodem			OBJECT-TYPE
	SYNTAX				INTEGER { false(1) , true(2) }
	ACCESS				read-only
	STATUS				mandatory
	DESCRIPTION		"Enable datamodem"
	::= { hostSecurity 6}

secRASip			OBJECT-TYPE
	SYNTAX				DisplayString
	ACCESS				read-only
	STATUS				mandatory
	DESCRIPTION		"RAS ip"
	::= { hostSecurity 7}

secWebProg			OBJECT-TYPE
	SYNTAX				INTEGER { false(1) , true(2) }
	ACCESS				read-only
	STATUS				mandatory
	DESCRIPTION		"Enable Web programming"
	::= { hostSecurity 8}

secWebProgPass			OBJECT-TYPE
	SYNTAX				INTEGER { false(1) , true(2) }
	ACCESS				read-only
	STATUS				mandatory
	DESCRIPTION		"Enable Web programming password"
	::= { hostSecurity 9}


-- Profile table

proTable	OBJECT-TYPE
	SYNTAX  SEQUENCE OF ProEntry
	ACCESS  not-accessible
	STATUS  mandatory
  DESCRIPTION	"A list of Profile entries"
  ::= { hostProfiles 1 }

proEntry OBJECT-TYPE
	SYNTAX  ProEntry
	ACCESS  not-accessible
	STATUS  mandatory
	DESCRIPTION	"A Profile entry"
	INDEX   {proIndex }
	::= { proTable 1 }

ProEntry ::=
	SEQUENCE {
		proIndex
			INTEGER,
		proName
			DisplayString,
		proCompany
			DisplayString,
		proDepartment
			DisplayString,
		proTitle
			DisplayString,
		proUsername
			DisplayString,
		proPassword
			DisplayString,
		proAckcode
			DisplayString,
		proPPP
			INTEGER,
		proInUse
			INTEGER,
		proValid
			INTEGER,
		proCon1Name
			DisplayString,
		proCon1Dest
			DisplayString,
		proCon1Type
			INTEGER,
		proCon1Enable
			INTEGER,
		proCon1Ack
			INTEGER,
		proCon1Inform
			INTEGER,
		proCon2Name
			DisplayString,
		proCon2Dest
			DisplayString,
		proCon2Type
			INTEGER,
		proCon2Enable
			INTEGER,
		proCon2Ack
			INTEGER,
		proCon2Inform
			INTEGER,
		proCon3Name
			DisplayString,
		proCon3Dest
			DisplayString,
		proCon3Type
			INTEGER,
		proCon3Enable
			INTEGER,
		proCon3Ack
			INTEGER,
		proCon3Inform
			INTEGER,
		proCon4Name
			DisplayString,
		proCon4Dest
			DisplayString,
		proCon4Type
			INTEGER,
		proCon4Enable
			INTEGER,
		proCon4Ack
			INTEGER,
		proCon4Inform
			INTEGER,
		proCon5Name
			DisplayString,
		proCon5Dest
			DisplayString,
		proCon5Type
			INTEGER,
		proCon5Enable
			INTEGER,
		proCon5Ack
			INTEGER,
		proCon5Inform
			INTEGER,
		proCon6Name
			DisplayString,
		proCon6Dest
			DisplayString,
		proCon6Type
			INTEGER,
		proCon6Enable
			INTEGER,
		proCon6Ack
			INTEGER,
		proCon6Inform
			INTEGER,
		proCon7Name
			DisplayString,
		proCon7Dest
			DisplayString,
		proCon7Type
			INTEGER,
		proCon7Enable
			INTEGER,
		proCon7Ack
			INTEGER,
		proCon7Inform
			INTEGER,
		proCon8Name
			DisplayString,
		proCon8Dest
			DisplayString,
		proCon8Type
			INTEGER,
		proCon8Enable
			INTEGER,
		proCon8Ack
			INTEGER,
		proCon8Inform
			INTEGER
	}

proIndex OBJECT-TYPE
	SYNTAX  INTEGER(1..64)
	ACCESS  read-only
	STATUS  mandatory
	DESCRIPTION	"The index of the Profile (1..64)"
	::= { proEntry 1 }

proName					OBJECT-TYPE
	SYNTAX				DisplayString
	ACCESS				read-write
	STATUS				mandatory
	DESCRIPTION		"Name"
	::= { proEntry 2}

proCompany			OBJECT-TYPE
	SYNTAX				DisplayString
	ACCESS				read-write
	STATUS				mandatory
	DESCRIPTION		"Company"
	::= { proEntry 3}

proDepartment		OBJECT-TYPE
	SYNTAX				DisplayString
	ACCESS				read-write
	STATUS				mandatory
	DESCRIPTION		"Department"
	::= { proEntry 4}

proTitle				OBJECT-TYPE
	SYNTAX				DisplayString
	ACCESS				read-write
	STATUS				mandatory
	DESCRIPTION		"Title"
	::= { proEntry 5}

proUsername			OBJECT-TYPE
	SYNTAX				DisplayString
	ACCESS				read-write
	STATUS				mandatory
	DESCRIPTION		"Username"
	::= { proEntry 6}

proPassword			OBJECT-TYPE
	SYNTAX				DisplayString
	ACCESS				read-write
	STATUS				mandatory
	DESCRIPTION		"Password"
	::= { proEntry 7}

proAckcode			OBJECT-TYPE
	SYNTAX				DisplayString
	ACCESS				read-write
	STATUS				mandatory
	DESCRIPTION		"Ack code"
	::= { proEntry 8}

proPPP					OBJECT-TYPE
	SYNTAX				INTEGER { false(1), true(2) }
	ACCESS				read-write
	STATUS				mandatory
	DESCRIPTION		"Enable PPP"
	::= { proEntry 9}

proInUse				OBJECT-TYPE
	SYNTAX				INTEGER { false(1), true(2) }
	ACCESS				read-write
	STATUS				mandatory
	DESCRIPTION		"In use"
	::= { proEntry 10}

proValid				OBJECT-TYPE
	SYNTAX				INTEGER { false(1), true(2) }
	ACCESS				read-only
	STATUS				mandatory
	DESCRIPTION		"Valid"
	::= { proEntry 11}

proCon1Name	OBJECT-TYPE
	SYNTAX				DisplayString
	ACCESS				read-write
	STATUS				mandatory
	DESCRIPTION		"Name"
	::= { proEntry 12}

proCon1Dest	OBJECT-TYPE
	SYNTAX				DisplayString
	ACCESS				read-write
	STATUS				mandatory
	DESCRIPTION		"Destination"
	::= { proEntry 13}

proCon1Type	OBJECT-TYPE
	SYNTAX				INTEGER	{	voice(1),numPage(2),alNumPage(3),
													fax(4),smtp(5),snmp(6) }
	ACCESS				read-write
	STATUS				mandatory
	DESCRIPTION		"Type"
	::= { proEntry 14}

proCon1Enable	OBJECT-TYPE
	SYNTAX				INTEGER	{	false(1), true(2) }
	ACCESS				read-only
	STATUS				mandatory
	DESCRIPTION		"Enable"
	::= { proEntry 15}

proCon1Ack	OBJECT-TYPE
	SYNTAX				INTEGER	{	false(1), true(2) }
	ACCESS				read-write
	STATUS				mandatory
	DESCRIPTION		"Ack"
	::= { proEntry 16}

proCon1Inform	OBJECT-TYPE
	SYNTAX				INTEGER	{	false(1), true(2) }
	ACCESS				read-write
	STATUS				mandatory
	DESCRIPTION		"Inform"
	::= { proEntry 17}

proCon2Name	OBJECT-TYPE
	SYNTAX				DisplayString
	ACCESS				read-write
	STATUS				mandatory
	DESCRIPTION		"Name"
	::= { proEntry 18}

proCon2Dest	OBJECT-TYPE
	SYNTAX				DisplayString
	ACCESS				read-write
	STATUS				mandatory
	DESCRIPTION		"Destination"
	::= { proEntry 19}

proCon2Type	OBJECT-TYPE
	SYNTAX				INTEGER	{	voice(1),numPage(2),alNumPage(3),
													fax(4),smtp(5),snmp(6) }
	ACCESS				read-write
	STATUS				mandatory
	DESCRIPTION		"Type"
	::= { proEntry 20}

proCon2Enable	OBJECT-TYPE
	SYNTAX				INTEGER	{	false(1), true(2) }
	ACCESS				read-only
	STATUS				mandatory
	DESCRIPTION		"Enable"
	::= { proEntry 21}

proCon2Ack	OBJECT-TYPE
	SYNTAX				INTEGER	{	false(1), true(2) }
	ACCESS				read-write
	STATUS				mandatory
	DESCRIPTION		"Ack"
	::= { proEntry 22}

proCon2Inform	OBJECT-TYPE
	SYNTAX				INTEGER	{	false(1), true(2) }
	ACCESS				read-write
	STATUS				mandatory
	DESCRIPTION		"Inform"
	::= { proEntry 23}


proCon3Name	OBJECT-TYPE
	SYNTAX				DisplayString
	ACCESS				read-write
	STATUS				mandatory
	DESCRIPTION		"Name"
	::= { proEntry 24}

proCon3Dest	OBJECT-TYPE
	SYNTAX				DisplayString
	ACCESS				read-write
	STATUS				mandatory
	DESCRIPTION		"Destination"
	::= { proEntry 25}

proCon3Type	OBJECT-TYPE
	SYNTAX				INTEGER	{	voice(1),numPage(2),alNumPage(3),
													fax(4),smtp(5),snmp(6) }
	ACCESS				read-write
	STATUS				mandatory
	DESCRIPTION		"Type"
	::= { proEntry 26}

proCon3Enable	OBJECT-TYPE
	SYNTAX				INTEGER	{	false(1), true(2) }
	ACCESS				read-only
	STATUS				mandatory
	DESCRIPTION		"Enable"
	::= { proEntry 27}

proCon3Ack	OBJECT-TYPE
	SYNTAX				INTEGER	{	false(1), true(2) }
	ACCESS				read-write
	STATUS				mandatory
	DESCRIPTION		"Ack"
	::= { proEntry 28}

proCon3Inform	OBJECT-TYPE
	SYNTAX				INTEGER	{	false(1), true(2) }
	ACCESS				read-write
	STATUS				mandatory
	DESCRIPTION		"Inform"
	::= { proEntry 29}

proCon4Name	OBJECT-TYPE
	SYNTAX				DisplayString
	ACCESS				read-write
	STATUS				mandatory
	DESCRIPTION		"Name"
	::= { proEntry 30}

proCon4Dest	OBJECT-TYPE
	SYNTAX				DisplayString
	ACCESS				read-write
	STATUS				mandatory
	DESCRIPTION		"Destination"
	::= { proEntry 31}

proCon4Type	OBJECT-TYPE
	SYNTAX				INTEGER	{	voice(1),numPage(2),alNumPage(3),
													fax(4),smtp(5),snmp(6) }
	ACCESS				read-write
	STATUS				mandatory
	DESCRIPTION		"Type"
	::= { proEntry 32}

proCon4Enable	OBJECT-TYPE
	SYNTAX				INTEGER	{	false(1), true(2) }
	ACCESS				read-only
	STATUS				mandatory
	DESCRIPTION		"Enable"
	::= { proEntry 33}

proCon4Ack	OBJECT-TYPE
	SYNTAX				INTEGER	{	false(1), true(2) }
	ACCESS				read-write
	STATUS				mandatory
	DESCRIPTION		"Ack"
	::= { proEntry 34}

proCon4Inform	OBJECT-TYPE
	SYNTAX				INTEGER	{	false(1), true(2) }
	ACCESS				read-write
	STATUS				mandatory
	DESCRIPTION		"Inform"
	::= { proEntry 35}

proCon5Name	OBJECT-TYPE
	SYNTAX				DisplayString
	ACCESS				read-write
	STATUS				mandatory
	DESCRIPTION		"Name"
	::= { proEntry 36}

proCon5Dest	OBJECT-TYPE
	SYNTAX				DisplayString
	ACCESS				read-write
	STATUS				mandatory
	DESCRIPTION		"Destination"
	::= { proEntry 37}

proCon5Type	OBJECT-TYPE
	SYNTAX				INTEGER	{	voice(1),numPage(2),alNumPage(3),
													fax(4),smtp(5),snmp(6) }
	ACCESS				read-write
	STATUS				mandatory
	DESCRIPTION		"Type"
	::= { proEntry 38}

proCon5Enable	OBJECT-TYPE
	SYNTAX				INTEGER	{	false(1), true(2) }
	ACCESS				read-only
	STATUS				mandatory
	DESCRIPTION		"Enable"
	::= { proEntry 39}

proCon5Ack	OBJECT-TYPE
	SYNTAX				INTEGER	{	false(1), true(2) }
	ACCESS				read-write
	STATUS				mandatory
	DESCRIPTION		"Ack"
	::= { proEntry 40}

proCon5Inform	OBJECT-TYPE
	SYNTAX				INTEGER	{	false(1), true(2) }
	ACCESS				read-write
	STATUS				mandatory
	DESCRIPTION		"Inform"
	::= { proEntry 41}

proCon6Name	OBJECT-TYPE
	SYNTAX				DisplayString
	ACCESS				read-write
	STATUS				mandatory
	DESCRIPTION		"Name"
	::= { proEntry 42}

proCon6Dest	OBJECT-TYPE
	SYNTAX				DisplayString
	ACCESS				read-write
	STATUS				mandatory
	DESCRIPTION		"Destination"
	::= { proEntry 43}

proCon6Type	OBJECT-TYPE
	SYNTAX				INTEGER	{	voice(1),numPage(2),alNumPage(3),
													fax(4),smtp(5),snmp(6) }
	ACCESS				read-write
	STATUS				mandatory
	DESCRIPTION		"Type"
	::= { proEntry 44}

proCon6Enable	OBJECT-TYPE
	SYNTAX				INTEGER	{	false(1), true(2) }
	ACCESS				read-only
	STATUS				mandatory
	DESCRIPTION		"Enable"
	::= { proEntry 45}

proCon6Ack	OBJECT-TYPE
	SYNTAX				INTEGER	{	false(1), true(2) }
	ACCESS				read-write
	STATUS				mandatory
	DESCRIPTION		"Ack"
	::= { proEntry 46}

proCon6Inform	OBJECT-TYPE
	SYNTAX				INTEGER	{	false(1), true(2) }
	ACCESS				read-write
	STATUS				mandatory
	DESCRIPTION		"Inform"
	::= { proEntry 47}

proCon7Name	OBJECT-TYPE
	SYNTAX				DisplayString
	ACCESS				read-write
	STATUS				mandatory
	DESCRIPTION		"Name"
	::= { proEntry 48}

proCon7Dest	OBJECT-TYPE
	SYNTAX				DisplayString
	ACCESS				read-write
	STATUS				mandatory
	DESCRIPTION		"Destination"
	::= { proEntry 49}

proCon7Type	OBJECT-TYPE
	SYNTAX				INTEGER	{	voice(1),numPage(2),alNumPage(3),
													fax(4),smtp(5),snmp(6) }
	ACCESS				read-write
	STATUS				mandatory
	DESCRIPTION		"Type"
	::= { proEntry 50}

proCon7Enable	OBJECT-TYPE
	SYNTAX				INTEGER	{	false(1), true(2) }
	ACCESS				read-only
	STATUS				mandatory
	DESCRIPTION		"Enable"
	::= { proEntry 51}

proCon7Ack	OBJECT-TYPE
	SYNTAX				INTEGER	{	false(1), true(2) }
	ACCESS				read-write
	STATUS				mandatory
	DESCRIPTION		"Ack"
	::= { proEntry 52}

proCon7Inform	OBJECT-TYPE
	SYNTAX				INTEGER	{	false(1), true(2) }
	ACCESS				read-write
	STATUS				mandatory
	DESCRIPTION		"Inform"
	::= { proEntry 53}

proCon8Name	OBJECT-TYPE
	SYNTAX				DisplayString
	ACCESS				read-write
	STATUS				mandatory
	DESCRIPTION		"Name"
	::= { proEntry 54}

proCon8Dest	OBJECT-TYPE
	SYNTAX				DisplayString
	ACCESS				read-write
	STATUS				mandatory
	DESCRIPTION		"Destination"
	::= { proEntry 55}

proCon8Type	OBJECT-TYPE
	SYNTAX				INTEGER	{	voice(1),numPage(2),alNumPage(3),
													fax(4),smtp(5),snmp(6) }
	ACCESS				read-write
	STATUS				mandatory
	DESCRIPTION		"Type"
	::= { proEntry 56}

proCon8Enable	OBJECT-TYPE
	SYNTAX				INTEGER	{	false(1), true(2) }
	ACCESS				read-only
	STATUS				mandatory
	DESCRIPTION		"Enable"
	::= { proEntry 57}

proCon8Ack	OBJECT-TYPE
	SYNTAX				INTEGER	{	false(1), true(2) }
	ACCESS				read-write
	STATUS				mandatory
	DESCRIPTION		"Ack"
	::= { proEntry 58}

proCon8Inform	OBJECT-TYPE
	SYNTAX				INTEGER	{	false(1), true(2) }
	ACCESS				read-write
	STATUS				mandatory
	DESCRIPTION		"Inform"
	::= { proEntry 59}

--	Class Tables

clsTable	OBJECT-TYPE
	SYNTAX  SEQUENCE OF ClsEntry
	ACCESS  not-accessible
	STATUS  mandatory
  DESCRIPTION	"A list of Class Names"
  ::= { hostClasses 1 }

clsEntry 	OBJECT-TYPE
	SYNTAX  ClsEntry
	ACCESS  not-accessible
	STATUS  mandatory
	DESCRIPTION	"A Class Name entry"
	INDEX   {clsIndex }
	::= { clsTable 1 }

ClsEntry ::=
	SEQUENCE {
		clsIndex
			INTEGER,
		clsName
			DisplayString
	}

clsIndex 	OBJECT-TYPE
	SYNTAX  INTEGER(1..64)
	ACCESS  read-only
	STATUS  mandatory
	DESCRIPTION	"Index of Class Names (1..64)"
	::= { clsEntry 1 }

clsName					OBJECT-TYPE
	SYNTAX				DisplayString
	ACCESS				read-write
	STATUS				mandatory
	DESCRIPTION		"Valid for index (or instance) 1..63"
	::= { clsEntry	2 }


-- Input Templates table

tmpTable	OBJECT-TYPE
	SYNTAX  SEQUENCE OF TmpEntry
	ACCESS  not-accessible
	STATUS  mandatory
  DESCRIPTION	"A list of Input Templates"
  ::= { hostTemplates 1 }

tmpEntry OBJECT-TYPE
	SYNTAX  TmpEntry
	ACCESS  not-accessible
	STATUS  mandatory
	DESCRIPTION	"An Input Template entry"
	INDEX   {tmpIndex }
	::= { tmpTable 1 }

TmpEntry ::=
	SEQUENCE {
		tmpIndex
			INTEGER,
		tmpCalibration
			INTEGER,
		tmpAlarmLow
			INTEGER,
		tmpAlarmHigh
			INTEGER,
		tmpRecTime
			INTEGER,
		tmpResetTime
			INTEGER,
		tmpName
			DisplayString,
		tmpCustVoice
			DisplayString,
		tmpAlarmOnRTN
			INTEGER,
		tmpIOClass
			DisplayString,
		tmpDatalog
			INTEGER
	}

tmpIndex OBJECT-TYPE
	SYNTAX  INTEGER(1..15)
	ACCESS  read-only
	STATUS  mandatory
	DESCRIPTION	"The index of the Input Template (1..15)"
	::= { tmpEntry 1 }

tmpCalibration	OBJECT-TYPE
	SYNTAX				INTEGER
	ACCESS				read-write
	STATUS				mandatory
	DESCRIPTION		"Input template calibration
 1-TempF 2-TempC 3-Humidity 4-Water 5-Ext Power
 6-NC 7 NO 8-Smoke 9-Motion 10-Humidity W/Disp
 11-TempF W/Disp 12 TempC W/Disp 13- 4-20ma Trans"
	::= { tmpEntry 2 }

tmpAlarmLow		OBJECT-TYPE
	SYNTAX				INTEGER
	ACCESS				read-write
	STATUS				mandatory
	DESCRIPTION		"Input template alarm low
 1-TempF 2-TempC 3-Humidity 4-Water 5-Ext Power
 6-NC 7 NO 8-Smoke 9-Motion  10-Humidity W/Disp
 11-TempF W/Disp 12 TempC W/Disp 13- 4-20ma Trans"
	::= { tmpEntry 3 }

tmpAlarmHigh		OBJECT-TYPE
	SYNTAX				INTEGER
	ACCESS				read-write
	STATUS				mandatory
	DESCRIPTION		"Input template alarm high
 1-TempF 2-TempC 3-Humidity 4-Water 5-Ext Power
 6-NC 7 NO 8-Smoke 9-Motion 10-Humidity W/Disp
 11-TempF W/Disp 12 TempC W/Disp 13- 4-20ma Trans"
	::= { tmpEntry 4 }

tmpRecTime			OBJECT-TYPE
	SYNTAX				INTEGER
	ACCESS				read-write
	STATUS				mandatory
	DESCRIPTION		"Input template recogntion time
 1-TempF 2-TempC 3-Humidity 4-Water 5-Ext Power
 6-NC 7 NO 8-Smoke 9-Motion 10-Humidity W/Disp
 11-TempF W/Disp 12 TempC W/Disp 13- 4-20ma Trans"
	::= { tmpEntry 5 }

tmpResetTime		OBJECT-TYPE
	SYNTAX				INTEGER
	ACCESS				read-write
	STATUS				mandatory
	DESCRIPTION		"Input template reset time
 1-TempF 2-TempC 3-Humidity 4-Water 5-Ext Power
 6-NC 7 NO 8-Smoke 9-Motion 10-Humidity W/Disp
 11-TempF W/Disp 12 TempC W/Disp 13- 4-20ma Trans"
	::= { tmpEntry 6 }

tmpName				OBJECT-TYPE
	SYNTAX				DisplayString
	ACCESS				read-write
	STATUS				mandatory
	DESCRIPTION		"Input template name
 1-TempF 2-TempC 3-Humidity 4-Water 5-Ext Power
 6-NC 7 NO 8-Smoke 9-Motion 10-Humidity W/Disp
 11-TempF W/Disp 12 TempC W/Disp 13- 4-20ma Trans"
	::= { tmpEntry 7 }

tmpCustVoice		OBJECT-TYPE
	SYNTAX				DisplayString
	ACCESS				read-write
	STATUS				mandatory
	DESCRIPTION		"Input template custom voice
 1-TempF 2-TempC 3-Humidity 4-Water 5-Ext Power
 6-NC 7 NO 8-Smoke 9-Motion 10-Humidity W/Disp
 11-TempF W/Disp 12 TempC W/Disp 13- 4-20ma Trans"
	::= { tmpEntry 8 }

tmpIOClass				OBJECT-TYPE
	SYNTAX					DisplayString
	ACCESS					read-only
	STATUS					mandatory
	DESCRIPTION			"Input template IO class
 1-TempF 2-TempC 3-Humidity 4-Water 5-Ext Power
 6-NC 7 NO 8-Smoke 9-Motion 10-Humidity W/Disp
 11-TempF W/Disp 12 TempC W/Disp 13- 4-20ma Trans"
	::= { tmpEntry 9 }

tmpAlarmOnRTN	OBJECT-TYPE
	SYNTAX					INTEGER { false(1), true(2) }
	ACCESS					read-write
	STATUS					mandatory
	DESCRIPTION			"Input template alarm on return to normal
 1-TempF 2-TempC 3-Humidity 4-Water 5-Ext Power
 6-NC 7 NO 8-Smoke 9-Motion 10-Humidity W/Disp
 11-TempF W/Disp 12 TempC W/Disp 13- 4-20ma Trans"
	::= { tmpEntry 10 }

tmpDatalog				OBJECT-TYPE
	SYNTAX					INTEGER { false(1), true(2) }
	ACCESS					read-write
	STATUS					mandatory
	DESCRIPTION			"Datalog Input template
 1-TempF 2-TempC 3-Humidity 4-Water 5-Ext Power
 6-NC 7 NO 8-Smoke 9-Motion 10-Humidity W/Disp
 11-TempF W/Disp 12 TempC W/Disp 13- 4-20ma Trans"
	::= { tmpEntry 11 }



--	Camera table

cmTable	OBJECT-TYPE
	SYNTAX  SEQUENCE OF CmEntry
	ACCESS  not-accessible
	STATUS  mandatory
  DESCRIPTION	"A list of Cameras"
  ::= { hostCameras 1 }

cmEntry OBJECT-TYPE
	SYNTAX  CmEntry
	ACCESS  not-accessible
	STATUS  mandatory
	DESCRIPTION	"A Camera entry"
	INDEX   {cmIndex }
	::= { cmTable 1 }

CmEntry ::=
	SEQUENCE {
		cmIndex
			INTEGER,
		cmType
			INTEGER,
		cmPort
			INTEGER,
		cmIP
			DisplayString,
		cmName
			DisplayString
	}

cmIndex OBJECT-TYPE
	SYNTAX  INTEGER(1..128)
	ACCESS  read-only
	STATUS  mandatory
	DESCRIPTION	"The index of the ICameras (1..128)"
	::= { cmEntry 1 }

cmType						OBJECT-TYPE
	SYNTAX					INTEGER { none(1),axis2100(2),ax2400(3) }
	ACCESS					read-write
	STATUS					mandatory
	DESCRIPTION			"Camera type"
	::= { cmEntry 2 }

cmPort						OBJECT-TYPE
	SYNTAX					INTEGER
	ACCESS					read-write
	STATUS					mandatory
	DESCRIPTION			"Camera port"
	::= { cmEntry 3 }

cmIP							OBJECT-TYPE
	SYNTAX					DisplayString
	ACCESS					read-write
	STATUS					mandatory
	DESCRIPTION			"Camera IP"
	::= { cmEntry 4 }

cmName						OBJECT-TYPE
	SYNTAX					DisplayString
	ACCESS					read-write
	STATUS					mandatory
	DESCRIPTION			"Camera name"
	::= { cmEntry 5 }


-- Datalog

dlgEnable				OBJECT-TYPE
	SYNTAX				INTEGER { false(1) , true(2) }
	ACCESS				read-write
	STATUS				mandatory
	DESCRIPTION		"Enable datalog"
	::= { hostDatalog 1}

dlgInterval			OBJECT-TYPE
	SYNTAX				INTEGER
	ACCESS				read-write
	STATUS				mandatory
	DESCRIPTION		"Logging interval"
	::= { hostDatalog 2 }

-- Units

unitHostIP					OBJECT-TYPE
	SYNTAX				DisplayString
	ACCESS				read-only
	STATUS				mandatory
	DESCRIPTION		"Unit IP addr"
	::= { hostUnit 1}

unitHostName				OBJECT-TYPE
	SYNTAX				DisplayString
	ACCESS				read-write
	STATUS				mandatory
	DESCRIPTION		"Unit name"
	::= { hostUnit 2}

unitHostCustomVoice	OBJECT-TYPE
	SYNTAX					DisplayString
	ACCESS					read-write
	STATUS					mandatory
	DESCRIPTION			"Unit Voice file"
	::= { hostUnit 3}

unitHostDescription	OBJECT-TYPE
	SYNTAX					DisplayString
	ACCESS					read-write
	STATUS					mandatory
	DESCRIPTION			"Unit Description"
	::= { hostUnit 4}

unitHostLocation			OBJECT-TYPE
	SYNTAX					DisplayString
	ACCESS					read-write
	STATUS					mandatory
	DESCRIPTION			"Unit Location"
	::= { hostUnit 5}

unitHostSerialNumber	OBJECT-TYPE
	SYNTAX					DisplayString
	ACCESS					read-only
	STATUS					mandatory
	DESCRIPTION			"Unit Serial Number"
	::= { hostUnit 6 }

unitHostSlavePerChgVal	OBJECT-TYPE
	SYNTAX					INTEGER
	ACCESS					read-write
	STATUS					mandatory
	DESCRIPTION			"Slave percent change value to trigger status"
	::= { hostUnit 7 }

unitHostSlaveAutoStatus	OBJECT-TYPE
	SYNTAX							INTEGER { false(1), true(2) }
	ACCESS							read-write
	STATUS							mandatory
	DESCRIPTION			"Enable Host to poll Slave"
	::= { hostUnit 8 }

unitHostSlavePerChgEnb	OBJECT-TYPE
	SYNTAX					INTEGER { false(1), true(2) }
	ACCESS					read-write
	STATUS					mandatory
	DESCRIPTION			"Enable Slave percent change"
	::= { hostUnit 9 }

unitHostInUse				OBJECT-TYPE
	SYNTAX					INTEGER	{	false(1),true(2) }
	ACCESS					read-only
	STATUS					mandatory
	DESCRIPTION			"Unit In Use"
	::= { hostUnit 10 }

unitHostStatus				OBJECT-TYPE
	SYNTAX					INTEGER { normal(1),alarm(2) }
	ACCESS					read-only
	STATUS					mandatory
	DESCRIPTION			"Unit Status"
	::= { hostUnit 11 }

unitHostPollInterval	OBJECT-TYPE
	SYNTAX					INTEGER
	ACCESS					read-write
	STATUS					mandatory
	DESCRIPTION			"Status polling interval"
	::= { hostUnit 12 }

unitNode1IP					OBJECT-TYPE
	SYNTAX				DisplayString
	ACCESS				read-only
	STATUS				mandatory
	DESCRIPTION		"Unit IP addr"
	::= { node1Unit 1}

unitNode1Name				OBJECT-TYPE
	SYNTAX				DisplayString
	ACCESS				read-write
	STATUS				mandatory
	DESCRIPTION		"Unit name"
	::= { node1Unit 2}

unitNode1CustomVoice	OBJECT-TYPE
	SYNTAX					DisplayString
	ACCESS					read-write
	STATUS					mandatory
	DESCRIPTION			"Unit Voice file"
	::= { node1Unit 3}

unitNode1Description	OBJECT-TYPE
	SYNTAX					DisplayString
	ACCESS					read-write
	STATUS					mandatory
	DESCRIPTION			"Unit Description"
	::= { node1Unit 4}

unitNode1Location			OBJECT-TYPE
	SYNTAX					DisplayString
	ACCESS					read-write
	STATUS					mandatory
	DESCRIPTION			"Unit Location"
	::= { node1Unit 5}

unitNode1SerialNumber	OBJECT-TYPE
	SYNTAX					DisplayString
	ACCESS					read-only
	STATUS					mandatory
	DESCRIPTION			"Unit Serial Number"
	::= { node1Unit 6 }

unitNode1SlavePerChgVal	OBJECT-TYPE
	SYNTAX					INTEGER
	ACCESS					read-write
	STATUS					mandatory
	DESCRIPTION			"Slave percent change value to trigger status"
	::= { node1Unit 7 }

unitNode1SlaveAutoStatus	OBJECT-TYPE
	SYNTAX							INTEGER { false(1), true(2) }
	ACCESS							read-write
	STATUS							mandatory
	DESCRIPTION			"Enable Host to poll Slave"
	::= { node1Unit 8 }

unitNode1SlavePerChgEnb	OBJECT-TYPE
	SYNTAX					INTEGER { false(1), true(2) }
	ACCESS					read-write
	STATUS					mandatory
	DESCRIPTION			"Enable Slave percent change"
	::= { node1Unit 9 }

unitNode1InUse				OBJECT-TYPE
	SYNTAX					INTEGER	{	false(1),true(2) }
	ACCESS					read-only
	STATUS					mandatory
	DESCRIPTION			"Unit In Use"
	::= { node1Unit 10 }

unitNode1Status				OBJECT-TYPE
	SYNTAX					INTEGER { normal(1),pending(2),trouble(3) }
	ACCESS					read-only
	STATUS					mandatory
	DESCRIPTION			"Unit Status"
	::= { node1Unit 11 }

unitNode1PollInterval	OBJECT-TYPE
	SYNTAX					INTEGER
	ACCESS					read-write
	STATUS					mandatory
	DESCRIPTION			"Status polling interval"
	::= { node1Unit 12 }

unitNode2IP					OBJECT-TYPE
	SYNTAX				DisplayString
	ACCESS				read-only
	STATUS				mandatory
	DESCRIPTION		"Unit IP addr"
	::= { node2Unit 1}

unitNode2Name				OBJECT-TYPE
	SYNTAX				DisplayString
	ACCESS				read-write
	STATUS				mandatory
	DESCRIPTION		"Unit name"
	::= { node2Unit 2}

unitNode2CustomVoice	OBJECT-TYPE
	SYNTAX					DisplayString
	ACCESS					read-write
	STATUS					mandatory
	DESCRIPTION			"Unit Voice file"
	::= { node2Unit 3}

unitNode2Description	OBJECT-TYPE
	SYNTAX					DisplayString
	ACCESS					read-write
	STATUS					mandatory
	DESCRIPTION			"Unit Description"
	::= { node2Unit 4}

unitNode2Location			OBJECT-TYPE
	SYNTAX					DisplayString
	ACCESS					read-write
	STATUS					mandatory
	DESCRIPTION			"Unit Location"
	::= { node2Unit 5}

unitNode2SerialNumber	OBJECT-TYPE
	SYNTAX					DisplayString
	ACCESS					read-only
	STATUS					mandatory
	DESCRIPTION			"Unit Serial Number"
	::= { node2Unit 6 }

unitNode2SlavePerChgVal	OBJECT-TYPE
	SYNTAX					INTEGER
	ACCESS					read-write
	STATUS					mandatory
	DESCRIPTION			"Slave percent change value to trigger status"
	::= { node2Unit 7 }

unitNode2SlaveAutoStatus	OBJECT-TYPE
	SYNTAX							INTEGER { false(1), true(2) }
	ACCESS							read-write
	STATUS							mandatory
	DESCRIPTION			"Enable Host to poll Slave"
	::= { node2Unit 8 }

unitNode2SlavePerChgEnb	OBJECT-TYPE
	SYNTAX					INTEGER { false(1), true(2) }
	ACCESS					read-write
	STATUS					mandatory
	DESCRIPTION			"Enable Slave percent change"
	::= { node2Unit 9 }

unitNode2InUse				OBJECT-TYPE
	SYNTAX					INTEGER	{	false(1),true(2) }
	ACCESS					read-only
	STATUS					mandatory
	DESCRIPTION			"Unit In Use"
	::= { node2Unit 10 }

unitNode2Status				OBJECT-TYPE
	SYNTAX					INTEGER { normal(1),pending(2),trouble(3) }
	ACCESS					read-only
	STATUS					mandatory
	DESCRIPTION			"Unit Status"
	::= { node2Unit 11 }

unitNode2PollInterval	OBJECT-TYPE
	SYNTAX					INTEGER
	ACCESS					read-write
	STATUS					mandatory
	DESCRIPTION			"Status polling interval"
	::= { node2Unit 12 }

unitNode3IP					OBJECT-TYPE
	SYNTAX				DisplayString
	ACCESS				read-only
	STATUS				mandatory
	DESCRIPTION		"Unit IP addr"
	::= { node3Unit 1}

unitNode3Name				OBJECT-TYPE
	SYNTAX				DisplayString
	ACCESS				read-write
	STATUS				mandatory
	DESCRIPTION		"Unit name"
	::= { node3Unit 2}

unitNode3CustomVoice	OBJECT-TYPE
	SYNTAX					DisplayString
	ACCESS					read-write
	STATUS					mandatory
	DESCRIPTION			"Unit Voice file"
	::= { node3Unit 3}

unitNode3Description	OBJECT-TYPE
	SYNTAX					DisplayString
	ACCESS					read-write
	STATUS					mandatory
	DESCRIPTION			"Unit Description"
	::= { node3Unit 4}

unitNode3Location			OBJECT-TYPE
	SYNTAX					DisplayString
	ACCESS					read-write
	STATUS					mandatory
	DESCRIPTION			"Unit Location"
	::= { node3Unit 5}

unitNode3SerialNumber	OBJECT-TYPE
	SYNTAX					DisplayString
	ACCESS					read-only
	STATUS					mandatory
	DESCRIPTION			"Unit Serial Number"
	::= { node3Unit 6 }

unitNode3SlavePerChgVal	OBJECT-TYPE
	SYNTAX					INTEGER
	ACCESS					read-write
	STATUS					mandatory
	DESCRIPTION			"Slave percent change value to trigger status"
	::= { node3Unit 7 }

unitNode3SlaveAutoStatus	OBJECT-TYPE
	SYNTAX							INTEGER { false(1), true(2) }
	ACCESS							read-write
	STATUS							mandatory
	DESCRIPTION			"Enable Host to poll Slave"
	::= { node3Unit 8 }

unitNode3SlavePerChgEnb	OBJECT-TYPE
	SYNTAX					INTEGER { false(1), true(2) }
	ACCESS					read-write
	STATUS					mandatory
	DESCRIPTION			"Enable Slave percent change"
	::= { node3Unit 9 }

unitNode3InUse				OBJECT-TYPE
	SYNTAX					INTEGER	{	false(1),true(2) }
	ACCESS					read-only
	STATUS					mandatory
	DESCRIPTION			"Unit In Use"
	::= { node3Unit 10 }

unitNode3Status				OBJECT-TYPE
	SYNTAX					INTEGER { normal(1),pending(2),trouble(3) }
	ACCESS					read-only
	STATUS					mandatory
	DESCRIPTION			"Unit Status"
	::= { node3Unit 11 }

unitNode3PollInterval	OBJECT-TYPE
	SYNTAX					INTEGER
	ACCESS					read-write
	STATUS					mandatory
	DESCRIPTION			"Status polling interval"
	::= { node3Unit 12 }

unitNode4IP					OBJECT-TYPE
	SYNTAX				DisplayString
	ACCESS				read-only
	STATUS				mandatory
	DESCRIPTION		"Unit IP addr"
	::= { node4Unit 1}

unitNode4Name				OBJECT-TYPE
	SYNTAX				DisplayString
	ACCESS				read-write
	STATUS				mandatory
	DESCRIPTION		"Unit name"
	::= { node4Unit 2}

unitNode4CustomVoice	OBJECT-TYPE
	SYNTAX					DisplayString
	ACCESS					read-write
	STATUS					mandatory
	DESCRIPTION			"Unit Voice file"
	::= { node4Unit 3}

unitNode4Description	OBJECT-TYPE
	SYNTAX					DisplayString
	ACCESS					read-write
	STATUS					mandatory
	DESCRIPTION			"Unit Description"
	::= { node4Unit 4}

unitNode4Location			OBJECT-TYPE
	SYNTAX					DisplayString
	ACCESS					read-write
	STATUS					mandatory
	DESCRIPTION			"Unit Location"
	::= { node4Unit 5}

unitNode4SerialNumber	OBJECT-TYPE
	SYNTAX					DisplayString
	ACCESS					read-only
	STATUS					mandatory
	DESCRIPTION			"Unit Serial Number"
	::= { node4Unit 6 }

unitNode4SlavePerChgVal	OBJECT-TYPE
	SYNTAX					INTEGER
	ACCESS					read-write
	STATUS					mandatory
	DESCRIPTION			"Slave percent change value to trigger status"
	::= { node4Unit 7 }

unitNode4SlaveAutoStatus	OBJECT-TYPE
	SYNTAX							INTEGER { false(1), true(2) }
	ACCESS							read-write
	STATUS							mandatory
	DESCRIPTION			"Enable Host to poll Slave"
	::= { node4Unit 8 }

unitNode4SlavePerChgEnb	OBJECT-TYPE
	SYNTAX					INTEGER { false(1), true(2) }
	ACCESS					read-write
	STATUS					mandatory
	DESCRIPTION			"Enable Slave percent change"
	::= { node4Unit 9 }

unitNode4InUse				OBJECT-TYPE
	SYNTAX					INTEGER	{	false(1),true(2) }
	ACCESS					read-only
	STATUS					mandatory
	DESCRIPTION			"Unit In Use"
	::= { node4Unit 10 }

unitNode4Status				OBJECT-TYPE
	SYNTAX					INTEGER { normal(1),pending(2),trouble(3) }
	ACCESS					read-only
	STATUS					mandatory
	DESCRIPTION			"Unit Status"
	::= { node4Unit 11 }

unitNode4PollInterval	OBJECT-TYPE
	SYNTAX					INTEGER
	ACCESS					read-write
	STATUS					mandatory
	DESCRIPTION			"Status polling interval"
	::= { node4Unit 12 }

unitNode5IP					OBJECT-TYPE
	SYNTAX				DisplayString
	ACCESS				read-only
	STATUS				mandatory
	DESCRIPTION		"Unit IP addr"
	::= { node5Unit 1}

unitNode5Name				OBJECT-TYPE
	SYNTAX				DisplayString
	ACCESS				read-write
	STATUS				mandatory
	DESCRIPTION		"Unit name"
	::= { node5Unit 2}

unitNode5CustomVoice	OBJECT-TYPE
	SYNTAX					DisplayString
	ACCESS					read-write
	STATUS					mandatory
	DESCRIPTION			"Unit Voice file"
	::= { node5Unit 3}

unitNode5Description	OBJECT-TYPE
	SYNTAX					DisplayString
	ACCESS					read-write
	STATUS					mandatory
	DESCRIPTION			"Unit Description"
	::= { node5Unit 4}

unitNode5Location			OBJECT-TYPE
	SYNTAX					DisplayString
	ACCESS					read-write
	STATUS					mandatory
	DESCRIPTION			"Unit Location"
	::= { node5Unit 5}

unitNode5SerialNumber	OBJECT-TYPE
	SYNTAX					DisplayString
	ACCESS					read-only
	STATUS					mandatory
	DESCRIPTION			"Unit Serial Number"
	::= { node5Unit 6 }

unitNode5SlavePerChgVal	OBJECT-TYPE
	SYNTAX					INTEGER
	ACCESS					read-write
	STATUS					mandatory
	DESCRIPTION			"Slave percent change value to trigger status"
	::= { node5Unit 7 }

unitNode5SlaveAutoStatus	OBJECT-TYPE
	SYNTAX							INTEGER { false(1), true(2) }
	ACCESS							read-write
	STATUS							mandatory
	DESCRIPTION			"Enable Host to poll Slave"
	::= { node5Unit 8 }

unitNode5SlavePerChgEnb	OBJECT-TYPE
	SYNTAX					INTEGER { false(1), true(2) }
	ACCESS					read-write
	STATUS					mandatory
	DESCRIPTION			"Enable Slave percent change"
	::= { node5Unit 9 }

unitNode5InUse				OBJECT-TYPE
	SYNTAX					INTEGER	{	false(1),true(2) }
	ACCESS					read-only
	STATUS					mandatory
	DESCRIPTION			"Unit In Use"
	::= { node5Unit 10 }

unitNode5Status				OBJECT-TYPE
	SYNTAX					INTEGER { normal(1),pending(2),trouble(3) }
	ACCESS					read-only
	STATUS					mandatory
	DESCRIPTION			"Unit Status"
	::= { node5Unit 11 }

unitNode5PollInterval	OBJECT-TYPE
	SYNTAX					INTEGER
	ACCESS					read-write
	STATUS					mandatory
	DESCRIPTION			"Status polling interval"
	::= { node5Unit 12 }

unitNode6IP					OBJECT-TYPE
	SYNTAX				DisplayString
	ACCESS				read-only
	STATUS				mandatory
	DESCRIPTION		"Unit IP addr"
	::= { node6Unit 1}

unitNode6Name				OBJECT-TYPE
	SYNTAX				DisplayString
	ACCESS				read-write
	STATUS				mandatory
	DESCRIPTION		"Unit name"
	::= { node6Unit 2}

unitNode6CustomVoice	OBJECT-TYPE
	SYNTAX					DisplayString
	ACCESS					read-write
	STATUS					mandatory
	DESCRIPTION			"Unit Voice file"
	::= { node6Unit 3}

unitNode6Description	OBJECT-TYPE
	SYNTAX					DisplayString
	ACCESS					read-write
	STATUS					mandatory
	DESCRIPTION			"Unit Description"
	::= { node6Unit 4}

unitNode6Location			OBJECT-TYPE
	SYNTAX					DisplayString
	ACCESS					read-write
	STATUS					mandatory
	DESCRIPTION			"Unit Location"
	::= { node6Unit 5}

unitNode6SerialNumber	OBJECT-TYPE
	SYNTAX					DisplayString
	ACCESS					read-only
	STATUS					mandatory
	DESCRIPTION			"Unit Serial Number"
	::= { node6Unit 6 }

unitNode6SlavePerChgVal	OBJECT-TYPE
	SYNTAX					INTEGER
	ACCESS					read-write
	STATUS					mandatory
	DESCRIPTION			"Slave percent change value to trigger status"
	::= { node6Unit 7 }

unitNode6SlaveAutoStatus	OBJECT-TYPE
	SYNTAX							INTEGER { false(1), true(2) }
	ACCESS							read-write
	STATUS							mandatory
	DESCRIPTION			"Enable Host to poll Slave"
	::= { node6Unit 8 }

unitNode6SlavePerChgEnb	OBJECT-TYPE
	SYNTAX					INTEGER { false(1), true(2) }
	ACCESS					read-write
	STATUS					mandatory
	DESCRIPTION			"Enable Slave percent change"
	::= { node6Unit 9 }

unitNode6InUse				OBJECT-TYPE
	SYNTAX					INTEGER	{	false(1),true(2) }
	ACCESS					read-only
	STATUS					mandatory
	DESCRIPTION			"Unit In Use"
	::= { node6Unit 10 }

unitNode6Status				OBJECT-TYPE
	SYNTAX					INTEGER { normal(1),pending(2),trouble(3) }
	ACCESS					read-only
	STATUS					mandatory
	DESCRIPTION			"Unit Status"
	::= { node6Unit 11 }

unitNode6PollInterval	OBJECT-TYPE
	SYNTAX					INTEGER
	ACCESS					read-write
	STATUS					mandatory
	DESCRIPTION			"Status polling interval"
	::= { node6Unit 12 }

unitNode7IP					OBJECT-TYPE
	SYNTAX				DisplayString
	ACCESS				read-only
	STATUS				mandatory
	DESCRIPTION		"Unit IP addr"
	::= { node7Unit 1}

unitNode7Name				OBJECT-TYPE
	SYNTAX				DisplayString
	ACCESS				read-write
	STATUS				mandatory
	DESCRIPTION		"Unit name"
	::= { node7Unit 2}

unitNode7CustomVoice	OBJECT-TYPE
	SYNTAX					DisplayString
	ACCESS					read-write
	STATUS					mandatory
	DESCRIPTION			"Unit Voice file"
	::= { node7Unit 3}

unitNode7Description	OBJECT-TYPE
	SYNTAX					DisplayString
	ACCESS					read-write
	STATUS					mandatory
	DESCRIPTION			"Unit Description"
	::= { node7Unit 4}

unitNode7Location			OBJECT-TYPE
	SYNTAX					DisplayString
	ACCESS					read-write
	STATUS					mandatory
	DESCRIPTION			"Unit Location"
	::= { node7Unit 5}

unitNode7SerialNumber	OBJECT-TYPE
	SYNTAX					DisplayString
	ACCESS					read-only
	STATUS					mandatory
	DESCRIPTION			"Unit Serial Number"
	::= { node7Unit 6 }

unitNode7SlavePerChgVal	OBJECT-TYPE
	SYNTAX					INTEGER
	ACCESS					read-write
	STATUS					mandatory
	DESCRIPTION			"Slave percent change value to trigger status"
	::= { node7Unit 7 }

unitNode7SlaveAutoStatus	OBJECT-TYPE
	SYNTAX							INTEGER { false(1), true(2) }
	ACCESS							read-write
	STATUS							mandatory
	DESCRIPTION			"Enable Host to poll Slave"
	::= { node7Unit 8 }

unitNode7SlavePerChgEnb	OBJECT-TYPE
	SYNTAX					INTEGER { false(1), true(2) }
	ACCESS					read-write
	STATUS					mandatory
	DESCRIPTION			"Enable Slave percent change"
	::= { node7Unit 9 }

unitNode7InUse				OBJECT-TYPE
	SYNTAX					INTEGER	{	false(1),true(2) }
	ACCESS					read-only
	STATUS					mandatory
	DESCRIPTION			"Unit In Use"
	::= { node7Unit 10 }

unitNode7Status				OBJECT-TYPE
	SYNTAX					INTEGER { normal(1),pending(2),trouble(3) }
	ACCESS					read-only
	STATUS					mandatory
	DESCRIPTION			"Unit Status"
	::= { node7Unit 11 }

unitNode7PollInterval	OBJECT-TYPE
	SYNTAX					INTEGER
	ACCESS					read-write
	STATUS					mandatory
	DESCRIPTION			"Status polling interval"
	::= { node7Unit 12 }

unitNode8IP					OBJECT-TYPE
	SYNTAX				DisplayString
	ACCESS				read-only
	STATUS				mandatory
	DESCRIPTION		"Unit IP addr"
	::= { node8Unit 1}

unitNode8Name				OBJECT-TYPE
	SYNTAX				DisplayString
	ACCESS				read-write
	STATUS				mandatory
	DESCRIPTION		"Unit name"
	::= { node8Unit 2}

unitNode8CustomVoice	OBJECT-TYPE
	SYNTAX					DisplayString
	ACCESS					read-write
	STATUS					mandatory
	DESCRIPTION			"Unit Voice file"
	::= { node8Unit 3}

unitNode8Description	OBJECT-TYPE
	SYNTAX					DisplayString
	ACCESS					read-write
	STATUS					mandatory
	DESCRIPTION			"Unit Description"
	::= { node8Unit 4}

unitNode8Location			OBJECT-TYPE
	SYNTAX					DisplayString
	ACCESS					read-write
	STATUS					mandatory
	DESCRIPTION			"Unit Location"
	::= { node8Unit 5}

unitNode8SerialNumber	OBJECT-TYPE
	SYNTAX					DisplayString
	ACCESS					read-only
	STATUS					mandatory
	DESCRIPTION			"Unit Serial Number"
	::= { node8Unit 6 }

unitNode8SlavePerChgVal	OBJECT-TYPE
	SYNTAX					INTEGER
	ACCESS					read-write
	STATUS					mandatory
	DESCRIPTION			"Slave percent change value to trigger status"
	::= { node8Unit 7 }

unitNode8SlaveAutoStatus	OBJECT-TYPE
	SYNTAX							INTEGER { false(1), true(2) }
	ACCESS							read-write
	STATUS							mandatory
	DESCRIPTION			"Enable Host to poll Slave"
	::= { node8Unit 8 }

unitNode8SlavePerChgEnb	OBJECT-TYPE
	SYNTAX					INTEGER { false(1), true(2) }
	ACCESS					read-write
	STATUS					mandatory
	DESCRIPTION			"Enable Slave percent change"
	::= { node8Unit 9 }

unitNode8InUse				OBJECT-TYPE
	SYNTAX					INTEGER	{	false(1),true(2) }
	ACCESS					read-only
	STATUS					mandatory
	DESCRIPTION			"Unit In Use"
	::= { node8Unit 10 }

unitNode8Status				OBJECT-TYPE
	SYNTAX					INTEGER { normal(1),pending(2),trouble(3) }
	ACCESS					read-only
	STATUS					mandatory
	DESCRIPTION			"Unit Status"
	::= { node8Unit 11 }

unitNode8PollInterval	OBJECT-TYPE
	SYNTAX					INTEGER
	ACCESS					read-write
	STATUS					mandatory
	DESCRIPTION			"Status polling interval"
	::= { node8Unit 12 }

unitNode9IP					OBJECT-TYPE
	SYNTAX				DisplayString
	ACCESS				read-only
	STATUS				mandatory
	DESCRIPTION		"Unit IP addr"
	::= { node9Unit 1}

unitNode9Name				OBJECT-TYPE
	SYNTAX				DisplayString
	ACCESS				read-write
	STATUS				mandatory
	DESCRIPTION		"Unit name"
	::= { node9Unit 2}

unitNode9CustomVoice	OBJECT-TYPE
	SYNTAX					DisplayString
	ACCESS					read-write
	STATUS					mandatory
	DESCRIPTION			"Unit Voice file"
	::= { node9Unit 3}

unitNode9Description	OBJECT-TYPE
	SYNTAX					DisplayString
	ACCESS					read-write
	STATUS					mandatory
	DESCRIPTION			"Unit Description"
	::= { node9Unit 4}

unitNode9Location			OBJECT-TYPE
	SYNTAX					DisplayString
	ACCESS					read-write
	STATUS					mandatory
	DESCRIPTION			"Unit Location"
	::= { node9Unit 5}

unitNode9SerialNumber	OBJECT-TYPE
	SYNTAX					DisplayString
	ACCESS					read-only
	STATUS					mandatory
	DESCRIPTION			"Unit Serial Number"
	::= { node9Unit 6 }

unitNode9SlavePerChgVal	OBJECT-TYPE
	SYNTAX					INTEGER
	ACCESS					read-write
	STATUS					mandatory
	DESCRIPTION			"Slave percent change value to trigger status"
	::= { node9Unit 7 }

unitNode9SlaveAutoStatus	OBJECT-TYPE
	SYNTAX							INTEGER { false(1), true(2) }
	ACCESS							read-write
	STATUS							mandatory
	DESCRIPTION			"Enable Host to poll Slave"
	::= { node9Unit 8 }

unitNode9SlavePerChgEnb	OBJECT-TYPE
	SYNTAX					INTEGER { false(1), true(2) }
	ACCESS					read-write
	STATUS					mandatory
	DESCRIPTION			"Enable Slave percent change"
	::= { node9Unit 9 }

unitNode9InUse				OBJECT-TYPE
	SYNTAX					INTEGER	{	false(1),true(2) }
	ACCESS					read-only
	STATUS					mandatory
	DESCRIPTION			"Unit In Use"
	::= { node9Unit 10 }

unitNode9Status				OBJECT-TYPE
	SYNTAX					INTEGER { normal(1),pending(2),trouble(3) }
	ACCESS					read-only
	STATUS					mandatory
	DESCRIPTION			"Unit Status"
	::= { node9Unit 11 }

unitNode9PollInterval	OBJECT-TYPE
	SYNTAX					INTEGER
	ACCESS					read-write
	STATUS					mandatory
	DESCRIPTION			"Status polling interval"
	::= { node9Unit 12 }

unitNode10IP					OBJECT-TYPE
	SYNTAX				DisplayString
	ACCESS				read-only
	STATUS				mandatory
	DESCRIPTION		"Unit IP addr"
	::= { node10Unit 1}

unitNode10Name				OBJECT-TYPE
	SYNTAX				DisplayString
	ACCESS				read-write
	STATUS				mandatory
	DESCRIPTION		"Unit name"
	::= { node10Unit 2}

unitNode10CustomVoice	OBJECT-TYPE
	SYNTAX					DisplayString
	ACCESS					read-write
	STATUS					mandatory
	DESCRIPTION			"Unit Voice file"
	::= { node10Unit 3}

unitNode10Description	OBJECT-TYPE
	SYNTAX					DisplayString
	ACCESS					read-write
	STATUS					mandatory
	DESCRIPTION			"Unit Description"
	::= { node10Unit 4}

unitNode10Location			OBJECT-TYPE
	SYNTAX					DisplayString
	ACCESS					read-write
	STATUS					mandatory
	DESCRIPTION			"Unit Location"
	::= { node10Unit 5}

unitNode10SerialNumber	OBJECT-TYPE
	SYNTAX					DisplayString
	ACCESS					read-only
	STATUS					mandatory
	DESCRIPTION			"Unit Serial Number"
	::= { node10Unit 6 }

unitNode10SlavePerChgVal	OBJECT-TYPE
	SYNTAX					INTEGER
	ACCESS					read-write
	STATUS					mandatory
	DESCRIPTION			"Slave percent change value to trigger status"
	::= { node10Unit 7 }

unitNode10SlaveAutoStatus	OBJECT-TYPE
	SYNTAX							INTEGER { false(1), true(2) }
	ACCESS							read-write
	STATUS							mandatory
	DESCRIPTION			"Enable Host to poll Slave"
	::= { node10Unit 8 }

unitNode10SlavePerChgEnb	OBJECT-TYPE
	SYNTAX					INTEGER { false(1), true(2) }
	ACCESS					read-write
	STATUS					mandatory
	DESCRIPTION			"Enable Slave percent change"
	::= { node10Unit 9 }

unitNode10InUse				OBJECT-TYPE
	SYNTAX					INTEGER	{	false(1),true(2) }
	ACCESS					read-only
	STATUS					mandatory
	DESCRIPTION			"Unit In Use"
	::= { node10Unit 10 }

unitNode10Status				OBJECT-TYPE
	SYNTAX					INTEGER { normal(1),pending(2),trouble(3) }
	ACCESS					read-only
	STATUS					mandatory
	DESCRIPTION			"Unit Status"
	::= { node10Unit 11 }

unitNode10PollInterval	OBJECT-TYPE
	SYNTAX					INTEGER
	ACCESS					read-write
	STATUS					mandatory
	DESCRIPTION			"Status polling interval"
	::= { node10Unit 12 }

unitNode11IP					OBJECT-TYPE
	SYNTAX				DisplayString
	ACCESS				read-only
	STATUS				mandatory
	DESCRIPTION		"Unit IP addr"
	::= { node11Unit 1}

unitNode11Name				OBJECT-TYPE
	SYNTAX				DisplayString
	ACCESS				read-write
	STATUS				mandatory
	DESCRIPTION		"Unit name"
	::= { node11Unit 2}

unitNode11CustomVoice	OBJECT-TYPE
	SYNTAX					DisplayString
	ACCESS					read-write
	STATUS					mandatory
	DESCRIPTION			"Unit Voice file"
	::= { node11Unit 3}

unitNode11Description	OBJECT-TYPE
	SYNTAX					DisplayString
	ACCESS					read-write
	STATUS					mandatory
	DESCRIPTION			"Unit Description"
	::= { node11Unit 4}

unitNode11Location			OBJECT-TYPE
	SYNTAX					DisplayString
	ACCESS					read-write
	STATUS					mandatory
	DESCRIPTION			"Unit Location"
	::= { node11Unit 5}

unitNode11SerialNumber	OBJECT-TYPE
	SYNTAX					DisplayString
	ACCESS					read-only
	STATUS					mandatory
	DESCRIPTION			"Unit Serial Number"
	::= { node11Unit 6 }

unitNode11SlavePerChgVal	OBJECT-TYPE
	SYNTAX					INTEGER
	ACCESS					read-write
	STATUS					mandatory
	DESCRIPTION			"Slave percent change value to trigger status"
	::= { node11Unit 7 }

unitNode11SlaveAutoStatus	OBJECT-TYPE
	SYNTAX							INTEGER { false(1), true(2) }
	ACCESS							read-write
	STATUS							mandatory
	DESCRIPTION			"Enable Host to poll Slave"
	::= { node11Unit 8 }

unitNode11SlavePerChgEnb	OBJECT-TYPE
	SYNTAX					INTEGER { false(1), true(2) }
	ACCESS					read-write
	STATUS					mandatory
	DESCRIPTION			"Enable Slave percent change"
	::= { node11Unit 9 }

unitNode11InUse				OBJECT-TYPE
	SYNTAX					INTEGER	{	false(1),true(2) }
	ACCESS					read-only
	STATUS					mandatory
	DESCRIPTION			"Unit In Use"
	::= { node11Unit 10 }

unitNode11Status				OBJECT-TYPE
	SYNTAX					INTEGER { normal(1),pending(2),trouble(3) }
	ACCESS					read-only
	STATUS					mandatory
	DESCRIPTION			"Unit Status"
	::= { node11Unit 11 }

unitNode11PollInterval	OBJECT-TYPE
	SYNTAX					INTEGER
	ACCESS					read-write
	STATUS					mandatory
	DESCRIPTION			"Status polling interval"
	::= { node11Unit 12 }

unitNode12IP					OBJECT-TYPE
	SYNTAX				DisplayString
	ACCESS				read-only
	STATUS				mandatory
	DESCRIPTION		"Unit IP addr"
	::= { node12Unit 1}

unitNode12Name				OBJECT-TYPE
	SYNTAX				DisplayString
	ACCESS				read-write
	STATUS				mandatory
	DESCRIPTION		"Unit name"
	::= { node12Unit 2}

unitNode12CustomVoice	OBJECT-TYPE
	SYNTAX					DisplayString
	ACCESS					read-write
	STATUS					mandatory
	DESCRIPTION			"Unit Voice file"
	::= { node12Unit 3}

unitNode12Description	OBJECT-TYPE
	SYNTAX					DisplayString
	ACCESS					read-write
	STATUS					mandatory
	DESCRIPTION			"Unit Description"
	::= { node12Unit 4}

unitNode12Location			OBJECT-TYPE
	SYNTAX					DisplayString
	ACCESS					read-write
	STATUS					mandatory
	DESCRIPTION			"Unit Location"
	::= { node12Unit 5}

unitNode12SerialNumber	OBJECT-TYPE
	SYNTAX					DisplayString
	ACCESS					read-only
	STATUS					mandatory
	DESCRIPTION			"Unit Serial Number"
	::= { node12Unit 6 }

unitNode12SlavePerChgVal	OBJECT-TYPE
	SYNTAX					INTEGER
	ACCESS					read-write
	STATUS					mandatory
	DESCRIPTION			"Slave percent change value to trigger status"
	::= { node12Unit 7 }

unitNode12SlaveAutoStatus	OBJECT-TYPE
	SYNTAX							INTEGER { false(1), true(2) }
	ACCESS							read-write
	STATUS							mandatory
	DESCRIPTION			"Enable Host to poll Slave"
	::= { node12Unit 8 }

unitNode12SlavePerChgEnb	OBJECT-TYPE
	SYNTAX					INTEGER { false(1), true(2) }
	ACCESS					read-write
	STATUS					mandatory
	DESCRIPTION			"Enable Slave percent change"
	::= { node12Unit 9 }

unitNode12InUse				OBJECT-TYPE
	SYNTAX					INTEGER	{	false(1),true(2) }
	ACCESS					read-only
	STATUS					mandatory
	DESCRIPTION			"Unit In Use"
	::= { node12Unit 10 }

unitNode12Status				OBJECT-TYPE
	SYNTAX					INTEGER { normal(1),pending(2),trouble(3) }
	ACCESS					read-only
	STATUS					mandatory
	DESCRIPTION			"Unit Status"
	::= { node12Unit 11 }

unitNode12PollInterval	OBJECT-TYPE
	SYNTAX					INTEGER
	ACCESS					read-write
	STATUS					mandatory
	DESCRIPTION			"Status polling interval"
	::= { node12Unit 12 }

unitNode13IP					OBJECT-TYPE
	SYNTAX				DisplayString
	ACCESS				read-only
	STATUS				mandatory
	DESCRIPTION		"Unit IP addr"
	::= { node13Unit 1}

unitNode13Name				OBJECT-TYPE
	SYNTAX				DisplayString
	ACCESS				read-write
	STATUS				mandatory
	DESCRIPTION		"Unit name"
	::= { node13Unit 2}

unitNode13CustomVoice	OBJECT-TYPE
	SYNTAX					DisplayString
	ACCESS					read-write
	STATUS					mandatory
	DESCRIPTION			"Unit Voice file"
	::= { node13Unit 3}

unitNode13Description	OBJECT-TYPE
	SYNTAX					DisplayString
	ACCESS					read-write
	STATUS					mandatory
	DESCRIPTION			"Unit Description"
	::= { node13Unit 4}

unitNode13Location			OBJECT-TYPE
	SYNTAX					DisplayString
	ACCESS					read-write
	STATUS					mandatory
	DESCRIPTION			"Unit Location"
	::= { node13Unit 5}

unitNode13SerialNumber	OBJECT-TYPE
	SYNTAX					DisplayString
	ACCESS					read-only
	STATUS					mandatory
	DESCRIPTION			"Unit Serial Number"
	::= { node13Unit 6 }

unitNode13SlavePerChgVal	OBJECT-TYPE
	SYNTAX					INTEGER
	ACCESS					read-write
	STATUS					mandatory
	DESCRIPTION			"Slave percent change value to trigger status"
	::= { node13Unit 7 }

unitNode13SlaveAutoStatus	OBJECT-TYPE
	SYNTAX							INTEGER { false(1), true(2) }
	ACCESS							read-write
	STATUS							mandatory
	DESCRIPTION			"Enable Host to poll Slave"
	::= { node13Unit 8 }

unitNode13SlavePerChgEnb	OBJECT-TYPE
	SYNTAX					INTEGER { false(1), true(2) }
	ACCESS					read-write
	STATUS					mandatory
	DESCRIPTION			"Enable Slave percent change"
	::= { node13Unit 9 }

unitNode13InUse				OBJECT-TYPE
	SYNTAX					INTEGER	{	false(1),true(2) }
	ACCESS					read-only
	STATUS					mandatory
	DESCRIPTION			"Unit In Use"
	::= { node13Unit 10 }

unitNode13Status				OBJECT-TYPE
	SYNTAX					INTEGER { normal(1),pending(2),trouble(3) }
	ACCESS					read-only
	STATUS					mandatory
	DESCRIPTION			"Unit Status"
	::= { node13Unit 11 }

unitNode13PollInterval	OBJECT-TYPE
	SYNTAX					INTEGER
	ACCESS					read-write
	STATUS					mandatory
	DESCRIPTION			"Status polling interval"
	::= { node13Unit 12 }

unitNode14IP					OBJECT-TYPE
	SYNTAX				DisplayString
	ACCESS				read-only
	STATUS				mandatory
	DESCRIPTION		"Unit IP addr"
	::= { node14Unit 1}

unitNode14Name				OBJECT-TYPE
	SYNTAX				DisplayString
	ACCESS				read-write
	STATUS				mandatory
	DESCRIPTION		"Unit name"
	::= { node14Unit 2}

unitNode14CustomVoice	OBJECT-TYPE
	SYNTAX					DisplayString
	ACCESS					read-write
	STATUS					mandatory
	DESCRIPTION			"Unit Voice file"
	::= { node14Unit 3}

unitNode14Description	OBJECT-TYPE
	SYNTAX					DisplayString
	ACCESS					read-write
	STATUS					mandatory
	DESCRIPTION			"Unit Description"
	::= { node14Unit 4}

unitNode14Location			OBJECT-TYPE
	SYNTAX					DisplayString
	ACCESS					read-write
	STATUS					mandatory
	DESCRIPTION			"Unit Location"
	::= { node14Unit 5}

unitNode14SerialNumber	OBJECT-TYPE
	SYNTAX					DisplayString
	ACCESS					read-only
	STATUS					mandatory
	DESCRIPTION			"Unit Serial Number"
	::= { node14Unit 6 }

unitNode14SlavePerChgVal	OBJECT-TYPE
	SYNTAX					INTEGER
	ACCESS					read-write
	STATUS					mandatory
	DESCRIPTION			"Slave percent change value to trigger status"
	::= { node14Unit 7 }

unitNode14SlaveAutoStatus	OBJECT-TYPE
	SYNTAX							INTEGER { false(1), true(2) }
	ACCESS							read-write
	STATUS							mandatory
	DESCRIPTION			"Enable Host to poll Slave"
	::= { node14Unit 8 }

unitNode14SlavePerChgEnb	OBJECT-TYPE
	SYNTAX					INTEGER { false(1), true(2) }
	ACCESS					read-write
	STATUS					mandatory
	DESCRIPTION			"Enable Slave percent change"
	::= { node14Unit 9 }

unitNode14InUse				OBJECT-TYPE
	SYNTAX					INTEGER	{	false(1),true(2) }
	ACCESS					read-only
	STATUS					mandatory
	DESCRIPTION			"Unit In Use"
	::= { node14Unit 10 }

unitNode14Status				OBJECT-TYPE
	SYNTAX					INTEGER { normal(1),pending(2),trouble(3) }
	ACCESS					read-only
	STATUS					mandatory
	DESCRIPTION			"Unit Status"
	::= { node14Unit 11 }

unitNode14PollInterval	OBJECT-TYPE
	SYNTAX					INTEGER
	ACCESS					read-write
	STATUS					mandatory
	DESCRIPTION			"Status polling interval"
	::= { node14Unit 12 }

unitNode15IP					OBJECT-TYPE
	SYNTAX				DisplayString
	ACCESS				read-only
	STATUS				mandatory
	DESCRIPTION		"Unit IP addr"
	::= { node15Unit 1}

unitNode15Name				OBJECT-TYPE
	SYNTAX				DisplayString
	ACCESS				read-write
	STATUS				mandatory
	DESCRIPTION		"Unit name"
	::= { node15Unit 2}

unitNode15CustomVoice	OBJECT-TYPE
	SYNTAX					DisplayString
	ACCESS					read-write
	STATUS					mandatory
	DESCRIPTION			"Unit Voice file"
	::= { node15Unit 3}

unitNode15Description	OBJECT-TYPE
	SYNTAX					DisplayString
	ACCESS					read-write
	STATUS					mandatory
	DESCRIPTION			"Unit Description"
	::= { node15Unit 4}

unitNode15Location			OBJECT-TYPE
	SYNTAX					DisplayString
	ACCESS					read-write
	STATUS					mandatory
	DESCRIPTION			"Unit Location"
	::= { node15Unit 5}

unitNode15SerialNumber	OBJECT-TYPE
	SYNTAX					DisplayString
	ACCESS					read-only
	STATUS					mandatory
	DESCRIPTION			"Unit Serial Number"
	::= { node15Unit 6 }

unitNode15SlavePerChgVal	OBJECT-TYPE
	SYNTAX					INTEGER
	ACCESS					read-write
	STATUS					mandatory
	DESCRIPTION			"Slave percent change value to trigger status"
	::= { node15Unit 7 }

unitNode15SlaveAutoStatus	OBJECT-TYPE
	SYNTAX							INTEGER { false(1), true(2) }
	ACCESS							read-write
	STATUS							mandatory
	DESCRIPTION			"Enable Host to poll Slave"
	::= { node15Unit 8 }

unitNode15SlavePerChgEnb	OBJECT-TYPE
	SYNTAX					INTEGER { false(1), true(2) }
	ACCESS					read-write
	STATUS					mandatory
	DESCRIPTION			"Enable Slave percent change"
	::= { node15Unit 9 }

unitNode15InUse				OBJECT-TYPE
	SYNTAX					INTEGER	{	false(1),true(2) }
	ACCESS					read-only
	STATUS					mandatory
	DESCRIPTION			"Unit In Use"
	::= { node15Unit 10 }

unitNode15Status				OBJECT-TYPE
	SYNTAX					INTEGER { normal(1),pending(2),trouble(3) }
	ACCESS					read-only
	STATUS					mandatory
	DESCRIPTION			"Unit Status"
	::= { node15Unit 11 }

unitNode15PollInterval	OBJECT-TYPE
	SYNTAX					INTEGER
	ACCESS					read-write
	STATUS					mandatory
	DESCRIPTION			"Status polling interval"
	::= { node15Unit 12 }

unitNode16IP					OBJECT-TYPE
	SYNTAX				DisplayString
	ACCESS				read-only
	STATUS				mandatory
	DESCRIPTION		"Unit IP addr"
	::= { node16Unit 1}

unitNode16Name				OBJECT-TYPE
	SYNTAX				DisplayString
	ACCESS				read-write
	STATUS				mandatory
	DESCRIPTION		"Unit name"
	::= { node16Unit 2}

unitNode16CustomVoice	OBJECT-TYPE
	SYNTAX					DisplayString
	ACCESS					read-write
	STATUS					mandatory
	DESCRIPTION			"Unit Voice file"
	::= { node16Unit 3}

unitNode16Description	OBJECT-TYPE
	SYNTAX					DisplayString
	ACCESS					read-write
	STATUS					mandatory
	DESCRIPTION			"Unit Description"
	::= { node16Unit 4}

unitNode16Location			OBJECT-TYPE
	SYNTAX					DisplayString
	ACCESS					read-write
	STATUS					mandatory
	DESCRIPTION			"Unit Location"
	::= { node16Unit 5}

unitNode16SerialNumber	OBJECT-TYPE
	SYNTAX					DisplayString
	ACCESS					read-only
	STATUS					mandatory
	DESCRIPTION			"Unit Serial Number"
	::= { node16Unit 6 }

unitNode16SlavePerChgVal	OBJECT-TYPE
	SYNTAX					INTEGER
	ACCESS					read-write
	STATUS					mandatory
	DESCRIPTION			"Slave percent change value to trigger status"
	::= { node16Unit 7 }

unitNode16SlaveAutoStatus	OBJECT-TYPE
	SYNTAX							INTEGER { false(1), true(2) }
	ACCESS							read-write
	STATUS							mandatory
	DESCRIPTION			"Enable Host to poll Slave"
	::= { node16Unit 8 }

unitNode16SlavePerChgEnb	OBJECT-TYPE
	SYNTAX					INTEGER { false(1), true(2) }
	ACCESS					read-write
	STATUS					mandatory
	DESCRIPTION			"Enable Slave percent change"
	::= { node16Unit 9 }

unitNode16InUse				OBJECT-TYPE
	SYNTAX					INTEGER	{	false(1),true(2) }
	ACCESS					read-only
	STATUS					mandatory
	DESCRIPTION			"Unit In Use"
	::= { node16Unit 10 }

unitNode16Status				OBJECT-TYPE
	SYNTAX					INTEGER { normal(1),pending(2),trouble(3) }
	ACCESS					read-only
	STATUS					mandatory
	DESCRIPTION			"Unit Status"
	::= { node16Unit 11 }

unitNode16PollInterval	OBJECT-TYPE
	SYNTAX					INTEGER
	ACCESS					read-write
	STATUS					mandatory
	DESCRIPTION			"Status polling interval"
	::= { node16Unit 12 }

unitNode17IP					OBJECT-TYPE
	SYNTAX				DisplayString
	ACCESS				read-only
	STATUS				mandatory
	DESCRIPTION		"Unit IP addr"
	::= { node17Unit 1}

unitNode17Name				OBJECT-TYPE
	SYNTAX				DisplayString
	ACCESS				read-write
	STATUS				mandatory
	DESCRIPTION		"Unit name"
	::= { node17Unit 2}

unitNode17CustomVoice	OBJECT-TYPE
	SYNTAX					DisplayString
	ACCESS					read-write
	STATUS					mandatory
	DESCRIPTION			"Unit Voice file"
	::= { node17Unit 3}

unitNode17Description	OBJECT-TYPE
	SYNTAX					DisplayString
	ACCESS					read-write
	STATUS					mandatory
	DESCRIPTION			"Unit Description"
	::= { node17Unit 4}

unitNode17Location			OBJECT-TYPE
	SYNTAX					DisplayString
	ACCESS					read-write
	STATUS					mandatory
	DESCRIPTION			"Unit Location"
	::= { node17Unit 5}

unitNode17SerialNumber	OBJECT-TYPE
	SYNTAX					DisplayString
	ACCESS					read-only
	STATUS					mandatory
	DESCRIPTION			"Unit Serial Number"
	::= { node17Unit 6 }

unitNode17SlavePerChgVal	OBJECT-TYPE
	SYNTAX					INTEGER
	ACCESS					read-write
	STATUS					mandatory
	DESCRIPTION			"Slave percent change value to trigger status"
	::= { node17Unit 7 }

unitNode17SlaveAutoStatus	OBJECT-TYPE
	SYNTAX							INTEGER { false(1), true(2) }
	ACCESS							read-write
	STATUS							mandatory
	DESCRIPTION			"Enable Host to poll Slave"
	::= { node17Unit 8 }

unitNode17SlavePerChgEnb	OBJECT-TYPE
	SYNTAX					INTEGER { false(1), true(2) }
	ACCESS					read-write
	STATUS					mandatory
	DESCRIPTION			"Enable Slave percent change"
	::= { node17Unit 9 }

unitNode17InUse				OBJECT-TYPE
	SYNTAX					INTEGER	{	false(1),true(2) }
	ACCESS					read-only
	STATUS					mandatory
	DESCRIPTION			"Unit In Use"
	::= { node17Unit 10 }

unitNode17Status				OBJECT-TYPE
	SYNTAX					INTEGER { normal(1),pending(2),trouble(3) }
	ACCESS					read-only
	STATUS					mandatory
	DESCRIPTION			"Unit Status"
	::= { node17Unit 11 }

unitNode17PollInterval	OBJECT-TYPE
	SYNTAX					INTEGER
	ACCESS					read-write
	STATUS					mandatory
	DESCRIPTION			"Status polling interval"
	::= { node17Unit 12 }

unitNode18IP					OBJECT-TYPE
	SYNTAX				DisplayString
	ACCESS				read-only
	STATUS				mandatory
	DESCRIPTION		"Unit IP addr"
	::= { node18Unit 1}

unitNode18Name				OBJECT-TYPE
	SYNTAX				DisplayString
	ACCESS				read-write
	STATUS				mandatory
	DESCRIPTION		"Unit name"
	::= { node18Unit 2}

unitNode18CustomVoice	OBJECT-TYPE
	SYNTAX					DisplayString
	ACCESS					read-write
	STATUS					mandatory
	DESCRIPTION			"Unit Voice file"
	::= { node18Unit 3}

unitNode18Description	OBJECT-TYPE
	SYNTAX					DisplayString
	ACCESS					read-write
	STATUS					mandatory
	DESCRIPTION			"Unit Description"
	::= { node18Unit 4}

unitNode18Location			OBJECT-TYPE
	SYNTAX					DisplayString
	ACCESS					read-write
	STATUS					mandatory
	DESCRIPTION			"Unit Location"
	::= { node18Unit 5}

unitNode18SerialNumber	OBJECT-TYPE
	SYNTAX					DisplayString
	ACCESS					read-only
	STATUS					mandatory
	DESCRIPTION			"Unit Serial Number"
	::= { node18Unit 6 }

unitNode18SlavePerChgVal	OBJECT-TYPE
	SYNTAX					INTEGER
	ACCESS					read-write
	STATUS					mandatory
	DESCRIPTION			"Slave percent change value to trigger status"
	::= { node18Unit 7 }

unitNode18SlaveAutoStatus	OBJECT-TYPE
	SYNTAX							INTEGER { false(1), true(2) }
	ACCESS							read-write
	STATUS							mandatory
	DESCRIPTION			"Enable Host to poll Slave"
	::= { node18Unit 8 }

unitNode18SlavePerChgEnb	OBJECT-TYPE
	SYNTAX					INTEGER { false(1), true(2) }
	ACCESS					read-write
	STATUS					mandatory
	DESCRIPTION			"Enable Slave percent change"
	::= { node18Unit 9 }

unitNode18InUse				OBJECT-TYPE
	SYNTAX					INTEGER	{	false(1),true(2) }
	ACCESS					read-only
	STATUS					mandatory
	DESCRIPTION			"Unit In Use"
	::= { node18Unit 10 }

unitNode18Status				OBJECT-TYPE
	SYNTAX					INTEGER { normal(1),pending(2),trouble(3) }
	ACCESS					read-only
	STATUS					mandatory
	DESCRIPTION			"Unit Status"
	::= { node18Unit 11 }

unitNode18PollInterval	OBJECT-TYPE
	SYNTAX					INTEGER
	ACCESS					read-write
	STATUS					mandatory
	DESCRIPTION			"Status polling interval"
	::= { node18Unit 12 }

unitNode19IP					OBJECT-TYPE
	SYNTAX				DisplayString
	ACCESS				read-only
	STATUS				mandatory
	DESCRIPTION		"Unit IP addr"
	::= { node19Unit 1}

unitNode19Name				OBJECT-TYPE
	SYNTAX				DisplayString
	ACCESS				read-write
	STATUS				mandatory
	DESCRIPTION		"Unit name"
	::= { node19Unit 2}

unitNode19CustomVoice	OBJECT-TYPE
	SYNTAX					DisplayString
	ACCESS					read-write
	STATUS					mandatory
	DESCRIPTION			"Unit Voice file"
	::= { node19Unit 3}

unitNode19Description	OBJECT-TYPE
	SYNTAX					DisplayString
	ACCESS					read-write
	STATUS					mandatory
	DESCRIPTION			"Unit Description"
	::= { node19Unit 4}

unitNode19Location			OBJECT-TYPE
	SYNTAX					DisplayString
	ACCESS					read-write
	STATUS					mandatory
	DESCRIPTION			"Unit Location"
	::= { node19Unit 5}

unitNode19SerialNumber	OBJECT-TYPE
	SYNTAX					DisplayString
	ACCESS					read-only
	STATUS					mandatory
	DESCRIPTION			"Unit Serial Number"
	::= { node19Unit 6 }

unitNode19SlavePerChgVal	OBJECT-TYPE
	SYNTAX					INTEGER
	ACCESS					read-write
	STATUS					mandatory
	DESCRIPTION			"Slave percent change value to trigger status"
	::= { node19Unit 7 }

unitNode19SlaveAutoStatus	OBJECT-TYPE
	SYNTAX							INTEGER { false(1), true(2) }
	ACCESS							read-write
	STATUS							mandatory
	DESCRIPTION			"Enable Host to poll Slave"
	::= { node19Unit 8 }

unitNode19SlavePerChgEnb	OBJECT-TYPE
	SYNTAX					INTEGER { false(1), true(2) }
	ACCESS					read-write
	STATUS					mandatory
	DESCRIPTION			"Enable Slave percent change"
	::= { node19Unit 9 }

unitNode19InUse				OBJECT-TYPE
	SYNTAX					INTEGER	{	false(1),true(2) }
	ACCESS					read-only
	STATUS					mandatory
	DESCRIPTION			"Unit In Use"
	::= { node19Unit 10 }

unitNode19Status				OBJECT-TYPE
	SYNTAX					INTEGER { normal(1),pending(2),trouble(3) }
	ACCESS					read-only
	STATUS					mandatory
	DESCRIPTION			"Unit Status"
	::= { node19Unit 11 }

unitNode19PollInterval	OBJECT-TYPE
	SYNTAX					INTEGER
	ACCESS					read-write
	STATUS					mandatory
	DESCRIPTION			"Status polling interval"
	::= { node19Unit 12 }

unitNode20IP					OBJECT-TYPE
	SYNTAX				DisplayString
	ACCESS				read-only
	STATUS				mandatory
	DESCRIPTION		"Unit IP addr"
	::= { node20Unit 1}

unitNode20Name				OBJECT-TYPE
	SYNTAX				DisplayString
	ACCESS				read-write
	STATUS				mandatory
	DESCRIPTION		"Unit name"
	::= { node20Unit 2}

unitNode20CustomVoice	OBJECT-TYPE
	SYNTAX					DisplayString
	ACCESS					read-write
	STATUS					mandatory
	DESCRIPTION			"Unit Voice file"
	::= { node20Unit 3}

unitNode20Description	OBJECT-TYPE
	SYNTAX					DisplayString
	ACCESS					read-write
	STATUS					mandatory
	DESCRIPTION			"Unit Description"
	::= { node20Unit 4}

unitNode20Location			OBJECT-TYPE
	SYNTAX					DisplayString
	ACCESS					read-write
	STATUS					mandatory
	DESCRIPTION			"Unit Location"
	::= { node20Unit 5}

unitNode20SerialNumber	OBJECT-TYPE
	SYNTAX					DisplayString
	ACCESS					read-only
	STATUS					mandatory
	DESCRIPTION			"Unit Serial Number"
	::= { node20Unit 6 }

unitNode20SlavePerChgVal	OBJECT-TYPE
	SYNTAX					INTEGER
	ACCESS					read-write
	STATUS					mandatory
	DESCRIPTION			"Slave percent change value to trigger status"
	::= { node20Unit 7 }

unitNode20SlaveAutoStatus	OBJECT-TYPE
	SYNTAX							INTEGER { false(1), true(2) }
	ACCESS							read-write
	STATUS							mandatory
	DESCRIPTION			"Enable Host to poll Slave"
	::= { node20Unit 8 }

unitNode20SlavePerChgEnb	OBJECT-TYPE
	SYNTAX					INTEGER { false(1), true(2) }
	ACCESS					read-write
	STATUS					mandatory
	DESCRIPTION			"Enable Slave percent change"
	::= { node20Unit 9 }

unitNode20InUse				OBJECT-TYPE
	SYNTAX					INTEGER	{	false(1),true(2) }
	ACCESS					read-only
	STATUS					mandatory
	DESCRIPTION			"Unit In Use"
	::= { node20Unit 10 }

unitNode20Status				OBJECT-TYPE
	SYNTAX					INTEGER { normal(1),pending(2),trouble(3) }
	ACCESS					read-only
	STATUS					mandatory
	DESCRIPTION			"Unit Status"
	::= { node20Unit 11 }

unitNode20PollInterval	OBJECT-TYPE
	SYNTAX					INTEGER
	ACCESS					read-write
	STATUS					mandatory
	DESCRIPTION			"Status polling interval"
	::= { node20Unit 12 }

unitNode21IP					OBJECT-TYPE
	SYNTAX				DisplayString
	ACCESS				read-only
	STATUS				mandatory
	DESCRIPTION		"Unit IP addr"
	::= { node21Unit 1}

unitNode21Name				OBJECT-TYPE
	SYNTAX				DisplayString
	ACCESS				read-write
	STATUS				mandatory
	DESCRIPTION		"Unit name"
	::= { node21Unit 2}

unitNode21CustomVoice	OBJECT-TYPE
	SYNTAX					DisplayString
	ACCESS					read-write
	STATUS					mandatory
	DESCRIPTION			"Unit Voice file"
	::= { node21Unit 3}

unitNode21Description	OBJECT-TYPE
	SYNTAX					DisplayString
	ACCESS					read-write
	STATUS					mandatory
	DESCRIPTION			"Unit Description"
	::= { node21Unit 4}

unitNode21Location			OBJECT-TYPE
	SYNTAX					DisplayString
	ACCESS					read-write
	STATUS					mandatory
	DESCRIPTION			"Unit Location"
	::= { node21Unit 5}

unitNode21SerialNumber	OBJECT-TYPE
	SYNTAX					DisplayString
	ACCESS					read-only
	STATUS					mandatory
	DESCRIPTION			"Unit Serial Number"
	::= { node21Unit 6 }

unitNode21SlavePerChgVal	OBJECT-TYPE
	SYNTAX					INTEGER
	ACCESS					read-write
	STATUS					mandatory
	DESCRIPTION			"Slave percent change value to trigger status"
	::= { node21Unit 7 }

unitNode21SlaveAutoStatus	OBJECT-TYPE
	SYNTAX							INTEGER { false(1), true(2) }
	ACCESS							read-write
	STATUS							mandatory
	DESCRIPTION			"Enable Host to poll Slave"
	::= { node21Unit 8 }

unitNode21SlavePerChgEnb	OBJECT-TYPE
	SYNTAX					INTEGER { false(1), true(2) }
	ACCESS					read-write
	STATUS					mandatory
	DESCRIPTION			"Enable Slave percent change"
	::= { node21Unit 9 }

unitNode21InUse				OBJECT-TYPE
	SYNTAX					INTEGER	{	false(1),true(2) }
	ACCESS					read-only
	STATUS					mandatory
	DESCRIPTION			"Unit In Use"
	::= { node21Unit 10 }

unitNode21Status				OBJECT-TYPE
	SYNTAX					INTEGER { normal(1),pending(2),trouble(3) }
	ACCESS					read-only
	STATUS					mandatory
	DESCRIPTION			"Unit Status"
	::= { node21Unit 11 }

unitNode21PollInterval	OBJECT-TYPE
	SYNTAX					INTEGER
	ACCESS					read-write
	STATUS					mandatory
	DESCRIPTION			"Status polling interval"
	::= { node21Unit 12 }

unitNode22IP					OBJECT-TYPE
	SYNTAX				DisplayString
	ACCESS				read-only
	STATUS				mandatory
	DESCRIPTION		"Unit IP addr"
	::= { node22Unit 1}

unitNode22Name				OBJECT-TYPE
	SYNTAX				DisplayString
	ACCESS				read-write
	STATUS				mandatory
	DESCRIPTION		"Unit name"
	::= { node22Unit 2}

unitNode22CustomVoice	OBJECT-TYPE
	SYNTAX					DisplayString
	ACCESS					read-write
	STATUS					mandatory
	DESCRIPTION			"Unit Voice file"
	::= { node22Unit 3}

unitNode22Description	OBJECT-TYPE
	SYNTAX					DisplayString
	ACCESS					read-write
	STATUS					mandatory
	DESCRIPTION			"Unit Description"
	::= { node22Unit 4}

unitNode22Location			OBJECT-TYPE
	SYNTAX					DisplayString
	ACCESS					read-write
	STATUS					mandatory
	DESCRIPTION			"Unit Location"
	::= { node22Unit 5}

unitNode22SerialNumber	OBJECT-TYPE
	SYNTAX					DisplayString
	ACCESS					read-only
	STATUS					mandatory
	DESCRIPTION			"Unit Serial Number"
	::= { node22Unit 6 }

unitNode22SlavePerChgVal	OBJECT-TYPE
	SYNTAX					INTEGER
	ACCESS					read-write
	STATUS					mandatory
	DESCRIPTION			"Slave percent change value to trigger status"
	::= { node22Unit 7 }

unitNode22SlaveAutoStatus	OBJECT-TYPE
	SYNTAX							INTEGER { false(1), true(2) }
	ACCESS							read-write
	STATUS							mandatory
	DESCRIPTION			"Enable Host to poll Slave"
	::= { node22Unit 8 }

unitNode22SlavePerChgEnb	OBJECT-TYPE
	SYNTAX					INTEGER { false(1), true(2) }
	ACCESS					read-write
	STATUS					mandatory
	DESCRIPTION			"Enable Slave percent change"
	::= { node22Unit 9 }

unitNode22InUse				OBJECT-TYPE
	SYNTAX					INTEGER	{	false(1),true(2) }
	ACCESS					read-only
	STATUS					mandatory
	DESCRIPTION			"Unit In Use"
	::= { node22Unit 10 }

unitNode22Status				OBJECT-TYPE
	SYNTAX					INTEGER { normal(1),pending(2),trouble(3) }
	ACCESS					read-only
	STATUS					mandatory
	DESCRIPTION			"Unit Status"
	::= { node22Unit 11 }

unitNode22PollInterval	OBJECT-TYPE
	SYNTAX					INTEGER
	ACCESS					read-write
	STATUS					mandatory
	DESCRIPTION			"Status polling interval"
	::= { node22Unit 12 }

unitNode23IP					OBJECT-TYPE
	SYNTAX				DisplayString
	ACCESS				read-only
	STATUS				mandatory
	DESCRIPTION		"Unit IP addr"
	::= { node23Unit 1}

unitNode23Name				OBJECT-TYPE
	SYNTAX				DisplayString
	ACCESS				read-write
	STATUS				mandatory
	DESCRIPTION		"Unit name"
	::= { node23Unit 2}

unitNode23CustomVoice	OBJECT-TYPE
	SYNTAX					DisplayString
	ACCESS					read-write
	STATUS					mandatory
	DESCRIPTION			"Unit Voice file"
	::= { node23Unit 3}

unitNode23Description	OBJECT-TYPE
	SYNTAX					DisplayString
	ACCESS					read-write
	STATUS					mandatory
	DESCRIPTION			"Unit Description"
	::= { node23Unit 4}

unitNode23Location			OBJECT-TYPE
	SYNTAX					DisplayString
	ACCESS					read-write
	STATUS					mandatory
	DESCRIPTION			"Unit Location"
	::= { node23Unit 5}

unitNode23SerialNumber	OBJECT-TYPE
	SYNTAX					DisplayString
	ACCESS					read-only
	STATUS					mandatory
	DESCRIPTION			"Unit Serial Number"
	::= { node23Unit 6 }

unitNode23SlavePerChgVal	OBJECT-TYPE
	SYNTAX					INTEGER
	ACCESS					read-write
	STATUS					mandatory
	DESCRIPTION			"Slave percent change value to trigger status"
	::= { node23Unit 7 }

unitNode23SlaveAutoStatus	OBJECT-TYPE
	SYNTAX							INTEGER { false(1), true(2) }
	ACCESS							read-write
	STATUS							mandatory
	DESCRIPTION			"Enable Host to poll Slave"
	::= { node23Unit 8 }

unitNode23SlavePerChgEnb	OBJECT-TYPE
	SYNTAX					INTEGER { false(1), true(2) }
	ACCESS					read-write
	STATUS					mandatory
	DESCRIPTION			"Enable Slave percent change"
	::= { node23Unit 9 }

unitNode23InUse				OBJECT-TYPE
	SYNTAX					INTEGER	{	false(1),true(2) }
	ACCESS					read-only
	STATUS					mandatory
	DESCRIPTION			"Unit In Use"
	::= { node23Unit 10 }

unitNode23Status				OBJECT-TYPE
	SYNTAX					INTEGER { normal(1),pending(2),trouble(3) }
	ACCESS					read-only
	STATUS					mandatory
	DESCRIPTION			"Unit Status"
	::= { node23Unit 11 }

unitNode23PollInterval	OBJECT-TYPE
	SYNTAX					INTEGER
	ACCESS					read-write
	STATUS					mandatory
	DESCRIPTION			"Status polling interval"
	::= { node23Unit 12 }

unitNode24IP					OBJECT-TYPE
	SYNTAX				DisplayString
	ACCESS				read-only
	STATUS				mandatory
	DESCRIPTION		"Unit IP addr"
	::= { node24Unit 1}

unitNode24Name				OBJECT-TYPE
	SYNTAX				DisplayString
	ACCESS				read-write
	STATUS				mandatory
	DESCRIPTION		"Unit name"
	::= { node24Unit 2}

unitNode24CustomVoice	OBJECT-TYPE
	SYNTAX					DisplayString
	ACCESS					read-write
	STATUS					mandatory
	DESCRIPTION			"Unit Voice file"
	::= { node24Unit 3}

unitNode24Description	OBJECT-TYPE
	SYNTAX					DisplayString
	ACCESS					read-write
	STATUS					mandatory
	DESCRIPTION			"Unit Description"
	::= { node24Unit 4}

unitNode24Location			OBJECT-TYPE
	SYNTAX					DisplayString
	ACCESS					read-write
	STATUS					mandatory
	DESCRIPTION			"Unit Location"
	::= { node24Unit 5}

unitNode24SerialNumber	OBJECT-TYPE
	SYNTAX					DisplayString
	ACCESS					read-only
	STATUS					mandatory
	DESCRIPTION			"Unit Serial Number"
	::= { node24Unit 6 }

unitNode24SlavePerChgVal	OBJECT-TYPE
	SYNTAX					INTEGER
	ACCESS					read-write
	STATUS					mandatory
	DESCRIPTION			"Slave percent change value to trigger status"
	::= { node24Unit 7 }

unitNode24SlaveAutoStatus	OBJECT-TYPE
	SYNTAX							INTEGER { false(1), true(2) }
	ACCESS							read-write
	STATUS							mandatory
	DESCRIPTION			"Enable Host to poll Slave"
	::= { node24Unit 8 }

unitNode24SlavePerChgEnb	OBJECT-TYPE
	SYNTAX					INTEGER { false(1), true(2) }
	ACCESS					read-write
	STATUS					mandatory
	DESCRIPTION			"Enable Slave percent change"
	::= { node24Unit 9 }

unitNode24InUse				OBJECT-TYPE
	SYNTAX					INTEGER	{	false(1),true(2) }
	ACCESS					read-only
	STATUS					mandatory
	DESCRIPTION			"Unit In Use"
	::= { node24Unit 10 }

unitNode24Status				OBJECT-TYPE
	SYNTAX					INTEGER { normal(1),pending(2),trouble(3) }
	ACCESS					read-only
	STATUS					mandatory
	DESCRIPTION			"Unit Status"
	::= { node24Unit 11 }

unitNode24PollInterval	OBJECT-TYPE
	SYNTAX					INTEGER
	ACCESS					read-write
	STATUS					mandatory
	DESCRIPTION			"Status polling interval"
	::= { node24Unit 12 }

unitNode25IP					OBJECT-TYPE
	SYNTAX				DisplayString
	ACCESS				read-only
	STATUS				mandatory
	DESCRIPTION		"Unit IP addr"
	::= { node25Unit 1}

unitNode25Name				OBJECT-TYPE
	SYNTAX				DisplayString
	ACCESS				read-write
	STATUS				mandatory
	DESCRIPTION		"Unit name"
	::= { node25Unit 2}

unitNode25CustomVoice	OBJECT-TYPE
	SYNTAX					DisplayString
	ACCESS					read-write
	STATUS					mandatory
	DESCRIPTION			"Unit Voice file"
	::= { node25Unit 3}

unitNode25Description	OBJECT-TYPE
	SYNTAX					DisplayString
	ACCESS					read-write
	STATUS					mandatory
	DESCRIPTION			"Unit Description"
	::= { node25Unit 4}

unitNode25Location			OBJECT-TYPE
	SYNTAX					DisplayString
	ACCESS					read-write
	STATUS					mandatory
	DESCRIPTION			"Unit Location"
	::= { node25Unit 5}

unitNode25SerialNumber	OBJECT-TYPE
	SYNTAX					DisplayString
	ACCESS					read-only
	STATUS					mandatory
	DESCRIPTION			"Unit Serial Number"
	::= { node25Unit 6 }

unitNode25SlavePerChgVal	OBJECT-TYPE
	SYNTAX					INTEGER
	ACCESS					read-write
	STATUS					mandatory
	DESCRIPTION			"Slave percent change value to trigger status"
	::= { node25Unit 7 }

unitNode25SlaveAutoStatus	OBJECT-TYPE
	SYNTAX							INTEGER { false(1), true(2) }
	ACCESS							read-write
	STATUS							mandatory
	DESCRIPTION			"Enable Host to poll Slave"
	::= { node25Unit 8 }

unitNode25SlavePerChgEnb	OBJECT-TYPE
	SYNTAX					INTEGER { false(1), true(2) }
	ACCESS					read-write
	STATUS					mandatory
	DESCRIPTION			"Enable Slave percent change"
	::= { node25Unit 9 }

unitNode25InUse				OBJECT-TYPE
	SYNTAX					INTEGER	{	false(1),true(2) }
	ACCESS					read-only
	STATUS					mandatory
	DESCRIPTION			"Unit In Use"
	::= { node25Unit 10 }

unitNode25Status				OBJECT-TYPE
	SYNTAX					INTEGER { normal(1),pending(2),trouble(3) }
	ACCESS					read-only
	STATUS					mandatory
	DESCRIPTION			"Unit Status"
	::= { node25Unit 11 }

unitNode25PollInterval	OBJECT-TYPE
	SYNTAX					INTEGER
	ACCESS					read-write
	STATUS					mandatory
	DESCRIPTION			"Status polling interval"
	::= { node25Unit 12 }

unitNode26IP					OBJECT-TYPE
	SYNTAX				DisplayString
	ACCESS				read-only
	STATUS				mandatory
	DESCRIPTION		"Unit IP addr"
	::= { node26Unit 1}

unitNode26Name				OBJECT-TYPE
	SYNTAX				DisplayString
	ACCESS				read-write
	STATUS				mandatory
	DESCRIPTION		"Unit name"
	::= { node26Unit 2}

unitNode26CustomVoice	OBJECT-TYPE
	SYNTAX					DisplayString
	ACCESS					read-write
	STATUS					mandatory
	DESCRIPTION			"Unit Voice file"
	::= { node26Unit 3}

unitNode26Description	OBJECT-TYPE
	SYNTAX					DisplayString
	ACCESS					read-write
	STATUS					mandatory
	DESCRIPTION			"Unit Description"
	::= { node26Unit 4}

unitNode26Location			OBJECT-TYPE
	SYNTAX					DisplayString
	ACCESS					read-write
	STATUS					mandatory
	DESCRIPTION			"Unit Location"
	::= { node26Unit 5}

unitNode26SerialNumber	OBJECT-TYPE
	SYNTAX					DisplayString
	ACCESS					read-only
	STATUS					mandatory
	DESCRIPTION			"Unit Serial Number"
	::= { node26Unit 6 }

unitNode26SlavePerChgVal	OBJECT-TYPE
	SYNTAX					INTEGER
	ACCESS					read-write
	STATUS					mandatory
	DESCRIPTION			"Slave percent change value to trigger status"
	::= { node26Unit 7 }

unitNode26SlaveAutoStatus	OBJECT-TYPE
	SYNTAX							INTEGER { false(1), true(2) }
	ACCESS							read-write
	STATUS							mandatory
	DESCRIPTION			"Enable Host to poll Slave"
	::= { node26Unit 8 }

unitNode26SlavePerChgEnb	OBJECT-TYPE
	SYNTAX					INTEGER { false(1), true(2) }
	ACCESS					read-write
	STATUS					mandatory
	DESCRIPTION			"Enable Slave percent change"
	::= { node26Unit 9 }

unitNode26InUse				OBJECT-TYPE
	SYNTAX					INTEGER	{	false(1),true(2) }
	ACCESS					read-only
	STATUS					mandatory
	DESCRIPTION			"Unit In Use"
	::= { node26Unit 10 }

unitNode26Status				OBJECT-TYPE
	SYNTAX					INTEGER { normal(1),pending(2),trouble(3) }
	ACCESS					read-only
	STATUS					mandatory
	DESCRIPTION			"Unit Status"
	::= { node26Unit 11 }

unitNode26PollInterval	OBJECT-TYPE
	SYNTAX					INTEGER
	ACCESS					read-write
	STATUS					mandatory
	DESCRIPTION			"Status polling interval"
	::= { node26Unit 12 }

unitNode27IP					OBJECT-TYPE
	SYNTAX				DisplayString
	ACCESS				read-only
	STATUS				mandatory
	DESCRIPTION		"Unit IP addr"
	::= { node27Unit 1}

unitNode27Name				OBJECT-TYPE
	SYNTAX				DisplayString
	ACCESS				read-write
	STATUS				mandatory
	DESCRIPTION		"Unit name"
	::= { node27Unit 2}

unitNode27CustomVoice	OBJECT-TYPE
	SYNTAX					DisplayString
	ACCESS					read-write
	STATUS					mandatory
	DESCRIPTION			"Unit Voice file"
	::= { node27Unit 3}

unitNode27Description	OBJECT-TYPE
	SYNTAX					DisplayString
	ACCESS					read-write
	STATUS					mandatory
	DESCRIPTION			"Unit Description"
	::= { node27Unit 4}

unitNode27Location			OBJECT-TYPE
	SYNTAX					DisplayString
	ACCESS					read-write
	STATUS					mandatory
	DESCRIPTION			"Unit Location"
	::= { node27Unit 5}

unitNode27SerialNumber	OBJECT-TYPE
	SYNTAX					DisplayString
	ACCESS					read-only
	STATUS					mandatory
	DESCRIPTION			"Unit Serial Number"
	::= { node27Unit 6 }

unitNode27SlavePerChgVal	OBJECT-TYPE
	SYNTAX					INTEGER
	ACCESS					read-write
	STATUS					mandatory
	DESCRIPTION			"Slave percent change value to trigger status"
	::= { node27Unit 7 }

unitNode27SlaveAutoStatus	OBJECT-TYPE
	SYNTAX							INTEGER { false(1), true(2) }
	ACCESS							read-write
	STATUS							mandatory
	DESCRIPTION			"Enable Host to poll Slave"
	::= { node27Unit 8 }

unitNode27SlavePerChgEnb	OBJECT-TYPE
	SYNTAX					INTEGER { false(1), true(2) }
	ACCESS					read-write
	STATUS					mandatory
	DESCRIPTION			"Enable Slave percent change"
	::= { node27Unit 9 }

unitNode27InUse				OBJECT-TYPE
	SYNTAX					INTEGER	{	false(1),true(2) }
	ACCESS					read-only
	STATUS					mandatory
	DESCRIPTION			"Unit In Use"
	::= { node27Unit 10 }

unitNode27Status				OBJECT-TYPE
	SYNTAX					INTEGER { normal(1),pending(2),trouble(3) }
	ACCESS					read-only
	STATUS					mandatory
	DESCRIPTION			"Unit Status"
	::= { node27Unit 11 }

unitNode27PollInterval	OBJECT-TYPE
	SYNTAX					INTEGER
	ACCESS					read-write
	STATUS					mandatory
	DESCRIPTION			"Status polling interval"
	::= { node27Unit 12 }

unitNode28IP					OBJECT-TYPE
	SYNTAX				DisplayString
	ACCESS				read-only
	STATUS				mandatory
	DESCRIPTION		"Unit IP addr"
	::= { node28Unit 1}

unitNode28Name				OBJECT-TYPE
	SYNTAX				DisplayString
	ACCESS				read-write
	STATUS				mandatory
	DESCRIPTION		"Unit name"
	::= { node28Unit 2}

unitNode28CustomVoice	OBJECT-TYPE
	SYNTAX					DisplayString
	ACCESS					read-write
	STATUS					mandatory
	DESCRIPTION			"Unit Voice file"
	::= { node28Unit 3}

unitNode28Description	OBJECT-TYPE
	SYNTAX					DisplayString
	ACCESS					read-write
	STATUS					mandatory
	DESCRIPTION			"Unit Description"
	::= { node28Unit 4}

unitNode28Location			OBJECT-TYPE
	SYNTAX					DisplayString
	ACCESS					read-write
	STATUS					mandatory
	DESCRIPTION			"Unit Location"
	::= { node28Unit 5}

unitNode28SerialNumber	OBJECT-TYPE
	SYNTAX					DisplayString
	ACCESS					read-only
	STATUS					mandatory
	DESCRIPTION			"Unit Serial Number"
	::= { node28Unit 6 }

unitNode28SlavePerChgVal	OBJECT-TYPE
	SYNTAX					INTEGER
	ACCESS					read-write
	STATUS					mandatory
	DESCRIPTION			"Slave percent change value to trigger status"
	::= { node28Unit 7 }

unitNode28SlaveAutoStatus	OBJECT-TYPE
	SYNTAX							INTEGER { false(1), true(2) }
	ACCESS							read-write
	STATUS							mandatory
	DESCRIPTION			"Enable Host to poll Slave"
	::= { node28Unit 8 }

unitNode28SlavePerChgEnb	OBJECT-TYPE
	SYNTAX					INTEGER { false(1), true(2) }
	ACCESS					read-write
	STATUS					mandatory
	DESCRIPTION			"Enable Slave percent change"
	::= { node28Unit 9 }

unitNode28InUse				OBJECT-TYPE
	SYNTAX					INTEGER	{	false(1),true(2) }
	ACCESS					read-only
	STATUS					mandatory
	DESCRIPTION			"Unit In Use"
	::= { node28Unit 10 }

unitNode28Status				OBJECT-TYPE
	SYNTAX					INTEGER { normal(1),pending(2),trouble(3) }
	ACCESS					read-only
	STATUS					mandatory
	DESCRIPTION			"Unit Status"
	::= { node28Unit 11 }

unitNode28PollInterval	OBJECT-TYPE
	SYNTAX					INTEGER
	ACCESS					read-write
	STATUS					mandatory
	DESCRIPTION			"Status polling interval"
	::= { node28Unit 12 }

unitNode29IP					OBJECT-TYPE
	SYNTAX				DisplayString
	ACCESS				read-only
	STATUS				mandatory
	DESCRIPTION		"Unit IP addr"
	::= { node29Unit 1}

unitNode29Name				OBJECT-TYPE
	SYNTAX				DisplayString
	ACCESS				read-write
	STATUS				mandatory
	DESCRIPTION		"Unit name"
	::= { node29Unit 2}

unitNode29CustomVoice	OBJECT-TYPE
	SYNTAX					DisplayString
	ACCESS					read-write
	STATUS					mandatory
	DESCRIPTION			"Unit Voice file"
	::= { node29Unit 3}

unitNode29Description	OBJECT-TYPE
	SYNTAX					DisplayString
	ACCESS					read-write
	STATUS					mandatory
	DESCRIPTION			"Unit Description"
	::= { node29Unit 4}

unitNode29Location			OBJECT-TYPE
	SYNTAX					DisplayString
	ACCESS					read-write
	STATUS					mandatory
	DESCRIPTION			"Unit Location"
	::= { node29Unit 5}

unitNode29SerialNumber	OBJECT-TYPE
	SYNTAX					DisplayString
	ACCESS					read-only
	STATUS					mandatory
	DESCRIPTION			"Unit Serial Number"
	::= { node29Unit 6 }

unitNode29SlavePerChgVal	OBJECT-TYPE
	SYNTAX					INTEGER
	ACCESS					read-write
	STATUS					mandatory
	DESCRIPTION			"Slave percent change value to trigger status"
	::= { node29Unit 7 }

unitNode29SlaveAutoStatus	OBJECT-TYPE
	SYNTAX							INTEGER { false(1), true(2) }
	ACCESS							read-write
	STATUS							mandatory
	DESCRIPTION			"Enable Host to poll Slave"
	::= { node29Unit 8 }

unitNode29SlavePerChgEnb	OBJECT-TYPE
	SYNTAX					INTEGER { false(1), true(2) }
	ACCESS					read-write
	STATUS					mandatory
	DESCRIPTION			"Enable Slave percent change"
	::= { node29Unit 9 }

unitNode29InUse				OBJECT-TYPE
	SYNTAX					INTEGER	{	false(1),true(2) }
	ACCESS					read-only
	STATUS					mandatory
	DESCRIPTION			"Unit In Use"
	::= { node29Unit 10 }

unitNode29Status				OBJECT-TYPE
	SYNTAX					INTEGER { normal(1),pending(2),trouble(3) }
	ACCESS					read-only
	STATUS					mandatory
	DESCRIPTION			"Unit Status"
	::= { node29Unit 11 }

unitNode29PollInterval	OBJECT-TYPE
	SYNTAX					INTEGER
	ACCESS					read-write
	STATUS					mandatory
	DESCRIPTION			"Status polling interval"
	::= { node29Unit 12 }

unitNode30IP					OBJECT-TYPE
	SYNTAX				DisplayString
	ACCESS				read-only
	STATUS				mandatory
	DESCRIPTION		"Unit IP addr"
	::= { node30Unit 1}

unitNode30Name				OBJECT-TYPE
	SYNTAX				DisplayString
	ACCESS				read-write
	STATUS				mandatory
	DESCRIPTION		"Unit name"
	::= { node30Unit 2}

unitNode30CustomVoice	OBJECT-TYPE
	SYNTAX					DisplayString
	ACCESS					read-write
	STATUS					mandatory
	DESCRIPTION			"Unit Voice file"
	::= { node30Unit 3}

unitNode30Description	OBJECT-TYPE
	SYNTAX					DisplayString
	ACCESS					read-write
	STATUS					mandatory
	DESCRIPTION			"Unit Description"
	::= { node30Unit 4}

unitNode30Location			OBJECT-TYPE
	SYNTAX					DisplayString
	ACCESS					read-write
	STATUS					mandatory
	DESCRIPTION			"Unit Location"
	::= { node30Unit 5}

unitNode30SerialNumber	OBJECT-TYPE
	SYNTAX					DisplayString
	ACCESS					read-only
	STATUS					mandatory
	DESCRIPTION			"Unit Serial Number"
	::= { node30Unit 6 }

unitNode30SlavePerChgVal	OBJECT-TYPE
	SYNTAX					INTEGER
	ACCESS					read-write
	STATUS					mandatory
	DESCRIPTION			"Slave percent change value to trigger status"
	::= { node30Unit 7 }

unitNode30SlaveAutoStatus	OBJECT-TYPE
	SYNTAX							INTEGER { false(1), true(2) }
	ACCESS							read-write
	STATUS							mandatory
	DESCRIPTION			"Enable Host to poll Slave"
	::= { node30Unit 8 }

unitNode30SlavePerChgEnb	OBJECT-TYPE
	SYNTAX					INTEGER { false(1), true(2) }
	ACCESS					read-write
	STATUS					mandatory
	DESCRIPTION			"Enable Slave percent change"
	::= { node30Unit 9 }

unitNode30InUse				OBJECT-TYPE
	SYNTAX					INTEGER	{	false(1),true(2) }
	ACCESS					read-only
	STATUS					mandatory
	DESCRIPTION			"Unit In Use"
	::= { node30Unit 10 }

unitNode30Status				OBJECT-TYPE
	SYNTAX					INTEGER { normal(1),pending(2),trouble(3) }
	ACCESS					read-only
	STATUS					mandatory
	DESCRIPTION			"Unit Status"
	::= { node30Unit 11 }

unitNode30PollInterval	OBJECT-TYPE
	SYNTAX					INTEGER
	ACCESS					read-write
	STATUS					mandatory
	DESCRIPTION			"Status polling interval"
	::= { node30Unit 12 }

unitNode31IP					OBJECT-TYPE
	SYNTAX				DisplayString
	ACCESS				read-only
	STATUS				mandatory
	DESCRIPTION		"Unit IP addr"
	::= { node31Unit 1}

unitNode31Name				OBJECT-TYPE
	SYNTAX				DisplayString
	ACCESS				read-write
	STATUS				mandatory
	DESCRIPTION		"Unit name"
	::= { node31Unit 2}

unitNode31CustomVoice	OBJECT-TYPE
	SYNTAX					DisplayString
	ACCESS					read-write
	STATUS					mandatory
	DESCRIPTION			"Unit Voice file"
	::= { node31Unit 3}

unitNode31Description	OBJECT-TYPE
	SYNTAX					DisplayString
	ACCESS					read-write
	STATUS					mandatory
	DESCRIPTION			"Unit Description"
	::= { node31Unit 4}

unitNode31Location			OBJECT-TYPE
	SYNTAX					DisplayString
	ACCESS					read-write
	STATUS					mandatory
	DESCRIPTION			"Unit Location"
	::= { node31Unit 5}

unitNode31SerialNumber	OBJECT-TYPE
	SYNTAX					DisplayString
	ACCESS					read-only
	STATUS					mandatory
	DESCRIPTION			"Unit Serial Number"
	::= { node31Unit 6 }

unitNode31SlavePerChgVal	OBJECT-TYPE
	SYNTAX					INTEGER
	ACCESS					read-write
	STATUS					mandatory
	DESCRIPTION			"Slave percent change value to trigger status"
	::= { node31Unit 7 }

unitNode31SlaveAutoStatus	OBJECT-TYPE
	SYNTAX							INTEGER { false(1), true(2) }
	ACCESS							read-write
	STATUS							mandatory
	DESCRIPTION			"Enable Host to poll Slave"
	::= { node31Unit 8 }

unitNode31SlavePerChgEnb	OBJECT-TYPE
	SYNTAX					INTEGER { false(1), true(2) }
	ACCESS					read-write
	STATUS					mandatory
	DESCRIPTION			"Enable Slave percent change"
	::= { node31Unit 9 }

unitNode31InUse				OBJECT-TYPE
	SYNTAX					INTEGER	{	false(1),true(2) }
	ACCESS					read-only
	STATUS					mandatory
	DESCRIPTION			"Unit In Use"
	::= { node31Unit 10 }

unitNode31Status				OBJECT-TYPE
	SYNTAX					INTEGER { normal(1),pending(2),trouble(3) }
	ACCESS					read-only
	STATUS					mandatory
	DESCRIPTION			"Unit Status"
	::= { node31Unit 11 }

unitNode31PollInterval	OBJECT-TYPE
	SYNTAX					INTEGER
	ACCESS					read-write
	STATUS					mandatory
	DESCRIPTION			"Status polling interval"
	::= { node31Unit 12 }

-- PowerGate

pgHostInUse					OBJECT-TYPE
	SYNTAX					INTEGER { false(1),true(2) }
	ACCESS					read-only
	STATUS					mandatory
	DESCRIPTION			"PG in use"
	::= { hostPG 1 }

pgHostStatus					OBJECT-TYPE
	SYNTAX					INTEGER { normal(1),pending(2), trouble(3) }
	ACCESS					read-only
	STATUS					mandatory
	DESCRIPTION			"PG status"
	::= { hostPG 2 }

pgHostStatusSupport	OBJECT-TYPE
	SYNTAX					INTEGER { true1(1),false(2) }
	ACCESS					read-only
	STATUS					mandatory
	DESCRIPTION			"PG status support level"
	::= { hostPG 3 }

pgHostVer						OBJECT-TYPE
	SYNTAX					INTEGER { pgate1(1),pgate2(2) }
	ACCESS					read-only
	STATUS					mandatory
	DESCRIPTION			"PG version"
	::= { hostPG 4 }

pgHostVolts					OBJECT-TYPE
	SYNTAX					INTEGER
	ACCESS					read-only
	STATUS					mandatory
	DESCRIPTION			"PG voltage"
	::= { hostPG 5 }

pgHostAmps						OBJECT-TYPE
	SYNTAX					INTEGER
	ACCESS					read-only
	STATUS					mandatory
	DESCRIPTION			"PG amps"
	::= { hostPG 6 }

pgHostWatts					OBJECT-TYPE
	SYNTAX					INTEGER
	ACCESS					read-only
	STATUS					mandatory
	DESCRIPTION			"PG Watts"
	::= { hostPG 7 }

pgHostName						OBJECT-TYPE
	SYNTAX					DisplayString
	ACCESS					read-write
	STATUS					mandatory
	DESCRIPTION			"PG name"
	::= { hostPG 8 }

pgHostCustVoice			OBJECT-TYPE
	SYNTAX					DisplayString
	ACCESS					read-write
	STATUS					mandatory
	DESCRIPTION			"PG custom voice"
	::= { hostPG 9 }

pgHostOut1Name				OBJECT-TYPE
	SYNTAX					DisplayString
	ACCESS					read-write
	STATUS					mandatory
	DESCRIPTION			"PG Outlet 1 name"
	::= { hostPG 10 }

pgHostOut1CustVoice	OBJECT-TYPE
	SYNTAX					DisplayString
	ACCESS					read-write
	STATUS					mandatory
	DESCRIPTION			"PG Outlet 1 custom voice"
	::= { hostPG 11 }

pgHostOut1Volts			OBJECT-TYPE
	SYNTAX					INTEGER
	ACCESS					read-only
	STATUS					mandatory
	DESCRIPTION			"PG Outlet 1 volts"
	::= { hostPG 12 }

pgHostOut1Amps				OBJECT-TYPE
	SYNTAX					INTEGER
	ACCESS					read-only
	STATUS					mandatory
	DESCRIPTION			"PG Outlet 1 amps"
	::= { hostPG 13 }

pgHostOut1Watts			OBJECT-TYPE
	SYNTAX					INTEGER
	ACCESS					read-only
	STATUS					mandatory
	DESCRIPTION			"PG Outlet 1 watts"
	::= { hostPG 14 }

pgHostOut1State			OBJECT-TYPE
	SYNTAX					INTEGER { off(1),on(2),cycle(3) }
	ACCESS					read-only
	STATUS					mandatory
	DESCRIPTION			"PG Outlet 1 state"
	::= { hostPG 15 }

pgHostOut1Cmd				OBJECT-TYPE
	SYNTAX					INTEGER { off(1),on(2),cycle(3) }
	ACCESS					read-write
	STATUS					mandatory
	DESCRIPTION			"PG Outlet 1 command"
	::= { hostPG 16 }

pgHostOut2Name				OBJECT-TYPE
	SYNTAX					DisplayString
	ACCESS					read-write
	STATUS					mandatory
	DESCRIPTION			"PG Outlet 2 name"
	::= { hostPG 17 }

pgHostOut2CustVoice	OBJECT-TYPE
	SYNTAX					DisplayString
	ACCESS					read-write
	STATUS					mandatory
	DESCRIPTION			"PG Outlet 2 custom voice"
	::= { hostPG 18 }

pgHostOut2Volts			OBJECT-TYPE
	SYNTAX					INTEGER
	ACCESS					read-only
	STATUS					mandatory
	DESCRIPTION			"PG Outlet 2 volts"
	::= { hostPG 19 }

pgHostOut2Amps				OBJECT-TYPE
	SYNTAX					INTEGER
	ACCESS					read-only
	STATUS					mandatory
	DESCRIPTION			"PG Outlet 2 amps"
	::= { hostPG 20 }

pgHostOut2Watts			OBJECT-TYPE
	SYNTAX					INTEGER
	ACCESS					read-only
	STATUS					mandatory
	DESCRIPTION			"PG Outlet 2 watts"
	::= { hostPG 21 }


pgHostOut2State			OBJECT-TYPE
	SYNTAX					INTEGER { off(1),on(2),cycle(3) }
	ACCESS					read-only
	STATUS					mandatory
	DESCRIPTION			"PG Outlet 2 state"
	::= { hostPG 22 }

pgHostOut2Cmd				OBJECT-TYPE
	SYNTAX					INTEGER { off(1),on(2),cycle(3) }
	ACCESS					read-write
	STATUS					mandatory
	DESCRIPTION			"PG Outlet 2 command"
	::= { hostPG 23 }

pgHostOut3Name				OBJECT-TYPE
	SYNTAX					DisplayString
	ACCESS					read-write
	STATUS					mandatory
	DESCRIPTION			"PG Outlet 3 name"
	::= { hostPG 24 }

pgHostOut3CustVoice	OBJECT-TYPE
	SYNTAX					DisplayString
	ACCESS					read-write
	STATUS					mandatory
	DESCRIPTION			"PG Outlet 3 custom voice"
	::= { hostPG 25 }

pgHostOut3Volts			OBJECT-TYPE
	SYNTAX					INTEGER
	ACCESS					read-only
	STATUS					mandatory
	DESCRIPTION			"PG Outlet 3 volts"
	::= { hostPG 26 }

pgHostOut3Amps				OBJECT-TYPE
	SYNTAX					INTEGER
	ACCESS					read-only
	STATUS					mandatory
	DESCRIPTION			"PG Outlet 3 amps"
	::= { hostPG 27 }

pgHostOut3Watts			OBJECT-TYPE
	SYNTAX					INTEGER
	ACCESS					read-only
	STATUS					mandatory
	DESCRIPTION			"PG Outlet 3 watts"
	::= { hostPG 28 }

pgHostOut3State			OBJECT-TYPE
	SYNTAX					INTEGER { off(1),on(2),cycle(3) }
	ACCESS					read-only
	STATUS					mandatory
	DESCRIPTION			"PG Outlet 3 state"
	::= { hostPG 29 }

pgHostOut3Cmd				OBJECT-TYPE
	SYNTAX					INTEGER { off(1),on(2),cycle(3) }
	ACCESS					read-write
	STATUS					mandatory
	DESCRIPTION			"PG Outlet 3 command"
	::= { hostPG 30 }

pgHostOut4Name				OBJECT-TYPE
	SYNTAX					DisplayString
	ACCESS					read-write
	STATUS					mandatory
	DESCRIPTION			"PG Outlet 4 name"
	::= { hostPG 31 }

pgHostOut4CustVoice	OBJECT-TYPE
	SYNTAX					DisplayString
	ACCESS					read-write
	STATUS					mandatory
	DESCRIPTION			"PG Outlet 4 custom voice"
	::= { hostPG 32 }

pgHostOut4Volts			OBJECT-TYPE
	SYNTAX					INTEGER
	ACCESS					read-only
	STATUS					mandatory
	DESCRIPTION			"PG Outlet 4 volts"
	::= { hostPG 33 }

pgHostOut4Amps				OBJECT-TYPE
	SYNTAX					INTEGER
	ACCESS					read-only
	STATUS					mandatory
	DESCRIPTION			"PG Outlet 4 amps"
	::= { hostPG 34 }

pgHostOut4Watts			OBJECT-TYPE
	SYNTAX					INTEGER
	ACCESS					read-only
	STATUS					mandatory
	DESCRIPTION			"PG Outlet 4 watts"
	::= { hostPG 35 }

pgHostOut4State			OBJECT-TYPE
	SYNTAX					INTEGER { off(1),on(2),cycle(3) }
	ACCESS					read-only
	STATUS					mandatory
	DESCRIPTION			"PG Outlet 4 state"
	::= { hostPG 36 }

pgHostOut4Cmd				OBJECT-TYPE
	SYNTAX					INTEGER { off(1),on(2),cycle(3) }
	ACCESS					read-write
	STATUS					mandatory
	DESCRIPTION			"PG Outlet 4 command"
	::= { hostPG 37 }

pgHostOut5Name				OBJECT-TYPE
	SYNTAX					DisplayString
	ACCESS					read-write
	STATUS					mandatory
	DESCRIPTION			"PG Outlet 5 name"
	::= { hostPG 38 }

pgHostOut5CustVoice	OBJECT-TYPE
	SYNTAX					DisplayString
	ACCESS					read-write
	STATUS					mandatory
	DESCRIPTION			"PG Outlet 5 custom voice"
	::= { hostPG 39 }

pgHostOut5Volts			OBJECT-TYPE
	SYNTAX					INTEGER
	ACCESS					read-only
	STATUS					mandatory
	DESCRIPTION			"PG Outlet 5 volts"
	::= { hostPG 40 }

pgHostOut5Amps				OBJECT-TYPE
	SYNTAX					INTEGER
	ACCESS					read-only
	STATUS					mandatory
	DESCRIPTION			"PG Outlet 5 amps"
	::= { hostPG 41 }

pgHostOut5Watts			OBJECT-TYPE
	SYNTAX					INTEGER
	ACCESS					read-only
	STATUS					mandatory
	DESCRIPTION			"PG Outlet 5 watts"
	::= { hostPG 42 }

pgHostOut5State			OBJECT-TYPE
	SYNTAX					INTEGER { off(1),on(2),cycle(3) }
	ACCESS					read-only
	STATUS					mandatory
	DESCRIPTION			"PG Outlet 5 state"
	::= { hostPG 43 }

pgHostOut5Cmd				OBJECT-TYPE
	SYNTAX					INTEGER { off(1),on(2),cycle(3) }
	ACCESS					read-write
	STATUS					mandatory
	DESCRIPTION			"PG Outlet 5 command"
	::= { hostPG 44 }

pgHostOut6Name				OBJECT-TYPE
	SYNTAX					DisplayString
	ACCESS					read-write
	STATUS					mandatory
	DESCRIPTION			"PG Outlet 6 name"
	::= { hostPG 45 }

pgHostOut6CustVoice	OBJECT-TYPE
	SYNTAX					DisplayString
	ACCESS					read-write
	STATUS					mandatory
	DESCRIPTION			"PG Outlet 6 custom voice"
	::= { hostPG 46 }

pgHostOut6Volts			OBJECT-TYPE
	SYNTAX					INTEGER
	ACCESS					read-only
	STATUS					mandatory
	DESCRIPTION			"PG Outlet 6 volts"
	::= { hostPG 47 }

pgHostOut6Amps				OBJECT-TYPE
	SYNTAX					INTEGER
	ACCESS					read-only
	STATUS					mandatory
	DESCRIPTION			"PG Outlet 6 amps"
	::= { hostPG 48 }

pgHostOut6Watts			OBJECT-TYPE
	SYNTAX					INTEGER
	ACCESS					read-only
	STATUS					mandatory
	DESCRIPTION			"PG Outlet 6 watts"
	::= { hostPG 49 }


pgHostOut6State			OBJECT-TYPE
	SYNTAX					INTEGER { off(1),on(2),cycle(3) }
	ACCESS					read-only
	STATUS					mandatory
	DESCRIPTION			"PG Outlet 6 state"
	::= { hostPG 50 }

pgHostOut6Cmd				OBJECT-TYPE
	SYNTAX					INTEGER { off(1),on(2),cycle(3) }
	ACCESS					read-write
	STATUS					mandatory
	DESCRIPTION			"PG Outlet 6 command"
	::= { hostPG 51 }

pgHostOut7Name				OBJECT-TYPE
	SYNTAX					DisplayString
	ACCESS					read-write
	STATUS					mandatory
	DESCRIPTION			"PG Outlet 7 name"
	::= { hostPG 52 }

pgHostOut7CustVoice	OBJECT-TYPE
	SYNTAX					DisplayString
	ACCESS					read-write
	STATUS					mandatory
	DESCRIPTION			"PG Outlet 7 custom voice"
	::= { hostPG 53 }

pgHostOut7Volts			OBJECT-TYPE
	SYNTAX					INTEGER
	ACCESS					read-only
	STATUS					mandatory
	DESCRIPTION			"PG Outlet 7 volts"
	::= { hostPG 54 }

pgHostOut7Amps				OBJECT-TYPE
	SYNTAX					INTEGER
	ACCESS					read-only
	STATUS					mandatory
	DESCRIPTION			"PG Outlet 7 amps"
	::= { hostPG 55 }

pgHostOut7Watts			OBJECT-TYPE
	SYNTAX					INTEGER
	ACCESS					read-only
	STATUS					mandatory
	DESCRIPTION			"PG Outlet 7 watts"
	::= { hostPG 56 }

pgHostOut7State			OBJECT-TYPE
	SYNTAX					INTEGER { off(1),on(2),cycle(3) }
	ACCESS					read-only
	STATUS					mandatory
	DESCRIPTION			"PG Outlet 7 state"
	::= { hostPG 57 }

pgHostOut7Cmd				OBJECT-TYPE
	SYNTAX					INTEGER { off(1),on(2),cycle(3) }
	ACCESS					read-write
	STATUS					mandatory
	DESCRIPTION			"PG Outlet 7 command"
	::= { hostPG 58 }

pgHostOut8Name				OBJECT-TYPE
	SYNTAX					DisplayString
	ACCESS					read-write
	STATUS					mandatory
	DESCRIPTION			"PG Outlet 8 name"
	::= { hostPG 59 }

pgHostOut8CustVoice	OBJECT-TYPE
	SYNTAX					DisplayString
	ACCESS					read-write
	STATUS					mandatory
	DESCRIPTION			"PG Outlet 8 custom voice"
	::= { hostPG 60 }

pgHostOut8Volts			OBJECT-TYPE
	SYNTAX					INTEGER
	ACCESS					read-only
	STATUS					mandatory
	DESCRIPTION			"PG Outlet 8 volts"
	::= { hostPG 61 }

pgHostOut8Amps				OBJECT-TYPE
	SYNTAX					INTEGER
	ACCESS					read-only
	STATUS					mandatory
	DESCRIPTION			"PG Outlet 8 amps"
	::= { hostPG 62 }

pgHostOut8Watts			OBJECT-TYPE
	SYNTAX					INTEGER
	ACCESS					read-only
	STATUS					mandatory
	DESCRIPTION			"PG Outlet 8 watts"
	::= { hostPG 63 }


pgHostOut8State			OBJECT-TYPE
	SYNTAX					INTEGER { off(1),on(2),cycle(3) }
	ACCESS					read-only
	STATUS					mandatory
	DESCRIPTION			"PG Outlet 8 state"
	::= { hostPG 64 }

pgHostOut8Cmd				OBJECT-TYPE
	SYNTAX					INTEGER { off(1),on(2),cycle(3) }
	ACCESS					read-write
	STATUS					mandatory
	DESCRIPTION			"PG Outlet 8 command"
	::= { hostPG 65 }

pgNode1InUse					OBJECT-TYPE
	SYNTAX					INTEGER { false(1),true(2) }
	ACCESS					read-only
	STATUS					mandatory
	DESCRIPTION			"PG in use"
	::= { node1PG 1 }

pgNode1Status					OBJECT-TYPE
	SYNTAX					INTEGER { normal(1),pending(2), trouble(3) }
	ACCESS					read-only
	STATUS					mandatory
	DESCRIPTION			"PG status"
	::= { node1PG 2 }

pgNode1StatusSupport	OBJECT-TYPE
	SYNTAX					INTEGER { true1(1),false(2) }
	ACCESS					read-only
	STATUS					mandatory
	DESCRIPTION			"PG status support level"
	::= { node1PG 3 }

pgNode1Ver						OBJECT-TYPE
	SYNTAX					INTEGER { pgate1(1),pgate2(2) }
	ACCESS					read-only
	STATUS					mandatory
	DESCRIPTION			"PG version"
	::= { node1PG 4 }

pgNode1Volts					OBJECT-TYPE
	SYNTAX					INTEGER
	ACCESS					read-only
	STATUS					mandatory
	DESCRIPTION			"PG voltage"
	::= { node1PG 5 }

pgNode1Amps						OBJECT-TYPE
	SYNTAX					INTEGER
	ACCESS					read-only
	STATUS					mandatory
	DESCRIPTION			"PG amps"
	::= { node1PG 6 }

pgNode1Watts					OBJECT-TYPE
	SYNTAX					INTEGER
	ACCESS					read-only
	STATUS					mandatory
	DESCRIPTION			"PG Watts"
	::= { node1PG 7 }

pgNode1Name						OBJECT-TYPE
	SYNTAX					DisplayString
	ACCESS					read-write
	STATUS					mandatory
	DESCRIPTION			"PG name"
	::= { node1PG 8 }

pgNode1CustVoice			OBJECT-TYPE
	SYNTAX					DisplayString
	ACCESS					read-write
	STATUS					mandatory
	DESCRIPTION			"PG custom voice"
	::= { node1PG 9 }

pgNode1Out1Name				OBJECT-TYPE
	SYNTAX					DisplayString
	ACCESS					read-write
	STATUS					mandatory
	DESCRIPTION			"PG Outlet 1 name"
	::= { node1PG 10 }

pgNode1Out1CustVoice	OBJECT-TYPE
	SYNTAX					DisplayString
	ACCESS					read-write
	STATUS					mandatory
	DESCRIPTION			"PG Outlet 1 custom voice"
	::= { node1PG 11 }

pgNode1Out1Volts			OBJECT-TYPE
	SYNTAX					INTEGER
	ACCESS					read-only
	STATUS					mandatory
	DESCRIPTION			"PG Outlet 1 volts"
	::= { node1PG 12 }

pgNode1Out1Amps				OBJECT-TYPE
	SYNTAX					INTEGER
	ACCESS					read-only
	STATUS					mandatory
	DESCRIPTION			"PG Outlet 1 amps"
	::= { node1PG 13 }

pgNode1Out1Watts			OBJECT-TYPE
	SYNTAX					INTEGER
	ACCESS					read-only
	STATUS					mandatory
	DESCRIPTION			"PG Outlet 1 watts"
	::= { node1PG 14 }

pgNode1Out1State			OBJECT-TYPE
	SYNTAX					INTEGER { off(1),on(2),cycle(3) }
	ACCESS					read-only
	STATUS					mandatory
	DESCRIPTION			"PG Outlet 1 state"
	::= { node1PG 15 }

pgNode1Out1Cmd				OBJECT-TYPE
	SYNTAX					INTEGER { off(1),on(2),cycle(3) }
	ACCESS					read-write
	STATUS					mandatory
	DESCRIPTION			"PG Outlet 1 command"
	::= { node1PG 16 }

pgNode1Out2Name				OBJECT-TYPE
	SYNTAX					DisplayString
	ACCESS					read-write
	STATUS					mandatory
	DESCRIPTION			"PG Outlet 2 name"
	::= { node1PG 17 }

pgNode1Out2CustVoice	OBJECT-TYPE
	SYNTAX					DisplayString
	ACCESS					read-write
	STATUS					mandatory
	DESCRIPTION			"PG Outlet 2 custom voice"
	::= { node1PG 18 }

pgNode1Out2Volts			OBJECT-TYPE
	SYNTAX					INTEGER
	ACCESS					read-only
	STATUS					mandatory
	DESCRIPTION			"PG Outlet 2 volts"
	::= { node1PG 19 }

pgNode1Out2Amps				OBJECT-TYPE
	SYNTAX					INTEGER
	ACCESS					read-only
	STATUS					mandatory
	DESCRIPTION			"PG Outlet 2 amps"
	::= { node1PG 20 }

pgNode1Out2Watts			OBJECT-TYPE
	SYNTAX					INTEGER
	ACCESS					read-only
	STATUS					mandatory
	DESCRIPTION			"PG Outlet 2 watts"
	::= { node1PG 21 }


pgNode1Out2State			OBJECT-TYPE
	SYNTAX					INTEGER { off(1),on(2),cycle(3) }
	ACCESS					read-only
	STATUS					mandatory
	DESCRIPTION			"PG Outlet 2 state"
	::= { node1PG 22 }

pgNode1Out2Cmd				OBJECT-TYPE
	SYNTAX					INTEGER { off(1),on(2),cycle(3) }
	ACCESS					read-write
	STATUS					mandatory
	DESCRIPTION			"PG Outlet 2 command"
	::= { node1PG 23 }

pgNode1Out3Name				OBJECT-TYPE
	SYNTAX					DisplayString
	ACCESS					read-write
	STATUS					mandatory
	DESCRIPTION			"PG Outlet 3 name"
	::= { node1PG 24 }

pgNode1Out3CustVoice	OBJECT-TYPE
	SYNTAX					DisplayString
	ACCESS					read-write
	STATUS					mandatory
	DESCRIPTION			"PG Outlet 3 custom voice"
	::= { node1PG 25 }

pgNode1Out3Volts			OBJECT-TYPE
	SYNTAX					INTEGER
	ACCESS					read-only
	STATUS					mandatory
	DESCRIPTION			"PG Outlet 3 volts"
	::= { node1PG 26 }

pgNode1Out3Amps				OBJECT-TYPE
	SYNTAX					INTEGER
	ACCESS					read-only
	STATUS					mandatory
	DESCRIPTION			"PG Outlet 3 amps"
	::= { node1PG 27 }

pgNode1Out3Watts			OBJECT-TYPE
	SYNTAX					INTEGER
	ACCESS					read-only
	STATUS					mandatory
	DESCRIPTION			"PG Outlet 3 watts"
	::= { node1PG 28 }

pgNode1Out3State			OBJECT-TYPE
	SYNTAX					INTEGER { off(1),on(2),cycle(3) }
	ACCESS					read-only
	STATUS					mandatory
	DESCRIPTION			"PG Outlet 3 state"
	::= { node1PG 29 }

pgNode1Out3Cmd				OBJECT-TYPE
	SYNTAX					INTEGER { off(1),on(2),cycle(3) }
	ACCESS					read-write
	STATUS					mandatory
	DESCRIPTION			"PG Outlet 3 command"
	::= { node1PG 30 }

pgNode1Out4Name				OBJECT-TYPE
	SYNTAX					DisplayString
	ACCESS					read-write
	STATUS					mandatory
	DESCRIPTION			"PG Outlet 4 name"
	::= { node1PG 31 }

pgNode1Out4CustVoice	OBJECT-TYPE
	SYNTAX					DisplayString
	ACCESS					read-write
	STATUS					mandatory
	DESCRIPTION			"PG Outlet 4 custom voice"
	::= { node1PG 32 }

pgNode1Out4Volts			OBJECT-TYPE
	SYNTAX					INTEGER
	ACCESS					read-only
	STATUS					mandatory
	DESCRIPTION			"PG Outlet 4 volts"
	::= { node1PG 33 }

pgNode1Out4Amps				OBJECT-TYPE
	SYNTAX					INTEGER
	ACCESS					read-only
	STATUS					mandatory
	DESCRIPTION			"PG Outlet 4 amps"
	::= { node1PG 34 }

pgNode1Out4Watts			OBJECT-TYPE
	SYNTAX					INTEGER
	ACCESS					read-only
	STATUS					mandatory
	DESCRIPTION			"PG Outlet 4 watts"
	::= { node1PG 35 }

pgNode1Out4State			OBJECT-TYPE
	SYNTAX					INTEGER { off(1),on(2),cycle(3) }
	ACCESS					read-only
	STATUS					mandatory
	DESCRIPTION			"PG Outlet 4 state"
	::= { node1PG 36 }

pgNode1Out4Cmd				OBJECT-TYPE
	SYNTAX					INTEGER { off(1),on(2),cycle(3) }
	ACCESS					read-write
	STATUS					mandatory
	DESCRIPTION			"PG Outlet 4 command"
	::= { node1PG 37 }

pgNode1Out5Name				OBJECT-TYPE
	SYNTAX					DisplayString
	ACCESS					read-write
	STATUS					mandatory
	DESCRIPTION			"PG Outlet 5 name"
	::= { node1PG 38 }

pgNode1Out5CustVoice	OBJECT-TYPE
	SYNTAX					DisplayString
	ACCESS					read-write
	STATUS					mandatory
	DESCRIPTION			"PG Outlet 5 custom voice"
	::= { node1PG 39 }

pgNode1Out5Volts			OBJECT-TYPE
	SYNTAX					INTEGER
	ACCESS					read-only
	STATUS					mandatory
	DESCRIPTION			"PG Outlet 5 volts"
	::= { node1PG 40 }

pgNode1Out5Amps				OBJECT-TYPE
	SYNTAX					INTEGER
	ACCESS					read-only
	STATUS					mandatory
	DESCRIPTION			"PG Outlet 5 amps"
	::= { node1PG 41 }

pgNode1Out5Watts			OBJECT-TYPE
	SYNTAX					INTEGER
	ACCESS					read-only
	STATUS					mandatory
	DESCRIPTION			"PG Outlet 5 watts"
	::= { node1PG 42 }

pgNode1Out5State			OBJECT-TYPE
	SYNTAX					INTEGER { off(1),on(2),cycle(3) }
	ACCESS					read-only
	STATUS					mandatory
	DESCRIPTION			"PG Outlet 5 state"
	::= { node1PG 43 }

pgNode1Out5Cmd				OBJECT-TYPE
	SYNTAX					INTEGER { off(1),on(2),cycle(3) }
	ACCESS					read-write
	STATUS					mandatory
	DESCRIPTION			"PG Outlet 5 command"
	::= { node1PG 44 }

pgNode1Out6Name				OBJECT-TYPE
	SYNTAX					DisplayString
	ACCESS					read-write
	STATUS					mandatory
	DESCRIPTION			"PG Outlet 6 name"
	::= { node1PG 45 }

pgNode1Out6CustVoice	OBJECT-TYPE
	SYNTAX					DisplayString
	ACCESS					read-write
	STATUS					mandatory
	DESCRIPTION			"PG Outlet 6 custom voice"
	::= { node1PG 46 }

pgNode1Out6Volts			OBJECT-TYPE
	SYNTAX					INTEGER
	ACCESS					read-only
	STATUS					mandatory
	DESCRIPTION			"PG Outlet 6 volts"
	::= { node1PG 47 }

pgNode1Out6Amps				OBJECT-TYPE
	SYNTAX					INTEGER
	ACCESS					read-only
	STATUS					mandatory
	DESCRIPTION			"PG Outlet 6 amps"
	::= { node1PG 48 }

pgNode1Out6Watts			OBJECT-TYPE
	SYNTAX					INTEGER
	ACCESS					read-only
	STATUS					mandatory
	DESCRIPTION			"PG Outlet 6 watts"
	::= { node1PG 49 }


pgNode1Out6State			OBJECT-TYPE
	SYNTAX					INTEGER { off(1),on(2),cycle(3) }
	ACCESS					read-only
	STATUS					mandatory
	DESCRIPTION			"PG Outlet 6 state"
	::= { node1PG 50 }

pgNode1Out6Cmd				OBJECT-TYPE
	SYNTAX					INTEGER { off(1),on(2),cycle(3) }
	ACCESS					read-write
	STATUS					mandatory
	DESCRIPTION			"PG Outlet 6 command"
	::= { node1PG 51 }

pgNode1Out7Name				OBJECT-TYPE
	SYNTAX					DisplayString
	ACCESS					read-write
	STATUS					mandatory
	DESCRIPTION			"PG Outlet 7 name"
	::= { node1PG 52 }

pgNode1Out7CustVoice	OBJECT-TYPE
	SYNTAX					DisplayString
	ACCESS					read-write
	STATUS					mandatory
	DESCRIPTION			"PG Outlet 7 custom voice"
	::= { node1PG 53 }

pgNode1Out7Volts			OBJECT-TYPE
	SYNTAX					INTEGER
	ACCESS					read-only
	STATUS					mandatory
	DESCRIPTION			"PG Outlet 7 volts"
	::= { node1PG 54 }

pgNode1Out7Amps				OBJECT-TYPE
	SYNTAX					INTEGER
	ACCESS					read-only
	STATUS					mandatory
	DESCRIPTION			"PG Outlet 7 amps"
	::= { node1PG 55 }

pgNode1Out7Watts			OBJECT-TYPE
	SYNTAX					INTEGER
	ACCESS					read-only
	STATUS					mandatory
	DESCRIPTION			"PG Outlet 7 watts"
	::= { node1PG 56 }

pgNode1Out7State			OBJECT-TYPE
	SYNTAX					INTEGER { off(1),on(2),cycle(3) }
	ACCESS					read-only
	STATUS					mandatory
	DESCRIPTION			"PG Outlet 7 state"
	::= { node1PG 57 }

pgNode1Out7Cmd				OBJECT-TYPE
	SYNTAX					INTEGER { off(1),on(2),cycle(3) }
	ACCESS					read-write
	STATUS					mandatory
	DESCRIPTION			"PG Outlet 7 command"
	::= { node1PG 58 }

pgNode1Out8Name				OBJECT-TYPE
	SYNTAX					DisplayString
	ACCESS					read-write
	STATUS					mandatory
	DESCRIPTION			"PG Outlet 8 name"
	::= { node1PG 59 }

pgNode1Out8CustVoice	OBJECT-TYPE
	SYNTAX					DisplayString
	ACCESS					read-write
	STATUS					mandatory
	DESCRIPTION			"PG Outlet 8 custom voice"
	::= { node1PG 60 }

pgNode1Out8Volts			OBJECT-TYPE
	SYNTAX					INTEGER
	ACCESS					read-only
	STATUS					mandatory
	DESCRIPTION			"PG Outlet 8 volts"
	::= { node1PG 61 }

pgNode1Out8Amps				OBJECT-TYPE
	SYNTAX					INTEGER
	ACCESS					read-only
	STATUS					mandatory
	DESCRIPTION			"PG Outlet 8 amps"
	::= { node1PG 62 }

pgNode1Out8Watts			OBJECT-TYPE
	SYNTAX					INTEGER
	ACCESS					read-only
	STATUS					mandatory
	DESCRIPTION			"PG Outlet 8 watts"
	::= { node1PG 63 }


pgNode1Out8State			OBJECT-TYPE
	SYNTAX					INTEGER { off(1),on(2),cycle(3) }
	ACCESS					read-only
	STATUS					mandatory
	DESCRIPTION			"PG Outlet 8 state"
	::= { node1PG 64 }

pgNode1Out8Cmd				OBJECT-TYPE
	SYNTAX					INTEGER { off(1),on(2),cycle(3) }
	ACCESS					read-write
	STATUS					mandatory
	DESCRIPTION			"PG Outlet 8 command"
	::= { node1PG 65 }

pgNode2InUse					OBJECT-TYPE
	SYNTAX					INTEGER { false(1),true(2) }
	ACCESS					read-only
	STATUS					mandatory
	DESCRIPTION			"PG in use"
	::= { node2PG 1 }

pgNode2Status					OBJECT-TYPE
	SYNTAX					INTEGER { normal(1),pending(2), trouble(3) }
	ACCESS					read-only
	STATUS					mandatory
	DESCRIPTION			"PG status"
	::= { node2PG 2 }

pgNode2StatusSupport	OBJECT-TYPE
	SYNTAX					INTEGER { true1(1),false(2) }
	ACCESS					read-only
	STATUS					mandatory
	DESCRIPTION			"PG status support level"
	::= { node2PG 3 }

pgNode2Ver						OBJECT-TYPE
	SYNTAX					INTEGER { pgate1(1),pgate2(2) }
	ACCESS					read-only
	STATUS					mandatory
	DESCRIPTION			"PG version"
	::= { node2PG 4 }

pgNode2Volts					OBJECT-TYPE
	SYNTAX					INTEGER
	ACCESS					read-only
	STATUS					mandatory
	DESCRIPTION			"PG voltage"
	::= { node2PG 5 }

pgNode2Amps						OBJECT-TYPE
	SYNTAX					INTEGER
	ACCESS					read-only
	STATUS					mandatory
	DESCRIPTION			"PG amps"
	::= { node2PG 6 }

pgNode2Watts					OBJECT-TYPE
	SYNTAX					INTEGER
	ACCESS					read-only
	STATUS					mandatory
	DESCRIPTION			"PG Watts"
	::= { node2PG 7 }

pgNode2Name						OBJECT-TYPE
	SYNTAX					DisplayString
	ACCESS					read-write
	STATUS					mandatory
	DESCRIPTION			"PG name"
	::= { node2PG 8 }

pgNode2CustVoice			OBJECT-TYPE
	SYNTAX					DisplayString
	ACCESS					read-write
	STATUS					mandatory
	DESCRIPTION			"PG custom voice"
	::= { node2PG 9 }

pgNode2Out1Name				OBJECT-TYPE
	SYNTAX					DisplayString
	ACCESS					read-write
	STATUS					mandatory
	DESCRIPTION			"PG Outlet 1 name"
	::= { node2PG 10 }

pgNode2Out1CustVoice	OBJECT-TYPE
	SYNTAX					DisplayString
	ACCESS					read-write
	STATUS					mandatory
	DESCRIPTION			"PG Outlet 1 custom voice"
	::= { node2PG 11 }

pgNode2Out1Volts			OBJECT-TYPE
	SYNTAX					INTEGER
	ACCESS					read-only
	STATUS					mandatory
	DESCRIPTION			"PG Outlet 1 volts"
	::= { node2PG 12 }

pgNode2Out1Amps				OBJECT-TYPE
	SYNTAX					INTEGER
	ACCESS					read-only
	STATUS					mandatory
	DESCRIPTION			"PG Outlet 1 amps"
	::= { node2PG 13 }

pgNode2Out1Watts			OBJECT-TYPE
	SYNTAX					INTEGER
	ACCESS					read-only
	STATUS					mandatory
	DESCRIPTION			"PG Outlet 1 watts"
	::= { node2PG 14 }

pgNode2Out1State			OBJECT-TYPE
	SYNTAX					INTEGER { off(1),on(2),cycle(3) }
	ACCESS					read-only
	STATUS					mandatory
	DESCRIPTION			"PG Outlet 1 state"
	::= { node2PG 15 }

pgNode2Out1Cmd				OBJECT-TYPE
	SYNTAX					INTEGER { off(1),on(2),cycle(3) }
	ACCESS					read-write
	STATUS					mandatory
	DESCRIPTION			"PG Outlet 1 command"
	::= { node2PG 16 }

pgNode2Out2Name				OBJECT-TYPE
	SYNTAX					DisplayString
	ACCESS					read-write
	STATUS					mandatory
	DESCRIPTION			"PG Outlet 2 name"
	::= { node2PG 17 }

pgNode2Out2CustVoice	OBJECT-TYPE
	SYNTAX					DisplayString
	ACCESS					read-write
	STATUS					mandatory
	DESCRIPTION			"PG Outlet 2 custom voice"
	::= { node2PG 18 }

pgNode2Out2Volts			OBJECT-TYPE
	SYNTAX					INTEGER
	ACCESS					read-only
	STATUS					mandatory
	DESCRIPTION			"PG Outlet 2 volts"
	::= { node2PG 19 }

pgNode2Out2Amps				OBJECT-TYPE
	SYNTAX					INTEGER
	ACCESS					read-only
	STATUS					mandatory
	DESCRIPTION			"PG Outlet 2 amps"
	::= { node2PG 20 }

pgNode2Out2Watts			OBJECT-TYPE
	SYNTAX					INTEGER
	ACCESS					read-only
	STATUS					mandatory
	DESCRIPTION			"PG Outlet 2 watts"
	::= { node2PG 21 }


pgNode2Out2State			OBJECT-TYPE
	SYNTAX					INTEGER { off(1),on(2),cycle(3) }
	ACCESS					read-only
	STATUS					mandatory
	DESCRIPTION			"PG Outlet 2 state"
	::= { node2PG 22 }

pgNode2Out2Cmd				OBJECT-TYPE
	SYNTAX					INTEGER { off(1),on(2),cycle(3) }
	ACCESS					read-write
	STATUS					mandatory
	DESCRIPTION			"PG Outlet 2 command"
	::= { node2PG 23 }

pgNode2Out3Name				OBJECT-TYPE
	SYNTAX					DisplayString
	ACCESS					read-write
	STATUS					mandatory
	DESCRIPTION			"PG Outlet 3 name"
	::= { node2PG 24 }

pgNode2Out3CustVoice	OBJECT-TYPE
	SYNTAX					DisplayString
	ACCESS					read-write
	STATUS					mandatory
	DESCRIPTION			"PG Outlet 3 custom voice"
	::= { node2PG 25 }

pgNode2Out3Volts			OBJECT-TYPE
	SYNTAX					INTEGER
	ACCESS					read-only
	STATUS					mandatory
	DESCRIPTION			"PG Outlet 3 volts"
	::= { node2PG 26 }

pgNode2Out3Amps				OBJECT-TYPE
	SYNTAX					INTEGER
	ACCESS					read-only
	STATUS					mandatory
	DESCRIPTION			"PG Outlet 3 amps"
	::= { node2PG 27 }

pgNode2Out3Watts			OBJECT-TYPE
	SYNTAX					INTEGER
	ACCESS					read-only
	STATUS					mandatory
	DESCRIPTION			"PG Outlet 3 watts"
	::= { node2PG 28 }

pgNode2Out3State			OBJECT-TYPE
	SYNTAX					INTEGER { off(1),on(2),cycle(3) }
	ACCESS					read-only
	STATUS					mandatory
	DESCRIPTION			"PG Outlet 3 state"
	::= { node2PG 29 }

pgNode2Out3Cmd				OBJECT-TYPE
	SYNTAX					INTEGER { off(1),on(2),cycle(3) }
	ACCESS					read-write
	STATUS					mandatory
	DESCRIPTION			"PG Outlet 3 command"
	::= { node2PG 30 }

pgNode2Out4Name				OBJECT-TYPE
	SYNTAX					DisplayString
	ACCESS					read-write
	STATUS					mandatory
	DESCRIPTION			"PG Outlet 4 name"
	::= { node2PG 31 }

pgNode2Out4CustVoice	OBJECT-TYPE
	SYNTAX					DisplayString
	ACCESS					read-write
	STATUS					mandatory
	DESCRIPTION			"PG Outlet 4 custom voice"
	::= { node2PG 32 }

pgNode2Out4Volts			OBJECT-TYPE
	SYNTAX					INTEGER
	ACCESS					read-only
	STATUS					mandatory
	DESCRIPTION			"PG Outlet 4 volts"
	::= { node2PG 33 }

pgNode2Out4Amps				OBJECT-TYPE
	SYNTAX					INTEGER
	ACCESS					read-only
	STATUS					mandatory
	DESCRIPTION			"PG Outlet 4 amps"
	::= { node2PG 34 }

pgNode2Out4Watts			OBJECT-TYPE
	SYNTAX					INTEGER
	ACCESS					read-only
	STATUS					mandatory
	DESCRIPTION			"PG Outlet 4 watts"
	::= { node2PG 35 }

pgNode2Out4State			OBJECT-TYPE
	SYNTAX					INTEGER { off(1),on(2),cycle(3) }
	ACCESS					read-only
	STATUS					mandatory
	DESCRIPTION			"PG Outlet 4 state"
	::= { node2PG 36 }

pgNode2Out4Cmd				OBJECT-TYPE
	SYNTAX					INTEGER { off(1),on(2),cycle(3) }
	ACCESS					read-write
	STATUS					mandatory
	DESCRIPTION			"PG Outlet 4 command"
	::= { node2PG 37 }

pgNode2Out5Name				OBJECT-TYPE
	SYNTAX					DisplayString
	ACCESS					read-write
	STATUS					mandatory
	DESCRIPTION			"PG Outlet 5 name"
	::= { node2PG 38 }

pgNode2Out5CustVoice	OBJECT-TYPE
	SYNTAX					DisplayString
	ACCESS					read-write
	STATUS					mandatory
	DESCRIPTION			"PG Outlet 5 custom voice"
	::= { node2PG 39 }

pgNode2Out5Volts			OBJECT-TYPE
	SYNTAX					INTEGER
	ACCESS					read-only
	STATUS					mandatory
	DESCRIPTION			"PG Outlet 5 volts"
	::= { node2PG 40 }

pgNode2Out5Amps				OBJECT-TYPE
	SYNTAX					INTEGER
	ACCESS					read-only
	STATUS					mandatory
	DESCRIPTION			"PG Outlet 5 amps"
	::= { node2PG 41 }

pgNode2Out5Watts			OBJECT-TYPE
	SYNTAX					INTEGER
	ACCESS					read-only
	STATUS					mandatory
	DESCRIPTION			"PG Outlet 5 watts"
	::= { node2PG 42 }

pgNode2Out5State			OBJECT-TYPE
	SYNTAX					INTEGER { off(1),on(2),cycle(3) }
	ACCESS					read-only
	STATUS					mandatory
	DESCRIPTION			"PG Outlet 5 state"
	::= { node2PG 43 }

pgNode2Out5Cmd				OBJECT-TYPE
	SYNTAX					INTEGER { off(1),on(2),cycle(3) }
	ACCESS					read-write
	STATUS					mandatory
	DESCRIPTION			"PG Outlet 5 command"
	::= { node2PG 44 }

pgNode2Out6Name				OBJECT-TYPE
	SYNTAX					DisplayString
	ACCESS					read-write
	STATUS					mandatory
	DESCRIPTION			"PG Outlet 6 name"
	::= { node2PG 45 }

pgNode2Out6CustVoice	OBJECT-TYPE
	SYNTAX					DisplayString
	ACCESS					read-write
	STATUS					mandatory
	DESCRIPTION			"PG Outlet 6 custom voice"
	::= { node2PG 46 }

pgNode2Out6Volts			OBJECT-TYPE
	SYNTAX					INTEGER
	ACCESS					read-only
	STATUS					mandatory
	DESCRIPTION			"PG Outlet 6 volts"
	::= { node2PG 47 }

pgNode2Out6Amps				OBJECT-TYPE
	SYNTAX					INTEGER
	ACCESS					read-only
	STATUS					mandatory
	DESCRIPTION			"PG Outlet 6 amps"
	::= { node2PG 48 }

pgNode2Out6Watts			OBJECT-TYPE
	SYNTAX					INTEGER
	ACCESS					read-only
	STATUS					mandatory
	DESCRIPTION			"PG Outlet 6 watts"
	::= { node2PG 49 }


pgNode2Out6State			OBJECT-TYPE
	SYNTAX					INTEGER { off(1),on(2),cycle(3) }
	ACCESS					read-only
	STATUS					mandatory
	DESCRIPTION			"PG Outlet 6 state"
	::= { node2PG 50 }

pgNode2Out6Cmd				OBJECT-TYPE
	SYNTAX					INTEGER { off(1),on(2),cycle(3) }
	ACCESS					read-write
	STATUS					mandatory
	DESCRIPTION			"PG Outlet 6 command"
	::= { node2PG 51 }

pgNode2Out7Name				OBJECT-TYPE
	SYNTAX					DisplayString
	ACCESS					read-write
	STATUS					mandatory
	DESCRIPTION			"PG Outlet 7 name"
	::= { node2PG 52 }

pgNode2Out7CustVoice	OBJECT-TYPE
	SYNTAX					DisplayString
	ACCESS					read-write
	STATUS					mandatory
	DESCRIPTION			"PG Outlet 7 custom voice"
	::= { node2PG 53 }

pgNode2Out7Volts			OBJECT-TYPE
	SYNTAX					INTEGER
	ACCESS					read-only
	STATUS					mandatory
	DESCRIPTION			"PG Outlet 7 volts"
	::= { node2PG 54 }

pgNode2Out7Amps				OBJECT-TYPE
	SYNTAX					INTEGER
	ACCESS					read-only
	STATUS					mandatory
	DESCRIPTION			"PG Outlet 7 amps"
	::= { node2PG 55 }

pgNode2Out7Watts			OBJECT-TYPE
	SYNTAX					INTEGER
	ACCESS					read-only
	STATUS					mandatory
	DESCRIPTION			"PG Outlet 7 watts"
	::= { node2PG 56 }

pgNode2Out7State			OBJECT-TYPE
	SYNTAX					INTEGER { off(1),on(2),cycle(3) }
	ACCESS					read-only
	STATUS					mandatory
	DESCRIPTION			"PG Outlet 7 state"
	::= { node2PG 57 }

pgNode2Out7Cmd				OBJECT-TYPE
	SYNTAX					INTEGER { off(1),on(2),cycle(3) }
	ACCESS					read-write
	STATUS					mandatory
	DESCRIPTION			"PG Outlet 7 command"
	::= { node2PG 58 }

pgNode2Out8Name				OBJECT-TYPE
	SYNTAX					DisplayString
	ACCESS					read-write
	STATUS					mandatory
	DESCRIPTION			"PG Outlet 8 name"
	::= { node2PG 59 }

pgNode2Out8CustVoice	OBJECT-TYPE
	SYNTAX					DisplayString
	ACCESS					read-write
	STATUS					mandatory
	DESCRIPTION			"PG Outlet 8 custom voice"
	::= { node2PG 60 }

pgNode2Out8Volts			OBJECT-TYPE
	SYNTAX					INTEGER
	ACCESS					read-only
	STATUS					mandatory
	DESCRIPTION			"PG Outlet 8 volts"
	::= { node2PG 61 }

pgNode2Out8Amps				OBJECT-TYPE
	SYNTAX					INTEGER
	ACCESS					read-only
	STATUS					mandatory
	DESCRIPTION			"PG Outlet 8 amps"
	::= { node2PG 62 }

pgNode2Out8Watts			OBJECT-TYPE
	SYNTAX					INTEGER
	ACCESS					read-only
	STATUS					mandatory
	DESCRIPTION			"PG Outlet 8 watts"
	::= { node2PG 63 }


pgNode2Out8State			OBJECT-TYPE
	SYNTAX					INTEGER { off(1),on(2),cycle(3) }
	ACCESS					read-only
	STATUS					mandatory
	DESCRIPTION			"PG Outlet 8 state"
	::= { node2PG 64 }

pgNode2Out8Cmd				OBJECT-TYPE
	SYNTAX					INTEGER { off(1),on(2),cycle(3) }
	ACCESS					read-write
	STATUS					mandatory
	DESCRIPTION			"PG Outlet 8 command"
	::= { node2PG 65 }

pgNode3InUse					OBJECT-TYPE
	SYNTAX					INTEGER { false(1),true(2) }
	ACCESS					read-only
	STATUS					mandatory
	DESCRIPTION			"PG in use"
	::= { node3PG 1 }

pgNode3Status					OBJECT-TYPE
	SYNTAX					INTEGER { normal(1),pending(2), trouble(3) }
	ACCESS					read-only
	STATUS					mandatory
	DESCRIPTION			"PG status"
	::= { node3PG 2 }

pgNode3StatusSupport	OBJECT-TYPE
	SYNTAX					INTEGER { true1(1),false(2) }
	ACCESS					read-only
	STATUS					mandatory
	DESCRIPTION			"PG status support level"
	::= { node3PG 3 }

pgNode3Ver						OBJECT-TYPE
	SYNTAX					INTEGER { pgate1(1),pgate2(2) }
	ACCESS					read-only
	STATUS					mandatory
	DESCRIPTION			"PG version"
	::= { node3PG 4 }

pgNode3Volts					OBJECT-TYPE
	SYNTAX					INTEGER
	ACCESS					read-only
	STATUS					mandatory
	DESCRIPTION			"PG voltage"
	::= { node3PG 5 }

pgNode3Amps						OBJECT-TYPE
	SYNTAX					INTEGER
	ACCESS					read-only
	STATUS					mandatory
	DESCRIPTION			"PG amps"
	::= { node3PG 6 }

pgNode3Watts					OBJECT-TYPE
	SYNTAX					INTEGER
	ACCESS					read-only
	STATUS					mandatory
	DESCRIPTION			"PG Watts"
	::= { node3PG 7 }

pgNode3Name						OBJECT-TYPE
	SYNTAX					DisplayString
	ACCESS					read-write
	STATUS					mandatory
	DESCRIPTION			"PG name"
	::= { node3PG 8 }

pgNode3CustVoice			OBJECT-TYPE
	SYNTAX					DisplayString
	ACCESS					read-write
	STATUS					mandatory
	DESCRIPTION			"PG custom voice"
	::= { node3PG 9 }

pgNode3Out1Name				OBJECT-TYPE
	SYNTAX					DisplayString
	ACCESS					read-write
	STATUS					mandatory
	DESCRIPTION			"PG Outlet 1 name"
	::= { node3PG 10 }

pgNode3Out1CustVoice	OBJECT-TYPE
	SYNTAX					DisplayString
	ACCESS					read-write
	STATUS					mandatory
	DESCRIPTION			"PG Outlet 1 custom voice"
	::= { node3PG 11 }

pgNode3Out1Volts			OBJECT-TYPE
	SYNTAX					INTEGER
	ACCESS					read-only
	STATUS					mandatory
	DESCRIPTION			"PG Outlet 1 volts"
	::= { node3PG 12 }

pgNode3Out1Amps				OBJECT-TYPE
	SYNTAX					INTEGER
	ACCESS					read-only
	STATUS					mandatory
	DESCRIPTION			"PG Outlet 1 amps"
	::= { node3PG 13 }

pgNode3Out1Watts			OBJECT-TYPE
	SYNTAX					INTEGER
	ACCESS					read-only
	STATUS					mandatory
	DESCRIPTION			"PG Outlet 1 watts"
	::= { node3PG 14 }

pgNode3Out1State			OBJECT-TYPE
	SYNTAX					INTEGER { off(1),on(2),cycle(3) }
	ACCESS					read-only
	STATUS					mandatory
	DESCRIPTION			"PG Outlet 1 state"
	::= { node3PG 15 }

pgNode3Out1Cmd				OBJECT-TYPE
	SYNTAX					INTEGER { off(1),on(2),cycle(3) }
	ACCESS					read-write
	STATUS					mandatory
	DESCRIPTION			"PG Outlet 1 command"
	::= { node3PG 16 }

pgNode3Out2Name				OBJECT-TYPE
	SYNTAX					DisplayString
	ACCESS					read-write
	STATUS					mandatory
	DESCRIPTION			"PG Outlet 2 name"
	::= { node3PG 17 }

pgNode3Out2CustVoice	OBJECT-TYPE
	SYNTAX					DisplayString
	ACCESS					read-write
	STATUS					mandatory
	DESCRIPTION			"PG Outlet 2 custom voice"
	::= { node3PG 18 }

pgNode3Out2Volts			OBJECT-TYPE
	SYNTAX					INTEGER
	ACCESS					read-only
	STATUS					mandatory
	DESCRIPTION			"PG Outlet 2 volts"
	::= { node3PG 19 }

pgNode3Out2Amps				OBJECT-TYPE
	SYNTAX					INTEGER
	ACCESS					read-only
	STATUS					mandatory
	DESCRIPTION			"PG Outlet 2 amps"
	::= { node3PG 20 }

pgNode3Out2Watts			OBJECT-TYPE
	SYNTAX					INTEGER
	ACCESS					read-only
	STATUS					mandatory
	DESCRIPTION			"PG Outlet 2 watts"
	::= { node3PG 21 }


pgNode3Out2State			OBJECT-TYPE
	SYNTAX					INTEGER { off(1),on(2),cycle(3) }
	ACCESS					read-only
	STATUS					mandatory
	DESCRIPTION			"PG Outlet 2 state"
	::= { node3PG 22 }

pgNode3Out2Cmd				OBJECT-TYPE
	SYNTAX					INTEGER { off(1),on(2),cycle(3) }
	ACCESS					read-write
	STATUS					mandatory
	DESCRIPTION			"PG Outlet 2 command"
	::= { node3PG 23 }

pgNode3Out3Name				OBJECT-TYPE
	SYNTAX					DisplayString
	ACCESS					read-write
	STATUS					mandatory
	DESCRIPTION			"PG Outlet 3 name"
	::= { node3PG 24 }

pgNode3Out3CustVoice	OBJECT-TYPE
	SYNTAX					DisplayString
	ACCESS					read-write
	STATUS					mandatory
	DESCRIPTION			"PG Outlet 3 custom voice"
	::= { node3PG 25 }

pgNode3Out3Volts			OBJECT-TYPE
	SYNTAX					INTEGER
	ACCESS					read-only
	STATUS					mandatory
	DESCRIPTION			"PG Outlet 3 volts"
	::= { node3PG 26 }

pgNode3Out3Amps				OBJECT-TYPE
	SYNTAX					INTEGER
	ACCESS					read-only
	STATUS					mandatory
	DESCRIPTION			"PG Outlet 3 amps"
	::= { node3PG 27 }

pgNode3Out3Watts			OBJECT-TYPE
	SYNTAX					INTEGER
	ACCESS					read-only
	STATUS					mandatory
	DESCRIPTION			"PG Outlet 3 watts"
	::= { node3PG 28 }

pgNode3Out3State			OBJECT-TYPE
	SYNTAX					INTEGER { off(1),on(2),cycle(3) }
	ACCESS					read-only
	STATUS					mandatory
	DESCRIPTION			"PG Outlet 3 state"
	::= { node3PG 29 }

pgNode3Out3Cmd				OBJECT-TYPE
	SYNTAX					INTEGER { off(1),on(2),cycle(3) }
	ACCESS					read-write
	STATUS					mandatory
	DESCRIPTION			"PG Outlet 3 command"
	::= { node3PG 30 }

pgNode3Out4Name				OBJECT-TYPE
	SYNTAX					DisplayString
	ACCESS					read-write
	STATUS					mandatory
	DESCRIPTION			"PG Outlet 4 name"
	::= { node3PG 31 }

pgNode3Out4CustVoice	OBJECT-TYPE
	SYNTAX					DisplayString
	ACCESS					read-write
	STATUS					mandatory
	DESCRIPTION			"PG Outlet 4 custom voice"
	::= { node3PG 32 }

pgNode3Out4Volts			OBJECT-TYPE
	SYNTAX					INTEGER
	ACCESS					read-only
	STATUS					mandatory
	DESCRIPTION			"PG Outlet 4 volts"
	::= { node3PG 33 }

pgNode3Out4Amps				OBJECT-TYPE
	SYNTAX					INTEGER
	ACCESS					read-only
	STATUS					mandatory
	DESCRIPTION			"PG Outlet 4 amps"
	::= { node3PG 34 }

pgNode3Out4Watts			OBJECT-TYPE
	SYNTAX					INTEGER
	ACCESS					read-only
	STATUS					mandatory
	DESCRIPTION			"PG Outlet 4 watts"
	::= { node3PG 35 }

pgNode3Out4State			OBJECT-TYPE
	SYNTAX					INTEGER { off(1),on(2),cycle(3) }
	ACCESS					read-only
	STATUS					mandatory
	DESCRIPTION			"PG Outlet 4 state"
	::= { node3PG 36 }

pgNode3Out4Cmd				OBJECT-TYPE
	SYNTAX					INTEGER { off(1),on(2),cycle(3) }
	ACCESS					read-write
	STATUS					mandatory
	DESCRIPTION			"PG Outlet 4 command"
	::= { node3PG 37 }

pgNode3Out5Name				OBJECT-TYPE
	SYNTAX					DisplayString
	ACCESS					read-write
	STATUS					mandatory
	DESCRIPTION			"PG Outlet 5 name"
	::= { node3PG 38 }

pgNode3Out5CustVoice	OBJECT-TYPE
	SYNTAX					DisplayString
	ACCESS					read-write
	STATUS					mandatory
	DESCRIPTION			"PG Outlet 5 custom voice"
	::= { node3PG 39 }

pgNode3Out5Volts			OBJECT-TYPE
	SYNTAX					INTEGER
	ACCESS					read-only
	STATUS					mandatory
	DESCRIPTION			"PG Outlet 5 volts"
	::= { node3PG 40 }

pgNode3Out5Amps				OBJECT-TYPE
	SYNTAX					INTEGER
	ACCESS					read-only
	STATUS					mandatory
	DESCRIPTION			"PG Outlet 5 amps"
	::= { node3PG 41 }

pgNode3Out5Watts			OBJECT-TYPE
	SYNTAX					INTEGER
	ACCESS					read-only
	STATUS					mandatory
	DESCRIPTION			"PG Outlet 5 watts"
	::= { node3PG 42 }

pgNode3Out5State			OBJECT-TYPE
	SYNTAX					INTEGER { off(1),on(2),cycle(3) }
	ACCESS					read-only
	STATUS					mandatory
	DESCRIPTION			"PG Outlet 5 state"
	::= { node3PG 43 }

pgNode3Out5Cmd				OBJECT-TYPE
	SYNTAX					INTEGER { off(1),on(2),cycle(3) }
	ACCESS					read-write
	STATUS					mandatory
	DESCRIPTION			"PG Outlet 5 command"
	::= { node3PG 44 }

pgNode3Out6Name				OBJECT-TYPE
	SYNTAX					DisplayString
	ACCESS					read-write
	STATUS					mandatory
	DESCRIPTION			"PG Outlet 6 name"
	::= { node3PG 45 }

pgNode3Out6CustVoice	OBJECT-TYPE
	SYNTAX					DisplayString
	ACCESS					read-write
	STATUS					mandatory
	DESCRIPTION			"PG Outlet 6 custom voice"
	::= { node3PG 46 }

pgNode3Out6Volts			OBJECT-TYPE
	SYNTAX					INTEGER
	ACCESS					read-only
	STATUS					mandatory
	DESCRIPTION			"PG Outlet 6 volts"
	::= { node3PG 47 }

pgNode3Out6Amps				OBJECT-TYPE
	SYNTAX					INTEGER
	ACCESS					read-only
	STATUS					mandatory
	DESCRIPTION			"PG Outlet 6 amps"
	::= { node3PG 48 }

pgNode3Out6Watts			OBJECT-TYPE
	SYNTAX					INTEGER
	ACCESS					read-only
	STATUS					mandatory
	DESCRIPTION			"PG Outlet 6 watts"
	::= { node3PG 49 }


pgNode3Out6State			OBJECT-TYPE
	SYNTAX					INTEGER { off(1),on(2),cycle(3) }
	ACCESS					read-only
	STATUS					mandatory
	DESCRIPTION			"PG Outlet 6 state"
	::= { node3PG 50 }

pgNode3Out6Cmd				OBJECT-TYPE
	SYNTAX					INTEGER { off(1),on(2),cycle(3) }
	ACCESS					read-write
	STATUS					mandatory
	DESCRIPTION			"PG Outlet 6 command"
	::= { node3PG 51 }

pgNode3Out7Name				OBJECT-TYPE
	SYNTAX					DisplayString
	ACCESS					read-write
	STATUS					mandatory
	DESCRIPTION			"PG Outlet 7 name"
	::= { node3PG 52 }

pgNode3Out7CustVoice	OBJECT-TYPE
	SYNTAX					DisplayString
	ACCESS					read-write
	STATUS					mandatory
	DESCRIPTION			"PG Outlet 7 custom voice"
	::= { node3PG 53 }

pgNode3Out7Volts			OBJECT-TYPE
	SYNTAX					INTEGER
	ACCESS					read-only
	STATUS					mandatory
	DESCRIPTION			"PG Outlet 7 volts"
	::= { node3PG 54 }

pgNode3Out7Amps				OBJECT-TYPE
	SYNTAX					INTEGER
	ACCESS					read-only
	STATUS					mandatory
	DESCRIPTION			"PG Outlet 7 amps"
	::= { node3PG 55 }

pgNode3Out7Watts			OBJECT-TYPE
	SYNTAX					INTEGER
	ACCESS					read-only
	STATUS					mandatory
	DESCRIPTION			"PG Outlet 7 watts"
	::= { node3PG 56 }

pgNode3Out7State			OBJECT-TYPE
	SYNTAX					INTEGER { off(1),on(2),cycle(3) }
	ACCESS					read-only
	STATUS					mandatory
	DESCRIPTION			"PG Outlet 7 state"
	::= { node3PG 57 }

pgNode3Out7Cmd				OBJECT-TYPE
	SYNTAX					INTEGER { off(1),on(2),cycle(3) }
	ACCESS					read-write
	STATUS					mandatory
	DESCRIPTION			"PG Outlet 7 command"
	::= { node3PG 58 }

pgNode3Out8Name				OBJECT-TYPE
	SYNTAX					DisplayString
	ACCESS					read-write
	STATUS					mandatory
	DESCRIPTION			"PG Outlet 8 name"
	::= { node3PG 59 }

pgNode3Out8CustVoice	OBJECT-TYPE
	SYNTAX					DisplayString
	ACCESS					read-write
	STATUS					mandatory
	DESCRIPTION			"PG Outlet 8 custom voice"
	::= { node3PG 60 }

pgNode3Out8Volts			OBJECT-TYPE
	SYNTAX					INTEGER
	ACCESS					read-only
	STATUS					mandatory
	DESCRIPTION			"PG Outlet 8 volts"
	::= { node3PG 61 }

pgNode3Out8Amps				OBJECT-TYPE
	SYNTAX					INTEGER
	ACCESS					read-only
	STATUS					mandatory
	DESCRIPTION			"PG Outlet 8 amps"
	::= { node3PG 62 }

pgNode3Out8Watts			OBJECT-TYPE
	SYNTAX					INTEGER
	ACCESS					read-only
	STATUS					mandatory
	DESCRIPTION			"PG Outlet 8 watts"
	::= { node3PG 63 }

pgNode3Out8State			OBJECT-TYPE
	SYNTAX					INTEGER { off(1),on(2),cycle(3) }
	ACCESS					read-only
	STATUS					mandatory
	DESCRIPTION			"PG Outlet 8 state"
	::= { node3PG 64 }

pgNode3Out8Cmd				OBJECT-TYPE
	SYNTAX					INTEGER { off(1),on(2),cycle(3) }
	ACCESS					read-write
	STATUS					mandatory
	DESCRIPTION			"PG Outlet 8 command"
	::= { node3PG 65 }

pgNode4InUse					OBJECT-TYPE
	SYNTAX					INTEGER { false(1),true(2) }
	ACCESS					read-only
	STATUS					mandatory
	DESCRIPTION			"PG in use"
	::= { node4PG 1 }

pgNode4Status					OBJECT-TYPE
	SYNTAX					INTEGER { normal(1),pending(2), trouble(3) }
	ACCESS					read-only
	STATUS					mandatory
	DESCRIPTION			"PG status"
	::= { node4PG 2 }

pgNode4StatusSupport	OBJECT-TYPE
	SYNTAX					INTEGER { true1(1),false(2) }
	ACCESS					read-only
	STATUS					mandatory
	DESCRIPTION			"PG status support level"
	::= { node4PG 3 }

pgNode4Ver						OBJECT-TYPE
	SYNTAX					INTEGER { pgate1(1),pgate2(2) }
	ACCESS					read-only
	STATUS					mandatory
	DESCRIPTION			"PG version"
	::= { node4PG 4 }

pgNode4Volts					OBJECT-TYPE
	SYNTAX					INTEGER
	ACCESS					read-only
	STATUS					mandatory
	DESCRIPTION			"PG voltage"
	::= { node4PG 5 }

pgNode4Amps						OBJECT-TYPE
	SYNTAX					INTEGER
	ACCESS					read-only
	STATUS					mandatory
	DESCRIPTION			"PG amps"
	::= { node4PG 6 }

pgNode4Watts					OBJECT-TYPE
	SYNTAX					INTEGER
	ACCESS					read-only
	STATUS					mandatory
	DESCRIPTION			"PG Watts"
	::= { node4PG 7 }

pgNode4Name						OBJECT-TYPE
	SYNTAX					DisplayString
	ACCESS					read-write
	STATUS					mandatory
	DESCRIPTION			"PG name"
	::= { node4PG 8 }

pgNode4CustVoice			OBJECT-TYPE
	SYNTAX					DisplayString
	ACCESS					read-write
	STATUS					mandatory
	DESCRIPTION			"PG custom voice"
	::= { node4PG 9 }

pgNode4Out1Name				OBJECT-TYPE
	SYNTAX					DisplayString
	ACCESS					read-write
	STATUS					mandatory
	DESCRIPTION			"PG Outlet 1 name"
	::= { node4PG 10 }

pgNode4Out1CustVoice	OBJECT-TYPE
	SYNTAX					DisplayString
	ACCESS					read-write
	STATUS					mandatory
	DESCRIPTION			"PG Outlet 1 custom voice"
	::= { node4PG 11 }

pgNode4Out1Volts			OBJECT-TYPE
	SYNTAX					INTEGER
	ACCESS					read-only
	STATUS					mandatory
	DESCRIPTION			"PG Outlet 1 volts"
	::= { node4PG 12 }

pgNode4Out1Amps				OBJECT-TYPE
	SYNTAX					INTEGER
	ACCESS					read-only
	STATUS					mandatory
	DESCRIPTION			"PG Outlet 1 amps"
	::= { node4PG 13 }

pgNode4Out1Watts			OBJECT-TYPE
	SYNTAX					INTEGER
	ACCESS					read-only
	STATUS					mandatory
	DESCRIPTION			"PG Outlet 1 watts"
	::= { node4PG 14 }

pgNode4Out1State			OBJECT-TYPE
	SYNTAX					INTEGER { off(1),on(2),cycle(3) }
	ACCESS					read-only
	STATUS					mandatory
	DESCRIPTION			"PG Outlet 1 state"
	::= { node4PG 15 }

pgNode4Out1Cmd				OBJECT-TYPE
	SYNTAX					INTEGER { off(1),on(2),cycle(3) }
	ACCESS					read-write
	STATUS					mandatory
	DESCRIPTION			"PG Outlet 1 command"
	::= { node4PG 16 }

pgNode4Out2Name				OBJECT-TYPE
	SYNTAX					DisplayString
	ACCESS					read-write
	STATUS					mandatory
	DESCRIPTION			"PG Outlet 2 name"
	::= { node4PG 17 }

pgNode4Out2CustVoice	OBJECT-TYPE
	SYNTAX					DisplayString
	ACCESS					read-write
	STATUS					mandatory
	DESCRIPTION			"PG Outlet 2 custom voice"
	::= { node4PG 18 }

pgNode4Out2Volts			OBJECT-TYPE
	SYNTAX					INTEGER
	ACCESS					read-only
	STATUS					mandatory
	DESCRIPTION			"PG Outlet 2 volts"
	::= { node4PG 19 }

pgNode4Out2Amps				OBJECT-TYPE
	SYNTAX					INTEGER
	ACCESS					read-only
	STATUS					mandatory
	DESCRIPTION			"PG Outlet 2 amps"
	::= { node4PG 20 }

pgNode4Out2Watts			OBJECT-TYPE
	SYNTAX					INTEGER
	ACCESS					read-only
	STATUS					mandatory
	DESCRIPTION			"PG Outlet 2 watts"
	::= { node4PG 21 }


pgNode4Out2State			OBJECT-TYPE
	SYNTAX					INTEGER { off(1),on(2),cycle(3) }
	ACCESS					read-only
	STATUS					mandatory
	DESCRIPTION			"PG Outlet 2 state"
	::= { node4PG 22 }

pgNode4Out2Cmd				OBJECT-TYPE
	SYNTAX					INTEGER { off(1),on(2),cycle(3) }
	ACCESS					read-write
	STATUS					mandatory
	DESCRIPTION			"PG Outlet 2 command"
	::= { node4PG 23 }

pgNode4Out3Name				OBJECT-TYPE
	SYNTAX					DisplayString
	ACCESS					read-write
	STATUS					mandatory
	DESCRIPTION			"PG Outlet 3 name"
	::= { node4PG 24 }

pgNode4Out3CustVoice	OBJECT-TYPE
	SYNTAX					DisplayString
	ACCESS					read-write
	STATUS					mandatory
	DESCRIPTION			"PG Outlet 3 custom voice"
	::= { node4PG 25 }

pgNode4Out3Volts			OBJECT-TYPE
	SYNTAX					INTEGER
	ACCESS					read-only
	STATUS					mandatory
	DESCRIPTION			"PG Outlet 3 volts"
	::= { node4PG 26 }

pgNode4Out3Amps				OBJECT-TYPE
	SYNTAX					INTEGER
	ACCESS					read-only
	STATUS					mandatory
	DESCRIPTION			"PG Outlet 3 amps"
	::= { node4PG 27 }

pgNode4Out3Watts			OBJECT-TYPE
	SYNTAX					INTEGER
	ACCESS					read-only
	STATUS					mandatory
	DESCRIPTION			"PG Outlet 3 watts"
	::= { node4PG 28 }

pgNode4Out3State			OBJECT-TYPE
	SYNTAX					INTEGER { off(1),on(2),cycle(3) }
	ACCESS					read-only
	STATUS					mandatory
	DESCRIPTION			"PG Outlet 3 state"
	::= { node4PG 29 }

pgNode4Out3Cmd				OBJECT-TYPE
	SYNTAX					INTEGER { off(1),on(2),cycle(3) }
	ACCESS					read-write
	STATUS					mandatory
	DESCRIPTION			"PG Outlet 3 command"
	::= { node4PG 30 }

pgNode4Out4Name				OBJECT-TYPE
	SYNTAX					DisplayString
	ACCESS					read-write
	STATUS					mandatory
	DESCRIPTION			"PG Outlet 4 name"
	::= { node4PG 31 }

pgNode4Out4CustVoice	OBJECT-TYPE
	SYNTAX					DisplayString
	ACCESS					read-write
	STATUS					mandatory
	DESCRIPTION			"PG Outlet 4 custom voice"
	::= { node4PG 32 }

pgNode4Out4Volts			OBJECT-TYPE
	SYNTAX					INTEGER
	ACCESS					read-only
	STATUS					mandatory
	DESCRIPTION			"PG Outlet 4 volts"
	::= { node4PG 33 }

pgNode4Out4Amps				OBJECT-TYPE
	SYNTAX					INTEGER
	ACCESS					read-only
	STATUS					mandatory
	DESCRIPTION			"PG Outlet 4 amps"
	::= { node4PG 34 }

pgNode4Out4Watts			OBJECT-TYPE
	SYNTAX					INTEGER
	ACCESS					read-only
	STATUS					mandatory
	DESCRIPTION			"PG Outlet 4 watts"
	::= { node4PG 35 }

pgNode4Out4State			OBJECT-TYPE
	SYNTAX					INTEGER { off(1),on(2),cycle(3) }
	ACCESS					read-only
	STATUS					mandatory
	DESCRIPTION			"PG Outlet 4 state"
	::= { node4PG 36 }

pgNode4Out4Cmd				OBJECT-TYPE
	SYNTAX					INTEGER { off(1),on(2),cycle(3) }
	ACCESS					read-write
	STATUS					mandatory
	DESCRIPTION			"PG Outlet 4 command"
	::= { node4PG 37 }

pgNode4Out5Name				OBJECT-TYPE
	SYNTAX					DisplayString
	ACCESS					read-write
	STATUS					mandatory
	DESCRIPTION			"PG Outlet 5 name"
	::= { node4PG 38 }

pgNode4Out5CustVoice	OBJECT-TYPE
	SYNTAX					DisplayString
	ACCESS					read-write
	STATUS					mandatory
	DESCRIPTION			"PG Outlet 5 custom voice"
	::= { node4PG 39 }

pgNode4Out5Volts			OBJECT-TYPE
	SYNTAX					INTEGER
	ACCESS					read-only
	STATUS					mandatory
	DESCRIPTION			"PG Outlet 5 volts"
	::= { node4PG 40 }

pgNode4Out5Amps				OBJECT-TYPE
	SYNTAX					INTEGER
	ACCESS					read-only
	STATUS					mandatory
	DESCRIPTION			"PG Outlet 5 amps"
	::= { node4PG 41 }

pgNode4Out5Watts			OBJECT-TYPE
	SYNTAX					INTEGER
	ACCESS					read-only
	STATUS					mandatory
	DESCRIPTION			"PG Outlet 5 watts"
	::= { node4PG 42 }

pgNode4Out5State			OBJECT-TYPE
	SYNTAX					INTEGER { off(1),on(2),cycle(3) }
	ACCESS					read-only
	STATUS					mandatory
	DESCRIPTION			"PG Outlet 5 state"
	::= { node4PG 43 }

pgNode4Out5Cmd				OBJECT-TYPE
	SYNTAX					INTEGER { off(1),on(2),cycle(3) }
	ACCESS					read-write
	STATUS					mandatory
	DESCRIPTION			"PG Outlet 5 command"
	::= { node4PG 44 }

pgNode4Out6Name				OBJECT-TYPE
	SYNTAX					DisplayString
	ACCESS					read-write
	STATUS					mandatory
	DESCRIPTION			"PG Outlet 6 name"
	::= { node4PG 45 }

pgNode4Out6CustVoice	OBJECT-TYPE
	SYNTAX					DisplayString
	ACCESS					read-write
	STATUS					mandatory
	DESCRIPTION			"PG Outlet 6 custom voice"
	::= { node4PG 46 }

pgNode4Out6Volts			OBJECT-TYPE
	SYNTAX					INTEGER
	ACCESS					read-only
	STATUS					mandatory
	DESCRIPTION			"PG Outlet 6 volts"
	::= { node4PG 47 }

pgNode4Out6Amps				OBJECT-TYPE
	SYNTAX					INTEGER
	ACCESS					read-only
	STATUS					mandatory
	DESCRIPTION			"PG Outlet 6 amps"
	::= { node4PG 48 }

pgNode4Out6Watts			OBJECT-TYPE
	SYNTAX					INTEGER
	ACCESS					read-only
	STATUS					mandatory
	DESCRIPTION			"PG Outlet 6 watts"
	::= { node4PG 49 }


pgNode4Out6State			OBJECT-TYPE
	SYNTAX					INTEGER { off(1),on(2),cycle(3) }
	ACCESS					read-only
	STATUS					mandatory
	DESCRIPTION			"PG Outlet 6 state"
	::= { node4PG 50 }

pgNode4Out6Cmd				OBJECT-TYPE
	SYNTAX					INTEGER { off(1),on(2),cycle(3) }
	ACCESS					read-write
	STATUS					mandatory
	DESCRIPTION			"PG Outlet 6 command"
	::= { node4PG 51 }

pgNode4Out7Name				OBJECT-TYPE
	SYNTAX					DisplayString
	ACCESS					read-write
	STATUS					mandatory
	DESCRIPTION			"PG Outlet 7 name"
	::= { node4PG 52 }

pgNode4Out7CustVoice	OBJECT-TYPE
	SYNTAX					DisplayString
	ACCESS					read-write
	STATUS					mandatory
	DESCRIPTION			"PG Outlet 7 custom voice"
	::= { node4PG 53 }

pgNode4Out7Volts			OBJECT-TYPE
	SYNTAX					INTEGER
	ACCESS					read-only
	STATUS					mandatory
	DESCRIPTION			"PG Outlet 7 volts"
	::= { node4PG 54 }

pgNode4Out7Amps				OBJECT-TYPE
	SYNTAX					INTEGER
	ACCESS					read-only
	STATUS					mandatory
	DESCRIPTION			"PG Outlet 7 amps"
	::= { node4PG 55 }

pgNode4Out7Watts			OBJECT-TYPE
	SYNTAX					INTEGER
	ACCESS					read-only
	STATUS					mandatory
	DESCRIPTION			"PG Outlet 7 watts"
	::= { node4PG 56 }

pgNode4Out7State			OBJECT-TYPE
	SYNTAX					INTEGER { off(1),on(2),cycle(3) }
	ACCESS					read-only
	STATUS					mandatory
	DESCRIPTION			"PG Outlet 7 state"
	::= { node4PG 57 }

pgNode4Out7Cmd				OBJECT-TYPE
	SYNTAX					INTEGER { off(1),on(2),cycle(3) }
	ACCESS					read-write
	STATUS					mandatory
	DESCRIPTION			"PG Outlet 7 command"
	::= { node4PG 58 }

pgNode4Out8Name				OBJECT-TYPE
	SYNTAX					DisplayString
	ACCESS					read-write
	STATUS					mandatory
	DESCRIPTION			"PG Outlet 8 name"
	::= { node4PG 59 }

pgNode4Out8CustVoice	OBJECT-TYPE
	SYNTAX					DisplayString
	ACCESS					read-write
	STATUS					mandatory
	DESCRIPTION			"PG Outlet 8 custom voice"
	::= { node4PG 60 }

pgNode4Out8Volts			OBJECT-TYPE
	SYNTAX					INTEGER
	ACCESS					read-only
	STATUS					mandatory
	DESCRIPTION			"PG Outlet 8 volts"
	::= { node4PG 61 }

pgNode4Out8Amps				OBJECT-TYPE
	SYNTAX					INTEGER
	ACCESS					read-only
	STATUS					mandatory
	DESCRIPTION			"PG Outlet 8 amps"
	::= { node4PG 62 }

pgNode4Out8Watts			OBJECT-TYPE
	SYNTAX					INTEGER
	ACCESS					read-only
	STATUS					mandatory
	DESCRIPTION			"PG Outlet 8 watts"
	::= { node4PG 63 }

pgNode4Out8State			OBJECT-TYPE
	SYNTAX					INTEGER { off(1),on(2),cycle(3) }
	ACCESS					read-only
	STATUS					mandatory
	DESCRIPTION			"PG Outlet 8 state"
	::= { node4PG 64 }

pgNode4Out8Cmd				OBJECT-TYPE
	SYNTAX					INTEGER { off(1),on(2),cycle(3) }
	ACCESS					read-write
	STATUS					mandatory
	DESCRIPTION			"PG Outlet 8 command"
	::= { node4PG 65 }

pgNode5InUse					OBJECT-TYPE
	SYNTAX					INTEGER { false(1),true(2) }
	ACCESS					read-only
	STATUS					mandatory
	DESCRIPTION			"PG in use"
	::= { node5PG 1 }

pgNode5Status					OBJECT-TYPE
	SYNTAX					INTEGER { normal(1),pending(2), trouble(3) }
	ACCESS					read-only
	STATUS					mandatory
	DESCRIPTION			"PG status"
	::= { node5PG 2 }

pgNode5StatusSupport	OBJECT-TYPE
	SYNTAX					INTEGER { true1(1),false(2) }
	ACCESS					read-only
	STATUS					mandatory
	DESCRIPTION			"PG status support level"
	::= { node5PG 3 }

pgNode5Ver						OBJECT-TYPE
	SYNTAX					INTEGER { pgate1(1),pgate2(2) }
	ACCESS					read-only
	STATUS					mandatory
	DESCRIPTION			"PG version"
	::= { node5PG 4 }

pgNode5Volts					OBJECT-TYPE
	SYNTAX					INTEGER
	ACCESS					read-only
	STATUS					mandatory
	DESCRIPTION			"PG voltage"
	::= { node5PG 5 }

pgNode5Amps						OBJECT-TYPE
	SYNTAX					INTEGER
	ACCESS					read-only
	STATUS					mandatory
	DESCRIPTION			"PG amps"
	::= { node5PG 6 }

pgNode5Watts					OBJECT-TYPE
	SYNTAX					INTEGER
	ACCESS					read-only
	STATUS					mandatory
	DESCRIPTION			"PG Watts"
	::= { node5PG 7 }

pgNode5Name						OBJECT-TYPE
	SYNTAX					DisplayString
	ACCESS					read-write
	STATUS					mandatory
	DESCRIPTION			"PG name"
	::= { node5PG 8 }

pgNode5CustVoice			OBJECT-TYPE
	SYNTAX					DisplayString
	ACCESS					read-write
	STATUS					mandatory
	DESCRIPTION			"PG custom voice"
	::= { node5PG 9 }

pgNode5Out1Name				OBJECT-TYPE
	SYNTAX					DisplayString
	ACCESS					read-write
	STATUS					mandatory
	DESCRIPTION			"PG Outlet 1 name"
	::= { node5PG 10 }

pgNode5Out1CustVoice	OBJECT-TYPE
	SYNTAX					DisplayString
	ACCESS					read-write
	STATUS					mandatory
	DESCRIPTION			"PG Outlet 1 custom voice"
	::= { node5PG 11 }

pgNode5Out1Volts			OBJECT-TYPE
	SYNTAX					INTEGER
	ACCESS					read-only
	STATUS					mandatory
	DESCRIPTION			"PG Outlet 1 volts"
	::= { node5PG 12 }

pgNode5Out1Amps				OBJECT-TYPE
	SYNTAX					INTEGER
	ACCESS					read-only
	STATUS					mandatory
	DESCRIPTION			"PG Outlet 1 amps"
	::= { node5PG 13 }

pgNode5Out1Watts			OBJECT-TYPE
	SYNTAX					INTEGER
	ACCESS					read-only
	STATUS					mandatory
	DESCRIPTION			"PG Outlet 1 watts"
	::= { node5PG 14 }

pgNode5Out1State			OBJECT-TYPE
	SYNTAX					INTEGER { off(1),on(2),cycle(3) }
	ACCESS					read-only
	STATUS					mandatory
	DESCRIPTION			"PG Outlet 1 state"
	::= { node5PG 15 }

pgNode5Out1Cmd				OBJECT-TYPE
	SYNTAX					INTEGER { off(1),on(2),cycle(3) }
	ACCESS					read-write
	STATUS					mandatory
	DESCRIPTION			"PG Outlet 1 command"
	::= { node5PG 16 }

pgNode5Out2Name				OBJECT-TYPE
	SYNTAX					DisplayString
	ACCESS					read-write
	STATUS					mandatory
	DESCRIPTION			"PG Outlet 2 name"
	::= { node5PG 17 }

pgNode5Out2CustVoice	OBJECT-TYPE
	SYNTAX					DisplayString
	ACCESS					read-write
	STATUS					mandatory
	DESCRIPTION			"PG Outlet 2 custom voice"
	::= { node5PG 18 }

pgNode5Out2Volts			OBJECT-TYPE
	SYNTAX					INTEGER
	ACCESS					read-only
	STATUS					mandatory
	DESCRIPTION			"PG Outlet 2 volts"
	::= { node5PG 19 }

pgNode5Out2Amps				OBJECT-TYPE
	SYNTAX					INTEGER
	ACCESS					read-only
	STATUS					mandatory
	DESCRIPTION			"PG Outlet 2 amps"
	::= { node5PG 20 }

pgNode5Out2Watts			OBJECT-TYPE
	SYNTAX					INTEGER
	ACCESS					read-only
	STATUS					mandatory
	DESCRIPTION			"PG Outlet 2 watts"
	::= { node5PG 21 }


pgNode5Out2State			OBJECT-TYPE
	SYNTAX					INTEGER { off(1),on(2),cycle(3) }
	ACCESS					read-only
	STATUS					mandatory
	DESCRIPTION			"PG Outlet 2 state"
	::= { node5PG 22 }

pgNode5Out2Cmd				OBJECT-TYPE
	SYNTAX					INTEGER { off(1),on(2),cycle(3) }
	ACCESS					read-write
	STATUS					mandatory
	DESCRIPTION			"PG Outlet 2 command"
	::= { node5PG 23 }

pgNode5Out3Name				OBJECT-TYPE
	SYNTAX					DisplayString
	ACCESS					read-write
	STATUS					mandatory
	DESCRIPTION			"PG Outlet 3 name"
	::= { node5PG 24 }

pgNode5Out3CustVoice	OBJECT-TYPE
	SYNTAX					DisplayString
	ACCESS					read-write
	STATUS					mandatory
	DESCRIPTION			"PG Outlet 3 custom voice"
	::= { node5PG 25 }

pgNode5Out3Volts			OBJECT-TYPE
	SYNTAX					INTEGER
	ACCESS					read-only
	STATUS					mandatory
	DESCRIPTION			"PG Outlet 3 volts"
	::= { node5PG 26 }

pgNode5Out3Amps				OBJECT-TYPE
	SYNTAX					INTEGER
	ACCESS					read-only
	STATUS					mandatory
	DESCRIPTION			"PG Outlet 3 amps"
	::= { node5PG 27 }

pgNode5Out3Watts			OBJECT-TYPE
	SYNTAX					INTEGER
	ACCESS					read-only
	STATUS					mandatory
	DESCRIPTION			"PG Outlet 3 watts"
	::= { node5PG 28 }

pgNode5Out3State			OBJECT-TYPE
	SYNTAX					INTEGER { off(1),on(2),cycle(3) }
	ACCESS					read-only
	STATUS					mandatory
	DESCRIPTION			"PG Outlet 3 state"
	::= { node5PG 29 }

pgNode5Out3Cmd				OBJECT-TYPE
	SYNTAX					INTEGER { off(1),on(2),cycle(3) }
	ACCESS					read-write
	STATUS					mandatory
	DESCRIPTION			"PG Outlet 3 command"
	::= { node5PG 30 }

pgNode5Out4Name				OBJECT-TYPE
	SYNTAX					DisplayString
	ACCESS					read-write
	STATUS					mandatory
	DESCRIPTION			"PG Outlet 4 name"
	::= { node5PG 31 }

pgNode5Out4CustVoice	OBJECT-TYPE
	SYNTAX					DisplayString
	ACCESS					read-write
	STATUS					mandatory
	DESCRIPTION			"PG Outlet 4 custom voice"
	::= { node5PG 32 }

pgNode5Out4Volts			OBJECT-TYPE
	SYNTAX					INTEGER
	ACCESS					read-only
	STATUS					mandatory
	DESCRIPTION			"PG Outlet 4 volts"
	::= { node5PG 33 }

pgNode5Out4Amps				OBJECT-TYPE
	SYNTAX					INTEGER
	ACCESS					read-only
	STATUS					mandatory
	DESCRIPTION			"PG Outlet 4 amps"
	::= { node5PG 34 }

pgNode5Out4Watts			OBJECT-TYPE
	SYNTAX					INTEGER
	ACCESS					read-only
	STATUS					mandatory
	DESCRIPTION			"PG Outlet 4 watts"
	::= { node5PG 35 }

pgNode5Out4State			OBJECT-TYPE
	SYNTAX					INTEGER { off(1),on(2),cycle(3) }
	ACCESS					read-only
	STATUS					mandatory
	DESCRIPTION			"PG Outlet 4 state"
	::= { node5PG 36 }

pgNode5Out4Cmd				OBJECT-TYPE
	SYNTAX					INTEGER { off(1),on(2),cycle(3) }
	ACCESS					read-write
	STATUS					mandatory
	DESCRIPTION			"PG Outlet 4 command"
	::= { node5PG 37 }

pgNode5Out5Name				OBJECT-TYPE
	SYNTAX					DisplayString
	ACCESS					read-write
	STATUS					mandatory
	DESCRIPTION			"PG Outlet 5 name"
	::= { node5PG 38 }

pgNode5Out5CustVoice	OBJECT-TYPE
	SYNTAX					DisplayString
	ACCESS					read-write
	STATUS					mandatory
	DESCRIPTION			"PG Outlet 5 custom voice"
	::= { node5PG 39 }

pgNode5Out5Volts			OBJECT-TYPE
	SYNTAX					INTEGER
	ACCESS					read-only
	STATUS					mandatory
	DESCRIPTION			"PG Outlet 5 volts"
	::= { node5PG 40 }

pgNode5Out5Amps				OBJECT-TYPE
	SYNTAX					INTEGER
	ACCESS					read-only
	STATUS					mandatory
	DESCRIPTION			"PG Outlet 5 amps"
	::= { node5PG 41 }

pgNode5Out5Watts			OBJECT-TYPE
	SYNTAX					INTEGER
	ACCESS					read-only
	STATUS					mandatory
	DESCRIPTION			"PG Outlet 5 watts"
	::= { node5PG 42 }

pgNode5Out5State			OBJECT-TYPE
	SYNTAX					INTEGER { off(1),on(2),cycle(3) }
	ACCESS					read-only
	STATUS					mandatory
	DESCRIPTION			"PG Outlet 5 state"
	::= { node5PG 43 }

pgNode5Out5Cmd				OBJECT-TYPE
	SYNTAX					INTEGER { off(1),on(2),cycle(3) }
	ACCESS					read-write
	STATUS					mandatory
	DESCRIPTION			"PG Outlet 5 command"
	::= { node5PG 44 }

pgNode5Out6Name				OBJECT-TYPE
	SYNTAX					DisplayString
	ACCESS					read-write
	STATUS					mandatory
	DESCRIPTION			"PG Outlet 6 name"
	::= { node5PG 45 }

pgNode5Out6CustVoice	OBJECT-TYPE
	SYNTAX					DisplayString
	ACCESS					read-write
	STATUS					mandatory
	DESCRIPTION			"PG Outlet 6 custom voice"
	::= { node5PG 46 }

pgNode5Out6Volts			OBJECT-TYPE
	SYNTAX					INTEGER
	ACCESS					read-only
	STATUS					mandatory
	DESCRIPTION			"PG Outlet 6 volts"
	::= { node5PG 47 }

pgNode5Out6Amps				OBJECT-TYPE
	SYNTAX					INTEGER
	ACCESS					read-only
	STATUS					mandatory
	DESCRIPTION			"PG Outlet 6 amps"
	::= { node5PG 48 }

pgNode5Out6Watts			OBJECT-TYPE
	SYNTAX					INTEGER
	ACCESS					read-only
	STATUS					mandatory
	DESCRIPTION			"PG Outlet 6 watts"
	::= { node5PG 49 }


pgNode5Out6State			OBJECT-TYPE
	SYNTAX					INTEGER { off(1),on(2),cycle(3) }
	ACCESS					read-only
	STATUS					mandatory
	DESCRIPTION			"PG Outlet 6 state"
	::= { node5PG 50 }

pgNode5Out6Cmd				OBJECT-TYPE
	SYNTAX					INTEGER { off(1),on(2),cycle(3) }
	ACCESS					read-write
	STATUS					mandatory
	DESCRIPTION			"PG Outlet 6 command"
	::= { node5PG 51 }

pgNode5Out7Name				OBJECT-TYPE
	SYNTAX					DisplayString
	ACCESS					read-write
	STATUS					mandatory
	DESCRIPTION			"PG Outlet 7 name"
	::= { node5PG 52 }

pgNode5Out7CustVoice	OBJECT-TYPE
	SYNTAX					DisplayString
	ACCESS					read-write
	STATUS					mandatory
	DESCRIPTION			"PG Outlet 7 custom voice"
	::= { node5PG 53 }

pgNode5Out7Volts			OBJECT-TYPE
	SYNTAX					INTEGER
	ACCESS					read-only
	STATUS					mandatory
	DESCRIPTION			"PG Outlet 7 volts"
	::= { node5PG 54 }

pgNode5Out7Amps				OBJECT-TYPE
	SYNTAX					INTEGER
	ACCESS					read-only
	STATUS					mandatory
	DESCRIPTION			"PG Outlet 7 amps"
	::= { node5PG 55 }

pgNode5Out7Watts			OBJECT-TYPE
	SYNTAX					INTEGER
	ACCESS					read-only
	STATUS					mandatory
	DESCRIPTION			"PG Outlet 7 watts"
	::= { node5PG 56 }

pgNode5Out7State			OBJECT-TYPE
	SYNTAX					INTEGER { off(1),on(2),cycle(3) }
	ACCESS					read-only
	STATUS					mandatory
	DESCRIPTION			"PG Outlet 7 state"
	::= { node5PG 57 }

pgNode5Out7Cmd				OBJECT-TYPE
	SYNTAX					INTEGER { off(1),on(2),cycle(3) }
	ACCESS					read-write
	STATUS					mandatory
	DESCRIPTION			"PG Outlet 7 command"
	::= { node5PG 58 }

pgNode5Out8Name				OBJECT-TYPE
	SYNTAX					DisplayString
	ACCESS					read-write
	STATUS					mandatory
	DESCRIPTION			"PG Outlet 8 name"
	::= { node5PG 59 }

pgNode5Out8CustVoice	OBJECT-TYPE
	SYNTAX					DisplayString
	ACCESS					read-write
	STATUS					mandatory
	DESCRIPTION			"PG Outlet 8 custom voice"
	::= { node5PG 60 }

pgNode5Out8Volts			OBJECT-TYPE
	SYNTAX					INTEGER
	ACCESS					read-only
	STATUS					mandatory
	DESCRIPTION			"PG Outlet 8 volts"
	::= { node5PG 61 }

pgNode5Out8Amps				OBJECT-TYPE
	SYNTAX					INTEGER
	ACCESS					read-only
	STATUS					mandatory
	DESCRIPTION			"PG Outlet 8 amps"
	::= { node5PG 62 }

pgNode5Out8Watts			OBJECT-TYPE
	SYNTAX					INTEGER
	ACCESS					read-only
	STATUS					mandatory
	DESCRIPTION			"PG Outlet 8 watts"
	::= { node5PG 63 }

pgNode5Out8State			OBJECT-TYPE
	SYNTAX					INTEGER { off(1),on(2),cycle(3) }
	ACCESS					read-only
	STATUS					mandatory
	DESCRIPTION			"PG Outlet 8 state"
	::= { node5PG 64 }

pgNode5Out8Cmd				OBJECT-TYPE
	SYNTAX					INTEGER { off(1),on(2),cycle(3) }
	ACCESS					read-write
	STATUS					mandatory
	DESCRIPTION			"PG Outlet 8 command"
	::= { node5PG 65 }

pgNode6InUse					OBJECT-TYPE
	SYNTAX					INTEGER { false(1),true(2) }
	ACCESS					read-only
	STATUS					mandatory
	DESCRIPTION			"PG in use"
	::= { node6PG 1 }

pgNode6Status					OBJECT-TYPE
	SYNTAX					INTEGER { normal(1),pending(2), trouble(3) }
	ACCESS					read-only
	STATUS					mandatory
	DESCRIPTION			"PG status"
	::= { node6PG 2 }

pgNode6StatusSupport	OBJECT-TYPE
	SYNTAX					INTEGER { true1(1),false(2) }
	ACCESS					read-only
	STATUS					mandatory
	DESCRIPTION			"PG status support level"
	::= { node6PG 3 }

pgNode6Ver						OBJECT-TYPE
	SYNTAX					INTEGER { pgate1(1),pgate2(2) }
	ACCESS					read-only
	STATUS					mandatory
	DESCRIPTION			"PG version"
	::= { node6PG 4 }

pgNode6Volts					OBJECT-TYPE
	SYNTAX					INTEGER
	ACCESS					read-only
	STATUS					mandatory
	DESCRIPTION			"PG voltage"
	::= { node6PG 5 }

pgNode6Amps						OBJECT-TYPE
	SYNTAX					INTEGER
	ACCESS					read-only
	STATUS					mandatory
	DESCRIPTION			"PG amps"
	::= { node6PG 6 }

pgNode6Watts					OBJECT-TYPE
	SYNTAX					INTEGER
	ACCESS					read-only
	STATUS					mandatory
	DESCRIPTION			"PG Watts"
	::= { node6PG 7 }

pgNode6Name						OBJECT-TYPE
	SYNTAX					DisplayString
	ACCESS					read-write
	STATUS					mandatory
	DESCRIPTION			"PG name"
	::= { node6PG 8 }

pgNode6CustVoice			OBJECT-TYPE
	SYNTAX					DisplayString
	ACCESS					read-write
	STATUS					mandatory
	DESCRIPTION			"PG custom voice"
	::= { node6PG 9 }

pgNode6Out1Name				OBJECT-TYPE
	SYNTAX					DisplayString
	ACCESS					read-write
	STATUS					mandatory
	DESCRIPTION			"PG Outlet 1 name"
	::= { node6PG 10 }

pgNode6Out1CustVoice	OBJECT-TYPE
	SYNTAX					DisplayString
	ACCESS					read-write
	STATUS					mandatory
	DESCRIPTION			"PG Outlet 1 custom voice"
	::= { node6PG 11 }

pgNode6Out1Volts			OBJECT-TYPE
	SYNTAX					INTEGER
	ACCESS					read-only
	STATUS					mandatory
	DESCRIPTION			"PG Outlet 1 volts"
	::= { node6PG 12 }

pgNode6Out1Amps				OBJECT-TYPE
	SYNTAX					INTEGER
	ACCESS					read-only
	STATUS					mandatory
	DESCRIPTION			"PG Outlet 1 amps"
	::= { node6PG 13 }

pgNode6Out1Watts			OBJECT-TYPE
	SYNTAX					INTEGER
	ACCESS					read-only
	STATUS					mandatory
	DESCRIPTION			"PG Outlet 1 watts"
	::= { node6PG 14 }

pgNode6Out1State			OBJECT-TYPE
	SYNTAX					INTEGER { off(1),on(2),cycle(3) }
	ACCESS					read-only
	STATUS					mandatory
	DESCRIPTION			"PG Outlet 1 state"
	::= { node6PG 15 }

pgNode6Out1Cmd				OBJECT-TYPE
	SYNTAX					INTEGER { off(1),on(2),cycle(3) }
	ACCESS					read-write
	STATUS					mandatory
	DESCRIPTION			"PG Outlet 1 command"
	::= { node6PG 16 }

pgNode6Out2Name				OBJECT-TYPE
	SYNTAX					DisplayString
	ACCESS					read-write
	STATUS					mandatory
	DESCRIPTION			"PG Outlet 2 name"
	::= { node6PG 17 }

pgNode6Out2CustVoice	OBJECT-TYPE
	SYNTAX					DisplayString
	ACCESS					read-write
	STATUS					mandatory
	DESCRIPTION			"PG Outlet 2 custom voice"
	::= { node6PG 18 }

pgNode6Out2Volts			OBJECT-TYPE
	SYNTAX					INTEGER
	ACCESS					read-only
	STATUS					mandatory
	DESCRIPTION			"PG Outlet 2 volts"
	::= { node6PG 19 }

pgNode6Out2Amps				OBJECT-TYPE
	SYNTAX					INTEGER
	ACCESS					read-only
	STATUS					mandatory
	DESCRIPTION			"PG Outlet 2 amps"
	::= { node6PG 20 }

pgNode6Out2Watts			OBJECT-TYPE
	SYNTAX					INTEGER
	ACCESS					read-only
	STATUS					mandatory
	DESCRIPTION			"PG Outlet 2 watts"
	::= { node6PG 21 }


pgNode6Out2State			OBJECT-TYPE
	SYNTAX					INTEGER { off(1),on(2),cycle(3) }
	ACCESS					read-only
	STATUS					mandatory
	DESCRIPTION			"PG Outlet 2 state"
	::= { node6PG 22 }

pgNode6Out2Cmd				OBJECT-TYPE
	SYNTAX					INTEGER { off(1),on(2),cycle(3) }
	ACCESS					read-write
	STATUS					mandatory
	DESCRIPTION			"PG Outlet 2 command"
	::= { node6PG 23 }

pgNode6Out3Name				OBJECT-TYPE
	SYNTAX					DisplayString
	ACCESS					read-write
	STATUS					mandatory
	DESCRIPTION			"PG Outlet 3 name"
	::= { node6PG 24 }

pgNode6Out3CustVoice	OBJECT-TYPE
	SYNTAX					DisplayString
	ACCESS					read-write
	STATUS					mandatory
	DESCRIPTION			"PG Outlet 3 custom voice"
	::= { node6PG 25 }

pgNode6Out3Volts			OBJECT-TYPE
	SYNTAX					INTEGER
	ACCESS					read-only
	STATUS					mandatory
	DESCRIPTION			"PG Outlet 3 volts"
	::= { node6PG 26 }

pgNode6Out3Amps				OBJECT-TYPE
	SYNTAX					INTEGER
	ACCESS					read-only
	STATUS					mandatory
	DESCRIPTION			"PG Outlet 3 amps"
	::= { node6PG 27 }

pgNode6Out3Watts			OBJECT-TYPE
	SYNTAX					INTEGER
	ACCESS					read-only
	STATUS					mandatory
	DESCRIPTION			"PG Outlet 3 watts"
	::= { node6PG 28 }

pgNode6Out3State			OBJECT-TYPE
	SYNTAX					INTEGER { off(1),on(2),cycle(3) }
	ACCESS					read-only
	STATUS					mandatory
	DESCRIPTION			"PG Outlet 3 state"
	::= { node6PG 29 }

pgNode6Out3Cmd				OBJECT-TYPE
	SYNTAX					INTEGER { off(1),on(2),cycle(3) }
	ACCESS					read-write
	STATUS					mandatory
	DESCRIPTION			"PG Outlet 3 command"
	::= { node6PG 30 }

pgNode6Out4Name				OBJECT-TYPE
	SYNTAX					DisplayString
	ACCESS					read-write
	STATUS					mandatory
	DESCRIPTION			"PG Outlet 4 name"
	::= { node6PG 31 }

pgNode6Out4CustVoice	OBJECT-TYPE
	SYNTAX					DisplayString
	ACCESS					read-write
	STATUS					mandatory
	DESCRIPTION			"PG Outlet 4 custom voice"
	::= { node6PG 32 }

pgNode6Out4Volts			OBJECT-TYPE
	SYNTAX					INTEGER
	ACCESS					read-only
	STATUS					mandatory
	DESCRIPTION			"PG Outlet 4 volts"
	::= { node6PG 33 }

pgNode6Out4Amps				OBJECT-TYPE
	SYNTAX					INTEGER
	ACCESS					read-only
	STATUS					mandatory
	DESCRIPTION			"PG Outlet 4 amps"
	::= { node6PG 34 }

pgNode6Out4Watts			OBJECT-TYPE
	SYNTAX					INTEGER
	ACCESS					read-only
	STATUS					mandatory
	DESCRIPTION			"PG Outlet 4 watts"
	::= { node6PG 35 }

pgNode6Out4State			OBJECT-TYPE
	SYNTAX					INTEGER { off(1),on(2),cycle(3) }
	ACCESS					read-only
	STATUS					mandatory
	DESCRIPTION			"PG Outlet 4 state"
	::= { node6PG 36 }

pgNode6Out4Cmd				OBJECT-TYPE
	SYNTAX					INTEGER { off(1),on(2),cycle(3) }
	ACCESS					read-write
	STATUS					mandatory
	DESCRIPTION			"PG Outlet 4 command"
	::= { node6PG 37 }

pgNode6Out5Name				OBJECT-TYPE
	SYNTAX					DisplayString
	ACCESS					read-write
	STATUS					mandatory
	DESCRIPTION			"PG Outlet 5 name"
	::= { node6PG 38 }

pgNode6Out5CustVoice	OBJECT-TYPE
	SYNTAX					DisplayString
	ACCESS					read-write
	STATUS					mandatory
	DESCRIPTION			"PG Outlet 5 custom voice"
	::= { node6PG 39 }

pgNode6Out5Volts			OBJECT-TYPE
	SYNTAX					INTEGER
	ACCESS					read-only
	STATUS					mandatory
	DESCRIPTION			"PG Outlet 5 volts"
	::= { node6PG 40 }

pgNode6Out5Amps				OBJECT-TYPE
	SYNTAX					INTEGER
	ACCESS					read-only
	STATUS					mandatory
	DESCRIPTION			"PG Outlet 5 amps"
	::= { node6PG 41 }

pgNode6Out5Watts			OBJECT-TYPE
	SYNTAX					INTEGER
	ACCESS					read-only
	STATUS					mandatory
	DESCRIPTION			"PG Outlet 5 watts"
	::= { node6PG 42 }

pgNode6Out5State			OBJECT-TYPE
	SYNTAX					INTEGER { off(1),on(2),cycle(3) }
	ACCESS					read-only
	STATUS					mandatory
	DESCRIPTION			"PG Outlet 5 state"
	::= { node6PG 43 }

pgNode6Out5Cmd				OBJECT-TYPE
	SYNTAX					INTEGER { off(1),on(2),cycle(3) }
	ACCESS					read-write
	STATUS					mandatory
	DESCRIPTION			"PG Outlet 5 command"
	::= { node6PG 44 }

pgNode6Out6Name				OBJECT-TYPE
	SYNTAX					DisplayString
	ACCESS					read-write
	STATUS					mandatory
	DESCRIPTION			"PG Outlet 6 name"
	::= { node6PG 45 }

pgNode6Out6CustVoice	OBJECT-TYPE
	SYNTAX					DisplayString
	ACCESS					read-write
	STATUS					mandatory
	DESCRIPTION			"PG Outlet 6 custom voice"
	::= { node6PG 46 }

pgNode6Out6Volts			OBJECT-TYPE
	SYNTAX					INTEGER
	ACCESS					read-only
	STATUS					mandatory
	DESCRIPTION			"PG Outlet 6 volts"
	::= { node6PG 47 }

pgNode6Out6Amps				OBJECT-TYPE
	SYNTAX					INTEGER
	ACCESS					read-only
	STATUS					mandatory
	DESCRIPTION			"PG Outlet 6 amps"
	::= { node6PG 48 }

pgNode6Out6Watts			OBJECT-TYPE
	SYNTAX					INTEGER
	ACCESS					read-only
	STATUS					mandatory
	DESCRIPTION			"PG Outlet 6 watts"
	::= { node6PG 49 }


pgNode6Out6State			OBJECT-TYPE
	SYNTAX					INTEGER { off(1),on(2),cycle(3) }
	ACCESS					read-only
	STATUS					mandatory
	DESCRIPTION			"PG Outlet 6 state"
	::= { node6PG 50 }

pgNode6Out6Cmd				OBJECT-TYPE
	SYNTAX					INTEGER { off(1),on(2),cycle(3) }
	ACCESS					read-write
	STATUS					mandatory
	DESCRIPTION			"PG Outlet 6 command"
	::= { node6PG 51 }

pgNode6Out7Name				OBJECT-TYPE
	SYNTAX					DisplayString
	ACCESS					read-write
	STATUS					mandatory
	DESCRIPTION			"PG Outlet 7 name"
	::= { node6PG 52 }

pgNode6Out7CustVoice	OBJECT-TYPE
	SYNTAX					DisplayString
	ACCESS					read-write
	STATUS					mandatory
	DESCRIPTION			"PG Outlet 7 custom voice"
	::= { node6PG 53 }

pgNode6Out7Volts			OBJECT-TYPE
	SYNTAX					INTEGER
	ACCESS					read-only
	STATUS					mandatory
	DESCRIPTION			"PG Outlet 7 volts"
	::= { node6PG 54 }

pgNode6Out7Amps				OBJECT-TYPE
	SYNTAX					INTEGER
	ACCESS					read-only
	STATUS					mandatory
	DESCRIPTION			"PG Outlet 7 amps"
	::= { node6PG 55 }

pgNode6Out7Watts			OBJECT-TYPE
	SYNTAX					INTEGER
	ACCESS					read-only
	STATUS					mandatory
	DESCRIPTION			"PG Outlet 7 watts"
	::= { node6PG 56 }

pgNode6Out7State			OBJECT-TYPE
	SYNTAX					INTEGER { off(1),on(2),cycle(3) }
	ACCESS					read-only
	STATUS					mandatory
	DESCRIPTION			"PG Outlet 7 state"
	::= { node6PG 57 }

pgNode6Out7Cmd				OBJECT-TYPE
	SYNTAX					INTEGER { off(1),on(2),cycle(3) }
	ACCESS					read-write
	STATUS					mandatory
	DESCRIPTION			"PG Outlet 7 command"
	::= { node6PG 58 }

pgNode6Out8Name				OBJECT-TYPE
	SYNTAX					DisplayString
	ACCESS					read-write
	STATUS					mandatory
	DESCRIPTION			"PG Outlet 8 name"
	::= { node6PG 59 }

pgNode6Out8CustVoice	OBJECT-TYPE
	SYNTAX					DisplayString
	ACCESS					read-write
	STATUS					mandatory
	DESCRIPTION			"PG Outlet 8 custom voice"
	::= { node6PG 60 }

pgNode6Out8Volts			OBJECT-TYPE
	SYNTAX					INTEGER
	ACCESS					read-only
	STATUS					mandatory
	DESCRIPTION			"PG Outlet 8 volts"
	::= { node6PG 61 }

pgNode6Out8Amps				OBJECT-TYPE
	SYNTAX					INTEGER
	ACCESS					read-only
	STATUS					mandatory
	DESCRIPTION			"PG Outlet 8 amps"
	::= { node6PG 62 }

pgNode6Out8Watts			OBJECT-TYPE
	SYNTAX					INTEGER
	ACCESS					read-only
	STATUS					mandatory
	DESCRIPTION			"PG Outlet 8 watts"
	::= { node6PG 63 }

pgNode6Out8State			OBJECT-TYPE
	SYNTAX					INTEGER { off(1),on(2),cycle(3) }
	ACCESS					read-only
	STATUS					mandatory
	DESCRIPTION			"PG Outlet 8 state"
	::= { node6PG 64 }

pgNode6Out8Cmd				OBJECT-TYPE
	SYNTAX					INTEGER { off(1),on(2),cycle(3) }
	ACCESS					read-write
	STATUS					mandatory
	DESCRIPTION			"PG Outlet 8 command"
	::= { node6PG 65 }

pgNode7InUse					OBJECT-TYPE
	SYNTAX					INTEGER { false(1),true(2) }
	ACCESS					read-only
	STATUS					mandatory
	DESCRIPTION			"PG in use"
	::= { node7PG 1 }

pgNode7Status					OBJECT-TYPE
	SYNTAX					INTEGER { normal(1),pending(2), trouble(3) }
	ACCESS					read-only
	STATUS					mandatory
	DESCRIPTION			"PG status"
	::= { node7PG 2 }

pgNode7StatusSupport	OBJECT-TYPE
	SYNTAX					INTEGER { true1(1),false(2) }
	ACCESS					read-only
	STATUS					mandatory
	DESCRIPTION			"PG status support level"
	::= { node7PG 3 }

pgNode7Ver						OBJECT-TYPE
	SYNTAX					INTEGER { pgate1(1),pgate2(2) }
	ACCESS					read-only
	STATUS					mandatory
	DESCRIPTION			"PG version"
	::= { node7PG 4 }

pgNode7Volts					OBJECT-TYPE
	SYNTAX					INTEGER
	ACCESS					read-only
	STATUS					mandatory
	DESCRIPTION			"PG voltage"
	::= { node7PG 5 }

pgNode7Amps						OBJECT-TYPE
	SYNTAX					INTEGER
	ACCESS					read-only
	STATUS					mandatory
	DESCRIPTION			"PG amps"
	::= { node7PG 6 }

pgNode7Watts					OBJECT-TYPE
	SYNTAX					INTEGER
	ACCESS					read-only
	STATUS					mandatory
	DESCRIPTION			"PG Watts"
	::= { node7PG 7 }

pgNode7Name						OBJECT-TYPE
	SYNTAX					DisplayString
	ACCESS					read-write
	STATUS					mandatory
	DESCRIPTION			"PG name"
	::= { node7PG 8 }

pgNode7CustVoice			OBJECT-TYPE
	SYNTAX					DisplayString
	ACCESS					read-write
	STATUS					mandatory
	DESCRIPTION			"PG custom voice"
	::= { node7PG 9 }

pgNode7Out1Name				OBJECT-TYPE
	SYNTAX					DisplayString
	ACCESS					read-write
	STATUS					mandatory
	DESCRIPTION			"PG Outlet 1 name"
	::= { node7PG 10 }

pgNode7Out1CustVoice	OBJECT-TYPE
	SYNTAX					DisplayString
	ACCESS					read-write
	STATUS					mandatory
	DESCRIPTION			"PG Outlet 1 custom voice"
	::= { node7PG 11 }

pgNode7Out1Volts			OBJECT-TYPE
	SYNTAX					INTEGER
	ACCESS					read-only
	STATUS					mandatory
	DESCRIPTION			"PG Outlet 1 volts"
	::= { node7PG 12 }

pgNode7Out1Amps				OBJECT-TYPE
	SYNTAX					INTEGER
	ACCESS					read-only
	STATUS					mandatory
	DESCRIPTION			"PG Outlet 1 amps"
	::= { node7PG 13 }

pgNode7Out1Watts			OBJECT-TYPE
	SYNTAX					INTEGER
	ACCESS					read-only
	STATUS					mandatory
	DESCRIPTION			"PG Outlet 1 watts"
	::= { node7PG 14 }

pgNode7Out1State			OBJECT-TYPE
	SYNTAX					INTEGER { off(1),on(2),cycle(3) }
	ACCESS					read-only
	STATUS					mandatory
	DESCRIPTION			"PG Outlet 1 state"
	::= { node7PG 15 }

pgNode7Out1Cmd				OBJECT-TYPE
	SYNTAX					INTEGER { off(1),on(2),cycle(3) }
	ACCESS					read-write
	STATUS					mandatory
	DESCRIPTION			"PG Outlet 1 command"
	::= { node7PG 16 }

pgNode7Out2Name				OBJECT-TYPE
	SYNTAX					DisplayString
	ACCESS					read-write
	STATUS					mandatory
	DESCRIPTION			"PG Outlet 2 name"
	::= { node7PG 17 }

pgNode7Out2CustVoice	OBJECT-TYPE
	SYNTAX					DisplayString
	ACCESS					read-write
	STATUS					mandatory
	DESCRIPTION			"PG Outlet 2 custom voice"
	::= { node7PG 18 }

pgNode7Out2Volts			OBJECT-TYPE
	SYNTAX					INTEGER
	ACCESS					read-only
	STATUS					mandatory
	DESCRIPTION			"PG Outlet 2 volts"
	::= { node7PG 19 }

pgNode7Out2Amps				OBJECT-TYPE
	SYNTAX					INTEGER
	ACCESS					read-only
	STATUS					mandatory
	DESCRIPTION			"PG Outlet 2 amps"
	::= { node7PG 20 }

pgNode7Out2Watts			OBJECT-TYPE
	SYNTAX					INTEGER
	ACCESS					read-only
	STATUS					mandatory
	DESCRIPTION			"PG Outlet 2 watts"
	::= { node7PG 21 }


pgNode7Out2State			OBJECT-TYPE
	SYNTAX					INTEGER { off(1),on(2),cycle(3) }
	ACCESS					read-only
	STATUS					mandatory
	DESCRIPTION			"PG Outlet 2 state"
	::= { node7PG 22 }

pgNode7Out2Cmd				OBJECT-TYPE
	SYNTAX					INTEGER { off(1),on(2),cycle(3) }
	ACCESS					read-write
	STATUS					mandatory
	DESCRIPTION			"PG Outlet 2 command"
	::= { node7PG 23 }

pgNode7Out3Name				OBJECT-TYPE
	SYNTAX					DisplayString
	ACCESS					read-write
	STATUS					mandatory
	DESCRIPTION			"PG Outlet 3 name"
	::= { node7PG 24 }

pgNode7Out3CustVoice	OBJECT-TYPE
	SYNTAX					DisplayString
	ACCESS					read-write
	STATUS					mandatory
	DESCRIPTION			"PG Outlet 3 custom voice"
	::= { node7PG 25 }

pgNode7Out3Volts			OBJECT-TYPE
	SYNTAX					INTEGER
	ACCESS					read-only
	STATUS					mandatory
	DESCRIPTION			"PG Outlet 3 volts"
	::= { node7PG 26 }

pgNode7Out3Amps				OBJECT-TYPE
	SYNTAX					INTEGER
	ACCESS					read-only
	STATUS					mandatory
	DESCRIPTION			"PG Outlet 3 amps"
	::= { node7PG 27 }

pgNode7Out3Watts			OBJECT-TYPE
	SYNTAX					INTEGER
	ACCESS					read-only
	STATUS					mandatory
	DESCRIPTION			"PG Outlet 3 watts"
	::= { node7PG 28 }

pgNode7Out3State			OBJECT-TYPE
	SYNTAX					INTEGER { off(1),on(2),cycle(3) }
	ACCESS					read-only
	STATUS					mandatory
	DESCRIPTION			"PG Outlet 3 state"
	::= { node7PG 29 }

pgNode7Out3Cmd				OBJECT-TYPE
	SYNTAX					INTEGER { off(1),on(2),cycle(3) }
	ACCESS					read-write
	STATUS					mandatory
	DESCRIPTION			"PG Outlet 3 command"
	::= { node7PG 30 }

pgNode7Out4Name				OBJECT-TYPE
	SYNTAX					DisplayString
	ACCESS					read-write
	STATUS					mandatory
	DESCRIPTION			"PG Outlet 4 name"
	::= { node7PG 31 }

pgNode7Out4CustVoice	OBJECT-TYPE
	SYNTAX					DisplayString
	ACCESS					read-write
	STATUS					mandatory
	DESCRIPTION			"PG Outlet 4 custom voice"
	::= { node7PG 32 }

pgNode7Out4Volts			OBJECT-TYPE
	SYNTAX					INTEGER
	ACCESS					read-only
	STATUS					mandatory
	DESCRIPTION			"PG Outlet 4 volts"
	::= { node7PG 33 }

pgNode7Out4Amps				OBJECT-TYPE
	SYNTAX					INTEGER
	ACCESS					read-only
	STATUS					mandatory
	DESCRIPTION			"PG Outlet 4 amps"
	::= { node7PG 34 }

pgNode7Out4Watts			OBJECT-TYPE
	SYNTAX					INTEGER
	ACCESS					read-only
	STATUS					mandatory
	DESCRIPTION			"PG Outlet 4 watts"
	::= { node7PG 35 }

pgNode7Out4State			OBJECT-TYPE
	SYNTAX					INTEGER { off(1),on(2),cycle(3) }
	ACCESS					read-only
	STATUS					mandatory
	DESCRIPTION			"PG Outlet 4 state"
	::= { node7PG 36 }

pgNode7Out4Cmd				OBJECT-TYPE
	SYNTAX					INTEGER { off(1),on(2),cycle(3) }
	ACCESS					read-write
	STATUS					mandatory
	DESCRIPTION			"PG Outlet 4 command"
	::= { node7PG 37 }

pgNode7Out5Name				OBJECT-TYPE
	SYNTAX					DisplayString
	ACCESS					read-write
	STATUS					mandatory
	DESCRIPTION			"PG Outlet 5 name"
	::= { node7PG 38 }

pgNode7Out5CustVoice	OBJECT-TYPE
	SYNTAX					DisplayString
	ACCESS					read-write
	STATUS					mandatory
	DESCRIPTION			"PG Outlet 5 custom voice"
	::= { node7PG 39 }

pgNode7Out5Volts			OBJECT-TYPE
	SYNTAX					INTEGER
	ACCESS					read-only
	STATUS					mandatory
	DESCRIPTION			"PG Outlet 5 volts"
	::= { node7PG 40 }

pgNode7Out5Amps				OBJECT-TYPE
	SYNTAX					INTEGER
	ACCESS					read-only
	STATUS					mandatory
	DESCRIPTION			"PG Outlet 5 amps"
	::= { node7PG 41 }

pgNode7Out5Watts			OBJECT-TYPE
	SYNTAX					INTEGER
	ACCESS					read-only
	STATUS					mandatory
	DESCRIPTION			"PG Outlet 5 watts"
	::= { node7PG 42 }

pgNode7Out5State			OBJECT-TYPE
	SYNTAX					INTEGER { off(1),on(2),cycle(3) }
	ACCESS					read-only
	STATUS					mandatory
	DESCRIPTION			"PG Outlet 5 state"
	::= { node7PG 43 }

pgNode7Out5Cmd				OBJECT-TYPE
	SYNTAX					INTEGER { off(1),on(2),cycle(3) }
	ACCESS					read-write
	STATUS					mandatory
	DESCRIPTION			"PG Outlet 5 command"
	::= { node7PG 44 }

pgNode7Out6Name				OBJECT-TYPE
	SYNTAX					DisplayString
	ACCESS					read-write
	STATUS					mandatory
	DESCRIPTION			"PG Outlet 6 name"
	::= { node7PG 45 }

pgNode7Out6CustVoice	OBJECT-TYPE
	SYNTAX					DisplayString
	ACCESS					read-write
	STATUS					mandatory
	DESCRIPTION			"PG Outlet 6 custom voice"
	::= { node7PG 46 }

pgNode7Out6Volts			OBJECT-TYPE
	SYNTAX					INTEGER
	ACCESS					read-only
	STATUS					mandatory
	DESCRIPTION			"PG Outlet 6 volts"
	::= { node7PG 47 }

pgNode7Out6Amps				OBJECT-TYPE
	SYNTAX					INTEGER
	ACCESS					read-only
	STATUS					mandatory
	DESCRIPTION			"PG Outlet 6 amps"
	::= { node7PG 48 }

pgNode7Out6Watts			OBJECT-TYPE
	SYNTAX					INTEGER
	ACCESS					read-only
	STATUS					mandatory
	DESCRIPTION			"PG Outlet 6 watts"
	::= { node7PG 49 }


pgNode7Out6State			OBJECT-TYPE
	SYNTAX					INTEGER { off(1),on(2),cycle(3) }
	ACCESS					read-only
	STATUS					mandatory
	DESCRIPTION			"PG Outlet 6 state"
	::= { node7PG 50 }

pgNode7Out6Cmd				OBJECT-TYPE
	SYNTAX					INTEGER { off(1),on(2),cycle(3) }
	ACCESS					read-write
	STATUS					mandatory
	DESCRIPTION			"PG Outlet 6 command"
	::= { node7PG 51 }

pgNode7Out7Name				OBJECT-TYPE
	SYNTAX					DisplayString
	ACCESS					read-write
	STATUS					mandatory
	DESCRIPTION			"PG Outlet 7 name"
	::= { node7PG 52 }

pgNode7Out7CustVoice	OBJECT-TYPE
	SYNTAX					DisplayString
	ACCESS					read-write
	STATUS					mandatory
	DESCRIPTION			"PG Outlet 7 custom voice"
	::= { node7PG 53 }

pgNode7Out7Volts			OBJECT-TYPE
	SYNTAX					INTEGER
	ACCESS					read-only
	STATUS					mandatory
	DESCRIPTION			"PG Outlet 7 volts"
	::= { node7PG 54 }

pgNode7Out7Amps				OBJECT-TYPE
	SYNTAX					INTEGER
	ACCESS					read-only
	STATUS					mandatory
	DESCRIPTION			"PG Outlet 7 amps"
	::= { node7PG 55 }

pgNode7Out7Watts			OBJECT-TYPE
	SYNTAX					INTEGER
	ACCESS					read-only
	STATUS					mandatory
	DESCRIPTION			"PG Outlet 7 watts"
	::= { node7PG 56 }

pgNode7Out7State			OBJECT-TYPE
	SYNTAX					INTEGER { off(1),on(2),cycle(3) }
	ACCESS					read-only
	STATUS					mandatory
	DESCRIPTION			"PG Outlet 7 state"
	::= { node7PG 57 }

pgNode7Out7Cmd				OBJECT-TYPE
	SYNTAX					INTEGER { off(1),on(2),cycle(3) }
	ACCESS					read-write
	STATUS					mandatory
	DESCRIPTION			"PG Outlet 7 command"
	::= { node7PG 58 }

pgNode7Out8Name				OBJECT-TYPE
	SYNTAX					DisplayString
	ACCESS					read-write
	STATUS					mandatory
	DESCRIPTION			"PG Outlet 8 name"
	::= { node7PG 59 }

pgNode7Out8CustVoice	OBJECT-TYPE
	SYNTAX					DisplayString
	ACCESS					read-write
	STATUS					mandatory
	DESCRIPTION			"PG Outlet 8 custom voice"
	::= { node7PG 60 }

pgNode7Out8Volts			OBJECT-TYPE
	SYNTAX					INTEGER
	ACCESS					read-only
	STATUS					mandatory
	DESCRIPTION			"PG Outlet 8 volts"
	::= { node7PG 61 }

pgNode7Out8Amps				OBJECT-TYPE
	SYNTAX					INTEGER
	ACCESS					read-only
	STATUS					mandatory
	DESCRIPTION			"PG Outlet 8 amps"
	::= { node7PG 62 }

pgNode7Out8Watts			OBJECT-TYPE
	SYNTAX					INTEGER
	ACCESS					read-only
	STATUS					mandatory
	DESCRIPTION			"PG Outlet 8 watts"
	::= { node7PG 63 }

pgNode7Out8State			OBJECT-TYPE
	SYNTAX					INTEGER { off(1),on(2),cycle(3) }
	ACCESS					read-only
	STATUS					mandatory
	DESCRIPTION			"PG Outlet 8 state"
	::= { node7PG 64 }

pgNode7Out8Cmd				OBJECT-TYPE
	SYNTAX					INTEGER { off(1),on(2),cycle(3) }
	ACCESS					read-write
	STATUS					mandatory
	DESCRIPTION			"PG Outlet 8 command"
	::= { node7PG 65 }

pg9InUse					OBJECT-TYPE
	SYNTAX					INTEGER { false(1),true(2) }
	ACCESS					read-only
	STATUS					mandatory
	DESCRIPTION			"PG in use"
	::= { node8PG 1 }

pgNode8Status					OBJECT-TYPE
	SYNTAX					INTEGER { normal(1),pending(2), trouble(3) }
	ACCESS					read-only
	STATUS					mandatory
	DESCRIPTION			"PG status"
	::= { node8PG 2 }

pgNode8StatusSupport	OBJECT-TYPE
	SYNTAX					INTEGER { true1(1),false(2) }
	ACCESS					read-only
	STATUS					mandatory
	DESCRIPTION			"PG status support level"
	::= { node8PG 3 }

pgNode8Ver						OBJECT-TYPE
	SYNTAX					INTEGER { pgate1(1),pgate2(2) }
	ACCESS					read-only
	STATUS					mandatory
	DESCRIPTION			"PG version"
	::= { node8PG 4 }

pgNode8Volts					OBJECT-TYPE
	SYNTAX					INTEGER
	ACCESS					read-only
	STATUS					mandatory
	DESCRIPTION			"PG voltage"
	::= { node8PG 5 }

pgNode8Amps						OBJECT-TYPE
	SYNTAX					INTEGER
	ACCESS					read-only
	STATUS					mandatory
	DESCRIPTION			"PG amps"
	::= { node8PG 6 }

pgNode8Watts					OBJECT-TYPE
	SYNTAX					INTEGER
	ACCESS					read-only
	STATUS					mandatory
	DESCRIPTION			"PG Watts"
	::= { node8PG 7 }

pgNode8Name						OBJECT-TYPE
	SYNTAX					DisplayString
	ACCESS					read-write
	STATUS					mandatory
	DESCRIPTION			"PG name"
	::= { node8PG 8 }

pgNode8CustVoice			OBJECT-TYPE
	SYNTAX					DisplayString
	ACCESS					read-write
	STATUS					mandatory
	DESCRIPTION			"PG custom voice"
	::= { node8PG 9 }

pgNode8Out1Name				OBJECT-TYPE
	SYNTAX					DisplayString
	ACCESS					read-write
	STATUS					mandatory
	DESCRIPTION			"PG Outlet 1 name"
	::= { node8PG 10 }

pgNode8Out1CustVoice	OBJECT-TYPE
	SYNTAX					DisplayString
	ACCESS					read-write
	STATUS					mandatory
	DESCRIPTION			"PG Outlet 1 custom voice"
	::= { node8PG 11 }

pgNode8Out1Volts			OBJECT-TYPE
	SYNTAX					INTEGER
	ACCESS					read-only
	STATUS					mandatory
	DESCRIPTION			"PG Outlet 1 volts"
	::= { node8PG 12 }

pgNode8Out1Amps				OBJECT-TYPE
	SYNTAX					INTEGER
	ACCESS					read-only
	STATUS					mandatory
	DESCRIPTION			"PG Outlet 1 amps"
	::= { node8PG 13 }

pgNode8Out1Watts			OBJECT-TYPE
	SYNTAX					INTEGER
	ACCESS					read-only
	STATUS					mandatory
	DESCRIPTION			"PG Outlet 1 watts"
	::= { node8PG 14 }

pgNode8Out1State			OBJECT-TYPE
	SYNTAX					INTEGER { off(1),on(2),cycle(3) }
	ACCESS					read-only
	STATUS					mandatory
	DESCRIPTION			"PG Outlet 1 state"
	::= { node8PG 15 }

pgNode8Out1Cmd				OBJECT-TYPE
	SYNTAX					INTEGER { off(1),on(2),cycle(3) }
	ACCESS					read-write
	STATUS					mandatory
	DESCRIPTION			"PG Outlet 1 command"
	::= { node8PG 16 }

pgNode8Out2Name				OBJECT-TYPE
	SYNTAX					DisplayString
	ACCESS					read-write
	STATUS					mandatory
	DESCRIPTION			"PG Outlet 2 name"
	::= { node8PG 17 }

pgNode8Out2CustVoice	OBJECT-TYPE
	SYNTAX					DisplayString
	ACCESS					read-write
	STATUS					mandatory
	DESCRIPTION			"PG Outlet 2 custom voice"
	::= { node8PG 18 }

pgNode8Out2Volts			OBJECT-TYPE
	SYNTAX					INTEGER
	ACCESS					read-only
	STATUS					mandatory
	DESCRIPTION			"PG Outlet 2 volts"
	::= { node8PG 19 }

pgNode8Out2Amps				OBJECT-TYPE
	SYNTAX					INTEGER
	ACCESS					read-only
	STATUS					mandatory
	DESCRIPTION			"PG Outlet 2 amps"
	::= { node8PG 20 }

pgNode8Out2Watts			OBJECT-TYPE
	SYNTAX					INTEGER
	ACCESS					read-only
	STATUS					mandatory
	DESCRIPTION			"PG Outlet 2 watts"
	::= { node8PG 21 }


pgNode8Out2State			OBJECT-TYPE
	SYNTAX					INTEGER { off(1),on(2),cycle(3) }
	ACCESS					read-only
	STATUS					mandatory
	DESCRIPTION			"PG Outlet 2 state"
	::= { node8PG 22 }

pgNode8Out2Cmd				OBJECT-TYPE
	SYNTAX					INTEGER { off(1),on(2),cycle(3) }
	ACCESS					read-write
	STATUS					mandatory
	DESCRIPTION			"PG Outlet 2 command"
	::= { node8PG 23 }

pgNode8Out3Name				OBJECT-TYPE
	SYNTAX					DisplayString
	ACCESS					read-write
	STATUS					mandatory
	DESCRIPTION			"PG Outlet 3 name"
	::= { node8PG 24 }

pgNode8Out3CustVoice	OBJECT-TYPE
	SYNTAX					DisplayString
	ACCESS					read-write
	STATUS					mandatory
	DESCRIPTION			"PG Outlet 3 custom voice"
	::= { node8PG 25 }

pgNode8Out3Volts			OBJECT-TYPE
	SYNTAX					INTEGER
	ACCESS					read-only
	STATUS					mandatory
	DESCRIPTION			"PG Outlet 3 volts"
	::= { node8PG 26 }

pgNode8Out3Amps				OBJECT-TYPE
	SYNTAX					INTEGER
	ACCESS					read-only
	STATUS					mandatory
	DESCRIPTION			"PG Outlet 3 amps"
	::= { node8PG 27 }

pgNode8Out3Watts			OBJECT-TYPE
	SYNTAX					INTEGER
	ACCESS					read-only
	STATUS					mandatory
	DESCRIPTION			"PG Outlet 3 watts"
	::= { node8PG 28 }

pgNode8Out3State			OBJECT-TYPE
	SYNTAX					INTEGER { off(1),on(2),cycle(3) }
	ACCESS					read-only
	STATUS					mandatory
	DESCRIPTION			"PG Outlet 3 state"
	::= { node8PG 29 }

pgNode8Out3Cmd				OBJECT-TYPE
	SYNTAX					INTEGER { off(1),on(2),cycle(3) }
	ACCESS					read-write
	STATUS					mandatory
	DESCRIPTION			"PG Outlet 3 command"
	::= { node8PG 30 }

pgNode8Out4Name				OBJECT-TYPE
	SYNTAX					DisplayString
	ACCESS					read-write
	STATUS					mandatory
	DESCRIPTION			"PG Outlet 4 name"
	::= { node8PG 31 }

pgNode8Out4CustVoice	OBJECT-TYPE
	SYNTAX					DisplayString
	ACCESS					read-write
	STATUS					mandatory
	DESCRIPTION			"PG Outlet 4 custom voice"
	::= { node8PG 32 }

pgNode8Out4Volts			OBJECT-TYPE
	SYNTAX					INTEGER
	ACCESS					read-only
	STATUS					mandatory
	DESCRIPTION			"PG Outlet 4 volts"
	::= { node8PG 33 }

pgNode8Out4Amps				OBJECT-TYPE
	SYNTAX					INTEGER
	ACCESS					read-only
	STATUS					mandatory
	DESCRIPTION			"PG Outlet 4 amps"
	::= { node8PG 34 }

pgNode8Out4Watts			OBJECT-TYPE
	SYNTAX					INTEGER
	ACCESS					read-only
	STATUS					mandatory
	DESCRIPTION			"PG Outlet 4 watts"
	::= { node8PG 35 }

pgNode8Out4State			OBJECT-TYPE
	SYNTAX					INTEGER { off(1),on(2),cycle(3) }
	ACCESS					read-only
	STATUS					mandatory
	DESCRIPTION			"PG Outlet 4 state"
	::= { node8PG 36 }

pgNode8Out4Cmd				OBJECT-TYPE
	SYNTAX					INTEGER { off(1),on(2),cycle(3) }
	ACCESS					read-write
	STATUS					mandatory
	DESCRIPTION			"PG Outlet 4 command"
	::= { node8PG 37 }

pgNode8Out5Name				OBJECT-TYPE
	SYNTAX					DisplayString
	ACCESS					read-write
	STATUS					mandatory
	DESCRIPTION			"PG Outlet 5 name"
	::= { node8PG 38 }

pgNode8Out5CustVoice	OBJECT-TYPE
	SYNTAX					DisplayString
	ACCESS					read-write
	STATUS					mandatory
	DESCRIPTION			"PG Outlet 5 custom voice"
	::= { node8PG 39 }

pgNode8Out5Volts			OBJECT-TYPE
	SYNTAX					INTEGER
	ACCESS					read-only
	STATUS					mandatory
	DESCRIPTION			"PG Outlet 5 volts"
	::= { node8PG 40 }

pgNode8Out5Amps				OBJECT-TYPE
	SYNTAX					INTEGER
	ACCESS					read-only
	STATUS					mandatory
	DESCRIPTION			"PG Outlet 5 amps"
	::= { node8PG 41 }

pgNode8Out5Watts			OBJECT-TYPE
	SYNTAX					INTEGER
	ACCESS					read-only
	STATUS					mandatory
	DESCRIPTION			"PG Outlet 5 watts"
	::= { node8PG 42 }

pgNode8Out5State			OBJECT-TYPE
	SYNTAX					INTEGER { off(1),on(2),cycle(3) }
	ACCESS					read-only
	STATUS					mandatory
	DESCRIPTION			"PG Outlet 5 state"
	::= { node8PG 43 }

pgNode8Out5Cmd				OBJECT-TYPE
	SYNTAX					INTEGER { off(1),on(2),cycle(3) }
	ACCESS					read-write
	STATUS					mandatory
	DESCRIPTION			"PG Outlet 5 command"
	::= { node8PG 44 }

pgNode8Out6Name				OBJECT-TYPE
	SYNTAX					DisplayString
	ACCESS					read-write
	STATUS					mandatory
	DESCRIPTION			"PG Outlet 6 name"
	::= { node8PG 45 }

pgNode8Out6CustVoice	OBJECT-TYPE
	SYNTAX					DisplayString
	ACCESS					read-write
	STATUS					mandatory
	DESCRIPTION			"PG Outlet 6 custom voice"
	::= { node8PG 46 }

pgNode8Out6Volts			OBJECT-TYPE
	SYNTAX					INTEGER
	ACCESS					read-only
	STATUS					mandatory
	DESCRIPTION			"PG Outlet 6 volts"
	::= { node8PG 47 }

pgNode8Out6Amps				OBJECT-TYPE
	SYNTAX					INTEGER
	ACCESS					read-only
	STATUS					mandatory
	DESCRIPTION			"PG Outlet 6 amps"
	::= { node8PG 48 }

pgNode8Out6Watts			OBJECT-TYPE
	SYNTAX					INTEGER
	ACCESS					read-only
	STATUS					mandatory
	DESCRIPTION			"PG Outlet 6 watts"
	::= { node8PG 49 }


pgNode8Out6State			OBJECT-TYPE
	SYNTAX					INTEGER { off(1),on(2),cycle(3) }
	ACCESS					read-only
	STATUS					mandatory
	DESCRIPTION			"PG Outlet 6 state"
	::= { node8PG 50 }

pgNode8Out6Cmd				OBJECT-TYPE
	SYNTAX					INTEGER { off(1),on(2),cycle(3) }
	ACCESS					read-write
	STATUS					mandatory
	DESCRIPTION			"PG Outlet 6 command"
	::= { node8PG 51 }

pgNode8Out7Name				OBJECT-TYPE
	SYNTAX					DisplayString
	ACCESS					read-write
	STATUS					mandatory
	DESCRIPTION			"PG Outlet 7 name"
	::= { node8PG 52 }

pgNode8Out7CustVoice	OBJECT-TYPE
	SYNTAX					DisplayString
	ACCESS					read-write
	STATUS					mandatory
	DESCRIPTION			"PG Outlet 7 custom voice"
	::= { node8PG 53 }

pgNode8Out7Volts			OBJECT-TYPE
	SYNTAX					INTEGER
	ACCESS					read-only
	STATUS					mandatory
	DESCRIPTION			"PG Outlet 7 volts"
	::= { node8PG 54 }

pgNode8Out7Amps				OBJECT-TYPE
	SYNTAX					INTEGER
	ACCESS					read-only
	STATUS					mandatory
	DESCRIPTION			"PG Outlet 7 amps"
	::= { node8PG 55 }

pgNode8Out7Watts			OBJECT-TYPE
	SYNTAX					INTEGER
	ACCESS					read-only
	STATUS					mandatory
	DESCRIPTION			"PG Outlet 7 watts"
	::= { node8PG 56 }

pgNode8Out7State			OBJECT-TYPE
	SYNTAX					INTEGER { off(1),on(2),cycle(3) }
	ACCESS					read-only
	STATUS					mandatory
	DESCRIPTION			"PG Outlet 7 state"
	::= { node8PG 57 }

pgNode8Out7Cmd				OBJECT-TYPE
	SYNTAX					INTEGER { off(1),on(2),cycle(3) }
	ACCESS					read-write
	STATUS					mandatory
	DESCRIPTION			"PG Outlet 7 command"
	::= { node8PG 58 }

pgNode8Out8Name				OBJECT-TYPE
	SYNTAX					DisplayString
	ACCESS					read-write
	STATUS					mandatory
	DESCRIPTION			"PG Outlet 8 name"
	::= { node8PG 59 }

pgNode8Out8CustVoice	OBJECT-TYPE
	SYNTAX					DisplayString
	ACCESS					read-write
	STATUS					mandatory
	DESCRIPTION			"PG Outlet 8 custom voice"
	::= { node8PG 60 }

pgNode8Out8Volts			OBJECT-TYPE
	SYNTAX					INTEGER
	ACCESS					read-only
	STATUS					mandatory
	DESCRIPTION			"PG Outlet 8 volts"
	::= { node8PG 61 }

pgNode8Out8Amps				OBJECT-TYPE
	SYNTAX					INTEGER
	ACCESS					read-only
	STATUS					mandatory
	DESCRIPTION			"PG Outlet 8 amps"
	::= { node8PG 62 }

pgNode8Out8Watts			OBJECT-TYPE
	SYNTAX					INTEGER
	ACCESS					read-only
	STATUS					mandatory
	DESCRIPTION			"PG Outlet 8 watts"
	::= { node8PG 63 }

pgNode8Out8State			OBJECT-TYPE
	SYNTAX					INTEGER { off(1),on(2),cycle(3) }
	ACCESS					read-only
	STATUS					mandatory
	DESCRIPTION			"PG Outlet 8 state"
	::= { node8PG 64 }

pgNode8Out8Cmd				OBJECT-TYPE
	SYNTAX					INTEGER { off(1),on(2),cycle(3) }
	ACCESS					read-write
	STATUS					mandatory
	DESCRIPTION			"PG Outlet 8 command"
	::= { node8PG 65 }

pgNode9InUse					OBJECT-TYPE
	SYNTAX					INTEGER { false(1),true(2) }
	ACCESS					read-only
	STATUS					mandatory
	DESCRIPTION			"PG in use"
	::= { node9PG 1 }

pgNode9Status					OBJECT-TYPE
	SYNTAX					INTEGER { normal(1),pending(2), trouble(3) }
	ACCESS					read-only
	STATUS					mandatory
	DESCRIPTION			"PG status"
	::= { node9PG 2 }

pgNode9StatusSupport	OBJECT-TYPE
	SYNTAX					INTEGER { true1(1),false(2) }
	ACCESS					read-only
	STATUS					mandatory
	DESCRIPTION			"PG status support level"
	::= { node9PG 3 }

pgNode9Ver						OBJECT-TYPE
	SYNTAX					INTEGER { pgate1(1),pgate2(2) }
	ACCESS					read-only
	STATUS					mandatory
	DESCRIPTION			"PG version"
	::= { node9PG 4 }

pgNode9Volts					OBJECT-TYPE
	SYNTAX					INTEGER
	ACCESS					read-only
	STATUS					mandatory
	DESCRIPTION			"PG voltage"
	::= { node9PG 5 }

pgNode9Amps						OBJECT-TYPE
	SYNTAX					INTEGER
	ACCESS					read-only
	STATUS					mandatory
	DESCRIPTION			"PG amps"
	::= { node9PG 6 }

pgNode9Watts					OBJECT-TYPE
	SYNTAX					INTEGER
	ACCESS					read-only
	STATUS					mandatory
	DESCRIPTION			"PG Watts"
	::= { node9PG 7 }

pgNode9Name						OBJECT-TYPE
	SYNTAX					DisplayString
	ACCESS					read-write
	STATUS					mandatory
	DESCRIPTION			"PG name"
	::= { node9PG 8 }

pgNode9CustVoice			OBJECT-TYPE
	SYNTAX					DisplayString
	ACCESS					read-write
	STATUS					mandatory
	DESCRIPTION			"PG custom voice"
	::= { node9PG 9 }

pgNode9Out1Name				OBJECT-TYPE
	SYNTAX					DisplayString
	ACCESS					read-write
	STATUS					mandatory
	DESCRIPTION			"PG Outlet 1 name"
	::= { node9PG 10 }

pgNode9Out1CustVoice	OBJECT-TYPE
	SYNTAX					DisplayString
	ACCESS					read-write
	STATUS					mandatory
	DESCRIPTION			"PG Outlet 1 custom voice"
	::= { node9PG 11 }

pgNode9Out1Volts			OBJECT-TYPE
	SYNTAX					INTEGER
	ACCESS					read-only
	STATUS					mandatory
	DESCRIPTION			"PG Outlet 1 volts"
	::= { node9PG 12 }

pgNode9Out1Amps				OBJECT-TYPE
	SYNTAX					INTEGER
	ACCESS					read-only
	STATUS					mandatory
	DESCRIPTION			"PG Outlet 1 amps"
	::= { node9PG 13 }

pgNode9Out1Watts			OBJECT-TYPE
	SYNTAX					INTEGER
	ACCESS					read-only
	STATUS					mandatory
	DESCRIPTION			"PG Outlet 1 watts"
	::= { node9PG 14 }

pgNode9Out1State			OBJECT-TYPE
	SYNTAX					INTEGER { off(1),on(2),cycle(3) }
	ACCESS					read-only
	STATUS					mandatory
	DESCRIPTION			"PG Outlet 1 state"
	::= { node9PG 15 }

pgNode9Out1Cmd				OBJECT-TYPE
	SYNTAX					INTEGER { off(1),on(2),cycle(3) }
	ACCESS					read-write
	STATUS					mandatory
	DESCRIPTION			"PG Outlet 1 command"
	::= { node9PG 16 }

pgNode9Out2Name				OBJECT-TYPE
	SYNTAX					DisplayString
	ACCESS					read-write
	STATUS					mandatory
	DESCRIPTION			"PG Outlet 2 name"
	::= { node9PG 17 }

pgNode9Out2CustVoice	OBJECT-TYPE
	SYNTAX					DisplayString
	ACCESS					read-write
	STATUS					mandatory
	DESCRIPTION			"PG Outlet 2 custom voice"
	::= { node9PG 18 }

pgNode9Out2Volts			OBJECT-TYPE
	SYNTAX					INTEGER
	ACCESS					read-only
	STATUS					mandatory
	DESCRIPTION			"PG Outlet 2 volts"
	::= { node9PG 19 }

pgNode9Out2Amps				OBJECT-TYPE
	SYNTAX					INTEGER
	ACCESS					read-only
	STATUS					mandatory
	DESCRIPTION			"PG Outlet 2 amps"
	::= { node9PG 20 }

pgNode9Out2Watts			OBJECT-TYPE
	SYNTAX					INTEGER
	ACCESS					read-only
	STATUS					mandatory
	DESCRIPTION			"PG Outlet 2 watts"
	::= { node9PG 21 }

pgNode9Out2State			OBJECT-TYPE
	SYNTAX					INTEGER { off(1),on(2),cycle(3) }
	ACCESS					read-only
	STATUS					mandatory
	DESCRIPTION			"PG Outlet 2 state"
	::= { node9PG 22 }

pgNode9Out2Cmd				OBJECT-TYPE
	SYNTAX					INTEGER { off(1),on(2),cycle(3) }
	ACCESS					read-write
	STATUS					mandatory
	DESCRIPTION			"PG Outlet 2 command"
	::= { node9PG 23 }

pgNode9Out3Name				OBJECT-TYPE
	SYNTAX					DisplayString
	ACCESS					read-write
	STATUS					mandatory
	DESCRIPTION			"PG Outlet 3 name"
	::= { node9PG 24 }

pgNode9Out3CustVoice	OBJECT-TYPE
	SYNTAX					DisplayString
	ACCESS					read-write
	STATUS					mandatory
	DESCRIPTION			"PG Outlet 3 custom voice"
	::= { node9PG 25 }

pgNode9Out3Volts			OBJECT-TYPE
	SYNTAX					INTEGER
	ACCESS					read-only
	STATUS					mandatory
	DESCRIPTION			"PG Outlet 3 volts"
	::= { node9PG 26 }

pgNode9Out3Amps				OBJECT-TYPE
	SYNTAX					INTEGER
	ACCESS					read-only
	STATUS					mandatory
	DESCRIPTION			"PG Outlet 3 amps"
	::= { node9PG 27 }

pgNode9Out3Watts			OBJECT-TYPE
	SYNTAX					INTEGER
	ACCESS					read-only
	STATUS					mandatory
	DESCRIPTION			"PG Outlet 3 watts"
	::= { node9PG 28 }

pgNode9Out3State			OBJECT-TYPE
	SYNTAX					INTEGER { off(1),on(2),cycle(3) }
	ACCESS					read-only
	STATUS					mandatory
	DESCRIPTION			"PG Outlet 3 state"
	::= { node9PG 29 }

pgNode9Out3Cmd				OBJECT-TYPE
	SYNTAX					INTEGER { off(1),on(2),cycle(3) }
	ACCESS					read-write
	STATUS					mandatory
	DESCRIPTION			"PG Outlet 3 command"
	::= { node9PG 30 }

pgNode9Out4Name				OBJECT-TYPE
	SYNTAX					DisplayString
	ACCESS					read-write
	STATUS					mandatory
	DESCRIPTION			"PG Outlet 4 name"
	::= { node9PG 31 }

pgNode9Out4CustVoice	OBJECT-TYPE
	SYNTAX					DisplayString
	ACCESS					read-write
	STATUS					mandatory
	DESCRIPTION			"PG Outlet 4 custom voice"
	::= { node9PG 32 }

pgNode9Out4Volts			OBJECT-TYPE
	SYNTAX					INTEGER
	ACCESS					read-only
	STATUS					mandatory
	DESCRIPTION			"PG Outlet 4 volts"
	::= { node9PG 33 }

pgNode9Out4Amps				OBJECT-TYPE
	SYNTAX					INTEGER
	ACCESS					read-only
	STATUS					mandatory
	DESCRIPTION			"PG Outlet 4 amps"
	::= { node9PG 34 }

pgNode9Out4Watts			OBJECT-TYPE
	SYNTAX					INTEGER
	ACCESS					read-only
	STATUS					mandatory
	DESCRIPTION			"PG Outlet 4 watts"
	::= { node9PG 35 }

pgNode9Out4State			OBJECT-TYPE
	SYNTAX					INTEGER { off(1),on(2),cycle(3) }
	ACCESS					read-only
	STATUS					mandatory
	DESCRIPTION			"PG Outlet 4 state"
	::= { node9PG 36 }

pgNode9Out4Cmd				OBJECT-TYPE
	SYNTAX					INTEGER { off(1),on(2),cycle(3) }
	ACCESS					read-write
	STATUS					mandatory
	DESCRIPTION			"PG Outlet 4 command"
	::= { node9PG 37 }

pgNode9Out5Name				OBJECT-TYPE
	SYNTAX					DisplayString
	ACCESS					read-write
	STATUS					mandatory
	DESCRIPTION			"PG Outlet 5 name"
	::= { node9PG 38 }

pgNode9Out5CustVoice	OBJECT-TYPE
	SYNTAX					DisplayString
	ACCESS					read-write
	STATUS					mandatory
	DESCRIPTION			"PG Outlet 5 custom voice"
	::= { node9PG 39 }

pgNode9Out5Volts			OBJECT-TYPE
	SYNTAX					INTEGER
	ACCESS					read-only
	STATUS					mandatory
	DESCRIPTION			"PG Outlet 5 volts"
	::= { node9PG 40 }

pgNode9Out5Amps				OBJECT-TYPE
	SYNTAX					INTEGER
	ACCESS					read-only
	STATUS					mandatory
	DESCRIPTION			"PG Outlet 5 amps"
	::= { node9PG 41 }

pgNode9Out5Watts			OBJECT-TYPE
	SYNTAX					INTEGER
	ACCESS					read-only
	STATUS					mandatory
	DESCRIPTION			"PG Outlet 5 watts"
	::= { node9PG 42 }

pgNode9Out5State			OBJECT-TYPE
	SYNTAX					INTEGER { off(1),on(2),cycle(3) }
	ACCESS					read-only
	STATUS					mandatory
	DESCRIPTION			"PG Outlet 5 state"
	::= { node9PG 43 }

pgNode9Out5Cmd				OBJECT-TYPE
	SYNTAX					INTEGER { off(1),on(2),cycle(3) }
	ACCESS					read-write
	STATUS					mandatory
	DESCRIPTION			"PG Outlet 5 command"
	::= { node9PG 44 }

pgNode9Out6Name				OBJECT-TYPE
	SYNTAX					DisplayString
	ACCESS					read-write
	STATUS					mandatory
	DESCRIPTION			"PG Outlet 6 name"
	::= { node9PG 45 }

pgNode9Out6CustVoice	OBJECT-TYPE
	SYNTAX					DisplayString
	ACCESS					read-write
	STATUS					mandatory
	DESCRIPTION			"PG Outlet 6 custom voice"
	::= { node9PG 46 }

pgNode9Out6Volts			OBJECT-TYPE
	SYNTAX					INTEGER
	ACCESS					read-only
	STATUS					mandatory
	DESCRIPTION			"PG Outlet 6 volts"
	::= { node9PG 47 }

pgNode9Out6Amps				OBJECT-TYPE
	SYNTAX					INTEGER
	ACCESS					read-only
	STATUS					mandatory
	DESCRIPTION			"PG Outlet 6 amps"
	::= { node9PG 48 }

pgNode9Out6Watts			OBJECT-TYPE
	SYNTAX					INTEGER
	ACCESS					read-only
	STATUS					mandatory
	DESCRIPTION			"PG Outlet 6 watts"
	::= { node9PG 49 }

pgNode9Out6State			OBJECT-TYPE
	SYNTAX					INTEGER { off(1),on(2),cycle(3) }
	ACCESS					read-only
	STATUS					mandatory
	DESCRIPTION			"PG Outlet 6 state"
	::= { node9PG 50 }

pgNode9Out6Cmd				OBJECT-TYPE
	SYNTAX					INTEGER { off(1),on(2),cycle(3) }
	ACCESS					read-write
	STATUS					mandatory
	DESCRIPTION			"PG Outlet 6 command"
	::= { node9PG 51 }

pgNode9Out7Name				OBJECT-TYPE
	SYNTAX					DisplayString
	ACCESS					read-write
	STATUS					mandatory
	DESCRIPTION			"PG Outlet 7 name"
	::= { node9PG 52 }

pgNode9Out7CustVoice	OBJECT-TYPE
	SYNTAX					DisplayString
	ACCESS					read-write
	STATUS					mandatory
	DESCRIPTION			"PG Outlet 7 custom voice"
	::= { node9PG 53 }

pgNode9Out7Volts			OBJECT-TYPE
	SYNTAX					INTEGER
	ACCESS					read-only
	STATUS					mandatory
	DESCRIPTION			"PG Outlet 7 volts"
	::= { node9PG 54 }

pgNode9Out7Amps				OBJECT-TYPE
	SYNTAX					INTEGER
	ACCESS					read-only
	STATUS					mandatory
	DESCRIPTION			"PG Outlet 7 amps"
	::= { node9PG 55 }

pgNode9Out7Watts			OBJECT-TYPE
	SYNTAX					INTEGER
	ACCESS					read-only
	STATUS					mandatory
	DESCRIPTION			"PG Outlet 7 watts"
	::= { node9PG 56 }

pgNode9Out7State			OBJECT-TYPE
	SYNTAX					INTEGER { off(1),on(2),cycle(3) }
	ACCESS					read-only
	STATUS					mandatory
	DESCRIPTION			"PG Outlet 7 state"
	::= { node9PG 57 }

pgNode9Out7Cmd				OBJECT-TYPE
	SYNTAX					INTEGER { off(1),on(2),cycle(3) }
	ACCESS					read-write
	STATUS					mandatory
	DESCRIPTION			"PG Outlet 7 command"
	::= { node9PG 58 }

pgNode9Out8Name				OBJECT-TYPE
	SYNTAX					DisplayString
	ACCESS					read-write
	STATUS					mandatory
	DESCRIPTION			"PG Outlet 8 name"
	::= { node9PG 59 }

pgNode9Out8CustVoice	OBJECT-TYPE
	SYNTAX					DisplayString
	ACCESS					read-write
	STATUS					mandatory
	DESCRIPTION			"PG Outlet 8 custom voice"
	::= { node9PG 60 }

pgNode9Out8Volts			OBJECT-TYPE
	SYNTAX					INTEGER
	ACCESS					read-only
	STATUS					mandatory
	DESCRIPTION			"PG Outlet 8 volts"
	::= { node9PG 61 }

pgNode9Out8Amps				OBJECT-TYPE
	SYNTAX					INTEGER
	ACCESS					read-only
	STATUS					mandatory
	DESCRIPTION			"PG Outlet 8 amps"
	::= { node9PG 62 }

pgNode9Out8Watts			OBJECT-TYPE
	SYNTAX					INTEGER
	ACCESS					read-only
	STATUS					mandatory
	DESCRIPTION			"PG Outlet 8 watts"
	::= { node9PG 63 }

pgNode9Out8State			OBJECT-TYPE
	SYNTAX					INTEGER { off(1),on(2),cycle(3) }
	ACCESS					read-only
	STATUS					mandatory
	DESCRIPTION			"PG Outlet 8 state"
	::= { node9PG 64 }

pgNode9Out8Cmd				OBJECT-TYPE
	SYNTAX					INTEGER { off(1),on(2),cycle(3) }
	ACCESS					read-write
	STATUS					mandatory
	DESCRIPTION			"PG Outlet 8 command"
	::= { node9PG 65 }

pgNode10InUse					OBJECT-TYPE
	SYNTAX					INTEGER { false(1),true(2) }
	ACCESS					read-only
	STATUS					mandatory
	DESCRIPTION			"PG in use"
	::= { node10PG 1 }

pgNode10Status					OBJECT-TYPE
	SYNTAX					INTEGER { normal(1),pending(2), trouble(3) }
	ACCESS					read-only
	STATUS					mandatory
	DESCRIPTION			"PG status"
	::= { node10PG 2 }

pgNode10StatusSupport	OBJECT-TYPE
	SYNTAX					INTEGER { true1(1),false(2) }
	ACCESS					read-only
	STATUS					mandatory
	DESCRIPTION			"PG status support level"
	::= { node10PG 3 }

pgNode10Ver						OBJECT-TYPE
	SYNTAX					INTEGER { pgate1(1),pgate2(2) }
	ACCESS					read-only
	STATUS					mandatory
	DESCRIPTION			"PG version"
	::= { node10PG 4 }

pgNode10Volts					OBJECT-TYPE
	SYNTAX					INTEGER
	ACCESS					read-only
	STATUS					mandatory
	DESCRIPTION			"PG voltage"
	::= { node10PG 5 }

pgNode10Amps						OBJECT-TYPE
	SYNTAX					INTEGER
	ACCESS					read-only
	STATUS					mandatory
	DESCRIPTION			"PG amps"
	::= { node10PG 6 }

pgNode10Watts					OBJECT-TYPE
	SYNTAX					INTEGER
	ACCESS					read-only
	STATUS					mandatory
	DESCRIPTION			"PG Watts"
	::= { node10PG 7 }

pgNode10Name						OBJECT-TYPE
	SYNTAX					DisplayString
	ACCESS					read-write
	STATUS					mandatory
	DESCRIPTION			"PG name"
	::= { node10PG 8 }

pgNode10CustVoice			OBJECT-TYPE
	SYNTAX					DisplayString
	ACCESS					read-write
	STATUS					mandatory
	DESCRIPTION			"PG custom voice"
	::= { node10PG 9 }

pgNode10Out1Name				OBJECT-TYPE
	SYNTAX					DisplayString
	ACCESS					read-write
	STATUS					mandatory
	DESCRIPTION			"PG Outlet 1 name"
	::= { node10PG 10 }

pgNode10Out1CustVoice	OBJECT-TYPE
	SYNTAX					DisplayString
	ACCESS					read-write
	STATUS					mandatory
	DESCRIPTION			"PG Outlet 1 custom voice"
	::= { node10PG 11 }

pgNode10Out1Volts			OBJECT-TYPE
	SYNTAX					INTEGER
	ACCESS					read-only
	STATUS					mandatory
	DESCRIPTION			"PG Outlet 1 volts"
	::= { node10PG 12 }

pgNode10Out1Amps				OBJECT-TYPE
	SYNTAX					INTEGER
	ACCESS					read-only
	STATUS					mandatory
	DESCRIPTION			"PG Outlet 1 amps"
	::= { node10PG 13 }

pgNode10Out1Watts			OBJECT-TYPE
	SYNTAX					INTEGER
	ACCESS					read-only
	STATUS					mandatory
	DESCRIPTION			"PG Outlet 1 watts"
	::= { node10PG 14 }

pgNode10Out1State			OBJECT-TYPE
	SYNTAX					INTEGER { off(1),on(2),cycle(3) }
	ACCESS					read-only
	STATUS					mandatory
	DESCRIPTION			"PG Outlet 1 state"
	::= { node10PG 15 }

pgNode10Out1Cmd				OBJECT-TYPE
	SYNTAX					INTEGER { off(1),on(2),cycle(3) }
	ACCESS					read-write
	STATUS					mandatory
	DESCRIPTION			"PG Outlet 1 command"
	::= { node10PG 16 }

pgNode10Out2Name				OBJECT-TYPE
	SYNTAX					DisplayString
	ACCESS					read-write
	STATUS					mandatory
	DESCRIPTION			"PG Outlet 2 name"
	::= { node10PG 17 }

pgNode10Out2CustVoice	OBJECT-TYPE
	SYNTAX					DisplayString
	ACCESS					read-write
	STATUS					mandatory
	DESCRIPTION			"PG Outlet 2 custom voice"
	::= { node10PG 18 }

pgNode10Out2Volts			OBJECT-TYPE
	SYNTAX					INTEGER
	ACCESS					read-only
	STATUS					mandatory
	DESCRIPTION			"PG Outlet 2 volts"
	::= { node10PG 19 }

pgNode10Out2Amps				OBJECT-TYPE
	SYNTAX					INTEGER
	ACCESS					read-only
	STATUS					mandatory
	DESCRIPTION			"PG Outlet 2 amps"
	::= { node10PG 20 }

pgNode10Out2Watts			OBJECT-TYPE
	SYNTAX					INTEGER
	ACCESS					read-only
	STATUS					mandatory
	DESCRIPTION			"PG Outlet 2 watts"
	::= { node10PG 21 }

pgNode10Out2State			OBJECT-TYPE
	SYNTAX					INTEGER { off(1),on(2),cycle(3) }
	ACCESS					read-only
	STATUS					mandatory
	DESCRIPTION			"PG Outlet 2 state"
	::= { node10PG 22 }

pgNode10Out2Cmd				OBJECT-TYPE
	SYNTAX					INTEGER { off(1),on(2),cycle(3) }
	ACCESS					read-write
	STATUS					mandatory
	DESCRIPTION			"PG Outlet 2 command"
	::= { node10PG 23 }

pgNode10Out3Name				OBJECT-TYPE
	SYNTAX					DisplayString
	ACCESS					read-write
	STATUS					mandatory
	DESCRIPTION			"PG Outlet 3 name"
	::= { node10PG 24 }

pgNode10Out3CustVoice	OBJECT-TYPE
	SYNTAX					DisplayString
	ACCESS					read-write
	STATUS					mandatory
	DESCRIPTION			"PG Outlet 3 custom voice"
	::= { node10PG 25 }

pgNode10Out3Volts			OBJECT-TYPE
	SYNTAX					INTEGER
	ACCESS					read-only
	STATUS					mandatory
	DESCRIPTION			"PG Outlet 3 volts"
	::= { node10PG 26 }

pgNode10Out3Amps				OBJECT-TYPE
	SYNTAX					INTEGER
	ACCESS					read-only
	STATUS					mandatory
	DESCRIPTION			"PG Outlet 3 amps"
	::= { node10PG 27 }

pgNode10Out3Watts			OBJECT-TYPE
	SYNTAX					INTEGER
	ACCESS					read-only
	STATUS					mandatory
	DESCRIPTION			"PG Outlet 3 watts"
	::= { node10PG 28 }

pgNode10Out3State			OBJECT-TYPE
	SYNTAX					INTEGER { off(1),on(2),cycle(3) }
	ACCESS					read-only
	STATUS					mandatory
	DESCRIPTION			"PG Outlet 3 state"
	::= { node10PG 29 }

pgNode10Out3Cmd				OBJECT-TYPE
	SYNTAX					INTEGER { off(1),on(2),cycle(3) }
	ACCESS					read-write
	STATUS					mandatory
	DESCRIPTION			"PG Outlet 3 command"
	::= { node10PG 30 }

pgNode10Out4Name				OBJECT-TYPE
	SYNTAX					DisplayString
	ACCESS					read-write
	STATUS					mandatory
	DESCRIPTION			"PG Outlet 4 name"
	::= { node10PG 31 }

pgNode10Out4CustVoice	OBJECT-TYPE
	SYNTAX					DisplayString
	ACCESS					read-write
	STATUS					mandatory
	DESCRIPTION			"PG Outlet 4 custom voice"
	::= { node10PG 32 }

pgNode10Out4Volts			OBJECT-TYPE
	SYNTAX					INTEGER
	ACCESS					read-only
	STATUS					mandatory
	DESCRIPTION			"PG Outlet 4 volts"
	::= { node10PG 33 }

pgNode10Out4Amps				OBJECT-TYPE
	SYNTAX					INTEGER
	ACCESS					read-only
	STATUS					mandatory
	DESCRIPTION			"PG Outlet 4 amps"
	::= { node10PG 34 }

pgNode10Out4Watts			OBJECT-TYPE
	SYNTAX					INTEGER
	ACCESS					read-only
	STATUS					mandatory
	DESCRIPTION			"PG Outlet 4 watts"
	::= { node10PG 35 }

pgNode10Out4State			OBJECT-TYPE
	SYNTAX					INTEGER { off(1),on(2),cycle(3) }
	ACCESS					read-only
	STATUS					mandatory
	DESCRIPTION			"PG Outlet 4 state"
	::= { node10PG 36 }

pgNode10Out4Cmd				OBJECT-TYPE
	SYNTAX					INTEGER { off(1),on(2),cycle(3) }
	ACCESS					read-write
	STATUS					mandatory
	DESCRIPTION			"PG Outlet 4 command"
	::= { node10PG 37 }

pgNode10Out5Name				OBJECT-TYPE
	SYNTAX					DisplayString
	ACCESS					read-write
	STATUS					mandatory
	DESCRIPTION			"PG Outlet 5 name"
	::= { node10PG 38 }

pgNode10Out5CustVoice	OBJECT-TYPE
	SYNTAX					DisplayString
	ACCESS					read-write
	STATUS					mandatory
	DESCRIPTION			"PG Outlet 5 custom voice"
	::= { node10PG 39 }

pgNode10Out5Volts			OBJECT-TYPE
	SYNTAX					INTEGER
	ACCESS					read-only
	STATUS					mandatory
	DESCRIPTION			"PG Outlet 5 volts"
	::= { node10PG 40 }

pgNode10Out5Amps				OBJECT-TYPE
	SYNTAX					INTEGER
	ACCESS					read-only
	STATUS					mandatory
	DESCRIPTION			"PG Outlet 5 amps"
	::= { node10PG 41 }

pgNode10Out5Watts			OBJECT-TYPE
	SYNTAX					INTEGER
	ACCESS					read-only
	STATUS					mandatory
	DESCRIPTION			"PG Outlet 5 watts"
	::= { node10PG 42 }

pgNode10Out5State			OBJECT-TYPE
	SYNTAX					INTEGER { off(1),on(2),cycle(3) }
	ACCESS					read-only
	STATUS					mandatory
	DESCRIPTION			"PG Outlet 5 state"
	::= { node10PG 43 }

pgNode10Out5Cmd				OBJECT-TYPE
	SYNTAX					INTEGER { off(1),on(2),cycle(3) }
	ACCESS					read-write
	STATUS					mandatory
	DESCRIPTION			"PG Outlet 5 command"
	::= { node10PG 44 }

pgNode10Out6Name				OBJECT-TYPE
	SYNTAX					DisplayString
	ACCESS					read-write
	STATUS					mandatory
	DESCRIPTION			"PG Outlet 6 name"
	::= { node10PG 45 }

pgNode10Out6CustVoice	OBJECT-TYPE
	SYNTAX					DisplayString
	ACCESS					read-write
	STATUS					mandatory
	DESCRIPTION			"PG Outlet 6 custom voice"
	::= { node10PG 46 }

pgNode10Out6Volts			OBJECT-TYPE
	SYNTAX					INTEGER
	ACCESS					read-only
	STATUS					mandatory
	DESCRIPTION			"PG Outlet 6 volts"
	::= { node10PG 47 }

pgNode10Out6Amps				OBJECT-TYPE
	SYNTAX					INTEGER
	ACCESS					read-only
	STATUS					mandatory
	DESCRIPTION			"PG Outlet 6 amps"
	::= { node10PG 48 }

pgNode10Out6Watts			OBJECT-TYPE
	SYNTAX					INTEGER
	ACCESS					read-only
	STATUS					mandatory
	DESCRIPTION			"PG Outlet 6 watts"
	::= { node10PG 49 }

pgNode10Out6State			OBJECT-TYPE
	SYNTAX					INTEGER { off(1),on(2),cycle(3) }
	ACCESS					read-only
	STATUS					mandatory
	DESCRIPTION			"PG Outlet 6 state"
	::= { node10PG 50 }

pgNode10Out6Cmd				OBJECT-TYPE
	SYNTAX					INTEGER { off(1),on(2),cycle(3) }
	ACCESS					read-write
	STATUS					mandatory
	DESCRIPTION			"PG Outlet 6 command"
	::= { node10PG 51 }

pgNode10Out7Name				OBJECT-TYPE
	SYNTAX					DisplayString
	ACCESS					read-write
	STATUS					mandatory
	DESCRIPTION			"PG Outlet 7 name"
	::= { node10PG 52 }

pgNode10Out7CustVoice	OBJECT-TYPE
	SYNTAX					DisplayString
	ACCESS					read-write
	STATUS					mandatory
	DESCRIPTION			"PG Outlet 7 custom voice"
	::= { node10PG 53 }

pgNode10Out7Volts			OBJECT-TYPE
	SYNTAX					INTEGER
	ACCESS					read-only
	STATUS					mandatory
	DESCRIPTION			"PG Outlet 7 volts"
	::= { node10PG 54 }

pgNode10Out7Amps				OBJECT-TYPE
	SYNTAX					INTEGER
	ACCESS					read-only
	STATUS					mandatory
	DESCRIPTION			"PG Outlet 7 amps"
	::= { node10PG 55 }

pgNode10Out7Watts			OBJECT-TYPE
	SYNTAX					INTEGER
	ACCESS					read-only
	STATUS					mandatory
	DESCRIPTION			"PG Outlet 7 watts"
	::= { node10PG 56 }

pgNode10Out7State			OBJECT-TYPE
	SYNTAX					INTEGER { off(1),on(2),cycle(3) }
	ACCESS					read-only
	STATUS					mandatory
	DESCRIPTION			"PG Outlet 7 state"
	::= { node10PG 57 }

pgNode10Out7Cmd				OBJECT-TYPE
	SYNTAX					INTEGER { off(1),on(2),cycle(3) }
	ACCESS					read-write
	STATUS					mandatory
	DESCRIPTION			"PG Outlet 7 command"
	::= { node10PG 58 }

pgNode10Out8Name				OBJECT-TYPE
	SYNTAX					DisplayString
	ACCESS					read-write
	STATUS					mandatory
	DESCRIPTION			"PG Outlet 8 name"
	::= { node10PG 59 }

pgNode10Out8CustVoice	OBJECT-TYPE
	SYNTAX					DisplayString
	ACCESS					read-write
	STATUS					mandatory
	DESCRIPTION			"PG Outlet 8 custom voice"
	::= { node10PG 60 }

pgNode10Out8Volts			OBJECT-TYPE
	SYNTAX					INTEGER
	ACCESS					read-only
	STATUS					mandatory
	DESCRIPTION			"PG Outlet 8 volts"
	::= { node10PG 61 }

pgNode10Out8Amps				OBJECT-TYPE
	SYNTAX					INTEGER
	ACCESS					read-only
	STATUS					mandatory
	DESCRIPTION			"PG Outlet 8 amps"
	::= { node10PG 62 }

pgNode10Out8Watts			OBJECT-TYPE
	SYNTAX					INTEGER
	ACCESS					read-only
	STATUS					mandatory
	DESCRIPTION			"PG Outlet 8 watts"
	::= { node10PG 63 }

pgNode10Out8State			OBJECT-TYPE
	SYNTAX					INTEGER { off(1),on(2),cycle(3) }
	ACCESS					read-only
	STATUS					mandatory
	DESCRIPTION			"PG Outlet 8 state"
	::= { node10PG 64 }

pgNode10Out8Cmd				OBJECT-TYPE
	SYNTAX					INTEGER { off(1),on(2),cycle(3) }
	ACCESS					read-write
	STATUS					mandatory
	DESCRIPTION			"PG Outlet 8 command"
	::= { node10PG 65 }

pgNode11InUse					OBJECT-TYPE
	SYNTAX					INTEGER { false(1),true(2) }
	ACCESS					read-only
	STATUS					mandatory
	DESCRIPTION			"PG in use"
	::= { node11PG 1 }

pgNode11Status					OBJECT-TYPE
	SYNTAX					INTEGER { normal(1),pending(2), trouble(3) }
	ACCESS					read-only
	STATUS					mandatory
	DESCRIPTION			"PG status"
	::= { node11PG 2 }

pgNode11StatusSupport	OBJECT-TYPE
	SYNTAX					INTEGER { true1(1),false(2) }
	ACCESS					read-only
	STATUS					mandatory
	DESCRIPTION			"PG status support level"
	::= { node11PG 3 }

pgNode11Ver						OBJECT-TYPE
	SYNTAX					INTEGER { pgate1(1),pgate2(2) }
	ACCESS					read-only
	STATUS					mandatory
	DESCRIPTION			"PG version"
	::= { node11PG 4 }

pgNode11Volts					OBJECT-TYPE
	SYNTAX					INTEGER
	ACCESS					read-only
	STATUS					mandatory
	DESCRIPTION			"PG voltage"
	::= { node11PG 5 }

pgNode11Amps						OBJECT-TYPE
	SYNTAX					INTEGER
	ACCESS					read-only
	STATUS					mandatory
	DESCRIPTION			"PG amps"
	::= { node11PG 6 }

pgNode11Watts					OBJECT-TYPE
	SYNTAX					INTEGER
	ACCESS					read-only
	STATUS					mandatory
	DESCRIPTION			"PG Watts"
	::= { node11PG 7 }

pgNode11Name						OBJECT-TYPE
	SYNTAX					DisplayString
	ACCESS					read-write
	STATUS					mandatory
	DESCRIPTION			"PG name"
	::= { node11PG 8 }

pgNode11CustVoice			OBJECT-TYPE
	SYNTAX					DisplayString
	ACCESS					read-write
	STATUS					mandatory
	DESCRIPTION			"PG custom voice"
	::= { node11PG 9 }

pgNode11Out1Name				OBJECT-TYPE
	SYNTAX					DisplayString
	ACCESS					read-write
	STATUS					mandatory
	DESCRIPTION			"PG Outlet 1 name"
	::= { node11PG 10 }

pgNode11Out1CustVoice	OBJECT-TYPE
	SYNTAX					DisplayString
	ACCESS					read-write
	STATUS					mandatory
	DESCRIPTION			"PG Outlet 1 custom voice"
	::= { node11PG 11 }

pgNode11Out1Volts			OBJECT-TYPE
	SYNTAX					INTEGER
	ACCESS					read-only
	STATUS					mandatory
	DESCRIPTION			"PG Outlet 1 volts"
	::= { node11PG 12 }

pgNode11Out1Amps				OBJECT-TYPE
	SYNTAX					INTEGER
	ACCESS					read-only
	STATUS					mandatory
	DESCRIPTION			"PG Outlet 1 amps"
	::= { node11PG 13 }

pgNode11Out1Watts			OBJECT-TYPE
	SYNTAX					INTEGER
	ACCESS					read-only
	STATUS					mandatory
	DESCRIPTION			"PG Outlet 1 watts"
	::= { node11PG 14 }

pgNode11Out1State			OBJECT-TYPE
	SYNTAX					INTEGER { off(1),on(2),cycle(3) }
	ACCESS					read-only
	STATUS					mandatory
	DESCRIPTION			"PG Outlet 1 state"
	::= { node11PG 15 }

pgNode11Out1Cmd				OBJECT-TYPE
	SYNTAX					INTEGER { off(1),on(2),cycle(3) }
	ACCESS					read-write
	STATUS					mandatory
	DESCRIPTION			"PG Outlet 1 command"
	::= { node11PG 16 }

pgNode11Out2Name				OBJECT-TYPE
	SYNTAX					DisplayString
	ACCESS					read-write
	STATUS					mandatory
	DESCRIPTION			"PG Outlet 2 name"
	::= { node11PG 17 }

pgNode11Out2CustVoice	OBJECT-TYPE
	SYNTAX					DisplayString
	ACCESS					read-write
	STATUS					mandatory
	DESCRIPTION			"PG Outlet 2 custom voice"
	::= { node11PG 18 }

pgNode11Out2Volts			OBJECT-TYPE
	SYNTAX					INTEGER
	ACCESS					read-only
	STATUS					mandatory
	DESCRIPTION			"PG Outlet 2 volts"
	::= { node11PG 19 }

pgNode11Out2Amps				OBJECT-TYPE
	SYNTAX					INTEGER
	ACCESS					read-only
	STATUS					mandatory
	DESCRIPTION			"PG Outlet 2 amps"
	::= { node11PG 20 }

pgNode11Out2Watts			OBJECT-TYPE
	SYNTAX					INTEGER
	ACCESS					read-only
	STATUS					mandatory
	DESCRIPTION			"PG Outlet 2 watts"
	::= { node11PG 21 }

pgNode11Out2State			OBJECT-TYPE
	SYNTAX					INTEGER { off(1),on(2),cycle(3) }
	ACCESS					read-only
	STATUS					mandatory
	DESCRIPTION			"PG Outlet 2 state"
	::= { node11PG 22 }

pgNode11Out2Cmd				OBJECT-TYPE
	SYNTAX					INTEGER { off(1),on(2),cycle(3) }
	ACCESS					read-write
	STATUS					mandatory
	DESCRIPTION			"PG Outlet 2 command"
	::= { node11PG 23 }

pgNode11Out3Name				OBJECT-TYPE
	SYNTAX					DisplayString
	ACCESS					read-write
	STATUS					mandatory
	DESCRIPTION			"PG Outlet 3 name"
	::= { node11PG 24 }

pgNode11Out3CustVoice	OBJECT-TYPE
	SYNTAX					DisplayString
	ACCESS					read-write
	STATUS					mandatory
	DESCRIPTION			"PG Outlet 3 custom voice"
	::= { node11PG 25 }

pgNode11Out3Volts			OBJECT-TYPE
	SYNTAX					INTEGER
	ACCESS					read-only
	STATUS					mandatory
	DESCRIPTION			"PG Outlet 3 volts"
	::= { node11PG 26 }

pgNode11Out3Amps				OBJECT-TYPE
	SYNTAX					INTEGER
	ACCESS					read-only
	STATUS					mandatory
	DESCRIPTION			"PG Outlet 3 amps"
	::= { node11PG 27 }

pgNode11Out3Watts			OBJECT-TYPE
	SYNTAX					INTEGER
	ACCESS					read-only
	STATUS					mandatory
	DESCRIPTION			"PG Outlet 3 watts"
	::= { node11PG 28 }

pgNode11Out3State			OBJECT-TYPE
	SYNTAX					INTEGER { off(1),on(2),cycle(3) }
	ACCESS					read-only
	STATUS					mandatory
	DESCRIPTION			"PG Outlet 3 state"
	::= { node11PG 29 }

pgNode11Out3Cmd				OBJECT-TYPE
	SYNTAX					INTEGER { off(1),on(2),cycle(3) }
	ACCESS					read-write
	STATUS					mandatory
	DESCRIPTION			"PG Outlet 3 command"
	::= { node11PG 30 }

pgNode11Out4Name				OBJECT-TYPE
	SYNTAX					DisplayString
	ACCESS					read-write
	STATUS					mandatory
	DESCRIPTION			"PG Outlet 4 name"
	::= { node11PG 31 }

pgNode11Out4CustVoice	OBJECT-TYPE
	SYNTAX					DisplayString
	ACCESS					read-write
	STATUS					mandatory
	DESCRIPTION			"PG Outlet 4 custom voice"
	::= { node11PG 32 }

pgNode11Out4Volts			OBJECT-TYPE
	SYNTAX					INTEGER
	ACCESS					read-only
	STATUS					mandatory
	DESCRIPTION			"PG Outlet 4 volts"
	::= { node11PG 33 }

pgNode11Out4Amps				OBJECT-TYPE
	SYNTAX					INTEGER
	ACCESS					read-only
	STATUS					mandatory
	DESCRIPTION			"PG Outlet 4 amps"
	::= { node11PG 34 }

pgNode11Out4Watts			OBJECT-TYPE
	SYNTAX					INTEGER
	ACCESS					read-only
	STATUS					mandatory
	DESCRIPTION			"PG Outlet 4 watts"
	::= { node11PG 35 }

pgNode11Out4State			OBJECT-TYPE
	SYNTAX					INTEGER { off(1),on(2),cycle(3) }
	ACCESS					read-only
	STATUS					mandatory
	DESCRIPTION			"PG Outlet 4 state"
	::= { node11PG 36 }

pgNode11Out4Cmd				OBJECT-TYPE
	SYNTAX					INTEGER { off(1),on(2),cycle(3) }
	ACCESS					read-write
	STATUS					mandatory
	DESCRIPTION			"PG Outlet 4 command"
	::= { node11PG 37 }

pgNode11Out5Name				OBJECT-TYPE
	SYNTAX					DisplayString
	ACCESS					read-write
	STATUS					mandatory
	DESCRIPTION			"PG Outlet 5 name"
	::= { node11PG 38 }

pgNode11Out5CustVoice	OBJECT-TYPE
	SYNTAX					DisplayString
	ACCESS					read-write
	STATUS					mandatory
	DESCRIPTION			"PG Outlet 5 custom voice"
	::= { node11PG 39 }

pgNode11Out5Volts			OBJECT-TYPE
	SYNTAX					INTEGER
	ACCESS					read-only
	STATUS					mandatory
	DESCRIPTION			"PG Outlet 5 volts"
	::= { node11PG 40 }

pgNode11Out5Amps				OBJECT-TYPE
	SYNTAX					INTEGER
	ACCESS					read-only
	STATUS					mandatory
	DESCRIPTION			"PG Outlet 5 amps"
	::= { node11PG 41 }

pgNode11Out5Watts			OBJECT-TYPE
	SYNTAX					INTEGER
	ACCESS					read-only
	STATUS					mandatory
	DESCRIPTION			"PG Outlet 5 watts"
	::= { node11PG 42 }

pgNode11Out5State			OBJECT-TYPE
	SYNTAX					INTEGER { off(1),on(2),cycle(3) }
	ACCESS					read-only
	STATUS					mandatory
	DESCRIPTION			"PG Outlet 5 state"
	::= { node11PG 43 }

pgNode11Out5Cmd				OBJECT-TYPE
	SYNTAX					INTEGER { off(1),on(2),cycle(3) }
	ACCESS					read-write
	STATUS					mandatory
	DESCRIPTION			"PG Outlet 5 command"
	::= { node11PG 44 }

pgNode11Out6Name				OBJECT-TYPE
	SYNTAX					DisplayString
	ACCESS					read-write
	STATUS					mandatory
	DESCRIPTION			"PG Outlet 6 name"
	::= { node11PG 45 }

pgNode11Out6CustVoice	OBJECT-TYPE
	SYNTAX					DisplayString
	ACCESS					read-write
	STATUS					mandatory
	DESCRIPTION			"PG Outlet 6 custom voice"
	::= { node11PG 46 }

pgNode11Out6Volts			OBJECT-TYPE
	SYNTAX					INTEGER
	ACCESS					read-only
	STATUS					mandatory
	DESCRIPTION			"PG Outlet 6 volts"
	::= { node11PG 47 }

pgNode11Out6Amps				OBJECT-TYPE
	SYNTAX					INTEGER
	ACCESS					read-only
	STATUS					mandatory
	DESCRIPTION			"PG Outlet 6 amps"
	::= { node11PG 48 }

pgNode11Out6Watts			OBJECT-TYPE
	SYNTAX					INTEGER
	ACCESS					read-only
	STATUS					mandatory
	DESCRIPTION			"PG Outlet 6 watts"
	::= { node11PG 49 }

pgNode11Out6State			OBJECT-TYPE
	SYNTAX					INTEGER { off(1),on(2),cycle(3) }
	ACCESS					read-only
	STATUS					mandatory
	DESCRIPTION			"PG Outlet 6 state"
	::= { node11PG 50 }

pgNode11Out6Cmd				OBJECT-TYPE
	SYNTAX					INTEGER { off(1),on(2),cycle(3) }
	ACCESS					read-write
	STATUS					mandatory
	DESCRIPTION			"PG Outlet 6 command"
	::= { node11PG 51 }

pgNode11Out7Name				OBJECT-TYPE
	SYNTAX					DisplayString
	ACCESS					read-write
	STATUS					mandatory
	DESCRIPTION			"PG Outlet 7 name"
	::= { node11PG 52 }

pgNode11Out7CustVoice	OBJECT-TYPE
	SYNTAX					DisplayString
	ACCESS					read-write
	STATUS					mandatory
	DESCRIPTION			"PG Outlet 7 custom voice"
	::= { node11PG 53 }

pgNode11Out7Volts			OBJECT-TYPE
	SYNTAX					INTEGER
	ACCESS					read-only
	STATUS					mandatory
	DESCRIPTION			"PG Outlet 7 volts"
	::= { node11PG 54 }

pgNode11Out7Amps				OBJECT-TYPE
	SYNTAX					INTEGER
	ACCESS					read-only
	STATUS					mandatory
	DESCRIPTION			"PG Outlet 7 amps"
	::= { node11PG 55 }

pgNode11Out7Watts			OBJECT-TYPE
	SYNTAX					INTEGER
	ACCESS					read-only
	STATUS					mandatory
	DESCRIPTION			"PG Outlet 7 watts"
	::= { node11PG 56 }

pgNode11Out7State			OBJECT-TYPE
	SYNTAX					INTEGER { off(1),on(2),cycle(3) }
	ACCESS					read-only
	STATUS					mandatory
	DESCRIPTION			"PG Outlet 7 state"
	::= { node11PG 57 }

pgNode11Out7Cmd				OBJECT-TYPE
	SYNTAX					INTEGER { off(1),on(2),cycle(3) }
	ACCESS					read-write
	STATUS					mandatory
	DESCRIPTION			"PG Outlet 7 command"
	::= { node11PG 58 }

pgNode11Out8Name				OBJECT-TYPE
	SYNTAX					DisplayString
	ACCESS					read-write
	STATUS					mandatory
	DESCRIPTION			"PG Outlet 8 name"
	::= { node11PG 59 }

pgNode11Out8CustVoice	OBJECT-TYPE
	SYNTAX					DisplayString
	ACCESS					read-write
	STATUS					mandatory
	DESCRIPTION			"PG Outlet 8 custom voice"
	::= { node11PG 60 }

pgNode11Out8Volts			OBJECT-TYPE
	SYNTAX					INTEGER
	ACCESS					read-only
	STATUS					mandatory
	DESCRIPTION			"PG Outlet 8 volts"
	::= { node11PG 61 }

pgNode11Out8Amps				OBJECT-TYPE
	SYNTAX					INTEGER
	ACCESS					read-only
	STATUS					mandatory
	DESCRIPTION			"PG Outlet 8 amps"
	::= { node11PG 62 }

pgNode11Out8Watts			OBJECT-TYPE
	SYNTAX					INTEGER
	ACCESS					read-only
	STATUS					mandatory
	DESCRIPTION			"PG Outlet 8 watts"
	::= { node11PG 63 }

pgNode11Out8State			OBJECT-TYPE
	SYNTAX					INTEGER { off(1),on(2),cycle(3) }
	ACCESS					read-only
	STATUS					mandatory
	DESCRIPTION			"PG Outlet 8 state"
	::= { node11PG 64 }

pgNode11Out8Cmd				OBJECT-TYPE
	SYNTAX					INTEGER { off(1),on(2),cycle(3) }
	ACCESS					read-write
	STATUS					mandatory
	DESCRIPTION			"PG Outlet 8 command"
	::= { node11PG 65 }

pgNode12InUse					OBJECT-TYPE
	SYNTAX					INTEGER { false(1),true(2) }
	ACCESS					read-only
	STATUS					mandatory
	DESCRIPTION			"PG in use"
	::= { node12PG 1 }

pgNode12Status					OBJECT-TYPE
	SYNTAX					INTEGER { normal(1),pending(2), trouble(3) }
	ACCESS					read-only
	STATUS					mandatory
	DESCRIPTION			"PG status"
	::= { node12PG 2 }

pgNode12StatusSupport	OBJECT-TYPE
	SYNTAX					INTEGER { true1(1),false(2) }
	ACCESS					read-only
	STATUS					mandatory
	DESCRIPTION			"PG status support level"
	::= { node12PG 3 }

pgNode12Ver						OBJECT-TYPE
	SYNTAX					INTEGER { pgate1(1),pgate2(2) }
	ACCESS					read-only
	STATUS					mandatory
	DESCRIPTION			"PG version"
	::= { node12PG 4 }

pgNode12Volts					OBJECT-TYPE
	SYNTAX					INTEGER
	ACCESS					read-only
	STATUS					mandatory
	DESCRIPTION			"PG voltage"
	::= { node12PG 5 }

pgNode12Amps						OBJECT-TYPE
	SYNTAX					INTEGER
	ACCESS					read-only
	STATUS					mandatory
	DESCRIPTION			"PG amps"
	::= { node12PG 6 }

pgNode12Watts					OBJECT-TYPE
	SYNTAX					INTEGER
	ACCESS					read-only
	STATUS					mandatory
	DESCRIPTION			"PG Watts"
	::= { node12PG 7 }

pgNode12Name						OBJECT-TYPE
	SYNTAX					DisplayString
	ACCESS					read-write
	STATUS					mandatory
	DESCRIPTION			"PG name"
	::= { node12PG 8 }

pgNode12CustVoice			OBJECT-TYPE
	SYNTAX					DisplayString
	ACCESS					read-write
	STATUS					mandatory
	DESCRIPTION			"PG custom voice"
	::= { node12PG 9 }

pgNode12Out1Name				OBJECT-TYPE
	SYNTAX					DisplayString
	ACCESS					read-write
	STATUS					mandatory
	DESCRIPTION			"PG Outlet 1 name"
	::= { node12PG 10 }

pgNode12Out1CustVoice	OBJECT-TYPE
	SYNTAX					DisplayString
	ACCESS					read-write
	STATUS					mandatory
	DESCRIPTION			"PG Outlet 1 custom voice"
	::= { node12PG 11 }

pgNode12Out1Volts			OBJECT-TYPE
	SYNTAX					INTEGER
	ACCESS					read-only
	STATUS					mandatory
	DESCRIPTION			"PG Outlet 1 volts"
	::= { node12PG 12 }

pgNode12Out1Amps				OBJECT-TYPE
	SYNTAX					INTEGER
	ACCESS					read-only
	STATUS					mandatory
	DESCRIPTION			"PG Outlet 1 amps"
	::= { node12PG 13 }

pgNode12Out1Watts			OBJECT-TYPE
	SYNTAX					INTEGER
	ACCESS					read-only
	STATUS					mandatory
	DESCRIPTION			"PG Outlet 1 watts"
	::= { node12PG 14 }

pgNode12Out1State			OBJECT-TYPE
	SYNTAX					INTEGER { off(1),on(2),cycle(3) }
	ACCESS					read-only
	STATUS					mandatory
	DESCRIPTION			"PG Outlet 1 state"
	::= { node12PG 15 }

pgNode12Out1Cmd				OBJECT-TYPE
	SYNTAX					INTEGER { off(1),on(2),cycle(3) }
	ACCESS					read-write
	STATUS					mandatory
	DESCRIPTION			"PG Outlet 1 command"
	::= { node12PG 16 }

pgNode12Out2Name				OBJECT-TYPE
	SYNTAX					DisplayString
	ACCESS					read-write
	STATUS					mandatory
	DESCRIPTION			"PG Outlet 2 name"
	::= { node12PG 17 }

pgNode12Out2CustVoice	OBJECT-TYPE
	SYNTAX					DisplayString
	ACCESS					read-write
	STATUS					mandatory
	DESCRIPTION			"PG Outlet 2 custom voice"
	::= { node12PG 18 }

pgNode12Out2Volts			OBJECT-TYPE
	SYNTAX					INTEGER
	ACCESS					read-only
	STATUS					mandatory
	DESCRIPTION			"PG Outlet 2 volts"
	::= { node12PG 19 }

pgNode12Out2Amps				OBJECT-TYPE
	SYNTAX					INTEGER
	ACCESS					read-only
	STATUS					mandatory
	DESCRIPTION			"PG Outlet 2 amps"
	::= { node12PG 20 }

pgNode12Out2Watts			OBJECT-TYPE
	SYNTAX					INTEGER
	ACCESS					read-only
	STATUS					mandatory
	DESCRIPTION			"PG Outlet 2 watts"
	::= { node12PG 21 }

pgNode12Out2State			OBJECT-TYPE
	SYNTAX					INTEGER { off(1),on(2),cycle(3) }
	ACCESS					read-only
	STATUS					mandatory
	DESCRIPTION			"PG Outlet 2 state"
	::= { node12PG 22 }

pgNode12Out2Cmd				OBJECT-TYPE
	SYNTAX					INTEGER { off(1),on(2),cycle(3) }
	ACCESS					read-write
	STATUS					mandatory
	DESCRIPTION			"PG Outlet 2 command"
	::= { node12PG 23 }

pgNode12Out3Name				OBJECT-TYPE
	SYNTAX					DisplayString
	ACCESS					read-write
	STATUS					mandatory
	DESCRIPTION			"PG Outlet 3 name"
	::= { node12PG 24 }

pgNode12Out3CustVoice	OBJECT-TYPE
	SYNTAX					DisplayString
	ACCESS					read-write
	STATUS					mandatory
	DESCRIPTION			"PG Outlet 3 custom voice"
	::= { node12PG 25 }

pgNode12Out3Volts			OBJECT-TYPE
	SYNTAX					INTEGER
	ACCESS					read-only
	STATUS					mandatory
	DESCRIPTION			"PG Outlet 3 volts"
	::= { node12PG 26 }

pgNode12Out3Amps				OBJECT-TYPE
	SYNTAX					INTEGER
	ACCESS					read-only
	STATUS					mandatory
	DESCRIPTION			"PG Outlet 3 amps"
	::= { node12PG 27 }

pgNode12Out3Watts			OBJECT-TYPE
	SYNTAX					INTEGER
	ACCESS					read-only
	STATUS					mandatory
	DESCRIPTION			"PG Outlet 3 watts"
	::= { node12PG 28 }

pgNode12Out3State			OBJECT-TYPE
	SYNTAX					INTEGER { off(1),on(2),cycle(3) }
	ACCESS					read-only
	STATUS					mandatory
	DESCRIPTION			"PG Outlet 3 state"
	::= { node12PG 29 }

pgNode12Out3Cmd				OBJECT-TYPE
	SYNTAX					INTEGER { off(1),on(2),cycle(3) }
	ACCESS					read-write
	STATUS					mandatory
	DESCRIPTION			"PG Outlet 3 command"
	::= { node12PG 30 }

pgNode12Out4Name				OBJECT-TYPE
	SYNTAX					DisplayString
	ACCESS					read-write
	STATUS					mandatory
	DESCRIPTION			"PG Outlet 4 name"
	::= { node12PG 31 }

pgNode12Out4CustVoice	OBJECT-TYPE
	SYNTAX					DisplayString
	ACCESS					read-write
	STATUS					mandatory
	DESCRIPTION			"PG Outlet 4 custom voice"
	::= { node12PG 32 }

pgNode12Out4Volts			OBJECT-TYPE
	SYNTAX					INTEGER
	ACCESS					read-only
	STATUS					mandatory
	DESCRIPTION			"PG Outlet 4 volts"
	::= { node12PG 33 }

pgNode12Out4Amps				OBJECT-TYPE
	SYNTAX					INTEGER
	ACCESS					read-only
	STATUS					mandatory
	DESCRIPTION			"PG Outlet 4 amps"
	::= { node12PG 34 }

pgNode12Out4Watts			OBJECT-TYPE
	SYNTAX					INTEGER
	ACCESS					read-only
	STATUS					mandatory
	DESCRIPTION			"PG Outlet 4 watts"
	::= { node12PG 35 }

pgNode12Out4State			OBJECT-TYPE
	SYNTAX					INTEGER { off(1),on(2),cycle(3) }
	ACCESS					read-only
	STATUS					mandatory
	DESCRIPTION			"PG Outlet 4 state"
	::= { node12PG 36 }

pgNode12Out4Cmd				OBJECT-TYPE
	SYNTAX					INTEGER { off(1),on(2),cycle(3) }
	ACCESS					read-write
	STATUS					mandatory
	DESCRIPTION			"PG Outlet 4 command"
	::= { node12PG 37 }

pgNode12Out5Name				OBJECT-TYPE
	SYNTAX					DisplayString
	ACCESS					read-write
	STATUS					mandatory
	DESCRIPTION			"PG Outlet 5 name"
	::= { node12PG 38 }

pgNode12Out5CustVoice	OBJECT-TYPE
	SYNTAX					DisplayString
	ACCESS					read-write
	STATUS					mandatory
	DESCRIPTION			"PG Outlet 5 custom voice"
	::= { node12PG 39 }

pgNode12Out5Volts			OBJECT-TYPE
	SYNTAX					INTEGER
	ACCESS					read-only
	STATUS					mandatory
	DESCRIPTION			"PG Outlet 5 volts"
	::= { node12PG 40 }

pgNode12Out5Amps				OBJECT-TYPE
	SYNTAX					INTEGER
	ACCESS					read-only
	STATUS					mandatory
	DESCRIPTION			"PG Outlet 5 amps"
	::= { node12PG 41 }

pgNode12Out5Watts			OBJECT-TYPE
	SYNTAX					INTEGER
	ACCESS					read-only
	STATUS					mandatory
	DESCRIPTION			"PG Outlet 5 watts"
	::= { node12PG 42 }

pgNode12Out5State			OBJECT-TYPE
	SYNTAX					INTEGER { off(1),on(2),cycle(3) }
	ACCESS					read-only
	STATUS					mandatory
	DESCRIPTION			"PG Outlet 5 state"
	::= { node12PG 43 }

pgNode12Out5Cmd				OBJECT-TYPE
	SYNTAX					INTEGER { off(1),on(2),cycle(3) }
	ACCESS					read-write
	STATUS					mandatory
	DESCRIPTION			"PG Outlet 5 command"
	::= { node12PG 44 }

pgNode12Out6Name				OBJECT-TYPE
	SYNTAX					DisplayString
	ACCESS					read-write
	STATUS					mandatory
	DESCRIPTION			"PG Outlet 6 name"
	::= { node12PG 45 }

pgNode12Out6CustVoice	OBJECT-TYPE
	SYNTAX					DisplayString
	ACCESS					read-write
	STATUS					mandatory
	DESCRIPTION			"PG Outlet 6 custom voice"
	::= { node12PG 46 }

pgNode12Out6Volts			OBJECT-TYPE
	SYNTAX					INTEGER
	ACCESS					read-only
	STATUS					mandatory
	DESCRIPTION			"PG Outlet 6 volts"
	::= { node12PG 47 }

pgNode12Out6Amps				OBJECT-TYPE
	SYNTAX					INTEGER
	ACCESS					read-only
	STATUS					mandatory
	DESCRIPTION			"PG Outlet 6 amps"
	::= { node12PG 48 }

pgNode12Out6Watts			OBJECT-TYPE
	SYNTAX					INTEGER
	ACCESS					read-only
	STATUS					mandatory
	DESCRIPTION			"PG Outlet 6 watts"
	::= { node12PG 49 }

pgNode12Out6State			OBJECT-TYPE
	SYNTAX					INTEGER { off(1),on(2),cycle(3) }
	ACCESS					read-only
	STATUS					mandatory
	DESCRIPTION			"PG Outlet 6 state"
	::= { node12PG 50 }

pgNode12Out6Cmd				OBJECT-TYPE
	SYNTAX					INTEGER { off(1),on(2),cycle(3) }
	ACCESS					read-write
	STATUS					mandatory
	DESCRIPTION			"PG Outlet 6 command"
	::= { node12PG 51 }

pgNode12Out7Name				OBJECT-TYPE
	SYNTAX					DisplayString
	ACCESS					read-write
	STATUS					mandatory
	DESCRIPTION			"PG Outlet 7 name"
	::= { node12PG 52 }

pgNode12Out7CustVoice	OBJECT-TYPE
	SYNTAX					DisplayString
	ACCESS					read-write
	STATUS					mandatory
	DESCRIPTION			"PG Outlet 7 custom voice"
	::= { node12PG 53 }

pgNode12Out7Volts			OBJECT-TYPE
	SYNTAX					INTEGER
	ACCESS					read-only
	STATUS					mandatory
	DESCRIPTION			"PG Outlet 7 volts"
	::= { node12PG 54 }

pgNode12Out7Amps				OBJECT-TYPE
	SYNTAX					INTEGER
	ACCESS					read-only
	STATUS					mandatory
	DESCRIPTION			"PG Outlet 7 amps"
	::= { node12PG 55 }

pgNode12Out7Watts			OBJECT-TYPE
	SYNTAX					INTEGER
	ACCESS					read-only
	STATUS					mandatory
	DESCRIPTION			"PG Outlet 7 watts"
	::= { node12PG 56 }

pgNode12Out7State			OBJECT-TYPE
	SYNTAX					INTEGER { off(1),on(2),cycle(3) }
	ACCESS					read-only
	STATUS					mandatory
	DESCRIPTION			"PG Outlet 7 state"
	::= { node12PG 57 }

pgNode12Out7Cmd				OBJECT-TYPE
	SYNTAX					INTEGER { off(1),on(2),cycle(3) }
	ACCESS					read-write
	STATUS					mandatory
	DESCRIPTION			"PG Outlet 7 command"
	::= { node12PG 58 }

pgNode12Out8Name				OBJECT-TYPE
	SYNTAX					DisplayString
	ACCESS					read-write
	STATUS					mandatory
	DESCRIPTION			"PG Outlet 8 name"
	::= { node12PG 59 }

pgNode12Out8CustVoice	OBJECT-TYPE
	SYNTAX					DisplayString
	ACCESS					read-write
	STATUS					mandatory
	DESCRIPTION			"PG Outlet 8 custom voice"
	::= { node12PG 60 }

pgNode12Out8Volts			OBJECT-TYPE
	SYNTAX					INTEGER
	ACCESS					read-only
	STATUS					mandatory
	DESCRIPTION			"PG Outlet 8 volts"
	::= { node12PG 61 }

pgNode12Out8Amps				OBJECT-TYPE
	SYNTAX					INTEGER
	ACCESS					read-only
	STATUS					mandatory
	DESCRIPTION			"PG Outlet 8 amps"
	::= { node12PG 62 }

pgNode12Out8Watts			OBJECT-TYPE
	SYNTAX					INTEGER
	ACCESS					read-only
	STATUS					mandatory
	DESCRIPTION			"PG Outlet 8 watts"
	::= { node12PG 63 }

pgNode12Out8State			OBJECT-TYPE
	SYNTAX					INTEGER { off(1),on(2),cycle(3) }
	ACCESS					read-only
	STATUS					mandatory
	DESCRIPTION			"PG Outlet 8 state"
	::= { node12PG 64 }

pgNode12Out8Cmd				OBJECT-TYPE
	SYNTAX					INTEGER { off(1),on(2),cycle(3) }
	ACCESS					read-write
	STATUS					mandatory
	DESCRIPTION			"PG Outlet 8 command"
	::= { node12PG 65 }

pgNode13InUse					OBJECT-TYPE
	SYNTAX					INTEGER { false(1),true(2) }
	ACCESS					read-only
	STATUS					mandatory
	DESCRIPTION			"PG in use"
	::= { node13PG 1 }

pgNode13Status					OBJECT-TYPE
	SYNTAX					INTEGER { normal(1),pending(2), trouble(3) }
	ACCESS					read-only
	STATUS					mandatory
	DESCRIPTION			"PG status"
	::= { node13PG 2 }

pgNode13StatusSupport	OBJECT-TYPE
	SYNTAX					INTEGER { true1(1),false(2) }
	ACCESS					read-only
	STATUS					mandatory
	DESCRIPTION			"PG status support level"
	::= { node13PG 3 }

pgNode13Ver						OBJECT-TYPE
	SYNTAX					INTEGER { pgate1(1),pgate2(2) }
	ACCESS					read-only
	STATUS					mandatory
	DESCRIPTION			"PG version"
	::= { node13PG 4 }

pgNode13Volts					OBJECT-TYPE
	SYNTAX					INTEGER
	ACCESS					read-only
	STATUS					mandatory
	DESCRIPTION			"PG voltage"
	::= { node13PG 5 }

pgNode13Amps						OBJECT-TYPE
	SYNTAX					INTEGER
	ACCESS					read-only
	STATUS					mandatory
	DESCRIPTION			"PG amps"
	::= { node13PG 6 }

pgNode13Watts					OBJECT-TYPE
	SYNTAX					INTEGER
	ACCESS					read-only
	STATUS					mandatory
	DESCRIPTION			"PG Watts"
	::= { node13PG 7 }

pgNode13Name						OBJECT-TYPE
	SYNTAX					DisplayString
	ACCESS					read-write
	STATUS					mandatory
	DESCRIPTION			"PG name"
	::= { node13PG 8 }

pgNode13CustVoice			OBJECT-TYPE
	SYNTAX					DisplayString
	ACCESS					read-write
	STATUS					mandatory
	DESCRIPTION			"PG custom voice"
	::= { node13PG 9 }

pgNode13Out1Name				OBJECT-TYPE
	SYNTAX					DisplayString
	ACCESS					read-write
	STATUS					mandatory
	DESCRIPTION			"PG Outlet 1 name"
	::= { node13PG 10 }

pgNode13Out1CustVoice	OBJECT-TYPE
	SYNTAX					DisplayString
	ACCESS					read-write
	STATUS					mandatory
	DESCRIPTION			"PG Outlet 1 custom voice"
	::= { node13PG 11 }

pgNode13Out1Volts			OBJECT-TYPE
	SYNTAX					INTEGER
	ACCESS					read-only
	STATUS					mandatory
	DESCRIPTION			"PG Outlet 1 volts"
	::= { node13PG 12 }

pgNode13Out1Amps				OBJECT-TYPE
	SYNTAX					INTEGER
	ACCESS					read-only
	STATUS					mandatory
	DESCRIPTION			"PG Outlet 1 amps"
	::= { node13PG 13 }

pgNode13Out1Watts			OBJECT-TYPE
	SYNTAX					INTEGER
	ACCESS					read-only
	STATUS					mandatory
	DESCRIPTION			"PG Outlet 1 watts"
	::= { node13PG 14 }

pgNode13Out1State			OBJECT-TYPE
	SYNTAX					INTEGER { off(1),on(2),cycle(3) }
	ACCESS					read-only
	STATUS					mandatory
	DESCRIPTION			"PG Outlet 1 state"
	::= { node13PG 15 }

pgNode13Out1Cmd				OBJECT-TYPE
	SYNTAX					INTEGER { off(1),on(2),cycle(3) }
	ACCESS					read-write
	STATUS					mandatory
	DESCRIPTION			"PG Outlet 1 command"
	::= { node13PG 16 }

pgNode13Out2Name				OBJECT-TYPE
	SYNTAX					DisplayString
	ACCESS					read-write
	STATUS					mandatory
	DESCRIPTION			"PG Outlet 2 name"
	::= { node13PG 17 }

pgNode13Out2CustVoice	OBJECT-TYPE
	SYNTAX					DisplayString
	ACCESS					read-write
	STATUS					mandatory
	DESCRIPTION			"PG Outlet 2 custom voice"
	::= { node13PG 18 }

pgNode13Out2Volts			OBJECT-TYPE
	SYNTAX					INTEGER
	ACCESS					read-only
	STATUS					mandatory
	DESCRIPTION			"PG Outlet 2 volts"
	::= { node13PG 19 }

pgNode13Out2Amps				OBJECT-TYPE
	SYNTAX					INTEGER
	ACCESS					read-only
	STATUS					mandatory
	DESCRIPTION			"PG Outlet 2 amps"
	::= { node13PG 20 }

pgNode13Out2Watts			OBJECT-TYPE
	SYNTAX					INTEGER
	ACCESS					read-only
	STATUS					mandatory
	DESCRIPTION			"PG Outlet 2 watts"
	::= { node13PG 21 }

pgNode13Out2State			OBJECT-TYPE
	SYNTAX					INTEGER { off(1),on(2),cycle(3) }
	ACCESS					read-only
	STATUS					mandatory
	DESCRIPTION			"PG Outlet 2 state"
	::= { node13PG 22 }

pgNode13Out2Cmd				OBJECT-TYPE
	SYNTAX					INTEGER { off(1),on(2),cycle(3) }
	ACCESS					read-write
	STATUS					mandatory
	DESCRIPTION			"PG Outlet 2 command"
	::= { node13PG 23 }

pgNode13Out3Name				OBJECT-TYPE
	SYNTAX					DisplayString
	ACCESS					read-write
	STATUS					mandatory
	DESCRIPTION			"PG Outlet 3 name"
	::= { node13PG 24 }

pgNode13Out3CustVoice	OBJECT-TYPE
	SYNTAX					DisplayString
	ACCESS					read-write
	STATUS					mandatory
	DESCRIPTION			"PG Outlet 3 custom voice"
	::= { node13PG 25 }

pgNode13Out3Volts			OBJECT-TYPE
	SYNTAX					INTEGER
	ACCESS					read-only
	STATUS					mandatory
	DESCRIPTION			"PG Outlet 3 volts"
	::= { node13PG 26 }

pgNode13Out3Amps				OBJECT-TYPE
	SYNTAX					INTEGER
	ACCESS					read-only
	STATUS					mandatory
	DESCRIPTION			"PG Outlet 3 amps"
	::= { node13PG 27 }

pgNode13Out3Watts			OBJECT-TYPE
	SYNTAX					INTEGER
	ACCESS					read-only
	STATUS					mandatory
	DESCRIPTION			"PG Outlet 3 watts"
	::= { node13PG 28 }

pgNode13Out3State			OBJECT-TYPE
	SYNTAX					INTEGER { off(1),on(2),cycle(3) }
	ACCESS					read-only
	STATUS					mandatory
	DESCRIPTION			"PG Outlet 3 state"
	::= { node13PG 29 }

pgNode13Out3Cmd				OBJECT-TYPE
	SYNTAX					INTEGER { off(1),on(2),cycle(3) }
	ACCESS					read-write
	STATUS					mandatory
	DESCRIPTION			"PG Outlet 3 command"
	::= { node13PG 30 }

pgNode13Out4Name				OBJECT-TYPE
	SYNTAX					DisplayString
	ACCESS					read-write
	STATUS					mandatory
	DESCRIPTION			"PG Outlet 4 name"
	::= { node13PG 31 }

pgNode13Out4CustVoice	OBJECT-TYPE
	SYNTAX					DisplayString
	ACCESS					read-write
	STATUS					mandatory
	DESCRIPTION			"PG Outlet 4 custom voice"
	::= { node13PG 32 }

pgNode13Out4Volts			OBJECT-TYPE
	SYNTAX					INTEGER
	ACCESS					read-only
	STATUS					mandatory
	DESCRIPTION			"PG Outlet 4 volts"
	::= { node13PG 33 }

pgNode13Out4Amps				OBJECT-TYPE
	SYNTAX					INTEGER
	ACCESS					read-only
	STATUS					mandatory
	DESCRIPTION			"PG Outlet 4 amps"
	::= { node13PG 34 }

pgNode13Out4Watts			OBJECT-TYPE
	SYNTAX					INTEGER
	ACCESS					read-only
	STATUS					mandatory
	DESCRIPTION			"PG Outlet 4 watts"
	::= { node13PG 35 }

pgNode13Out4State			OBJECT-TYPE
	SYNTAX					INTEGER { off(1),on(2),cycle(3) }
	ACCESS					read-only
	STATUS					mandatory
	DESCRIPTION			"PG Outlet 4 state"
	::= { node13PG 36 }

pgNode13Out4Cmd				OBJECT-TYPE
	SYNTAX					INTEGER { off(1),on(2),cycle(3) }
	ACCESS					read-write
	STATUS					mandatory
	DESCRIPTION			"PG Outlet 4 command"
	::= { node13PG 37 }

pgNode13Out5Name				OBJECT-TYPE
	SYNTAX					DisplayString
	ACCESS					read-write
	STATUS					mandatory
	DESCRIPTION			"PG Outlet 5 name"
	::= { node13PG 38 }

pgNode13Out5CustVoice	OBJECT-TYPE
	SYNTAX					DisplayString
	ACCESS					read-write
	STATUS					mandatory
	DESCRIPTION			"PG Outlet 5 custom voice"
	::= { node13PG 39 }

pgNode13Out5Volts			OBJECT-TYPE
	SYNTAX					INTEGER
	ACCESS					read-only
	STATUS					mandatory
	DESCRIPTION			"PG Outlet 5 volts"
	::= { node13PG 40 }

pgNode13Out5Amps				OBJECT-TYPE
	SYNTAX					INTEGER
	ACCESS					read-only
	STATUS					mandatory
	DESCRIPTION			"PG Outlet 5 amps"
	::= { node13PG 41 }

pgNode13Out5Watts			OBJECT-TYPE
	SYNTAX					INTEGER
	ACCESS					read-only
	STATUS					mandatory
	DESCRIPTION			"PG Outlet 5 watts"
	::= { node13PG 42 }

pgNode13Out5State			OBJECT-TYPE
	SYNTAX					INTEGER { off(1),on(2),cycle(3) }
	ACCESS					read-only
	STATUS					mandatory
	DESCRIPTION			"PG Outlet 5 state"
	::= { node13PG 43 }

pgNode13Out5Cmd				OBJECT-TYPE
	SYNTAX					INTEGER { off(1),on(2),cycle(3) }
	ACCESS					read-write
	STATUS					mandatory
	DESCRIPTION			"PG Outlet 5 command"
	::= { node13PG 44 }

pgNode13Out6Name				OBJECT-TYPE
	SYNTAX					DisplayString
	ACCESS					read-write
	STATUS					mandatory
	DESCRIPTION			"PG Outlet 6 name"
	::= { node13PG 45 }

pgNode13Out6CustVoice	OBJECT-TYPE
	SYNTAX					DisplayString
	ACCESS					read-write
	STATUS					mandatory
	DESCRIPTION			"PG Outlet 6 custom voice"
	::= { node13PG 46 }

pgNode13Out6Volts			OBJECT-TYPE
	SYNTAX					INTEGER
	ACCESS					read-only
	STATUS					mandatory
	DESCRIPTION			"PG Outlet 6 volts"
	::= { node13PG 47 }

pgNode13Out6Amps				OBJECT-TYPE
	SYNTAX					INTEGER
	ACCESS					read-only
	STATUS					mandatory
	DESCRIPTION			"PG Outlet 6 amps"
	::= { node13PG 48 }

pgNode13Out6Watts			OBJECT-TYPE
	SYNTAX					INTEGER
	ACCESS					read-only
	STATUS					mandatory
	DESCRIPTION			"PG Outlet 6 watts"
	::= { node13PG 49 }

pgNode13Out6State			OBJECT-TYPE
	SYNTAX					INTEGER { off(1),on(2),cycle(3) }
	ACCESS					read-only
	STATUS					mandatory
	DESCRIPTION			"PG Outlet 6 state"
	::= { node13PG 50 }

pgNode13Out6Cmd				OBJECT-TYPE
	SYNTAX					INTEGER { off(1),on(2),cycle(3) }
	ACCESS					read-write
	STATUS					mandatory
	DESCRIPTION			"PG Outlet 6 command"
	::= { node13PG 51 }

pgNode13Out7Name				OBJECT-TYPE
	SYNTAX					DisplayString
	ACCESS					read-write
	STATUS					mandatory
	DESCRIPTION			"PG Outlet 7 name"
	::= { node13PG 52 }

pgNode13Out7CustVoice	OBJECT-TYPE
	SYNTAX					DisplayString
	ACCESS					read-write
	STATUS					mandatory
	DESCRIPTION			"PG Outlet 7 custom voice"
	::= { node13PG 53 }

pgNode13Out7Volts			OBJECT-TYPE
	SYNTAX					INTEGER
	ACCESS					read-only
	STATUS					mandatory
	DESCRIPTION			"PG Outlet 7 volts"
	::= { node13PG 54 }

pgNode13Out7Amps				OBJECT-TYPE
	SYNTAX					INTEGER
	ACCESS					read-only
	STATUS					mandatory
	DESCRIPTION			"PG Outlet 7 amps"
	::= { node13PG 55 }

pgNode13Out7Watts			OBJECT-TYPE
	SYNTAX					INTEGER
	ACCESS					read-only
	STATUS					mandatory
	DESCRIPTION			"PG Outlet 7 watts"
	::= { node13PG 56 }

pgNode13Out7State			OBJECT-TYPE
	SYNTAX					INTEGER { off(1),on(2),cycle(3) }
	ACCESS					read-only
	STATUS					mandatory
	DESCRIPTION			"PG Outlet 7 state"
	::= { node13PG 57 }

pgNode13Out7Cmd				OBJECT-TYPE
	SYNTAX					INTEGER { off(1),on(2),cycle(3) }
	ACCESS					read-write
	STATUS					mandatory
	DESCRIPTION			"PG Outlet 7 command"
	::= { node13PG 58 }

pgNode13Out8Name				OBJECT-TYPE
	SYNTAX					DisplayString
	ACCESS					read-write
	STATUS					mandatory
	DESCRIPTION			"PG Outlet 8 name"
	::= { node13PG 59 }

pgNode13Out8CustVoice	OBJECT-TYPE
	SYNTAX					DisplayString
	ACCESS					read-write
	STATUS					mandatory
	DESCRIPTION			"PG Outlet 8 custom voice"
	::= { node13PG 60 }

pgNode13Out8Volts			OBJECT-TYPE
	SYNTAX					INTEGER
	ACCESS					read-only
	STATUS					mandatory
	DESCRIPTION			"PG Outlet 8 volts"
	::= { node13PG 61 }

pgNode13Out8Amps				OBJECT-TYPE
	SYNTAX					INTEGER
	ACCESS					read-only
	STATUS					mandatory
	DESCRIPTION			"PG Outlet 8 amps"
	::= { node13PG 62 }

pgNode13Out8Watts			OBJECT-TYPE
	SYNTAX					INTEGER
	ACCESS					read-only
	STATUS					mandatory
	DESCRIPTION			"PG Outlet 8 watts"
	::= { node13PG 63 }

pgNode13Out8State			OBJECT-TYPE
	SYNTAX					INTEGER { off(1),on(2),cycle(3) }
	ACCESS					read-only
	STATUS					mandatory
	DESCRIPTION			"PG Outlet 8 state"
	::= { node13PG 64 }

pgNode13Out8Cmd				OBJECT-TYPE
	SYNTAX					INTEGER { off(1),on(2),cycle(3) }
	ACCESS					read-write
	STATUS					mandatory
	DESCRIPTION			"PG Outlet 8 command"
	::= { node13PG 65 }

pgNode14InUse					OBJECT-TYPE
	SYNTAX					INTEGER { false(1),true(2) }
	ACCESS					read-only
	STATUS					mandatory
	DESCRIPTION			"PG in use"
	::= { node14PG 1 }

pgNode14Status					OBJECT-TYPE
	SYNTAX					INTEGER { normal(1),pending(2), trouble(3) }
	ACCESS					read-only
	STATUS					mandatory
	DESCRIPTION			"PG status"
	::= { node14PG 2 }

pgNode14StatusSupport	OBJECT-TYPE
	SYNTAX					INTEGER { true1(1),false(2) }
	ACCESS					read-only
	STATUS					mandatory
	DESCRIPTION			"PG status support level"
	::= { node14PG 3 }

pgNode14Ver						OBJECT-TYPE
	SYNTAX					INTEGER { pgate1(1),pgate2(2) }
	ACCESS					read-only
	STATUS					mandatory
	DESCRIPTION			"PG version"
	::= { node14PG 4 }

pgNode14Volts					OBJECT-TYPE
	SYNTAX					INTEGER
	ACCESS					read-only
	STATUS					mandatory
	DESCRIPTION			"PG voltage"
	::= { node14PG 5 }

pgNode14Amps						OBJECT-TYPE
	SYNTAX					INTEGER
	ACCESS					read-only
	STATUS					mandatory
	DESCRIPTION			"PG amps"
	::= { node14PG 6 }

pgNode14Watts					OBJECT-TYPE
	SYNTAX					INTEGER
	ACCESS					read-only
	STATUS					mandatory
	DESCRIPTION			"PG Watts"
	::= { node14PG 7 }

pgNode14Name						OBJECT-TYPE
	SYNTAX					DisplayString
	ACCESS					read-write
	STATUS					mandatory
	DESCRIPTION			"PG name"
	::= { node14PG 8 }

pgNode14CustVoice			OBJECT-TYPE
	SYNTAX					DisplayString
	ACCESS					read-write
	STATUS					mandatory
	DESCRIPTION			"PG custom voice"
	::= { node14PG 9 }

pgNode14Out1Name				OBJECT-TYPE
	SYNTAX					DisplayString
	ACCESS					read-write
	STATUS					mandatory
	DESCRIPTION			"PG Outlet 1 name"
	::= { node14PG 10 }

pgNode14Out1CustVoice	OBJECT-TYPE
	SYNTAX					DisplayString
	ACCESS					read-write
	STATUS					mandatory
	DESCRIPTION			"PG Outlet 1 custom voice"
	::= { node14PG 11 }

pgNode14Out1Volts			OBJECT-TYPE
	SYNTAX					INTEGER
	ACCESS					read-only
	STATUS					mandatory
	DESCRIPTION			"PG Outlet 1 volts"
	::= { node14PG 12 }

pgNode14Out1Amps				OBJECT-TYPE
	SYNTAX					INTEGER
	ACCESS					read-only
	STATUS					mandatory
	DESCRIPTION			"PG Outlet 1 amps"
	::= { node14PG 13 }

pgNode14Out1Watts			OBJECT-TYPE
	SYNTAX					INTEGER
	ACCESS					read-only
	STATUS					mandatory
	DESCRIPTION			"PG Outlet 1 watts"
	::= { node14PG 14 }

pgNode14Out1State			OBJECT-TYPE
	SYNTAX					INTEGER { off(1),on(2),cycle(3) }
	ACCESS					read-only
	STATUS					mandatory
	DESCRIPTION			"PG Outlet 1 state"
	::= { node14PG 15 }

pgNode14Out1Cmd				OBJECT-TYPE
	SYNTAX					INTEGER { off(1),on(2),cycle(3) }
	ACCESS					read-write
	STATUS					mandatory
	DESCRIPTION			"PG Outlet 1 command"
	::= { node14PG 16 }

pgNode14Out2Name				OBJECT-TYPE
	SYNTAX					DisplayString
	ACCESS					read-write
	STATUS					mandatory
	DESCRIPTION			"PG Outlet 2 name"
	::= { node14PG 17 }

pgNode14Out2CustVoice	OBJECT-TYPE
	SYNTAX					DisplayString
	ACCESS					read-write
	STATUS					mandatory
	DESCRIPTION			"PG Outlet 2 custom voice"
	::= { node14PG 18 }

pgNode14Out2Volts			OBJECT-TYPE
	SYNTAX					INTEGER
	ACCESS					read-only
	STATUS					mandatory
	DESCRIPTION			"PG Outlet 2 volts"
	::= { node14PG 19 }

pgNode14Out2Amps				OBJECT-TYPE
	SYNTAX					INTEGER
	ACCESS					read-only
	STATUS					mandatory
	DESCRIPTION			"PG Outlet 2 amps"
	::= { node14PG 20 }

pgNode14Out2Watts			OBJECT-TYPE
	SYNTAX					INTEGER
	ACCESS					read-only
	STATUS					mandatory
	DESCRIPTION			"PG Outlet 2 watts"
	::= { node14PG 21 }

pgNode14Out2State			OBJECT-TYPE
	SYNTAX					INTEGER { off(1),on(2),cycle(3) }
	ACCESS					read-only
	STATUS					mandatory
	DESCRIPTION			"PG Outlet 2 state"
	::= { node14PG 22 }

pgNode14Out2Cmd				OBJECT-TYPE
	SYNTAX					INTEGER { off(1),on(2),cycle(3) }
	ACCESS					read-write
	STATUS					mandatory
	DESCRIPTION			"PG Outlet 2 command"
	::= { node14PG 23 }

pgNode14Out3Name				OBJECT-TYPE
	SYNTAX					DisplayString
	ACCESS					read-write
	STATUS					mandatory
	DESCRIPTION			"PG Outlet 3 name"
	::= { node14PG 24 }

pgNode14Out3CustVoice	OBJECT-TYPE
	SYNTAX					DisplayString
	ACCESS					read-write
	STATUS					mandatory
	DESCRIPTION			"PG Outlet 3 custom voice"
	::= { node14PG 25 }

pgNode14Out3Volts			OBJECT-TYPE
	SYNTAX					INTEGER
	ACCESS					read-only
	STATUS					mandatory
	DESCRIPTION			"PG Outlet 3 volts"
	::= { node14PG 26 }

pgNode14Out3Amps				OBJECT-TYPE
	SYNTAX					INTEGER
	ACCESS					read-only
	STATUS					mandatory
	DESCRIPTION			"PG Outlet 3 amps"
	::= { node14PG 27 }

pgNode14Out3Watts			OBJECT-TYPE
	SYNTAX					INTEGER
	ACCESS					read-only
	STATUS					mandatory
	DESCRIPTION			"PG Outlet 3 watts"
	::= { node14PG 28 }

pgNode14Out3State			OBJECT-TYPE
	SYNTAX					INTEGER { off(1),on(2),cycle(3) }
	ACCESS					read-only
	STATUS					mandatory
	DESCRIPTION			"PG Outlet 3 state"
	::= { node14PG 29 }

pgNode14Out3Cmd				OBJECT-TYPE
	SYNTAX					INTEGER { off(1),on(2),cycle(3) }
	ACCESS					read-write
	STATUS					mandatory
	DESCRIPTION			"PG Outlet 3 command"
	::= { node14PG 30 }

pgNode14Out4Name				OBJECT-TYPE
	SYNTAX					DisplayString
	ACCESS					read-write
	STATUS					mandatory
	DESCRIPTION			"PG Outlet 4 name"
	::= { node14PG 31 }

pgNode14Out4CustVoice	OBJECT-TYPE
	SYNTAX					DisplayString
	ACCESS					read-write
	STATUS					mandatory
	DESCRIPTION			"PG Outlet 4 custom voice"
	::= { node14PG 32 }

pgNode14Out4Volts			OBJECT-TYPE
	SYNTAX					INTEGER
	ACCESS					read-only
	STATUS					mandatory
	DESCRIPTION			"PG Outlet 4 volts"
	::= { node14PG 33 }

pgNode14Out4Amps				OBJECT-TYPE
	SYNTAX					INTEGER
	ACCESS					read-only
	STATUS					mandatory
	DESCRIPTION			"PG Outlet 4 amps"
	::= { node14PG 34 }

pgNode14Out4Watts			OBJECT-TYPE
	SYNTAX					INTEGER
	ACCESS					read-only
	STATUS					mandatory
	DESCRIPTION			"PG Outlet 4 watts"
	::= { node14PG 35 }

pgNode14Out4State			OBJECT-TYPE
	SYNTAX					INTEGER { off(1),on(2),cycle(3) }
	ACCESS					read-only
	STATUS					mandatory
	DESCRIPTION			"PG Outlet 4 state"
	::= { node14PG 36 }

pgNode14Out4Cmd				OBJECT-TYPE
	SYNTAX					INTEGER { off(1),on(2),cycle(3) }
	ACCESS					read-write
	STATUS					mandatory
	DESCRIPTION			"PG Outlet 4 command"
	::= { node14PG 37 }

pgNode14Out5Name				OBJECT-TYPE
	SYNTAX					DisplayString
	ACCESS					read-write
	STATUS					mandatory
	DESCRIPTION			"PG Outlet 5 name"
	::= { node14PG 38 }

pgNode14Out5CustVoice	OBJECT-TYPE
	SYNTAX					DisplayString
	ACCESS					read-write
	STATUS					mandatory
	DESCRIPTION			"PG Outlet 5 custom voice"
	::= { node14PG 39 }

pgNode14Out5Volts			OBJECT-TYPE
	SYNTAX					INTEGER
	ACCESS					read-only
	STATUS					mandatory
	DESCRIPTION			"PG Outlet 5 volts"
	::= { node14PG 40 }

pgNode14Out5Amps				OBJECT-TYPE
	SYNTAX					INTEGER
	ACCESS					read-only
	STATUS					mandatory
	DESCRIPTION			"PG Outlet 5 amps"
	::= { node14PG 41 }

pgNode14Out5Watts			OBJECT-TYPE
	SYNTAX					INTEGER
	ACCESS					read-only
	STATUS					mandatory
	DESCRIPTION			"PG Outlet 5 watts"
	::= { node14PG 42 }

pgNode14Out5State			OBJECT-TYPE
	SYNTAX					INTEGER { off(1),on(2),cycle(3) }
	ACCESS					read-only
	STATUS					mandatory
	DESCRIPTION			"PG Outlet 5 state"
	::= { node14PG 43 }

pgNode14Out5Cmd				OBJECT-TYPE
	SYNTAX					INTEGER { off(1),on(2),cycle(3) }
	ACCESS					read-write
	STATUS					mandatory
	DESCRIPTION			"PG Outlet 5 command"
	::= { node14PG 44 }

pgNode14Out6Name				OBJECT-TYPE
	SYNTAX					DisplayString
	ACCESS					read-write
	STATUS					mandatory
	DESCRIPTION			"PG Outlet 6 name"
	::= { node14PG 45 }

pgNode14Out6CustVoice	OBJECT-TYPE
	SYNTAX					DisplayString
	ACCESS					read-write
	STATUS					mandatory
	DESCRIPTION			"PG Outlet 6 custom voice"
	::= { node14PG 46 }

pgNode14Out6Volts			OBJECT-TYPE
	SYNTAX					INTEGER
	ACCESS					read-only
	STATUS					mandatory
	DESCRIPTION			"PG Outlet 6 volts"
	::= { node14PG 47 }

pgNode14Out6Amps				OBJECT-TYPE
	SYNTAX					INTEGER
	ACCESS					read-only
	STATUS					mandatory
	DESCRIPTION			"PG Outlet 6 amps"
	::= { node14PG 48 }

pgNode14Out6Watts			OBJECT-TYPE
	SYNTAX					INTEGER
	ACCESS					read-only
	STATUS					mandatory
	DESCRIPTION			"PG Outlet 6 watts"
	::= { node14PG 49 }

pgNode14Out6State			OBJECT-TYPE
	SYNTAX					INTEGER { off(1),on(2),cycle(3) }
	ACCESS					read-only
	STATUS					mandatory
	DESCRIPTION			"PG Outlet 6 state"
	::= { node14PG 50 }

pgNode14Out6Cmd				OBJECT-TYPE
	SYNTAX					INTEGER { off(1),on(2),cycle(3) }
	ACCESS					read-write
	STATUS					mandatory
	DESCRIPTION			"PG Outlet 6 command"
	::= { node14PG 51 }

pgNode14Out7Name				OBJECT-TYPE
	SYNTAX					DisplayString
	ACCESS					read-write
	STATUS					mandatory
	DESCRIPTION			"PG Outlet 7 name"
	::= { node14PG 52 }

pgNode14Out7CustVoice	OBJECT-TYPE
	SYNTAX					DisplayString
	ACCESS					read-write
	STATUS					mandatory
	DESCRIPTION			"PG Outlet 7 custom voice"
	::= { node14PG 53 }

pgNode14Out7Volts			OBJECT-TYPE
	SYNTAX					INTEGER
	ACCESS					read-only
	STATUS					mandatory
	DESCRIPTION			"PG Outlet 7 volts"
	::= { node14PG 54 }

pgNode14Out7Amps				OBJECT-TYPE
	SYNTAX					INTEGER
	ACCESS					read-only
	STATUS					mandatory
	DESCRIPTION			"PG Outlet 7 amps"
	::= { node14PG 55 }

pgNode14Out7Watts			OBJECT-TYPE
	SYNTAX					INTEGER
	ACCESS					read-only
	STATUS					mandatory
	DESCRIPTION			"PG Outlet 7 watts"
	::= { node14PG 56 }

pgNode14Out7State			OBJECT-TYPE
	SYNTAX					INTEGER { off(1),on(2),cycle(3) }
	ACCESS					read-only
	STATUS					mandatory
	DESCRIPTION			"PG Outlet 7 state"
	::= { node14PG 57 }

pgNode14Out7Cmd				OBJECT-TYPE
	SYNTAX					INTEGER { off(1),on(2),cycle(3) }
	ACCESS					read-write
	STATUS					mandatory
	DESCRIPTION			"PG Outlet 7 command"
	::= { node14PG 58 }

pgNode14Out8Name				OBJECT-TYPE
	SYNTAX					DisplayString
	ACCESS					read-write
	STATUS					mandatory
	DESCRIPTION			"PG Outlet 8 name"
	::= { node14PG 59 }

pgNode14Out8CustVoice	OBJECT-TYPE
	SYNTAX					DisplayString
	ACCESS					read-write
	STATUS					mandatory
	DESCRIPTION			"PG Outlet 8 custom voice"
	::= { node14PG 60 }

pgNode14Out8Volts			OBJECT-TYPE
	SYNTAX					INTEGER
	ACCESS					read-only
	STATUS					mandatory
	DESCRIPTION			"PG Outlet 8 volts"
	::= { node14PG 61 }

pgNode14Out8Amps				OBJECT-TYPE
	SYNTAX					INTEGER
	ACCESS					read-only
	STATUS					mandatory
	DESCRIPTION			"PG Outlet 8 amps"
	::= { node14PG 62 }

pgNode14Out8Watts			OBJECT-TYPE
	SYNTAX					INTEGER
	ACCESS					read-only
	STATUS					mandatory
	DESCRIPTION			"PG Outlet 8 watts"
	::= { node14PG 63 }

pgNode14Out8State			OBJECT-TYPE
	SYNTAX					INTEGER { off(1),on(2),cycle(3) }
	ACCESS					read-only
	STATUS					mandatory
	DESCRIPTION			"PG Outlet 8 state"
	::= { node14PG 64 }

pgNode14Out8Cmd				OBJECT-TYPE
	SYNTAX					INTEGER { off(1),on(2),cycle(3) }
	ACCESS					read-write
	STATUS					mandatory
	DESCRIPTION			"PG Outlet 8 command"
	::= { node14PG 65 }

pgNode15InUse					OBJECT-TYPE
	SYNTAX					INTEGER { false(1),true(2) }
	ACCESS					read-only
	STATUS					mandatory
	DESCRIPTION			"PG in use"
	::= { node15PG 1 }

pgNode15Status					OBJECT-TYPE
	SYNTAX					INTEGER { normal(1),pending(2), trouble(3) }
	ACCESS					read-only
	STATUS					mandatory
	DESCRIPTION			"PG status"
	::= { node15PG 2 }

pgNode15StatusSupport	OBJECT-TYPE
	SYNTAX					INTEGER { true1(1),false(2) }
	ACCESS					read-only
	STATUS					mandatory
	DESCRIPTION			"PG status support level"
	::= { node15PG 3 }

pgNode15Ver						OBJECT-TYPE
	SYNTAX					INTEGER { pgate1(1),pgate2(2) }
	ACCESS					read-only
	STATUS					mandatory
	DESCRIPTION			"PG version"
	::= { node15PG 4 }

pgNode15Volts					OBJECT-TYPE
	SYNTAX					INTEGER
	ACCESS					read-only
	STATUS					mandatory
	DESCRIPTION			"PG voltage"
	::= { node15PG 5 }

pgNode15Amps						OBJECT-TYPE
	SYNTAX					INTEGER
	ACCESS					read-only
	STATUS					mandatory
	DESCRIPTION			"PG amps"
	::= { node15PG 6 }

pgNode15Watts					OBJECT-TYPE
	SYNTAX					INTEGER
	ACCESS					read-only
	STATUS					mandatory
	DESCRIPTION			"PG Watts"
	::= { node15PG 7 }

pgNode15Name						OBJECT-TYPE
	SYNTAX					DisplayString
	ACCESS					read-write
	STATUS					mandatory
	DESCRIPTION			"PG name"
	::= { node15PG 8 }

pgNode15CustVoice			OBJECT-TYPE
	SYNTAX					DisplayString
	ACCESS					read-write
	STATUS					mandatory
	DESCRIPTION			"PG custom voice"
	::= { node15PG 9 }

pgNode15Out1Name				OBJECT-TYPE
	SYNTAX					DisplayString
	ACCESS					read-write
	STATUS					mandatory
	DESCRIPTION			"PG Outlet 1 name"
	::= { node15PG 10 }

pgNode15Out1CustVoice	OBJECT-TYPE
	SYNTAX					DisplayString
	ACCESS					read-write
	STATUS					mandatory
	DESCRIPTION			"PG Outlet 1 custom voice"
	::= { node15PG 11 }

pgNode15Out1Volts			OBJECT-TYPE
	SYNTAX					INTEGER
	ACCESS					read-only
	STATUS					mandatory
	DESCRIPTION			"PG Outlet 1 volts"
	::= { node15PG 12 }

pgNode15Out1Amps				OBJECT-TYPE
	SYNTAX					INTEGER
	ACCESS					read-only
	STATUS					mandatory
	DESCRIPTION			"PG Outlet 1 amps"
	::= { node15PG 13 }

pgNode15Out1Watts			OBJECT-TYPE
	SYNTAX					INTEGER
	ACCESS					read-only
	STATUS					mandatory
	DESCRIPTION			"PG Outlet 1 watts"
	::= { node15PG 14 }

pgNode15Out1State			OBJECT-TYPE
	SYNTAX					INTEGER { off(1),on(2),cycle(3) }
	ACCESS					read-only
	STATUS					mandatory
	DESCRIPTION			"PG Outlet 1 state"
	::= { node15PG 15 }

pgNode15Out1Cmd				OBJECT-TYPE
	SYNTAX					INTEGER { off(1),on(2),cycle(3) }
	ACCESS					read-write
	STATUS					mandatory
	DESCRIPTION			"PG Outlet 1 command"
	::= { node15PG 16 }

pgNode15Out2Name				OBJECT-TYPE
	SYNTAX					DisplayString
	ACCESS					read-write
	STATUS					mandatory
	DESCRIPTION			"PG Outlet 2 name"
	::= { node15PG 17 }

pgNode15Out2CustVoice	OBJECT-TYPE
	SYNTAX					DisplayString
	ACCESS					read-write
	STATUS					mandatory
	DESCRIPTION			"PG Outlet 2 custom voice"
	::= { node15PG 18 }

pgNode15Out2Volts			OBJECT-TYPE
	SYNTAX					INTEGER
	ACCESS					read-only
	STATUS					mandatory
	DESCRIPTION			"PG Outlet 2 volts"
	::= { node15PG 19 }

pgNode15Out2Amps				OBJECT-TYPE
	SYNTAX					INTEGER
	ACCESS					read-only
	STATUS					mandatory
	DESCRIPTION			"PG Outlet 2 amps"
	::= { node15PG 20 }

pgNode15Out2Watts			OBJECT-TYPE
	SYNTAX					INTEGER
	ACCESS					read-only
	STATUS					mandatory
	DESCRIPTION			"PG Outlet 2 watts"
	::= { node15PG 21 }

pgNode15Out2State			OBJECT-TYPE
	SYNTAX					INTEGER { off(1),on(2),cycle(3) }
	ACCESS					read-only
	STATUS					mandatory
	DESCRIPTION			"PG Outlet 2 state"
	::= { node15PG 22 }

pgNode15Out2Cmd				OBJECT-TYPE
	SYNTAX					INTEGER { off(1),on(2),cycle(3) }
	ACCESS					read-write
	STATUS					mandatory
	DESCRIPTION			"PG Outlet 2 command"
	::= { node15PG 23 }

pgNode15Out3Name				OBJECT-TYPE
	SYNTAX					DisplayString
	ACCESS					read-write
	STATUS					mandatory
	DESCRIPTION			"PG Outlet 3 name"
	::= { node15PG 24 }

pgNode15Out3CustVoice	OBJECT-TYPE
	SYNTAX					DisplayString
	ACCESS					read-write
	STATUS					mandatory
	DESCRIPTION			"PG Outlet 3 custom voice"
	::= { node15PG 25 }

pgNode15Out3Volts			OBJECT-TYPE
	SYNTAX					INTEGER
	ACCESS					read-only
	STATUS					mandatory
	DESCRIPTION			"PG Outlet 3 volts"
	::= { node15PG 26 }

pgNode15Out3Amps				OBJECT-TYPE
	SYNTAX					INTEGER
	ACCESS					read-only
	STATUS					mandatory
	DESCRIPTION			"PG Outlet 3 amps"
	::= { node15PG 27 }

pgNode15Out3Watts			OBJECT-TYPE
	SYNTAX					INTEGER
	ACCESS					read-only
	STATUS					mandatory
	DESCRIPTION			"PG Outlet 3 watts"
	::= { node15PG 28 }

pgNode15Out3State			OBJECT-TYPE
	SYNTAX					INTEGER { off(1),on(2),cycle(3) }
	ACCESS					read-only
	STATUS					mandatory
	DESCRIPTION			"PG Outlet 3 state"
	::= { node15PG 29 }

pgNode15Out3Cmd				OBJECT-TYPE
	SYNTAX					INTEGER { off(1),on(2),cycle(3) }
	ACCESS					read-write
	STATUS					mandatory
	DESCRIPTION			"PG Outlet 3 command"
	::= { node15PG 30 }

pgNode15Out4Name				OBJECT-TYPE
	SYNTAX					DisplayString
	ACCESS					read-write
	STATUS					mandatory
	DESCRIPTION			"PG Outlet 4 name"
	::= { node15PG 31 }

pgNode15Out4CustVoice	OBJECT-TYPE
	SYNTAX					DisplayString
	ACCESS					read-write
	STATUS					mandatory
	DESCRIPTION			"PG Outlet 4 custom voice"
	::= { node15PG 32 }

pgNode15Out4Volts			OBJECT-TYPE
	SYNTAX					INTEGER
	ACCESS					read-only
	STATUS					mandatory
	DESCRIPTION			"PG Outlet 4 volts"
	::= { node15PG 33 }

pgNode15Out4Amps				OBJECT-TYPE
	SYNTAX					INTEGER
	ACCESS					read-only
	STATUS					mandatory
	DESCRIPTION			"PG Outlet 4 amps"
	::= { node15PG 34 }

pgNode15Out4Watts			OBJECT-TYPE
	SYNTAX					INTEGER
	ACCESS					read-only
	STATUS					mandatory
	DESCRIPTION			"PG Outlet 4 watts"
	::= { node15PG 35 }

pgNode15Out4State			OBJECT-TYPE
	SYNTAX					INTEGER { off(1),on(2),cycle(3) }
	ACCESS					read-only
	STATUS					mandatory
	DESCRIPTION			"PG Outlet 4 state"
	::= { node15PG 36 }

pgNode15Out4Cmd				OBJECT-TYPE
	SYNTAX					INTEGER { off(1),on(2),cycle(3) }
	ACCESS					read-write
	STATUS					mandatory
	DESCRIPTION			"PG Outlet 4 command"
	::= { node15PG 37 }

pgNode15Out5Name				OBJECT-TYPE
	SYNTAX					DisplayString
	ACCESS					read-write
	STATUS					mandatory
	DESCRIPTION			"PG Outlet 5 name"
	::= { node15PG 38 }

pgNode15Out5CustVoice	OBJECT-TYPE
	SYNTAX					DisplayString
	ACCESS					read-write
	STATUS					mandatory
	DESCRIPTION			"PG Outlet 5 custom voice"
	::= { node15PG 39 }

pgNode15Out5Volts			OBJECT-TYPE
	SYNTAX					INTEGER
	ACCESS					read-only
	STATUS					mandatory
	DESCRIPTION			"PG Outlet 5 volts"
	::= { node15PG 40 }

pgNode15Out5Amps				OBJECT-TYPE
	SYNTAX					INTEGER
	ACCESS					read-only
	STATUS					mandatory
	DESCRIPTION			"PG Outlet 5 amps"
	::= { node15PG 41 }

pgNode15Out5Watts			OBJECT-TYPE
	SYNTAX					INTEGER
	ACCESS					read-only
	STATUS					mandatory
	DESCRIPTION			"PG Outlet 5 watts"
	::= { node15PG 42 }

pgNode15Out5State			OBJECT-TYPE
	SYNTAX					INTEGER { off(1),on(2),cycle(3) }
	ACCESS					read-only
	STATUS					mandatory
	DESCRIPTION			"PG Outlet 5 state"
	::= { node15PG 43 }

pgNode15Out5Cmd				OBJECT-TYPE
	SYNTAX					INTEGER { off(1),on(2),cycle(3) }
	ACCESS					read-write
	STATUS					mandatory
	DESCRIPTION			"PG Outlet 5 command"
	::= { node15PG 44 }

pgNode15Out6Name				OBJECT-TYPE
	SYNTAX					DisplayString
	ACCESS					read-write
	STATUS					mandatory
	DESCRIPTION			"PG Outlet 6 name"
	::= { node15PG 45 }

pgNode15Out6CustVoice	OBJECT-TYPE
	SYNTAX					DisplayString
	ACCESS					read-write
	STATUS					mandatory
	DESCRIPTION			"PG Outlet 6 custom voice"
	::= { node15PG 46 }

pgNode15Out6Volts			OBJECT-TYPE
	SYNTAX					INTEGER
	ACCESS					read-only
	STATUS					mandatory
	DESCRIPTION			"PG Outlet 6 volts"
	::= { node15PG 47 }

pgNode15Out6Amps				OBJECT-TYPE
	SYNTAX					INTEGER
	ACCESS					read-only
	STATUS					mandatory
	DESCRIPTION			"PG Outlet 6 amps"
	::= { node15PG 48 }

pgNode15Out6Watts			OBJECT-TYPE
	SYNTAX					INTEGER
	ACCESS					read-only
	STATUS					mandatory
	DESCRIPTION			"PG Outlet 6 watts"
	::= { node15PG 49 }

pgNode15Out6State			OBJECT-TYPE
	SYNTAX					INTEGER { off(1),on(2),cycle(3) }
	ACCESS					read-only
	STATUS					mandatory
	DESCRIPTION			"PG Outlet 6 state"
	::= { node15PG 50 }

pgNode15Out6Cmd				OBJECT-TYPE
	SYNTAX					INTEGER { off(1),on(2),cycle(3) }
	ACCESS					read-write
	STATUS					mandatory
	DESCRIPTION			"PG Outlet 6 command"
	::= { node15PG 51 }

pgNode15Out7Name				OBJECT-TYPE
	SYNTAX					DisplayString
	ACCESS					read-write
	STATUS					mandatory
	DESCRIPTION			"PG Outlet 7 name"
	::= { node15PG 52 }

pgNode15Out7CustVoice	OBJECT-TYPE
	SYNTAX					DisplayString
	ACCESS					read-write
	STATUS					mandatory
	DESCRIPTION			"PG Outlet 7 custom voice"
	::= { node15PG 53 }

pgNode15Out7Volts			OBJECT-TYPE
	SYNTAX					INTEGER
	ACCESS					read-only
	STATUS					mandatory
	DESCRIPTION			"PG Outlet 7 volts"
	::= { node15PG 54 }

pgNode15Out7Amps				OBJECT-TYPE
	SYNTAX					INTEGER
	ACCESS					read-only
	STATUS					mandatory
	DESCRIPTION			"PG Outlet 7 amps"
	::= { node15PG 55 }

pgNode15Out7Watts			OBJECT-TYPE
	SYNTAX					INTEGER
	ACCESS					read-only
	STATUS					mandatory
	DESCRIPTION			"PG Outlet 7 watts"
	::= { node15PG 56 }

pgNode15Out7State			OBJECT-TYPE
	SYNTAX					INTEGER { off(1),on(2),cycle(3) }
	ACCESS					read-only
	STATUS					mandatory
	DESCRIPTION			"PG Outlet 7 state"
	::= { node15PG 57 }

pgNode15Out7Cmd				OBJECT-TYPE
	SYNTAX					INTEGER { off(1),on(2),cycle(3) }
	ACCESS					read-write
	STATUS					mandatory
	DESCRIPTION			"PG Outlet 7 command"
	::= { node15PG 58 }

pgNode15Out8Name				OBJECT-TYPE
	SYNTAX					DisplayString
	ACCESS					read-write
	STATUS					mandatory
	DESCRIPTION			"PG Outlet 8 name"
	::= { node15PG 59 }

pgNode15Out8CustVoice	OBJECT-TYPE
	SYNTAX					DisplayString
	ACCESS					read-write
	STATUS					mandatory
	DESCRIPTION			"PG Outlet 8 custom voice"
	::= { node15PG 60 }

pgNode15Out8Volts			OBJECT-TYPE
	SYNTAX					INTEGER
	ACCESS					read-only
	STATUS					mandatory
	DESCRIPTION			"PG Outlet 8 volts"
	::= { node15PG 61 }

pgNode15Out8Amps				OBJECT-TYPE
	SYNTAX					INTEGER
	ACCESS					read-only
	STATUS					mandatory
	DESCRIPTION			"PG Outlet 8 amps"
	::= { node15PG 62 }

pgNode15Out8Watts			OBJECT-TYPE
	SYNTAX					INTEGER
	ACCESS					read-only
	STATUS					mandatory
	DESCRIPTION			"PG Outlet 8 watts"
	::= { node15PG 63 }

pgNode15Out8State			OBJECT-TYPE
	SYNTAX					INTEGER { off(1),on(2),cycle(3) }
	ACCESS					read-only
	STATUS					mandatory
	DESCRIPTION			"PG Outlet 8 state"
	::= { node15PG 64 }

pgNode15Out8Cmd				OBJECT-TYPE
	SYNTAX					INTEGER { off(1),on(2),cycle(3) }
	ACCESS					read-write
	STATUS					mandatory
	DESCRIPTION			"PG Outlet 8 command"
	::= { node15PG 65 }

pgNode16InUse					OBJECT-TYPE
	SYNTAX					INTEGER { false(1),true(2) }
	ACCESS					read-only
	STATUS					mandatory
	DESCRIPTION			"PG in use"
	::= { node16PG 1 }

pgNode16Status					OBJECT-TYPE
	SYNTAX					INTEGER { normal(1),pending(2), trouble(3) }
	ACCESS					read-only
	STATUS					mandatory
	DESCRIPTION			"PG status"
	::= { node16PG 2 }

pgNode16StatusSupport	OBJECT-TYPE
	SYNTAX					INTEGER { true1(1),false(2) }
	ACCESS					read-only
	STATUS					mandatory
	DESCRIPTION			"PG status support level"
	::= { node16PG 3 }

pgNode16Ver						OBJECT-TYPE
	SYNTAX					INTEGER { pgate1(1),pgate2(2) }
	ACCESS					read-only
	STATUS					mandatory
	DESCRIPTION			"PG version"
	::= { node16PG 4 }

pgNode16Volts					OBJECT-TYPE
	SYNTAX					INTEGER
	ACCESS					read-only
	STATUS					mandatory
	DESCRIPTION			"PG voltage"
	::= { node16PG 5 }

pgNode16Amps						OBJECT-TYPE
	SYNTAX					INTEGER
	ACCESS					read-only
	STATUS					mandatory
	DESCRIPTION			"PG amps"
	::= { node16PG 6 }

pgNode16Watts					OBJECT-TYPE
	SYNTAX					INTEGER
	ACCESS					read-only
	STATUS					mandatory
	DESCRIPTION			"PG Watts"
	::= { node16PG 7 }

pgNode16Name						OBJECT-TYPE
	SYNTAX					DisplayString
	ACCESS					read-write
	STATUS					mandatory
	DESCRIPTION			"PG name"
	::= { node16PG 8 }

pgNode16CustVoice			OBJECT-TYPE
	SYNTAX					DisplayString
	ACCESS					read-write
	STATUS					mandatory
	DESCRIPTION			"PG custom voice"
	::= { node16PG 9 }

pgNode16Out1Name				OBJECT-TYPE
	SYNTAX					DisplayString
	ACCESS					read-write
	STATUS					mandatory
	DESCRIPTION			"PG Outlet 1 name"
	::= { node16PG 10 }

pgNode16Out1CustVoice	OBJECT-TYPE
	SYNTAX					DisplayString
	ACCESS					read-write
	STATUS					mandatory
	DESCRIPTION			"PG Outlet 1 custom voice"
	::= { node16PG 11 }

pgNode16Out1Volts			OBJECT-TYPE
	SYNTAX					INTEGER
	ACCESS					read-only
	STATUS					mandatory
	DESCRIPTION			"PG Outlet 1 volts"
	::= { node16PG 12 }

pgNode16Out1Amps				OBJECT-TYPE
	SYNTAX					INTEGER
	ACCESS					read-only
	STATUS					mandatory
	DESCRIPTION			"PG Outlet 1 amps"
	::= { node16PG 13 }

pgNode16Out1Watts			OBJECT-TYPE
	SYNTAX					INTEGER
	ACCESS					read-only
	STATUS					mandatory
	DESCRIPTION			"PG Outlet 1 watts"
	::= { node16PG 14 }

pgNode16Out1State			OBJECT-TYPE
	SYNTAX					INTEGER { off(1),on(2),cycle(3) }
	ACCESS					read-only
	STATUS					mandatory
	DESCRIPTION			"PG Outlet 1 state"
	::= { node16PG 15 }

pgNode16Out1Cmd				OBJECT-TYPE
	SYNTAX					INTEGER { off(1),on(2),cycle(3) }
	ACCESS					read-write
	STATUS					mandatory
	DESCRIPTION			"PG Outlet 1 command"
	::= { node16PG 16 }

pgNode16Out2Name				OBJECT-TYPE
	SYNTAX					DisplayString
	ACCESS					read-write
	STATUS					mandatory
	DESCRIPTION			"PG Outlet 2 name"
	::= { node16PG 17 }

pgNode16Out2CustVoice	OBJECT-TYPE
	SYNTAX					DisplayString
	ACCESS					read-write
	STATUS					mandatory
	DESCRIPTION			"PG Outlet 2 custom voice"
	::= { node16PG 18 }

pgNode16Out2Volts			OBJECT-TYPE
	SYNTAX					INTEGER
	ACCESS					read-only
	STATUS					mandatory
	DESCRIPTION			"PG Outlet 2 volts"
	::= { node16PG 19 }

pgNode16Out2Amps				OBJECT-TYPE
	SYNTAX					INTEGER
	ACCESS					read-only
	STATUS					mandatory
	DESCRIPTION			"PG Outlet 2 amps"
	::= { node16PG 20 }

pgNode16Out2Watts			OBJECT-TYPE
	SYNTAX					INTEGER
	ACCESS					read-only
	STATUS					mandatory
	DESCRIPTION			"PG Outlet 2 watts"
	::= { node16PG 21 }

pgNode16Out2State			OBJECT-TYPE
	SYNTAX					INTEGER { off(1),on(2),cycle(3) }
	ACCESS					read-only
	STATUS					mandatory
	DESCRIPTION			"PG Outlet 2 state"
	::= { node16PG 22 }

pgNode16Out2Cmd				OBJECT-TYPE
	SYNTAX					INTEGER { off(1),on(2),cycle(3) }
	ACCESS					read-write
	STATUS					mandatory
	DESCRIPTION			"PG Outlet 2 command"
	::= { node16PG 23 }

pgNode16Out3Name				OBJECT-TYPE
	SYNTAX					DisplayString
	ACCESS					read-write
	STATUS					mandatory
	DESCRIPTION			"PG Outlet 3 name"
	::= { node16PG 24 }

pgNode16Out3CustVoice	OBJECT-TYPE
	SYNTAX					DisplayString
	ACCESS					read-write
	STATUS					mandatory
	DESCRIPTION			"PG Outlet 3 custom voice"
	::= { node16PG 25 }

pgNode16Out3Volts			OBJECT-TYPE
	SYNTAX					INTEGER
	ACCESS					read-only
	STATUS					mandatory
	DESCRIPTION			"PG Outlet 3 volts"
	::= { node16PG 26 }

pgNode16Out3Amps				OBJECT-TYPE
	SYNTAX					INTEGER
	ACCESS					read-only
	STATUS					mandatory
	DESCRIPTION			"PG Outlet 3 amps"
	::= { node16PG 27 }

pgNode16Out3Watts			OBJECT-TYPE
	SYNTAX					INTEGER
	ACCESS					read-only
	STATUS					mandatory
	DESCRIPTION			"PG Outlet 3 watts"
	::= { node16PG 28 }

pgNode16Out3State			OBJECT-TYPE
	SYNTAX					INTEGER { off(1),on(2),cycle(3) }
	ACCESS					read-only
	STATUS					mandatory
	DESCRIPTION			"PG Outlet 3 state"
	::= { node16PG 29 }

pgNode16Out3Cmd				OBJECT-TYPE
	SYNTAX					INTEGER { off(1),on(2),cycle(3) }
	ACCESS					read-write
	STATUS					mandatory
	DESCRIPTION			"PG Outlet 3 command"
	::= { node16PG 30 }

pgNode16Out4Name				OBJECT-TYPE
	SYNTAX					DisplayString
	ACCESS					read-write
	STATUS					mandatory
	DESCRIPTION			"PG Outlet 4 name"
	::= { node16PG 31 }

pgNode16Out4CustVoice	OBJECT-TYPE
	SYNTAX					DisplayString
	ACCESS					read-write
	STATUS					mandatory
	DESCRIPTION			"PG Outlet 4 custom voice"
	::= { node16PG 32 }

pgNode16Out4Volts			OBJECT-TYPE
	SYNTAX					INTEGER
	ACCESS					read-only
	STATUS					mandatory
	DESCRIPTION			"PG Outlet 4 volts"
	::= { node16PG 33 }

pgNode16Out4Amps				OBJECT-TYPE
	SYNTAX					INTEGER
	ACCESS					read-only
	STATUS					mandatory
	DESCRIPTION			"PG Outlet 4 amps"
	::= { node16PG 34 }

pgNode16Out4Watts			OBJECT-TYPE
	SYNTAX					INTEGER
	ACCESS					read-only
	STATUS					mandatory
	DESCRIPTION			"PG Outlet 4 watts"
	::= { node16PG 35 }

pgNode16Out4State			OBJECT-TYPE
	SYNTAX					INTEGER { off(1),on(2),cycle(3) }
	ACCESS					read-only
	STATUS					mandatory
	DESCRIPTION			"PG Outlet 4 state"
	::= { node16PG 36 }

pgNode16Out4Cmd				OBJECT-TYPE
	SYNTAX					INTEGER { off(1),on(2),cycle(3) }
	ACCESS					read-write
	STATUS					mandatory
	DESCRIPTION			"PG Outlet 4 command"
	::= { node16PG 37 }

pgNode16Out5Name				OBJECT-TYPE
	SYNTAX					DisplayString
	ACCESS					read-write
	STATUS					mandatory
	DESCRIPTION			"PG Outlet 5 name"
	::= { node16PG 38 }

pgNode16Out5CustVoice	OBJECT-TYPE
	SYNTAX					DisplayString
	ACCESS					read-write
	STATUS					mandatory
	DESCRIPTION			"PG Outlet 5 custom voice"
	::= { node16PG 39 }

pgNode16Out5Volts			OBJECT-TYPE
	SYNTAX					INTEGER
	ACCESS					read-only
	STATUS					mandatory
	DESCRIPTION			"PG Outlet 5 volts"
	::= { node16PG 40 }

pgNode16Out5Amps				OBJECT-TYPE
	SYNTAX					INTEGER
	ACCESS					read-only
	STATUS					mandatory
	DESCRIPTION			"PG Outlet 5 amps"
	::= { node16PG 41 }

pgNode16Out5Watts			OBJECT-TYPE
	SYNTAX					INTEGER
	ACCESS					read-only
	STATUS					mandatory
	DESCRIPTION			"PG Outlet 5 watts"
	::= { node16PG 42 }

pgNode16Out5State			OBJECT-TYPE
	SYNTAX					INTEGER { off(1),on(2),cycle(3) }
	ACCESS					read-only
	STATUS					mandatory
	DESCRIPTION			"PG Outlet 5 state"
	::= { node16PG 43 }

pgNode16Out5Cmd				OBJECT-TYPE
	SYNTAX					INTEGER { off(1),on(2),cycle(3) }
	ACCESS					read-write
	STATUS					mandatory
	DESCRIPTION			"PG Outlet 5 command"
	::= { node16PG 44 }

pgNode16Out6Name				OBJECT-TYPE
	SYNTAX					DisplayString
	ACCESS					read-write
	STATUS					mandatory
	DESCRIPTION			"PG Outlet 6 name"
	::= { node16PG 45 }

pgNode16Out6CustVoice	OBJECT-TYPE
	SYNTAX					DisplayString
	ACCESS					read-write
	STATUS					mandatory
	DESCRIPTION			"PG Outlet 6 custom voice"
	::= { node16PG 46 }

pgNode16Out6Volts			OBJECT-TYPE
	SYNTAX					INTEGER
	ACCESS					read-only
	STATUS					mandatory
	DESCRIPTION			"PG Outlet 6 volts"
	::= { node16PG 47 }

pgNode16Out6Amps				OBJECT-TYPE
	SYNTAX					INTEGER
	ACCESS					read-only
	STATUS					mandatory
	DESCRIPTION			"PG Outlet 6 amps"
	::= { node16PG 48 }

pgNode16Out6Watts			OBJECT-TYPE
	SYNTAX					INTEGER
	ACCESS					read-only
	STATUS					mandatory
	DESCRIPTION			"PG Outlet 6 watts"
	::= { node16PG 49 }

pgNode16Out6State			OBJECT-TYPE
	SYNTAX					INTEGER { off(1),on(2),cycle(3) }
	ACCESS					read-only
	STATUS					mandatory
	DESCRIPTION			"PG Outlet 6 state"
	::= { node16PG 50 }

pgNode16Out6Cmd				OBJECT-TYPE
	SYNTAX					INTEGER { off(1),on(2),cycle(3) }
	ACCESS					read-write
	STATUS					mandatory
	DESCRIPTION			"PG Outlet 6 command"
	::= { node16PG 51 }

pgNode16Out7Name				OBJECT-TYPE
	SYNTAX					DisplayString
	ACCESS					read-write
	STATUS					mandatory
	DESCRIPTION			"PG Outlet 7 name"
	::= { node16PG 52 }

pgNode16Out7CustVoice	OBJECT-TYPE
	SYNTAX					DisplayString
	ACCESS					read-write
	STATUS					mandatory
	DESCRIPTION			"PG Outlet 7 custom voice"
	::= { node16PG 53 }

pgNode16Out7Volts			OBJECT-TYPE
	SYNTAX					INTEGER
	ACCESS					read-only
	STATUS					mandatory
	DESCRIPTION			"PG Outlet 7 volts"
	::= { node16PG 54 }

pgNode16Out7Amps				OBJECT-TYPE
	SYNTAX					INTEGER
	ACCESS					read-only
	STATUS					mandatory
	DESCRIPTION			"PG Outlet 7 amps"
	::= { node16PG 55 }

pgNode16Out7Watts			OBJECT-TYPE
	SYNTAX					INTEGER
	ACCESS					read-only
	STATUS					mandatory
	DESCRIPTION			"PG Outlet 7 watts"
	::= { node16PG 56 }

pgNode16Out7State			OBJECT-TYPE
	SYNTAX					INTEGER { off(1),on(2),cycle(3) }
	ACCESS					read-only
	STATUS					mandatory
	DESCRIPTION			"PG Outlet 7 state"
	::= { node16PG 57 }

pgNode16Out7Cmd				OBJECT-TYPE
	SYNTAX					INTEGER { off(1),on(2),cycle(3) }
	ACCESS					read-write
	STATUS					mandatory
	DESCRIPTION			"PG Outlet 7 command"
	::= { node16PG 58 }

pgNode16Out8Name				OBJECT-TYPE
	SYNTAX					DisplayString
	ACCESS					read-write
	STATUS					mandatory
	DESCRIPTION			"PG Outlet 8 name"
	::= { node16PG 59 }

pgNode16Out8CustVoice	OBJECT-TYPE
	SYNTAX					DisplayString
	ACCESS					read-write
	STATUS					mandatory
	DESCRIPTION			"PG Outlet 8 custom voice"
	::= { node16PG 60 }

pgNode16Out8Volts			OBJECT-TYPE
	SYNTAX					INTEGER
	ACCESS					read-only
	STATUS					mandatory
	DESCRIPTION			"PG Outlet 8 volts"
	::= { node16PG 61 }

pgNode16Out8Amps				OBJECT-TYPE
	SYNTAX					INTEGER
	ACCESS					read-only
	STATUS					mandatory
	DESCRIPTION			"PG Outlet 8 amps"
	::= { node16PG 62 }

pgNode16Out8Watts			OBJECT-TYPE
	SYNTAX					INTEGER
	ACCESS					read-only
	STATUS					mandatory
	DESCRIPTION			"PG Outlet 8 watts"
	::= { node16PG 63 }

pgNode16Out8State			OBJECT-TYPE
	SYNTAX					INTEGER { off(1),on(2),cycle(3) }
	ACCESS					read-only
	STATUS					mandatory
	DESCRIPTION			"PG Outlet 8 state"
	::= { node16PG 64 }

pgNode16Out8Cmd				OBJECT-TYPE
	SYNTAX					INTEGER { off(1),on(2),cycle(3) }
	ACCESS					read-write
	STATUS					mandatory
	DESCRIPTION			"PG Outlet 8 command"
	::= { node16PG 65 }

pgNode17InUse					OBJECT-TYPE
	SYNTAX					INTEGER { false(1),true(2) }
	ACCESS					read-only
	STATUS					mandatory
	DESCRIPTION			"PG in use"
	::= { node17PG 1 }

pgNode17Status					OBJECT-TYPE
	SYNTAX					INTEGER { normal(1),pending(2), trouble(3) }
	ACCESS					read-only
	STATUS					mandatory
	DESCRIPTION			"PG status"
	::= { node17PG 2 }

pgNode17StatusSupport	OBJECT-TYPE
	SYNTAX					INTEGER { true1(1),false(2) }
	ACCESS					read-only
	STATUS					mandatory
	DESCRIPTION			"PG status support level"
	::= { node17PG 3 }

pgNode17Ver						OBJECT-TYPE
	SYNTAX					INTEGER { pgate1(1),pgate2(2) }
	ACCESS					read-only
	STATUS					mandatory
	DESCRIPTION			"PG version"
	::= { node17PG 4 }

pgNode17Volts					OBJECT-TYPE
	SYNTAX					INTEGER
	ACCESS					read-only
	STATUS					mandatory
	DESCRIPTION			"PG voltage"
	::= { node17PG 5 }

pgNode17Amps						OBJECT-TYPE
	SYNTAX					INTEGER
	ACCESS					read-only
	STATUS					mandatory
	DESCRIPTION			"PG amps"
	::= { node17PG 6 }

pgNode17Watts					OBJECT-TYPE
	SYNTAX					INTEGER
	ACCESS					read-only
	STATUS					mandatory
	DESCRIPTION			"PG Watts"
	::= { node17PG 7 }

pgNode17Name						OBJECT-TYPE
	SYNTAX					DisplayString
	ACCESS					read-write
	STATUS					mandatory
	DESCRIPTION			"PG name"
	::= { node17PG 8 }

pgNode17CustVoice			OBJECT-TYPE
	SYNTAX					DisplayString
	ACCESS					read-write
	STATUS					mandatory
	DESCRIPTION			"PG custom voice"
	::= { node17PG 9 }

pgNode17Out1Name				OBJECT-TYPE
	SYNTAX					DisplayString
	ACCESS					read-write
	STATUS					mandatory
	DESCRIPTION			"PG Outlet 1 name"
	::= { node17PG 10 }

pgNode17Out1CustVoice	OBJECT-TYPE
	SYNTAX					DisplayString
	ACCESS					read-write
	STATUS					mandatory
	DESCRIPTION			"PG Outlet 1 custom voice"
	::= { node17PG 11 }

pgNode17Out1Volts			OBJECT-TYPE
	SYNTAX					INTEGER
	ACCESS					read-only
	STATUS					mandatory
	DESCRIPTION			"PG Outlet 1 volts"
	::= { node17PG 12 }

pgNode17Out1Amps				OBJECT-TYPE
	SYNTAX					INTEGER
	ACCESS					read-only
	STATUS					mandatory
	DESCRIPTION			"PG Outlet 1 amps"
	::= { node17PG 13 }

pgNode17Out1Watts			OBJECT-TYPE
	SYNTAX					INTEGER
	ACCESS					read-only
	STATUS					mandatory
	DESCRIPTION			"PG Outlet 1 watts"
	::= { node17PG 14 }

pgNode17Out1State			OBJECT-TYPE
	SYNTAX					INTEGER { off(1),on(2),cycle(3) }
	ACCESS					read-only
	STATUS					mandatory
	DESCRIPTION			"PG Outlet 1 state"
	::= { node17PG 15 }

pgNode17Out1Cmd				OBJECT-TYPE
	SYNTAX					INTEGER { off(1),on(2),cycle(3) }
	ACCESS					read-write
	STATUS					mandatory
	DESCRIPTION			"PG Outlet 1 command"
	::= { node17PG 16 }

pgNode17Out2Name				OBJECT-TYPE
	SYNTAX					DisplayString
	ACCESS					read-write
	STATUS					mandatory
	DESCRIPTION			"PG Outlet 2 name"
	::= { node17PG 17 }

pgNode17Out2CustVoice	OBJECT-TYPE
	SYNTAX					DisplayString
	ACCESS					read-write
	STATUS					mandatory
	DESCRIPTION			"PG Outlet 2 custom voice"
	::= { node17PG 18 }

pgNode17Out2Volts			OBJECT-TYPE
	SYNTAX					INTEGER
	ACCESS					read-only
	STATUS					mandatory
	DESCRIPTION			"PG Outlet 2 volts"
	::= { node17PG 19 }

pgNode17Out2Amps				OBJECT-TYPE
	SYNTAX					INTEGER
	ACCESS					read-only
	STATUS					mandatory
	DESCRIPTION			"PG Outlet 2 amps"
	::= { node17PG 20 }

pgNode17Out2Watts			OBJECT-TYPE
	SYNTAX					INTEGER
	ACCESS					read-only
	STATUS					mandatory
	DESCRIPTION			"PG Outlet 2 watts"
	::= { node17PG 21 }

pgNode17Out2State			OBJECT-TYPE
	SYNTAX					INTEGER { off(1),on(2),cycle(3) }
	ACCESS					read-only
	STATUS					mandatory
	DESCRIPTION			"PG Outlet 2 state"
	::= { node17PG 22 }

pgNode17Out2Cmd				OBJECT-TYPE
	SYNTAX					INTEGER { off(1),on(2),cycle(3) }
	ACCESS					read-write
	STATUS					mandatory
	DESCRIPTION			"PG Outlet 2 command"
	::= { node17PG 23 }

pgNode17Out3Name				OBJECT-TYPE
	SYNTAX					DisplayString
	ACCESS					read-write
	STATUS					mandatory
	DESCRIPTION			"PG Outlet 3 name"
	::= { node17PG 24 }

pgNode17Out3CustVoice	OBJECT-TYPE
	SYNTAX					DisplayString
	ACCESS					read-write
	STATUS					mandatory
	DESCRIPTION			"PG Outlet 3 custom voice"
	::= { node17PG 25 }

pgNode17Out3Volts			OBJECT-TYPE
	SYNTAX					INTEGER
	ACCESS					read-only
	STATUS					mandatory
	DESCRIPTION			"PG Outlet 3 volts"
	::= { node17PG 26 }

pgNode17Out3Amps				OBJECT-TYPE
	SYNTAX					INTEGER
	ACCESS					read-only
	STATUS					mandatory
	DESCRIPTION			"PG Outlet 3 amps"
	::= { node17PG 27 }

pgNode17Out3Watts			OBJECT-TYPE
	SYNTAX					INTEGER
	ACCESS					read-only
	STATUS					mandatory
	DESCRIPTION			"PG Outlet 3 watts"
	::= { node17PG 28 }

pgNode17Out3State			OBJECT-TYPE
	SYNTAX					INTEGER { off(1),on(2),cycle(3) }
	ACCESS					read-only
	STATUS					mandatory
	DESCRIPTION			"PG Outlet 3 state"
	::= { node17PG 29 }

pgNode17Out3Cmd				OBJECT-TYPE
	SYNTAX					INTEGER { off(1),on(2),cycle(3) }
	ACCESS					read-write
	STATUS					mandatory
	DESCRIPTION			"PG Outlet 3 command"
	::= { node17PG 30 }

pgNode17Out4Name				OBJECT-TYPE
	SYNTAX					DisplayString
	ACCESS					read-write
	STATUS					mandatory
	DESCRIPTION			"PG Outlet 4 name"
	::= { node17PG 31 }

pgNode17Out4CustVoice	OBJECT-TYPE
	SYNTAX					DisplayString
	ACCESS					read-write
	STATUS					mandatory
	DESCRIPTION			"PG Outlet 4 custom voice"
	::= { node17PG 32 }

pgNode17Out4Volts			OBJECT-TYPE
	SYNTAX					INTEGER
	ACCESS					read-only
	STATUS					mandatory
	DESCRIPTION			"PG Outlet 4 volts"
	::= { node17PG 33 }

pgNode17Out4Amps				OBJECT-TYPE
	SYNTAX					INTEGER
	ACCESS					read-only
	STATUS					mandatory
	DESCRIPTION			"PG Outlet 4 amps"
	::= { node17PG 34 }

pgNode17Out4Watts			OBJECT-TYPE
	SYNTAX					INTEGER
	ACCESS					read-only
	STATUS					mandatory
	DESCRIPTION			"PG Outlet 4 watts"
	::= { node17PG 35 }

pgNode17Out4State			OBJECT-TYPE
	SYNTAX					INTEGER { off(1),on(2),cycle(3) }
	ACCESS					read-only
	STATUS					mandatory
	DESCRIPTION			"PG Outlet 4 state"
	::= { node17PG 36 }

pgNode17Out4Cmd				OBJECT-TYPE
	SYNTAX					INTEGER { off(1),on(2),cycle(3) }
	ACCESS					read-write
	STATUS					mandatory
	DESCRIPTION			"PG Outlet 4 command"
	::= { node17PG 37 }

pgNode17Out5Name				OBJECT-TYPE
	SYNTAX					DisplayString
	ACCESS					read-write
	STATUS					mandatory
	DESCRIPTION			"PG Outlet 5 name"
	::= { node17PG 38 }

pgNode17Out5CustVoice	OBJECT-TYPE
	SYNTAX					DisplayString
	ACCESS					read-write
	STATUS					mandatory
	DESCRIPTION			"PG Outlet 5 custom voice"
	::= { node17PG 39 }

pgNode17Out5Volts			OBJECT-TYPE
	SYNTAX					INTEGER
	ACCESS					read-only
	STATUS					mandatory
	DESCRIPTION			"PG Outlet 5 volts"
	::= { node17PG 40 }

pgNode17Out5Amps				OBJECT-TYPE
	SYNTAX					INTEGER
	ACCESS					read-only
	STATUS					mandatory
	DESCRIPTION			"PG Outlet 5 amps"
	::= { node17PG 41 }

pgNode17Out5Watts			OBJECT-TYPE
	SYNTAX					INTEGER
	ACCESS					read-only
	STATUS					mandatory
	DESCRIPTION			"PG Outlet 5 watts"
	::= { node17PG 42 }

pgNode17Out5State			OBJECT-TYPE
	SYNTAX					INTEGER { off(1),on(2),cycle(3) }
	ACCESS					read-only
	STATUS					mandatory
	DESCRIPTION			"PG Outlet 5 state"
	::= { node17PG 43 }

pgNode17Out5Cmd				OBJECT-TYPE
	SYNTAX					INTEGER { off(1),on(2),cycle(3) }
	ACCESS					read-write
	STATUS					mandatory
	DESCRIPTION			"PG Outlet 5 command"
	::= { node17PG 44 }

pgNode17Out6Name				OBJECT-TYPE
	SYNTAX					DisplayString
	ACCESS					read-write
	STATUS					mandatory
	DESCRIPTION			"PG Outlet 6 name"
	::= { node17PG 45 }

pgNode17Out6CustVoice	OBJECT-TYPE
	SYNTAX					DisplayString
	ACCESS					read-write
	STATUS					mandatory
	DESCRIPTION			"PG Outlet 6 custom voice"
	::= { node17PG 46 }

pgNode17Out6Volts			OBJECT-TYPE
	SYNTAX					INTEGER
	ACCESS					read-only
	STATUS					mandatory
	DESCRIPTION			"PG Outlet 6 volts"
	::= { node17PG 47 }

pgNode17Out6Amps				OBJECT-TYPE
	SYNTAX					INTEGER
	ACCESS					read-only
	STATUS					mandatory
	DESCRIPTION			"PG Outlet 6 amps"
	::= { node17PG 48 }

pgNode17Out6Watts			OBJECT-TYPE
	SYNTAX					INTEGER
	ACCESS					read-only
	STATUS					mandatory
	DESCRIPTION			"PG Outlet 6 watts"
	::= { node17PG 49 }

pgNode17Out6State			OBJECT-TYPE
	SYNTAX					INTEGER { off(1),on(2),cycle(3) }
	ACCESS					read-only
	STATUS					mandatory
	DESCRIPTION			"PG Outlet 6 state"
	::= { node17PG 50 }

pgNode17Out6Cmd				OBJECT-TYPE
	SYNTAX					INTEGER { off(1),on(2),cycle(3) }
	ACCESS					read-write
	STATUS					mandatory
	DESCRIPTION			"PG Outlet 6 command"
	::= { node17PG 51 }

pgNode17Out7Name				OBJECT-TYPE
	SYNTAX					DisplayString
	ACCESS					read-write
	STATUS					mandatory
	DESCRIPTION			"PG Outlet 7 name"
	::= { node17PG 52 }

pgNode17Out7CustVoice	OBJECT-TYPE
	SYNTAX					DisplayString
	ACCESS					read-write
	STATUS					mandatory
	DESCRIPTION			"PG Outlet 7 custom voice"
	::= { node17PG 53 }

pgNode17Out7Volts			OBJECT-TYPE
	SYNTAX					INTEGER
	ACCESS					read-only
	STATUS					mandatory
	DESCRIPTION			"PG Outlet 7 volts"
	::= { node17PG 54 }

pgNode17Out7Amps				OBJECT-TYPE
	SYNTAX					INTEGER
	ACCESS					read-only
	STATUS					mandatory
	DESCRIPTION			"PG Outlet 7 amps"
	::= { node17PG 55 }

pgNode17Out7Watts			OBJECT-TYPE
	SYNTAX					INTEGER
	ACCESS					read-only
	STATUS					mandatory
	DESCRIPTION			"PG Outlet 7 watts"
	::= { node17PG 56 }

pgNode17Out7State			OBJECT-TYPE
	SYNTAX					INTEGER { off(1),on(2),cycle(3) }
	ACCESS					read-only
	STATUS					mandatory
	DESCRIPTION			"PG Outlet 7 state"
	::= { node17PG 57 }

pgNode17Out7Cmd				OBJECT-TYPE
	SYNTAX					INTEGER { off(1),on(2),cycle(3) }
	ACCESS					read-write
	STATUS					mandatory
	DESCRIPTION			"PG Outlet 7 command"
	::= { node17PG 58 }

pgNode17Out8Name				OBJECT-TYPE
	SYNTAX					DisplayString
	ACCESS					read-write
	STATUS					mandatory
	DESCRIPTION			"PG Outlet 8 name"
	::= { node17PG 59 }

pgNode17Out8CustVoice	OBJECT-TYPE
	SYNTAX					DisplayString
	ACCESS					read-write
	STATUS					mandatory
	DESCRIPTION			"PG Outlet 8 custom voice"
	::= { node17PG 60 }

pgNode17Out8Volts			OBJECT-TYPE
	SYNTAX					INTEGER
	ACCESS					read-only
	STATUS					mandatory
	DESCRIPTION			"PG Outlet 8 volts"
	::= { node17PG 61 }

pgNode17Out8Amps				OBJECT-TYPE
	SYNTAX					INTEGER
	ACCESS					read-only
	STATUS					mandatory
	DESCRIPTION			"PG Outlet 8 amps"
	::= { node17PG 62 }

pgNode17Out8Watts			OBJECT-TYPE
	SYNTAX					INTEGER
	ACCESS					read-only
	STATUS					mandatory
	DESCRIPTION			"PG Outlet 8 watts"
	::= { node17PG 63 }

pgNode17Out8State			OBJECT-TYPE
	SYNTAX					INTEGER { off(1),on(2),cycle(3) }
	ACCESS					read-only
	STATUS					mandatory
	DESCRIPTION			"PG Outlet 8 state"
	::= { node17PG 64 }

pgNode17Out8Cmd				OBJECT-TYPE
	SYNTAX					INTEGER { off(1),on(2),cycle(3) }
	ACCESS					read-write
	STATUS					mandatory
	DESCRIPTION			"PG Outlet 8 command"
	::= { node17PG 65 }

pgNode18InUse					OBJECT-TYPE
	SYNTAX					INTEGER { false(1),true(2) }
	ACCESS					read-only
	STATUS					mandatory
	DESCRIPTION			"PG in use"
	::= { node18PG 1 }

pgNode18Status					OBJECT-TYPE
	SYNTAX					INTEGER { normal(1),pending(2), trouble(3) }
	ACCESS					read-only
	STATUS					mandatory
	DESCRIPTION			"PG status"
	::= { node18PG 2 }

pgNode18StatusSupport	OBJECT-TYPE
	SYNTAX					INTEGER { true1(1),false(2) }
	ACCESS					read-only
	STATUS					mandatory
	DESCRIPTION			"PG status support level"
	::= { node18PG 3 }

pgNode18Ver						OBJECT-TYPE
	SYNTAX					INTEGER { pgate1(1),pgate2(2) }
	ACCESS					read-only
	STATUS					mandatory
	DESCRIPTION			"PG version"
	::= { node18PG 4 }

pgNode18Volts					OBJECT-TYPE
	SYNTAX					INTEGER
	ACCESS					read-only
	STATUS					mandatory
	DESCRIPTION			"PG voltage"
	::= { node18PG 5 }

pgNode18Amps						OBJECT-TYPE
	SYNTAX					INTEGER
	ACCESS					read-only
	STATUS					mandatory
	DESCRIPTION			"PG amps"
	::= { node18PG 6 }

pgNode18Watts					OBJECT-TYPE
	SYNTAX					INTEGER
	ACCESS					read-only
	STATUS					mandatory
	DESCRIPTION			"PG Watts"
	::= { node18PG 7 }

pgNode18Name						OBJECT-TYPE
	SYNTAX					DisplayString
	ACCESS					read-write
	STATUS					mandatory
	DESCRIPTION			"PG name"
	::= { node18PG 8 }

pgNode18CustVoice			OBJECT-TYPE
	SYNTAX					DisplayString
	ACCESS					read-write
	STATUS					mandatory
	DESCRIPTION			"PG custom voice"
	::= { node18PG 9 }

pgNode18Out1Name				OBJECT-TYPE
	SYNTAX					DisplayString
	ACCESS					read-write
	STATUS					mandatory
	DESCRIPTION			"PG Outlet 1 name"
	::= { node18PG 10 }

pgNode18Out1CustVoice	OBJECT-TYPE
	SYNTAX					DisplayString
	ACCESS					read-write
	STATUS					mandatory
	DESCRIPTION			"PG Outlet 1 custom voice"
	::= { node18PG 11 }

pgNode18Out1Volts			OBJECT-TYPE
	SYNTAX					INTEGER
	ACCESS					read-only
	STATUS					mandatory
	DESCRIPTION			"PG Outlet 1 volts"
	::= { node18PG 12 }

pgNode18Out1Amps				OBJECT-TYPE
	SYNTAX					INTEGER
	ACCESS					read-only
	STATUS					mandatory
	DESCRIPTION			"PG Outlet 1 amps"
	::= { node18PG 13 }

pgNode18Out1Watts			OBJECT-TYPE
	SYNTAX					INTEGER
	ACCESS					read-only
	STATUS					mandatory
	DESCRIPTION			"PG Outlet 1 watts"
	::= { node18PG 14 }

pgNode18Out1State			OBJECT-TYPE
	SYNTAX					INTEGER { off(1),on(2),cycle(3) }
	ACCESS					read-only
	STATUS					mandatory
	DESCRIPTION			"PG Outlet 1 state"
	::= { node18PG 15 }

pgNode18Out1Cmd				OBJECT-TYPE
	SYNTAX					INTEGER { off(1),on(2),cycle(3) }
	ACCESS					read-write
	STATUS					mandatory
	DESCRIPTION			"PG Outlet 1 command"
	::= { node18PG 16 }

pgNode18Out2Name				OBJECT-TYPE
	SYNTAX					DisplayString
	ACCESS					read-write
	STATUS					mandatory
	DESCRIPTION			"PG Outlet 2 name"
	::= { node18PG 17 }

pgNode18Out2CustVoice	OBJECT-TYPE
	SYNTAX					DisplayString
	ACCESS					read-write
	STATUS					mandatory
	DESCRIPTION			"PG Outlet 2 custom voice"
	::= { node18PG 18 }

pgNode18Out2Volts			OBJECT-TYPE
	SYNTAX					INTEGER
	ACCESS					read-only
	STATUS					mandatory
	DESCRIPTION			"PG Outlet 2 volts"
	::= { node18PG 19 }

pgNode18Out2Amps				OBJECT-TYPE
	SYNTAX					INTEGER
	ACCESS					read-only
	STATUS					mandatory
	DESCRIPTION			"PG Outlet 2 amps"
	::= { node18PG 20 }

pgNode18Out2Watts			OBJECT-TYPE
	SYNTAX					INTEGER
	ACCESS					read-only
	STATUS					mandatory
	DESCRIPTION			"PG Outlet 2 watts"
	::= { node18PG 21 }

pgNode18Out2State			OBJECT-TYPE
	SYNTAX					INTEGER { off(1),on(2),cycle(3) }
	ACCESS					read-only
	STATUS					mandatory
	DESCRIPTION			"PG Outlet 2 state"
	::= { node18PG 22 }

pgNode18Out2Cmd				OBJECT-TYPE
	SYNTAX					INTEGER { off(1),on(2),cycle(3) }
	ACCESS					read-write
	STATUS					mandatory
	DESCRIPTION			"PG Outlet 2 command"
	::= { node18PG 23 }

pgNode18Out3Name				OBJECT-TYPE
	SYNTAX					DisplayString
	ACCESS					read-write
	STATUS					mandatory
	DESCRIPTION			"PG Outlet 3 name"
	::= { node18PG 24 }

pgNode18Out3CustVoice	OBJECT-TYPE
	SYNTAX					DisplayString
	ACCESS					read-write
	STATUS					mandatory
	DESCRIPTION			"PG Outlet 3 custom voice"
	::= { node18PG 25 }

pgNode18Out3Volts			OBJECT-TYPE
	SYNTAX					INTEGER
	ACCESS					read-only
	STATUS					mandatory
	DESCRIPTION			"PG Outlet 3 volts"
	::= { node18PG 26 }

pgNode18Out3Amps				OBJECT-TYPE
	SYNTAX					INTEGER
	ACCESS					read-only
	STATUS					mandatory
	DESCRIPTION			"PG Outlet 3 amps"
	::= { node18PG 27 }

pgNode18Out3Watts			OBJECT-TYPE
	SYNTAX					INTEGER
	ACCESS					read-only
	STATUS					mandatory
	DESCRIPTION			"PG Outlet 3 watts"
	::= { node18PG 28 }

pgNode18Out3State			OBJECT-TYPE
	SYNTAX					INTEGER { off(1),on(2),cycle(3) }
	ACCESS					read-only
	STATUS					mandatory
	DESCRIPTION			"PG Outlet 3 state"
	::= { node18PG 29 }

pgNode18Out3Cmd				OBJECT-TYPE
	SYNTAX					INTEGER { off(1),on(2),cycle(3) }
	ACCESS					read-write
	STATUS					mandatory
	DESCRIPTION			"PG Outlet 3 command"
	::= { node18PG 30 }

pgNode18Out4Name				OBJECT-TYPE
	SYNTAX					DisplayString
	ACCESS					read-write
	STATUS					mandatory
	DESCRIPTION			"PG Outlet 4 name"
	::= { node18PG 31 }

pgNode18Out4CustVoice	OBJECT-TYPE
	SYNTAX					DisplayString
	ACCESS					read-write
	STATUS					mandatory
	DESCRIPTION			"PG Outlet 4 custom voice"
	::= { node18PG 32 }

pgNode18Out4Volts			OBJECT-TYPE
	SYNTAX					INTEGER
	ACCESS					read-only
	STATUS					mandatory
	DESCRIPTION			"PG Outlet 4 volts"
	::= { node18PG 33 }

pgNode18Out4Amps				OBJECT-TYPE
	SYNTAX					INTEGER
	ACCESS					read-only
	STATUS					mandatory
	DESCRIPTION			"PG Outlet 4 amps"
	::= { node18PG 34 }

pgNode18Out4Watts			OBJECT-TYPE
	SYNTAX					INTEGER
	ACCESS					read-only
	STATUS					mandatory
	DESCRIPTION			"PG Outlet 4 watts"
	::= { node18PG 35 }

pgNode18Out4State			OBJECT-TYPE
	SYNTAX					INTEGER { off(1),on(2),cycle(3) }
	ACCESS					read-only
	STATUS					mandatory
	DESCRIPTION			"PG Outlet 4 state"
	::= { node18PG 36 }

pgNode18Out4Cmd				OBJECT-TYPE
	SYNTAX					INTEGER { off(1),on(2),cycle(3) }
	ACCESS					read-write
	STATUS					mandatory
	DESCRIPTION			"PG Outlet 4 command"
	::= { node18PG 37 }

pgNode18Out5Name				OBJECT-TYPE
	SYNTAX					DisplayString
	ACCESS					read-write
	STATUS					mandatory
	DESCRIPTION			"PG Outlet 5 name"
	::= { node18PG 38 }

pgNode18Out5CustVoice	OBJECT-TYPE
	SYNTAX					DisplayString
	ACCESS					read-write
	STATUS					mandatory
	DESCRIPTION			"PG Outlet 5 custom voice"
	::= { node18PG 39 }

pgNode18Out5Volts			OBJECT-TYPE
	SYNTAX					INTEGER
	ACCESS					read-only
	STATUS					mandatory
	DESCRIPTION			"PG Outlet 5 volts"
	::= { node18PG 40 }

pgNode18Out5Amps				OBJECT-TYPE
	SYNTAX					INTEGER
	ACCESS					read-only
	STATUS					mandatory
	DESCRIPTION			"PG Outlet 5 amps"
	::= { node18PG 41 }

pgNode18Out5Watts			OBJECT-TYPE
	SYNTAX					INTEGER
	ACCESS					read-only
	STATUS					mandatory
	DESCRIPTION			"PG Outlet 5 watts"
	::= { node18PG 42 }

pgNode18Out5State			OBJECT-TYPE
	SYNTAX					INTEGER { off(1),on(2),cycle(3) }
	ACCESS					read-only
	STATUS					mandatory
	DESCRIPTION			"PG Outlet 5 state"
	::= { node18PG 43 }

pgNode18Out5Cmd				OBJECT-TYPE
	SYNTAX					INTEGER { off(1),on(2),cycle(3) }
	ACCESS					read-write
	STATUS					mandatory
	DESCRIPTION			"PG Outlet 5 command"
	::= { node18PG 44 }

pgNode18Out6Name				OBJECT-TYPE
	SYNTAX					DisplayString
	ACCESS					read-write
	STATUS					mandatory
	DESCRIPTION			"PG Outlet 6 name"
	::= { node18PG 45 }

pgNode18Out6CustVoice	OBJECT-TYPE
	SYNTAX					DisplayString
	ACCESS					read-write
	STATUS					mandatory
	DESCRIPTION			"PG Outlet 6 custom voice"
	::= { node18PG 46 }

pgNode18Out6Volts			OBJECT-TYPE
	SYNTAX					INTEGER
	ACCESS					read-only
	STATUS					mandatory
	DESCRIPTION			"PG Outlet 6 volts"
	::= { node18PG 47 }

pgNode18Out6Amps				OBJECT-TYPE
	SYNTAX					INTEGER
	ACCESS					read-only
	STATUS					mandatory
	DESCRIPTION			"PG Outlet 6 amps"
	::= { node18PG 48 }

pgNode18Out6Watts			OBJECT-TYPE
	SYNTAX					INTEGER
	ACCESS					read-only
	STATUS					mandatory
	DESCRIPTION			"PG Outlet 6 watts"
	::= { node18PG 49 }

pgNode18Out6State			OBJECT-TYPE
	SYNTAX					INTEGER { off(1),on(2),cycle(3) }
	ACCESS					read-only
	STATUS					mandatory
	DESCRIPTION			"PG Outlet 6 state"
	::= { node18PG 50 }

pgNode18Out6Cmd				OBJECT-TYPE
	SYNTAX					INTEGER { off(1),on(2),cycle(3) }
	ACCESS					read-write
	STATUS					mandatory
	DESCRIPTION			"PG Outlet 6 command"
	::= { node18PG 51 }

pgNode18Out7Name				OBJECT-TYPE
	SYNTAX					DisplayString
	ACCESS					read-write
	STATUS					mandatory
	DESCRIPTION			"PG Outlet 7 name"
	::= { node18PG 52 }

pgNode18Out7CustVoice	OBJECT-TYPE
	SYNTAX					DisplayString
	ACCESS					read-write
	STATUS					mandatory
	DESCRIPTION			"PG Outlet 7 custom voice"
	::= { node18PG 53 }

pgNode18Out7Volts			OBJECT-TYPE
	SYNTAX					INTEGER
	ACCESS					read-only
	STATUS					mandatory
	DESCRIPTION			"PG Outlet 7 volts"
	::= { node18PG 54 }

pgNode18Out7Amps				OBJECT-TYPE
	SYNTAX					INTEGER
	ACCESS					read-only
	STATUS					mandatory
	DESCRIPTION			"PG Outlet 7 amps"
	::= { node18PG 55 }

pgNode18Out7Watts			OBJECT-TYPE
	SYNTAX					INTEGER
	ACCESS					read-only
	STATUS					mandatory
	DESCRIPTION			"PG Outlet 7 watts"
	::= { node18PG 56 }

pgNode18Out7State			OBJECT-TYPE
	SYNTAX					INTEGER { off(1),on(2),cycle(3) }
	ACCESS					read-only
	STATUS					mandatory
	DESCRIPTION			"PG Outlet 7 state"
	::= { node18PG 57 }

pgNode18Out7Cmd				OBJECT-TYPE
	SYNTAX					INTEGER { off(1),on(2),cycle(3) }
	ACCESS					read-write
	STATUS					mandatory
	DESCRIPTION			"PG Outlet 7 command"
	::= { node18PG 58 }

pgNode18Out8Name				OBJECT-TYPE
	SYNTAX					DisplayString
	ACCESS					read-write
	STATUS					mandatory
	DESCRIPTION			"PG Outlet 8 name"
	::= { node18PG 59 }

pgNode18Out8CustVoice	OBJECT-TYPE
	SYNTAX					DisplayString
	ACCESS					read-write
	STATUS					mandatory
	DESCRIPTION			"PG Outlet 8 custom voice"
	::= { node18PG 60 }

pgNode18Out8Volts			OBJECT-TYPE
	SYNTAX					INTEGER
	ACCESS					read-only
	STATUS					mandatory
	DESCRIPTION			"PG Outlet 8 volts"
	::= { node18PG 61 }

pgNode18Out8Amps				OBJECT-TYPE
	SYNTAX					INTEGER
	ACCESS					read-only
	STATUS					mandatory
	DESCRIPTION			"PG Outlet 8 amps"
	::= { node18PG 62 }

pgNode18Out8Watts			OBJECT-TYPE
	SYNTAX					INTEGER
	ACCESS					read-only
	STATUS					mandatory
	DESCRIPTION			"PG Outlet 8 watts"
	::= { node18PG 63 }

pgNode18Out8State			OBJECT-TYPE
	SYNTAX					INTEGER { off(1),on(2),cycle(3) }
	ACCESS					read-only
	STATUS					mandatory
	DESCRIPTION			"PG Outlet 8 state"
	::= { node18PG 64 }

pgNode18Out8Cmd				OBJECT-TYPE
	SYNTAX					INTEGER { off(1),on(2),cycle(3) }
	ACCESS					read-write
	STATUS					mandatory
	DESCRIPTION			"PG Outlet 8 command"
	::= { node18PG 65 }

pgNode19InUse					OBJECT-TYPE
	SYNTAX					INTEGER { false(1),true(2) }
	ACCESS					read-only
	STATUS					mandatory
	DESCRIPTION			"PG in use"
	::= { node19PG 1 }

pgNode19Status					OBJECT-TYPE
	SYNTAX					INTEGER { normal(1),pending(2), trouble(3) }
	ACCESS					read-only
	STATUS					mandatory
	DESCRIPTION			"PG status"
	::= { node19PG 2 }

pgNode19StatusSupport	OBJECT-TYPE
	SYNTAX					INTEGER { true1(1),false(2) }
	ACCESS					read-only
	STATUS					mandatory
	DESCRIPTION			"PG status support level"
	::= { node19PG 3 }

pgNode19Ver						OBJECT-TYPE
	SYNTAX					INTEGER { pgate1(1),pgate2(2) }
	ACCESS					read-only
	STATUS					mandatory
	DESCRIPTION			"PG version"
	::= { node19PG 4 }

pgNode19Volts					OBJECT-TYPE
	SYNTAX					INTEGER
	ACCESS					read-only
	STATUS					mandatory
	DESCRIPTION			"PG voltage"
	::= { node19PG 5 }

pgNode19Amps						OBJECT-TYPE
	SYNTAX					INTEGER
	ACCESS					read-only
	STATUS					mandatory
	DESCRIPTION			"PG amps"
	::= { node19PG 6 }

pgNode19Watts					OBJECT-TYPE
	SYNTAX					INTEGER
	ACCESS					read-only
	STATUS					mandatory
	DESCRIPTION			"PG Watts"
	::= { node19PG 7 }

pgNode19Name						OBJECT-TYPE
	SYNTAX					DisplayString
	ACCESS					read-write
	STATUS					mandatory
	DESCRIPTION			"PG name"
	::= { node19PG 8 }

pgNode19CustVoice			OBJECT-TYPE
	SYNTAX					DisplayString
	ACCESS					read-write
	STATUS					mandatory
	DESCRIPTION			"PG custom voice"
	::= { node19PG 9 }

pgNode19Out1Name				OBJECT-TYPE
	SYNTAX					DisplayString
	ACCESS					read-write
	STATUS					mandatory
	DESCRIPTION			"PG Outlet 1 name"
	::= { node19PG 10 }

pgNode19Out1CustVoice	OBJECT-TYPE
	SYNTAX					DisplayString
	ACCESS					read-write
	STATUS					mandatory
	DESCRIPTION			"PG Outlet 1 custom voice"
	::= { node19PG 11 }

pgNode19Out1Volts			OBJECT-TYPE
	SYNTAX					INTEGER
	ACCESS					read-only
	STATUS					mandatory
	DESCRIPTION			"PG Outlet 1 volts"
	::= { node19PG 12 }

pgNode19Out1Amps				OBJECT-TYPE
	SYNTAX					INTEGER
	ACCESS					read-only
	STATUS					mandatory
	DESCRIPTION			"PG Outlet 1 amps"
	::= { node19PG 13 }

pgNode19Out1Watts			OBJECT-TYPE
	SYNTAX					INTEGER
	ACCESS					read-only
	STATUS					mandatory
	DESCRIPTION			"PG Outlet 1 watts"
	::= { node19PG 14 }

pgNode19Out1State			OBJECT-TYPE
	SYNTAX					INTEGER { off(1),on(2),cycle(3) }
	ACCESS					read-only
	STATUS					mandatory
	DESCRIPTION			"PG Outlet 1 state"
	::= { node19PG 15 }

pgNode19Out1Cmd				OBJECT-TYPE
	SYNTAX					INTEGER { off(1),on(2),cycle(3) }
	ACCESS					read-write
	STATUS					mandatory
	DESCRIPTION			"PG Outlet 1 command"
	::= { node19PG 16 }

pgNode19Out2Name				OBJECT-TYPE
	SYNTAX					DisplayString
	ACCESS					read-write
	STATUS					mandatory
	DESCRIPTION			"PG Outlet 2 name"
	::= { node19PG 17 }

pgNode19Out2CustVoice	OBJECT-TYPE
	SYNTAX					DisplayString
	ACCESS					read-write
	STATUS					mandatory
	DESCRIPTION			"PG Outlet 2 custom voice"
	::= { node19PG 18 }

pgNode19Out2Volts			OBJECT-TYPE
	SYNTAX					INTEGER
	ACCESS					read-only
	STATUS					mandatory
	DESCRIPTION			"PG Outlet 2 volts"
	::= { node19PG 19 }

pgNode19Out2Amps				OBJECT-TYPE
	SYNTAX					INTEGER
	ACCESS					read-only
	STATUS					mandatory
	DESCRIPTION			"PG Outlet 2 amps"
	::= { node19PG 20 }

pgNode19Out2Watts			OBJECT-TYPE
	SYNTAX					INTEGER
	ACCESS					read-only
	STATUS					mandatory
	DESCRIPTION			"PG Outlet 2 watts"
	::= { node19PG 21 }

pgNode19Out2State			OBJECT-TYPE
	SYNTAX					INTEGER { off(1),on(2),cycle(3) }
	ACCESS					read-only
	STATUS					mandatory
	DESCRIPTION			"PG Outlet 2 state"
	::= { node19PG 22 }

pgNode19Out2Cmd				OBJECT-TYPE
	SYNTAX					INTEGER { off(1),on(2),cycle(3) }
	ACCESS					read-write
	STATUS					mandatory
	DESCRIPTION			"PG Outlet 2 command"
	::= { node19PG 23 }

pgNode19Out3Name				OBJECT-TYPE
	SYNTAX					DisplayString
	ACCESS					read-write
	STATUS					mandatory
	DESCRIPTION			"PG Outlet 3 name"
	::= { node19PG 24 }

pgNode19Out3CustVoice	OBJECT-TYPE
	SYNTAX					DisplayString
	ACCESS					read-write
	STATUS					mandatory
	DESCRIPTION			"PG Outlet 3 custom voice"
	::= { node19PG 25 }

pgNode19Out3Volts			OBJECT-TYPE
	SYNTAX					INTEGER
	ACCESS					read-only
	STATUS					mandatory
	DESCRIPTION			"PG Outlet 3 volts"
	::= { node19PG 26 }

pgNode19Out3Amps				OBJECT-TYPE
	SYNTAX					INTEGER
	ACCESS					read-only
	STATUS					mandatory
	DESCRIPTION			"PG Outlet 3 amps"
	::= { node19PG 27 }

pgNode19Out3Watts			OBJECT-TYPE
	SYNTAX					INTEGER
	ACCESS					read-only
	STATUS					mandatory
	DESCRIPTION			"PG Outlet 3 watts"
	::= { node19PG 28 }

pgNode19Out3State			OBJECT-TYPE
	SYNTAX					INTEGER { off(1),on(2),cycle(3) }
	ACCESS					read-only
	STATUS					mandatory
	DESCRIPTION			"PG Outlet 3 state"
	::= { node19PG 29 }

pgNode19Out3Cmd				OBJECT-TYPE
	SYNTAX					INTEGER { off(1),on(2),cycle(3) }
	ACCESS					read-write
	STATUS					mandatory
	DESCRIPTION			"PG Outlet 3 command"
	::= { node19PG 30 }

pgNode19Out4Name				OBJECT-TYPE
	SYNTAX					DisplayString
	ACCESS					read-write
	STATUS					mandatory
	DESCRIPTION			"PG Outlet 4 name"
	::= { node19PG 31 }

pgNode19Out4CustVoice	OBJECT-TYPE
	SYNTAX					DisplayString
	ACCESS					read-write
	STATUS					mandatory
	DESCRIPTION			"PG Outlet 4 custom voice"
	::= { node19PG 32 }

pgNode19Out4Volts			OBJECT-TYPE
	SYNTAX					INTEGER
	ACCESS					read-only
	STATUS					mandatory
	DESCRIPTION			"PG Outlet 4 volts"
	::= { node19PG 33 }

pgNode19Out4Amps				OBJECT-TYPE
	SYNTAX					INTEGER
	ACCESS					read-only
	STATUS					mandatory
	DESCRIPTION			"PG Outlet 4 amps"
	::= { node19PG 34 }

pgNode19Out4Watts			OBJECT-TYPE
	SYNTAX					INTEGER
	ACCESS					read-only
	STATUS					mandatory
	DESCRIPTION			"PG Outlet 4 watts"
	::= { node19PG 35 }

pgNode19Out4State			OBJECT-TYPE
	SYNTAX					INTEGER { off(1),on(2),cycle(3) }
	ACCESS					read-only
	STATUS					mandatory
	DESCRIPTION			"PG Outlet 4 state"
	::= { node19PG 36 }

pgNode19Out4Cmd				OBJECT-TYPE
	SYNTAX					INTEGER { off(1),on(2),cycle(3) }
	ACCESS					read-write
	STATUS					mandatory
	DESCRIPTION			"PG Outlet 4 command"
	::= { node19PG 37 }

pgNode19Out5Name				OBJECT-TYPE
	SYNTAX					DisplayString
	ACCESS					read-write
	STATUS					mandatory
	DESCRIPTION			"PG Outlet 5 name"
	::= { node19PG 38 }

pgNode19Out5CustVoice	OBJECT-TYPE
	SYNTAX					DisplayString
	ACCESS					read-write
	STATUS					mandatory
	DESCRIPTION			"PG Outlet 5 custom voice"
	::= { node19PG 39 }

pgNode19Out5Volts			OBJECT-TYPE
	SYNTAX					INTEGER
	ACCESS					read-only
	STATUS					mandatory
	DESCRIPTION			"PG Outlet 5 volts"
	::= { node19PG 40 }

pgNode19Out5Amps				OBJECT-TYPE
	SYNTAX					INTEGER
	ACCESS					read-only
	STATUS					mandatory
	DESCRIPTION			"PG Outlet 5 amps"
	::= { node19PG 41 }

pgNode19Out5Watts			OBJECT-TYPE
	SYNTAX					INTEGER
	ACCESS					read-only
	STATUS					mandatory
	DESCRIPTION			"PG Outlet 5 watts"
	::= { node19PG 42 }

pgNode19Out5State			OBJECT-TYPE
	SYNTAX					INTEGER { off(1),on(2),cycle(3) }
	ACCESS					read-only
	STATUS					mandatory
	DESCRIPTION			"PG Outlet 5 state"
	::= { node19PG 43 }

pgNode19Out5Cmd				OBJECT-TYPE
	SYNTAX					INTEGER { off(1),on(2),cycle(3) }
	ACCESS					read-write
	STATUS					mandatory
	DESCRIPTION			"PG Outlet 5 command"
	::= { node19PG 44 }

pgNode19Out6Name				OBJECT-TYPE
	SYNTAX					DisplayString
	ACCESS					read-write
	STATUS					mandatory
	DESCRIPTION			"PG Outlet 6 name"
	::= { node19PG 45 }

pgNode19Out6CustVoice	OBJECT-TYPE
	SYNTAX					DisplayString
	ACCESS					read-write
	STATUS					mandatory
	DESCRIPTION			"PG Outlet 6 custom voice"
	::= { node19PG 46 }

pgNode19Out6Volts			OBJECT-TYPE
	SYNTAX					INTEGER
	ACCESS					read-only
	STATUS					mandatory
	DESCRIPTION			"PG Outlet 6 volts"
	::= { node19PG 47 }

pgNode19Out6Amps				OBJECT-TYPE
	SYNTAX					INTEGER
	ACCESS					read-only
	STATUS					mandatory
	DESCRIPTION			"PG Outlet 6 amps"
	::= { node19PG 48 }

pgNode19Out6Watts			OBJECT-TYPE
	SYNTAX					INTEGER
	ACCESS					read-only
	STATUS					mandatory
	DESCRIPTION			"PG Outlet 6 watts"
	::= { node19PG 49 }

pgNode19Out6State			OBJECT-TYPE
	SYNTAX					INTEGER { off(1),on(2),cycle(3) }
	ACCESS					read-only
	STATUS					mandatory
	DESCRIPTION			"PG Outlet 6 state"
	::= { node19PG 50 }

pgNode19Out6Cmd				OBJECT-TYPE
	SYNTAX					INTEGER { off(1),on(2),cycle(3) }
	ACCESS					read-write
	STATUS					mandatory
	DESCRIPTION			"PG Outlet 6 command"
	::= { node19PG 51 }

pgNode19Out7Name				OBJECT-TYPE
	SYNTAX					DisplayString
	ACCESS					read-write
	STATUS					mandatory
	DESCRIPTION			"PG Outlet 7 name"
	::= { node19PG 52 }

pgNode19Out7CustVoice	OBJECT-TYPE
	SYNTAX					DisplayString
	ACCESS					read-write
	STATUS					mandatory
	DESCRIPTION			"PG Outlet 7 custom voice"
	::= { node19PG 53 }

pgNode19Out7Volts			OBJECT-TYPE
	SYNTAX					INTEGER
	ACCESS					read-only
	STATUS					mandatory
	DESCRIPTION			"PG Outlet 7 volts"
	::= { node19PG 54 }

pgNode19Out7Amps				OBJECT-TYPE
	SYNTAX					INTEGER
	ACCESS					read-only
	STATUS					mandatory
	DESCRIPTION			"PG Outlet 7 amps"
	::= { node19PG 55 }

pgNode19Out7Watts			OBJECT-TYPE
	SYNTAX					INTEGER
	ACCESS					read-only
	STATUS					mandatory
	DESCRIPTION			"PG Outlet 7 watts"
	::= { node19PG 56 }

pgNode19Out7State			OBJECT-TYPE
	SYNTAX					INTEGER { off(1),on(2),cycle(3) }
	ACCESS					read-only
	STATUS					mandatory
	DESCRIPTION			"PG Outlet 7 state"
	::= { node19PG 57 }

pgNode19Out7Cmd				OBJECT-TYPE
	SYNTAX					INTEGER { off(1),on(2),cycle(3) }
	ACCESS					read-write
	STATUS					mandatory
	DESCRIPTION			"PG Outlet 7 command"
	::= { node19PG 58 }

pgNode19Out8Name				OBJECT-TYPE
	SYNTAX					DisplayString
	ACCESS					read-write
	STATUS					mandatory
	DESCRIPTION			"PG Outlet 8 name"
	::= { node19PG 59 }

pgNode19Out8CustVoice	OBJECT-TYPE
	SYNTAX					DisplayString
	ACCESS					read-write
	STATUS					mandatory
	DESCRIPTION			"PG Outlet 8 custom voice"
	::= { node19PG 60 }

pgNode19Out8Volts			OBJECT-TYPE
	SYNTAX					INTEGER
	ACCESS					read-only
	STATUS					mandatory
	DESCRIPTION			"PG Outlet 8 volts"
	::= { node19PG 61 }

pgNode19Out8Amps				OBJECT-TYPE
	SYNTAX					INTEGER
	ACCESS					read-only
	STATUS					mandatory
	DESCRIPTION			"PG Outlet 8 amps"
	::= { node19PG 62 }

pgNode19Out8Watts			OBJECT-TYPE
	SYNTAX					INTEGER
	ACCESS					read-only
	STATUS					mandatory
	DESCRIPTION			"PG Outlet 8 watts"
	::= { node19PG 63 }

pgNode19Out8State			OBJECT-TYPE
	SYNTAX					INTEGER { off(1),on(2),cycle(3) }
	ACCESS					read-only
	STATUS					mandatory
	DESCRIPTION			"PG Outlet 8 state"
	::= { node19PG 64 }

pgNode19Out8Cmd				OBJECT-TYPE
	SYNTAX					INTEGER { off(1),on(2),cycle(3) }
	ACCESS					read-write
	STATUS					mandatory
	DESCRIPTION			"PG Outlet 8 command"
	::= { node19PG 65 }

pgNode20InUse					OBJECT-TYPE
	SYNTAX					INTEGER { false(1),true(2) }
	ACCESS					read-only
	STATUS					mandatory
	DESCRIPTION			"PG in use"
	::= { node20PG 1 }

pgNode20Status					OBJECT-TYPE
	SYNTAX					INTEGER { normal(1),pending(2), trouble(3) }
	ACCESS					read-only
	STATUS					mandatory
	DESCRIPTION			"PG status"
	::= { node20PG 2 }

pgNode20StatusSupport	OBJECT-TYPE
	SYNTAX					INTEGER { true1(1),false(2) }
	ACCESS					read-only
	STATUS					mandatory
	DESCRIPTION			"PG status support level"
	::= { node20PG 3 }

pgNode20Ver						OBJECT-TYPE
	SYNTAX					INTEGER { pgate1(1),pgate2(2) }
	ACCESS					read-only
	STATUS					mandatory
	DESCRIPTION			"PG version"
	::= { node20PG 4 }

pgNode20Volts					OBJECT-TYPE
	SYNTAX					INTEGER
	ACCESS					read-only
	STATUS					mandatory
	DESCRIPTION			"PG voltage"
	::= { node20PG 5 }

pgNode20Amps						OBJECT-TYPE
	SYNTAX					INTEGER
	ACCESS					read-only
	STATUS					mandatory
	DESCRIPTION			"PG amps"
	::= { node20PG 6 }

pgNode20Watts					OBJECT-TYPE
	SYNTAX					INTEGER
	ACCESS					read-only
	STATUS					mandatory
	DESCRIPTION			"PG Watts"
	::= { node20PG 7 }

pgNode20Name						OBJECT-TYPE
	SYNTAX					DisplayString
	ACCESS					read-write
	STATUS					mandatory
	DESCRIPTION			"PG name"
	::= { node20PG 8 }

pgNode20CustVoice			OBJECT-TYPE
	SYNTAX					DisplayString
	ACCESS					read-write
	STATUS					mandatory
	DESCRIPTION			"PG custom voice"
	::= { node20PG 9 }

pgNode20Out1Name				OBJECT-TYPE
	SYNTAX					DisplayString
	ACCESS					read-write
	STATUS					mandatory
	DESCRIPTION			"PG Outlet 1 name"
	::= { node20PG 10 }

pgNode20Out1CustVoice	OBJECT-TYPE
	SYNTAX					DisplayString
	ACCESS					read-write
	STATUS					mandatory
	DESCRIPTION			"PG Outlet 1 custom voice"
	::= { node20PG 11 }

pgNode20Out1Volts			OBJECT-TYPE
	SYNTAX					INTEGER
	ACCESS					read-only
	STATUS					mandatory
	DESCRIPTION			"PG Outlet 1 volts"
	::= { node20PG 12 }

pgNode20Out1Amps				OBJECT-TYPE
	SYNTAX					INTEGER
	ACCESS					read-only
	STATUS					mandatory
	DESCRIPTION			"PG Outlet 1 amps"
	::= { node20PG 13 }

pgNode20Out1Watts			OBJECT-TYPE
	SYNTAX					INTEGER
	ACCESS					read-only
	STATUS					mandatory
	DESCRIPTION			"PG Outlet 1 watts"
	::= { node20PG 14 }

pgNode20Out1State			OBJECT-TYPE
	SYNTAX					INTEGER { off(1),on(2),cycle(3) }
	ACCESS					read-only
	STATUS					mandatory
	DESCRIPTION			"PG Outlet 1 state"
	::= { node20PG 15 }

pgNode20Out1Cmd				OBJECT-TYPE
	SYNTAX					INTEGER { off(1),on(2),cycle(3) }
	ACCESS					read-write
	STATUS					mandatory
	DESCRIPTION			"PG Outlet 1 command"
	::= { node20PG 16 }

pgNode20Out2Name				OBJECT-TYPE
	SYNTAX					DisplayString
	ACCESS					read-write
	STATUS					mandatory
	DESCRIPTION			"PG Outlet 2 name"
	::= { node20PG 17 }

pgNode20Out2CustVoice	OBJECT-TYPE
	SYNTAX					DisplayString
	ACCESS					read-write
	STATUS					mandatory
	DESCRIPTION			"PG Outlet 2 custom voice"
	::= { node20PG 18 }

pgNode20Out2Volts			OBJECT-TYPE
	SYNTAX					INTEGER
	ACCESS					read-only
	STATUS					mandatory
	DESCRIPTION			"PG Outlet 2 volts"
	::= { node20PG 19 }

pgNode20Out2Amps				OBJECT-TYPE
	SYNTAX					INTEGER
	ACCESS					read-only
	STATUS					mandatory
	DESCRIPTION			"PG Outlet 2 amps"
	::= { node20PG 20 }

pgNode20Out2Watts			OBJECT-TYPE
	SYNTAX					INTEGER
	ACCESS					read-only
	STATUS					mandatory
	DESCRIPTION			"PG Outlet 2 watts"
	::= { node20PG 21 }

pgNode20Out2State			OBJECT-TYPE
	SYNTAX					INTEGER { off(1),on(2),cycle(3) }
	ACCESS					read-only
	STATUS					mandatory
	DESCRIPTION			"PG Outlet 2 state"
	::= { node20PG 22 }

pgNode20Out2Cmd				OBJECT-TYPE
	SYNTAX					INTEGER { off(1),on(2),cycle(3) }
	ACCESS					read-write
	STATUS					mandatory
	DESCRIPTION			"PG Outlet 2 command"
	::= { node20PG 23 }

pgNode20Out3Name				OBJECT-TYPE
	SYNTAX					DisplayString
	ACCESS					read-write
	STATUS					mandatory
	DESCRIPTION			"PG Outlet 3 name"
	::= { node20PG 24 }

pgNode20Out3CustVoice	OBJECT-TYPE
	SYNTAX					DisplayString
	ACCESS					read-write
	STATUS					mandatory
	DESCRIPTION			"PG Outlet 3 custom voice"
	::= { node20PG 25 }

pgNode20Out3Volts			OBJECT-TYPE
	SYNTAX					INTEGER
	ACCESS					read-only
	STATUS					mandatory
	DESCRIPTION			"PG Outlet 3 volts"
	::= { node20PG 26 }

pgNode20Out3Amps				OBJECT-TYPE
	SYNTAX					INTEGER
	ACCESS					read-only
	STATUS					mandatory
	DESCRIPTION			"PG Outlet 3 amps"
	::= { node20PG 27 }

pgNode20Out3Watts			OBJECT-TYPE
	SYNTAX					INTEGER
	ACCESS					read-only
	STATUS					mandatory
	DESCRIPTION			"PG Outlet 3 watts"
	::= { node20PG 28 }

pgNode20Out3State			OBJECT-TYPE
	SYNTAX					INTEGER { off(1),on(2),cycle(3) }
	ACCESS					read-only
	STATUS					mandatory
	DESCRIPTION			"PG Outlet 3 state"
	::= { node20PG 29 }

pgNode20Out3Cmd				OBJECT-TYPE
	SYNTAX					INTEGER { off(1),on(2),cycle(3) }
	ACCESS					read-write
	STATUS					mandatory
	DESCRIPTION			"PG Outlet 3 command"
	::= { node20PG 30 }

pgNode20Out4Name				OBJECT-TYPE
	SYNTAX					DisplayString
	ACCESS					read-write
	STATUS					mandatory
	DESCRIPTION			"PG Outlet 4 name"
	::= { node20PG 31 }

pgNode20Out4CustVoice	OBJECT-TYPE
	SYNTAX					DisplayString
	ACCESS					read-write
	STATUS					mandatory
	DESCRIPTION			"PG Outlet 4 custom voice"
	::= { node20PG 32 }

pgNode20Out4Volts			OBJECT-TYPE
	SYNTAX					INTEGER
	ACCESS					read-only
	STATUS					mandatory
	DESCRIPTION			"PG Outlet 4 volts"
	::= { node20PG 33 }

pgNode20Out4Amps				OBJECT-TYPE
	SYNTAX					INTEGER
	ACCESS					read-only
	STATUS					mandatory
	DESCRIPTION			"PG Outlet 4 amps"
	::= { node20PG 34 }

pgNode20Out4Watts			OBJECT-TYPE
	SYNTAX					INTEGER
	ACCESS					read-only
	STATUS					mandatory
	DESCRIPTION			"PG Outlet 4 watts"
	::= { node20PG 35 }

pgNode20Out4State			OBJECT-TYPE
	SYNTAX					INTEGER { off(1),on(2),cycle(3) }
	ACCESS					read-only
	STATUS					mandatory
	DESCRIPTION			"PG Outlet 4 state"
	::= { node20PG 36 }

pgNode20Out4Cmd				OBJECT-TYPE
	SYNTAX					INTEGER { off(1),on(2),cycle(3) }
	ACCESS					read-write
	STATUS					mandatory
	DESCRIPTION			"PG Outlet 4 command"
	::= { node20PG 37 }

pgNode20Out5Name				OBJECT-TYPE
	SYNTAX					DisplayString
	ACCESS					read-write
	STATUS					mandatory
	DESCRIPTION			"PG Outlet 5 name"
	::= { node20PG 38 }

pgNode20Out5CustVoice	OBJECT-TYPE
	SYNTAX					DisplayString
	ACCESS					read-write
	STATUS					mandatory
	DESCRIPTION			"PG Outlet 5 custom voice"
	::= { node20PG 39 }

pgNode20Out5Volts			OBJECT-TYPE
	SYNTAX					INTEGER
	ACCESS					read-only
	STATUS					mandatory
	DESCRIPTION			"PG Outlet 5 volts"
	::= { node20PG 40 }

pgNode20Out5Amps				OBJECT-TYPE
	SYNTAX					INTEGER
	ACCESS					read-only
	STATUS					mandatory
	DESCRIPTION			"PG Outlet 5 amps"
	::= { node20PG 41 }

pgNode20Out5Watts			OBJECT-TYPE
	SYNTAX					INTEGER
	ACCESS					read-only
	STATUS					mandatory
	DESCRIPTION			"PG Outlet 5 watts"
	::= { node20PG 42 }

pgNode20Out5State			OBJECT-TYPE
	SYNTAX					INTEGER { off(1),on(2),cycle(3) }
	ACCESS					read-only
	STATUS					mandatory
	DESCRIPTION			"PG Outlet 5 state"
	::= { node20PG 43 }

pgNode20Out5Cmd				OBJECT-TYPE
	SYNTAX					INTEGER { off(1),on(2),cycle(3) }
	ACCESS					read-write
	STATUS					mandatory
	DESCRIPTION			"PG Outlet 5 command"
	::= { node20PG 44 }

pgNode20Out6Name				OBJECT-TYPE
	SYNTAX					DisplayString
	ACCESS					read-write
	STATUS					mandatory
	DESCRIPTION			"PG Outlet 6 name"
	::= { node20PG 45 }

pgNode20Out6CustVoice	OBJECT-TYPE
	SYNTAX					DisplayString
	ACCESS					read-write
	STATUS					mandatory
	DESCRIPTION			"PG Outlet 6 custom voice"
	::= { node20PG 46 }

pgNode20Out6Volts			OBJECT-TYPE
	SYNTAX					INTEGER
	ACCESS					read-only
	STATUS					mandatory
	DESCRIPTION			"PG Outlet 6 volts"
	::= { node20PG 47 }

pgNode20Out6Amps				OBJECT-TYPE
	SYNTAX					INTEGER
	ACCESS					read-only
	STATUS					mandatory
	DESCRIPTION			"PG Outlet 6 amps"
	::= { node20PG 48 }

pgNode20Out6Watts			OBJECT-TYPE
	SYNTAX					INTEGER
	ACCESS					read-only
	STATUS					mandatory
	DESCRIPTION			"PG Outlet 6 watts"
	::= { node20PG 49 }

pgNode20Out6State			OBJECT-TYPE
	SYNTAX					INTEGER { off(1),on(2),cycle(3) }
	ACCESS					read-only
	STATUS					mandatory
	DESCRIPTION			"PG Outlet 6 state"
	::= { node20PG 50 }

pgNode20Out6Cmd				OBJECT-TYPE
	SYNTAX					INTEGER { off(1),on(2),cycle(3) }
	ACCESS					read-write
	STATUS					mandatory
	DESCRIPTION			"PG Outlet 6 command"
	::= { node20PG 51 }

pgNode20Out7Name				OBJECT-TYPE
	SYNTAX					DisplayString
	ACCESS					read-write
	STATUS					mandatory
	DESCRIPTION			"PG Outlet 7 name"
	::= { node20PG 52 }

pgNode20Out7CustVoice	OBJECT-TYPE
	SYNTAX					DisplayString
	ACCESS					read-write
	STATUS					mandatory
	DESCRIPTION			"PG Outlet 7 custom voice"
	::= { node20PG 53 }

pgNode20Out7Volts			OBJECT-TYPE
	SYNTAX					INTEGER
	ACCESS					read-only
	STATUS					mandatory
	DESCRIPTION			"PG Outlet 7 volts"
	::= { node20PG 54 }

pgNode20Out7Amps				OBJECT-TYPE
	SYNTAX					INTEGER
	ACCESS					read-only
	STATUS					mandatory
	DESCRIPTION			"PG Outlet 7 amps"
	::= { node20PG 55 }

pgNode20Out7Watts			OBJECT-TYPE
	SYNTAX					INTEGER
	ACCESS					read-only
	STATUS					mandatory
	DESCRIPTION			"PG Outlet 7 watts"
	::= { node20PG 56 }

pgNode20Out7State			OBJECT-TYPE
	SYNTAX					INTEGER { off(1),on(2),cycle(3) }
	ACCESS					read-only
	STATUS					mandatory
	DESCRIPTION			"PG Outlet 7 state"
	::= { node20PG 57 }

pgNode20Out7Cmd				OBJECT-TYPE
	SYNTAX					INTEGER { off(1),on(2),cycle(3) }
	ACCESS					read-write
	STATUS					mandatory
	DESCRIPTION			"PG Outlet 7 command"
	::= { node20PG 58 }

pgNode20Out8Name				OBJECT-TYPE
	SYNTAX					DisplayString
	ACCESS					read-write
	STATUS					mandatory
	DESCRIPTION			"PG Outlet 8 name"
	::= { node20PG 59 }

pgNode20Out8CustVoice	OBJECT-TYPE
	SYNTAX					DisplayString
	ACCESS					read-write
	STATUS					mandatory
	DESCRIPTION			"PG Outlet 8 custom voice"
	::= { node20PG 60 }

pgNode20Out8Volts			OBJECT-TYPE
	SYNTAX					INTEGER
	ACCESS					read-only
	STATUS					mandatory
	DESCRIPTION			"PG Outlet 8 volts"
	::= { node20PG 61 }

pgNode20Out8Amps				OBJECT-TYPE
	SYNTAX					INTEGER
	ACCESS					read-only
	STATUS					mandatory
	DESCRIPTION			"PG Outlet 8 amps"
	::= { node20PG 62 }

pgNode20Out8Watts			OBJECT-TYPE
	SYNTAX					INTEGER
	ACCESS					read-only
	STATUS					mandatory
	DESCRIPTION			"PG Outlet 8 watts"
	::= { node20PG 63 }

pgNode20Out8State			OBJECT-TYPE
	SYNTAX					INTEGER { off(1),on(2),cycle(3) }
	ACCESS					read-only
	STATUS					mandatory
	DESCRIPTION			"PG Outlet 8 state"
	::= { node20PG 64 }

pgNode20Out8Cmd				OBJECT-TYPE
	SYNTAX					INTEGER { off(1),on(2),cycle(3) }
	ACCESS					read-write
	STATUS					mandatory
	DESCRIPTION			"PG Outlet 8 command"
	::= { node20PG 65 }

pgNode21InUse					OBJECT-TYPE
	SYNTAX					INTEGER { false(1),true(2) }
	ACCESS					read-only
	STATUS					mandatory
	DESCRIPTION			"PG in use"
	::= { node21PG 1 }

pgNode21Status					OBJECT-TYPE
	SYNTAX					INTEGER { normal(1),pending(2), trouble(3) }
	ACCESS					read-only
	STATUS					mandatory
	DESCRIPTION			"PG status"
	::= { node21PG 2 }

pgNode21StatusSupport	OBJECT-TYPE
	SYNTAX					INTEGER { true1(1),false(2) }
	ACCESS					read-only
	STATUS					mandatory
	DESCRIPTION			"PG status support level"
	::= { node21PG 3 }

pgNode21Ver						OBJECT-TYPE
	SYNTAX					INTEGER { pgate1(1),pgate2(2) }
	ACCESS					read-only
	STATUS					mandatory
	DESCRIPTION			"PG version"
	::= { node21PG 4 }

pgNode21Volts					OBJECT-TYPE
	SYNTAX					INTEGER
	ACCESS					read-only
	STATUS					mandatory
	DESCRIPTION			"PG voltage"
	::= { node21PG 5 }

pgNode21Amps						OBJECT-TYPE
	SYNTAX					INTEGER
	ACCESS					read-only
	STATUS					mandatory
	DESCRIPTION			"PG amps"
	::= { node21PG 6 }

pgNode21Watts					OBJECT-TYPE
	SYNTAX					INTEGER
	ACCESS					read-only
	STATUS					mandatory
	DESCRIPTION			"PG Watts"
	::= { node21PG 7 }

pgNode21Name						OBJECT-TYPE
	SYNTAX					DisplayString
	ACCESS					read-write
	STATUS					mandatory
	DESCRIPTION			"PG name"
	::= { node21PG 8 }

pgNode21CustVoice			OBJECT-TYPE
	SYNTAX					DisplayString
	ACCESS					read-write
	STATUS					mandatory
	DESCRIPTION			"PG custom voice"
	::= { node21PG 9 }

pgNode21Out1Name				OBJECT-TYPE
	SYNTAX					DisplayString
	ACCESS					read-write
	STATUS					mandatory
	DESCRIPTION			"PG Outlet 1 name"
	::= { node21PG 10 }

pgNode21Out1CustVoice	OBJECT-TYPE
	SYNTAX					DisplayString
	ACCESS					read-write
	STATUS					mandatory
	DESCRIPTION			"PG Outlet 1 custom voice"
	::= { node21PG 11 }

pgNode21Out1Volts			OBJECT-TYPE
	SYNTAX					INTEGER
	ACCESS					read-only
	STATUS					mandatory
	DESCRIPTION			"PG Outlet 1 volts"
	::= { node21PG 12 }

pgNode21Out1Amps				OBJECT-TYPE
	SYNTAX					INTEGER
	ACCESS					read-only
	STATUS					mandatory
	DESCRIPTION			"PG Outlet 1 amps"
	::= { node21PG 13 }

pgNode21Out1Watts			OBJECT-TYPE
	SYNTAX					INTEGER
	ACCESS					read-only
	STATUS					mandatory
	DESCRIPTION			"PG Outlet 1 watts"
	::= { node21PG 14 }

pgNode21Out1State			OBJECT-TYPE
	SYNTAX					INTEGER { off(1),on(2),cycle(3) }
	ACCESS					read-only
	STATUS					mandatory
	DESCRIPTION			"PG Outlet 1 state"
	::= { node21PG 15 }

pgNode21Out1Cmd				OBJECT-TYPE
	SYNTAX					INTEGER { off(1),on(2),cycle(3) }
	ACCESS					read-write
	STATUS					mandatory
	DESCRIPTION			"PG Outlet 1 command"
	::= { node21PG 16 }

pgNode21Out2Name				OBJECT-TYPE
	SYNTAX					DisplayString
	ACCESS					read-write
	STATUS					mandatory
	DESCRIPTION			"PG Outlet 2 name"
	::= { node21PG 17 }

pgNode21Out2CustVoice	OBJECT-TYPE
	SYNTAX					DisplayString
	ACCESS					read-write
	STATUS					mandatory
	DESCRIPTION			"PG Outlet 2 custom voice"
	::= { node21PG 18 }

pgNode21Out2Volts			OBJECT-TYPE
	SYNTAX					INTEGER
	ACCESS					read-only
	STATUS					mandatory
	DESCRIPTION			"PG Outlet 2 volts"
	::= { node21PG 19 }

pgNode21Out2Amps				OBJECT-TYPE
	SYNTAX					INTEGER
	ACCESS					read-only
	STATUS					mandatory
	DESCRIPTION			"PG Outlet 2 amps"
	::= { node21PG 20 }

pgNode21Out2Watts			OBJECT-TYPE
	SYNTAX					INTEGER
	ACCESS					read-only
	STATUS					mandatory
	DESCRIPTION			"PG Outlet 2 watts"
	::= { node21PG 21 }

pgNode21Out2State			OBJECT-TYPE
	SYNTAX					INTEGER { off(1),on(2),cycle(3) }
	ACCESS					read-only
	STATUS					mandatory
	DESCRIPTION			"PG Outlet 2 state"
	::= { node21PG 22 }

pgNode21Out2Cmd				OBJECT-TYPE
	SYNTAX					INTEGER { off(1),on(2),cycle(3) }
	ACCESS					read-write
	STATUS					mandatory
	DESCRIPTION			"PG Outlet 2 command"
	::= { node21PG 23 }

pgNode21Out3Name				OBJECT-TYPE
	SYNTAX					DisplayString
	ACCESS					read-write
	STATUS					mandatory
	DESCRIPTION			"PG Outlet 3 name"
	::= { node21PG 24 }

pgNode21Out3CustVoice	OBJECT-TYPE
	SYNTAX					DisplayString
	ACCESS					read-write
	STATUS					mandatory
	DESCRIPTION			"PG Outlet 3 custom voice"
	::= { node21PG 25 }

pgNode21Out3Volts			OBJECT-TYPE
	SYNTAX					INTEGER
	ACCESS					read-only
	STATUS					mandatory
	DESCRIPTION			"PG Outlet 3 volts"
	::= { node21PG 26 }

pgNode21Out3Amps				OBJECT-TYPE
	SYNTAX					INTEGER
	ACCESS					read-only
	STATUS					mandatory
	DESCRIPTION			"PG Outlet 3 amps"
	::= { node21PG 27 }

pgNode21Out3Watts			OBJECT-TYPE
	SYNTAX					INTEGER
	ACCESS					read-only
	STATUS					mandatory
	DESCRIPTION			"PG Outlet 3 watts"
	::= { node21PG 28 }

pgNode21Out3State			OBJECT-TYPE
	SYNTAX					INTEGER { off(1),on(2),cycle(3) }
	ACCESS					read-only
	STATUS					mandatory
	DESCRIPTION			"PG Outlet 3 state"
	::= { node21PG 29 }

pgNode21Out3Cmd				OBJECT-TYPE
	SYNTAX					INTEGER { off(1),on(2),cycle(3) }
	ACCESS					read-write
	STATUS					mandatory
	DESCRIPTION			"PG Outlet 3 command"
	::= { node21PG 30 }

pgNode21Out4Name				OBJECT-TYPE
	SYNTAX					DisplayString
	ACCESS					read-write
	STATUS					mandatory
	DESCRIPTION			"PG Outlet 4 name"
	::= { node21PG 31 }

pgNode21Out4CustVoice	OBJECT-TYPE
	SYNTAX					DisplayString
	ACCESS					read-write
	STATUS					mandatory
	DESCRIPTION			"PG Outlet 4 custom voice"
	::= { node21PG 32 }

pgNode21Out4Volts			OBJECT-TYPE
	SYNTAX					INTEGER
	ACCESS					read-only
	STATUS					mandatory
	DESCRIPTION			"PG Outlet 4 volts"
	::= { node21PG 33 }

pgNode21Out4Amps				OBJECT-TYPE
	SYNTAX					INTEGER
	ACCESS					read-only
	STATUS					mandatory
	DESCRIPTION			"PG Outlet 4 amps"
	::= { node21PG 34 }

pgNode21Out4Watts			OBJECT-TYPE
	SYNTAX					INTEGER
	ACCESS					read-only
	STATUS					mandatory
	DESCRIPTION			"PG Outlet 4 watts"
	::= { node21PG 35 }

pgNode21Out4State			OBJECT-TYPE
	SYNTAX					INTEGER { off(1),on(2),cycle(3) }
	ACCESS					read-only
	STATUS					mandatory
	DESCRIPTION			"PG Outlet 4 state"
	::= { node21PG 36 }

pgNode21Out4Cmd				OBJECT-TYPE
	SYNTAX					INTEGER { off(1),on(2),cycle(3) }
	ACCESS					read-write
	STATUS					mandatory
	DESCRIPTION			"PG Outlet 4 command"
	::= { node21PG 37 }

pgNode21Out5Name				OBJECT-TYPE
	SYNTAX					DisplayString
	ACCESS					read-write
	STATUS					mandatory
	DESCRIPTION			"PG Outlet 5 name"
	::= { node21PG 38 }

pgNode21Out5CustVoice	OBJECT-TYPE
	SYNTAX					DisplayString
	ACCESS					read-write
	STATUS					mandatory
	DESCRIPTION			"PG Outlet 5 custom voice"
	::= { node21PG 39 }

pgNode21Out5Volts			OBJECT-TYPE
	SYNTAX					INTEGER
	ACCESS					read-only
	STATUS					mandatory
	DESCRIPTION			"PG Outlet 5 volts"
	::= { node21PG 40 }

pgNode21Out5Amps				OBJECT-TYPE
	SYNTAX					INTEGER
	ACCESS					read-only
	STATUS					mandatory
	DESCRIPTION			"PG Outlet 5 amps"
	::= { node21PG 41 }

pgNode21Out5Watts			OBJECT-TYPE
	SYNTAX					INTEGER
	ACCESS					read-only
	STATUS					mandatory
	DESCRIPTION			"PG Outlet 5 watts"
	::= { node21PG 42 }

pgNode21Out5State			OBJECT-TYPE
	SYNTAX					INTEGER { off(1),on(2),cycle(3) }
	ACCESS					read-only
	STATUS					mandatory
	DESCRIPTION			"PG Outlet 5 state"
	::= { node21PG 43 }

pgNode21Out5Cmd				OBJECT-TYPE
	SYNTAX					INTEGER { off(1),on(2),cycle(3) }
	ACCESS					read-write
	STATUS					mandatory
	DESCRIPTION			"PG Outlet 5 command"
	::= { node21PG 44 }

pgNode21Out6Name				OBJECT-TYPE
	SYNTAX					DisplayString
	ACCESS					read-write
	STATUS					mandatory
	DESCRIPTION			"PG Outlet 6 name"
	::= { node21PG 45 }

pgNode21Out6CustVoice	OBJECT-TYPE
	SYNTAX					DisplayString
	ACCESS					read-write
	STATUS					mandatory
	DESCRIPTION			"PG Outlet 6 custom voice"
	::= { node21PG 46 }

pgNode21Out6Volts			OBJECT-TYPE
	SYNTAX					INTEGER
	ACCESS					read-only
	STATUS					mandatory
	DESCRIPTION			"PG Outlet 6 volts"
	::= { node21PG 47 }

pgNode21Out6Amps				OBJECT-TYPE
	SYNTAX					INTEGER
	ACCESS					read-only
	STATUS					mandatory
	DESCRIPTION			"PG Outlet 6 amps"
	::= { node21PG 48 }

pgNode21Out6Watts			OBJECT-TYPE
	SYNTAX					INTEGER
	ACCESS					read-only
	STATUS					mandatory
	DESCRIPTION			"PG Outlet 6 watts"
	::= { node21PG 49 }

pgNode21Out6State			OBJECT-TYPE
	SYNTAX					INTEGER { off(1),on(2),cycle(3) }
	ACCESS					read-only
	STATUS					mandatory
	DESCRIPTION			"PG Outlet 6 state"
	::= { node21PG 50 }

pgNode21Out6Cmd				OBJECT-TYPE
	SYNTAX					INTEGER { off(1),on(2),cycle(3) }
	ACCESS					read-write
	STATUS					mandatory
	DESCRIPTION			"PG Outlet 6 command"
	::= { node21PG 51 }

pgNode21Out7Name				OBJECT-TYPE
	SYNTAX					DisplayString
	ACCESS					read-write
	STATUS					mandatory
	DESCRIPTION			"PG Outlet 7 name"
	::= { node21PG 52 }

pgNode21Out7CustVoice	OBJECT-TYPE
	SYNTAX					DisplayString
	ACCESS					read-write
	STATUS					mandatory
	DESCRIPTION			"PG Outlet 7 custom voice"
	::= { node21PG 53 }

pgNode21Out7Volts			OBJECT-TYPE
	SYNTAX					INTEGER
	ACCESS					read-only
	STATUS					mandatory
	DESCRIPTION			"PG Outlet 7 volts"
	::= { node21PG 54 }

pgNode21Out7Amps				OBJECT-TYPE
	SYNTAX					INTEGER
	ACCESS					read-only
	STATUS					mandatory
	DESCRIPTION			"PG Outlet 7 amps"
	::= { node21PG 55 }

pgNode21Out7Watts			OBJECT-TYPE
	SYNTAX					INTEGER
	ACCESS					read-only
	STATUS					mandatory
	DESCRIPTION			"PG Outlet 7 watts"
	::= { node21PG 56 }

pgNode21Out7State			OBJECT-TYPE
	SYNTAX					INTEGER { off(1),on(2),cycle(3) }
	ACCESS					read-only
	STATUS					mandatory
	DESCRIPTION			"PG Outlet 7 state"
	::= { node21PG 57 }

pgNode21Out7Cmd				OBJECT-TYPE
	SYNTAX					INTEGER { off(1),on(2),cycle(3) }
	ACCESS					read-write
	STATUS					mandatory
	DESCRIPTION			"PG Outlet 7 command"
	::= { node21PG 58 }

pgNode21Out8Name				OBJECT-TYPE
	SYNTAX					DisplayString
	ACCESS					read-write
	STATUS					mandatory
	DESCRIPTION			"PG Outlet 8 name"
	::= { node21PG 59 }

pgNode21Out8CustVoice	OBJECT-TYPE
	SYNTAX					DisplayString
	ACCESS					read-write
	STATUS					mandatory
	DESCRIPTION			"PG Outlet 8 custom voice"
	::= { node21PG 60 }

pgNode21Out8Volts			OBJECT-TYPE
	SYNTAX					INTEGER
	ACCESS					read-only
	STATUS					mandatory
	DESCRIPTION			"PG Outlet 8 volts"
	::= { node21PG 61 }

pgNode21Out8Amps				OBJECT-TYPE
	SYNTAX					INTEGER
	ACCESS					read-only
	STATUS					mandatory
	DESCRIPTION			"PG Outlet 8 amps"
	::= { node21PG 62 }

pgNode21Out8Watts			OBJECT-TYPE
	SYNTAX					INTEGER
	ACCESS					read-only
	STATUS					mandatory
	DESCRIPTION			"PG Outlet 8 watts"
	::= { node21PG 63 }

pgNode21Out8State			OBJECT-TYPE
	SYNTAX					INTEGER { off(1),on(2),cycle(3) }
	ACCESS					read-only
	STATUS					mandatory
	DESCRIPTION			"PG Outlet 8 state"
	::= { node21PG 64 }

pgNode21Out8Cmd				OBJECT-TYPE
	SYNTAX					INTEGER { off(1),on(2),cycle(3) }
	ACCESS					read-write
	STATUS					mandatory
	DESCRIPTION			"PG Outlet 8 command"
	::= { node21PG 65 }

pgNode22InUse					OBJECT-TYPE
	SYNTAX					INTEGER { false(1),true(2) }
	ACCESS					read-only
	STATUS					mandatory
	DESCRIPTION			"PG in use"
	::= { node22PG 1 }

pgNode22Status					OBJECT-TYPE
	SYNTAX					INTEGER { normal(1),pending(2), trouble(3) }
	ACCESS					read-only
	STATUS					mandatory
	DESCRIPTION			"PG status"
	::= { node22PG 2 }

pgNode22StatusSupport	OBJECT-TYPE
	SYNTAX					INTEGER { true1(1),false(2) }
	ACCESS					read-only
	STATUS					mandatory
	DESCRIPTION			"PG status support level"
	::= { node22PG 3 }

pgNode22Ver						OBJECT-TYPE
	SYNTAX					INTEGER { pgate1(1),pgate2(2) }
	ACCESS					read-only
	STATUS					mandatory
	DESCRIPTION			"PG version"
	::= { node22PG 4 }

pgNode22Volts					OBJECT-TYPE
	SYNTAX					INTEGER
	ACCESS					read-only
	STATUS					mandatory
	DESCRIPTION			"PG voltage"
	::= { node22PG 5 }

pgNode22Amps						OBJECT-TYPE
	SYNTAX					INTEGER
	ACCESS					read-only
	STATUS					mandatory
	DESCRIPTION			"PG amps"
	::= { node22PG 6 }

pgNode22Watts					OBJECT-TYPE
	SYNTAX					INTEGER
	ACCESS					read-only
	STATUS					mandatory
	DESCRIPTION			"PG Watts"
	::= { node22PG 7 }

pgNode22Name						OBJECT-TYPE
	SYNTAX					DisplayString
	ACCESS					read-write
	STATUS					mandatory
	DESCRIPTION			"PG name"
	::= { node22PG 8 }

pgNode22CustVoice			OBJECT-TYPE
	SYNTAX					DisplayString
	ACCESS					read-write
	STATUS					mandatory
	DESCRIPTION			"PG custom voice"
	::= { node22PG 9 }

pgNode22Out1Name				OBJECT-TYPE
	SYNTAX					DisplayString
	ACCESS					read-write
	STATUS					mandatory
	DESCRIPTION			"PG Outlet 1 name"
	::= { node22PG 10 }

pgNode22Out1CustVoice	OBJECT-TYPE
	SYNTAX					DisplayString
	ACCESS					read-write
	STATUS					mandatory
	DESCRIPTION			"PG Outlet 1 custom voice"
	::= { node22PG 11 }

pgNode22Out1Volts			OBJECT-TYPE
	SYNTAX					INTEGER
	ACCESS					read-only
	STATUS					mandatory
	DESCRIPTION			"PG Outlet 1 volts"
	::= { node22PG 12 }

pgNode22Out1Amps				OBJECT-TYPE
	SYNTAX					INTEGER
	ACCESS					read-only
	STATUS					mandatory
	DESCRIPTION			"PG Outlet 1 amps"
	::= { node22PG 13 }

pgNode22Out1Watts			OBJECT-TYPE
	SYNTAX					INTEGER
	ACCESS					read-only
	STATUS					mandatory
	DESCRIPTION			"PG Outlet 1 watts"
	::= { node22PG 14 }

pgNode22Out1State			OBJECT-TYPE
	SYNTAX					INTEGER { off(1),on(2),cycle(3) }
	ACCESS					read-only
	STATUS					mandatory
	DESCRIPTION			"PG Outlet 1 state"
	::= { node22PG 15 }

pgNode22Out1Cmd				OBJECT-TYPE
	SYNTAX					INTEGER { off(1),on(2),cycle(3) }
	ACCESS					read-write
	STATUS					mandatory
	DESCRIPTION			"PG Outlet 1 command"
	::= { node22PG 16 }

pgNode22Out2Name				OBJECT-TYPE
	SYNTAX					DisplayString
	ACCESS					read-write
	STATUS					mandatory
	DESCRIPTION			"PG Outlet 2 name"
	::= { node22PG 17 }

pgNode22Out2CustVoice	OBJECT-TYPE
	SYNTAX					DisplayString
	ACCESS					read-write
	STATUS					mandatory
	DESCRIPTION			"PG Outlet 2 custom voice"
	::= { node22PG 18 }

pgNode22Out2Volts			OBJECT-TYPE
	SYNTAX					INTEGER
	ACCESS					read-only
	STATUS					mandatory
	DESCRIPTION			"PG Outlet 2 volts"
	::= { node22PG 19 }

pgNode22Out2Amps				OBJECT-TYPE
	SYNTAX					INTEGER
	ACCESS					read-only
	STATUS					mandatory
	DESCRIPTION			"PG Outlet 2 amps"
	::= { node22PG 20 }

pgNode22Out2Watts			OBJECT-TYPE
	SYNTAX					INTEGER
	ACCESS					read-only
	STATUS					mandatory
	DESCRIPTION			"PG Outlet 2 watts"
	::= { node22PG 21 }

pgNode22Out2State			OBJECT-TYPE
	SYNTAX					INTEGER { off(1),on(2),cycle(3) }
	ACCESS					read-only
	STATUS					mandatory
	DESCRIPTION			"PG Outlet 2 state"
	::= { node22PG 22 }

pgNode22Out2Cmd				OBJECT-TYPE
	SYNTAX					INTEGER { off(1),on(2),cycle(3) }
	ACCESS					read-write
	STATUS					mandatory
	DESCRIPTION			"PG Outlet 2 command"
	::= { node22PG 23 }

pgNode22Out3Name				OBJECT-TYPE
	SYNTAX					DisplayString
	ACCESS					read-write
	STATUS					mandatory
	DESCRIPTION			"PG Outlet 3 name"
	::= { node22PG 24 }

pgNode22Out3CustVoice	OBJECT-TYPE
	SYNTAX					DisplayString
	ACCESS					read-write
	STATUS					mandatory
	DESCRIPTION			"PG Outlet 3 custom voice"
	::= { node22PG 25 }

pgNode22Out3Volts			OBJECT-TYPE
	SYNTAX					INTEGER
	ACCESS					read-only
	STATUS					mandatory
	DESCRIPTION			"PG Outlet 3 volts"
	::= { node22PG 26 }

pgNode22Out3Amps				OBJECT-TYPE
	SYNTAX					INTEGER
	ACCESS					read-only
	STATUS					mandatory
	DESCRIPTION			"PG Outlet 3 amps"
	::= { node22PG 27 }

pgNode22Out3Watts			OBJECT-TYPE
	SYNTAX					INTEGER
	ACCESS					read-only
	STATUS					mandatory
	DESCRIPTION			"PG Outlet 3 watts"
	::= { node22PG 28 }

pgNode22Out3State			OBJECT-TYPE
	SYNTAX					INTEGER { off(1),on(2),cycle(3) }
	ACCESS					read-only
	STATUS					mandatory
	DESCRIPTION			"PG Outlet 3 state"
	::= { node22PG 29 }

pgNode22Out3Cmd				OBJECT-TYPE
	SYNTAX					INTEGER { off(1),on(2),cycle(3) }
	ACCESS					read-write
	STATUS					mandatory
	DESCRIPTION			"PG Outlet 3 command"
	::= { node22PG 30 }

pgNode22Out4Name				OBJECT-TYPE
	SYNTAX					DisplayString
	ACCESS					read-write
	STATUS					mandatory
	DESCRIPTION			"PG Outlet 4 name"
	::= { node22PG 31 }

pgNode22Out4CustVoice	OBJECT-TYPE
	SYNTAX					DisplayString
	ACCESS					read-write
	STATUS					mandatory
	DESCRIPTION			"PG Outlet 4 custom voice"
	::= { node22PG 32 }

pgNode22Out4Volts			OBJECT-TYPE
	SYNTAX					INTEGER
	ACCESS					read-only
	STATUS					mandatory
	DESCRIPTION			"PG Outlet 4 volts"
	::= { node22PG 33 }

pgNode22Out4Amps				OBJECT-TYPE
	SYNTAX					INTEGER
	ACCESS					read-only
	STATUS					mandatory
	DESCRIPTION			"PG Outlet 4 amps"
	::= { node22PG 34 }

pgNode22Out4Watts			OBJECT-TYPE
	SYNTAX					INTEGER
	ACCESS					read-only
	STATUS					mandatory
	DESCRIPTION			"PG Outlet 4 watts"
	::= { node22PG 35 }

pgNode22Out4State			OBJECT-TYPE
	SYNTAX					INTEGER { off(1),on(2),cycle(3) }
	ACCESS					read-only
	STATUS					mandatory
	DESCRIPTION			"PG Outlet 4 state"
	::= { node22PG 36 }

pgNode22Out4Cmd				OBJECT-TYPE
	SYNTAX					INTEGER { off(1),on(2),cycle(3) }
	ACCESS					read-write
	STATUS					mandatory
	DESCRIPTION			"PG Outlet 4 command"
	::= { node22PG 37 }

pgNode22Out5Name				OBJECT-TYPE
	SYNTAX					DisplayString
	ACCESS					read-write
	STATUS					mandatory
	DESCRIPTION			"PG Outlet 5 name"
	::= { node22PG 38 }

pgNode22Out5CustVoice	OBJECT-TYPE
	SYNTAX					DisplayString
	ACCESS					read-write
	STATUS					mandatory
	DESCRIPTION			"PG Outlet 5 custom voice"
	::= { node22PG 39 }

pgNode22Out5Volts			OBJECT-TYPE
	SYNTAX					INTEGER
	ACCESS					read-only
	STATUS					mandatory
	DESCRIPTION			"PG Outlet 5 volts"
	::= { node22PG 40 }

pgNode22Out5Amps				OBJECT-TYPE
	SYNTAX					INTEGER
	ACCESS					read-only
	STATUS					mandatory
	DESCRIPTION			"PG Outlet 5 amps"
	::= { node22PG 41 }

pgNode22Out5Watts			OBJECT-TYPE
	SYNTAX					INTEGER
	ACCESS					read-only
	STATUS					mandatory
	DESCRIPTION			"PG Outlet 5 watts"
	::= { node22PG 42 }

pgNode22Out5State			OBJECT-TYPE
	SYNTAX					INTEGER { off(1),on(2),cycle(3) }
	ACCESS					read-only
	STATUS					mandatory
	DESCRIPTION			"PG Outlet 5 state"
	::= { node22PG 43 }

pgNode22Out5Cmd				OBJECT-TYPE
	SYNTAX					INTEGER { off(1),on(2),cycle(3) }
	ACCESS					read-write
	STATUS					mandatory
	DESCRIPTION			"PG Outlet 5 command"
	::= { node22PG 44 }

pgNode22Out6Name				OBJECT-TYPE
	SYNTAX					DisplayString
	ACCESS					read-write
	STATUS					mandatory
	DESCRIPTION			"PG Outlet 6 name"
	::= { node22PG 45 }

pgNode22Out6CustVoice	OBJECT-TYPE
	SYNTAX					DisplayString
	ACCESS					read-write
	STATUS					mandatory
	DESCRIPTION			"PG Outlet 6 custom voice"
	::= { node22PG 46 }

pgNode22Out6Volts			OBJECT-TYPE
	SYNTAX					INTEGER
	ACCESS					read-only
	STATUS					mandatory
	DESCRIPTION			"PG Outlet 6 volts"
	::= { node22PG 47 }

pgNode22Out6Amps				OBJECT-TYPE
	SYNTAX					INTEGER
	ACCESS					read-only
	STATUS					mandatory
	DESCRIPTION			"PG Outlet 6 amps"
	::= { node22PG 48 }

pgNode22Out6Watts			OBJECT-TYPE
	SYNTAX					INTEGER
	ACCESS					read-only
	STATUS					mandatory
	DESCRIPTION			"PG Outlet 6 watts"
	::= { node22PG 49 }

pgNode22Out6State			OBJECT-TYPE
	SYNTAX					INTEGER { off(1),on(2),cycle(3) }
	ACCESS					read-only
	STATUS					mandatory
	DESCRIPTION			"PG Outlet 6 state"
	::= { node22PG 50 }

pgNode22Out6Cmd				OBJECT-TYPE
	SYNTAX					INTEGER { off(1),on(2),cycle(3) }
	ACCESS					read-write
	STATUS					mandatory
	DESCRIPTION			"PG Outlet 6 command"
	::= { node22PG 51 }

pgNode22Out7Name				OBJECT-TYPE
	SYNTAX					DisplayString
	ACCESS					read-write
	STATUS					mandatory
	DESCRIPTION			"PG Outlet 7 name"
	::= { node22PG 52 }

pgNode22Out7CustVoice	OBJECT-TYPE
	SYNTAX					DisplayString
	ACCESS					read-write
	STATUS					mandatory
	DESCRIPTION			"PG Outlet 7 custom voice"
	::= { node22PG 53 }

pgNode22Out7Volts			OBJECT-TYPE
	SYNTAX					INTEGER
	ACCESS					read-only
	STATUS					mandatory
	DESCRIPTION			"PG Outlet 7 volts"
	::= { node22PG 54 }

pgNode22Out7Amps				OBJECT-TYPE
	SYNTAX					INTEGER
	ACCESS					read-only
	STATUS					mandatory
	DESCRIPTION			"PG Outlet 7 amps"
	::= { node22PG 55 }

pgNode22Out7Watts			OBJECT-TYPE
	SYNTAX					INTEGER
	ACCESS					read-only
	STATUS					mandatory
	DESCRIPTION			"PG Outlet 7 watts"
	::= { node22PG 56 }

pgNode22Out7State			OBJECT-TYPE
	SYNTAX					INTEGER { off(1),on(2),cycle(3) }
	ACCESS					read-only
	STATUS					mandatory
	DESCRIPTION			"PG Outlet 7 state"
	::= { node22PG 57 }

pgNode22Out7Cmd				OBJECT-TYPE
	SYNTAX					INTEGER { off(1),on(2),cycle(3) }
	ACCESS					read-write
	STATUS					mandatory
	DESCRIPTION			"PG Outlet 7 command"
	::= { node22PG 58 }

pgNode22Out8Name				OBJECT-TYPE
	SYNTAX					DisplayString
	ACCESS					read-write
	STATUS					mandatory
	DESCRIPTION			"PG Outlet 8 name"
	::= { node22PG 59 }

pgNode22Out8CustVoice	OBJECT-TYPE
	SYNTAX					DisplayString
	ACCESS					read-write
	STATUS					mandatory
	DESCRIPTION			"PG Outlet 8 custom voice"
	::= { node22PG 60 }

pgNode22Out8Volts			OBJECT-TYPE
	SYNTAX					INTEGER
	ACCESS					read-only
	STATUS					mandatory
	DESCRIPTION			"PG Outlet 8 volts"
	::= { node22PG 61 }

pgNode22Out8Amps				OBJECT-TYPE
	SYNTAX					INTEGER
	ACCESS					read-only
	STATUS					mandatory
	DESCRIPTION			"PG Outlet 8 amps"
	::= { node22PG 62 }

pgNode22Out8Watts			OBJECT-TYPE
	SYNTAX					INTEGER
	ACCESS					read-only
	STATUS					mandatory
	DESCRIPTION			"PG Outlet 8 watts"
	::= { node22PG 63 }

pgNode22Out8State			OBJECT-TYPE
	SYNTAX					INTEGER { off(1),on(2),cycle(3) }
	ACCESS					read-only
	STATUS					mandatory
	DESCRIPTION			"PG Outlet 8 state"
	::= { node22PG 64 }

pgNode22Out8Cmd				OBJECT-TYPE
	SYNTAX					INTEGER { off(1),on(2),cycle(3) }
	ACCESS					read-write
	STATUS					mandatory
	DESCRIPTION			"PG Outlet 8 command"
	::= { node22PG 65 }

pgNode23InUse					OBJECT-TYPE
	SYNTAX					INTEGER { false(1),true(2) }
	ACCESS					read-only
	STATUS					mandatory
	DESCRIPTION			"PG in use"
	::= { node23PG 1 }

pgNode23Status					OBJECT-TYPE
	SYNTAX					INTEGER { normal(1),pending(2), trouble(3) }
	ACCESS					read-only
	STATUS					mandatory
	DESCRIPTION			"PG status"
	::= { node23PG 2 }

pgNode23StatusSupport	OBJECT-TYPE
	SYNTAX					INTEGER { true1(1),false(2) }
	ACCESS					read-only
	STATUS					mandatory
	DESCRIPTION			"PG status support level"
	::= { node23PG 3 }

pgNode23Ver						OBJECT-TYPE
	SYNTAX					INTEGER { pgate1(1),pgate2(2) }
	ACCESS					read-only
	STATUS					mandatory
	DESCRIPTION			"PG version"
	::= { node23PG 4 }

pgNode23Volts					OBJECT-TYPE
	SYNTAX					INTEGER
	ACCESS					read-only
	STATUS					mandatory
	DESCRIPTION			"PG voltage"
	::= { node23PG 5 }

pgNode23Amps						OBJECT-TYPE
	SYNTAX					INTEGER
	ACCESS					read-only
	STATUS					mandatory
	DESCRIPTION			"PG amps"
	::= { node23PG 6 }

pgNode23Watts					OBJECT-TYPE
	SYNTAX					INTEGER
	ACCESS					read-only
	STATUS					mandatory
	DESCRIPTION			"PG Watts"
	::= { node23PG 7 }

pgNode23Name						OBJECT-TYPE
	SYNTAX					DisplayString
	ACCESS					read-write
	STATUS					mandatory
	DESCRIPTION			"PG name"
	::= { node23PG 8 }

pgNode23CustVoice			OBJECT-TYPE
	SYNTAX					DisplayString
	ACCESS					read-write
	STATUS					mandatory
	DESCRIPTION			"PG custom voice"
	::= { node23PG 9 }

pgNode23Out1Name				OBJECT-TYPE
	SYNTAX					DisplayString
	ACCESS					read-write
	STATUS					mandatory
	DESCRIPTION			"PG Outlet 1 name"
	::= { node23PG 10 }

pgNode23Out1CustVoice	OBJECT-TYPE
	SYNTAX					DisplayString
	ACCESS					read-write
	STATUS					mandatory
	DESCRIPTION			"PG Outlet 1 custom voice"
	::= { node23PG 11 }

pgNode23Out1Volts			OBJECT-TYPE
	SYNTAX					INTEGER
	ACCESS					read-only
	STATUS					mandatory
	DESCRIPTION			"PG Outlet 1 volts"
	::= { node23PG 12 }

pgNode23Out1Amps				OBJECT-TYPE
	SYNTAX					INTEGER
	ACCESS					read-only
	STATUS					mandatory
	DESCRIPTION			"PG Outlet 1 amps"
	::= { node23PG 13 }

pgNode23Out1Watts			OBJECT-TYPE
	SYNTAX					INTEGER
	ACCESS					read-only
	STATUS					mandatory
	DESCRIPTION			"PG Outlet 1 watts"
	::= { node23PG 14 }

pgNode23Out1State			OBJECT-TYPE
	SYNTAX					INTEGER { off(1),on(2),cycle(3) }
	ACCESS					read-only
	STATUS					mandatory
	DESCRIPTION			"PG Outlet 1 state"
	::= { node23PG 15 }

pgNode23Out1Cmd				OBJECT-TYPE
	SYNTAX					INTEGER { off(1),on(2),cycle(3) }
	ACCESS					read-write
	STATUS					mandatory
	DESCRIPTION			"PG Outlet 1 command"
	::= { node23PG 16 }

pgNode23Out2Name				OBJECT-TYPE
	SYNTAX					DisplayString
	ACCESS					read-write
	STATUS					mandatory
	DESCRIPTION			"PG Outlet 2 name"
	::= { node23PG 17 }

pgNode23Out2CustVoice	OBJECT-TYPE
	SYNTAX					DisplayString
	ACCESS					read-write
	STATUS					mandatory
	DESCRIPTION			"PG Outlet 2 custom voice"
	::= { node23PG 18 }

pgNode23Out2Volts			OBJECT-TYPE
	SYNTAX					INTEGER
	ACCESS					read-only
	STATUS					mandatory
	DESCRIPTION			"PG Outlet 2 volts"
	::= { node23PG 19 }

pgNode23Out2Amps				OBJECT-TYPE
	SYNTAX					INTEGER
	ACCESS					read-only
	STATUS					mandatory
	DESCRIPTION			"PG Outlet 2 amps"
	::= { node23PG 20 }

pgNode23Out2Watts			OBJECT-TYPE
	SYNTAX					INTEGER
	ACCESS					read-only
	STATUS					mandatory
	DESCRIPTION			"PG Outlet 2 watts"
	::= { node23PG 21 }

pgNode23Out2State			OBJECT-TYPE
	SYNTAX					INTEGER { off(1),on(2),cycle(3) }
	ACCESS					read-only
	STATUS					mandatory
	DESCRIPTION			"PG Outlet 2 state"
	::= { node23PG 22 }

pgNode23Out2Cmd				OBJECT-TYPE
	SYNTAX					INTEGER { off(1),on(2),cycle(3) }
	ACCESS					read-write
	STATUS					mandatory
	DESCRIPTION			"PG Outlet 2 command"
	::= { node23PG 23 }

pgNode23Out3Name				OBJECT-TYPE
	SYNTAX					DisplayString
	ACCESS					read-write
	STATUS					mandatory
	DESCRIPTION			"PG Outlet 3 name"
	::= { node23PG 24 }

pgNode23Out3CustVoice	OBJECT-TYPE
	SYNTAX					DisplayString
	ACCESS					read-write
	STATUS					mandatory
	DESCRIPTION			"PG Outlet 3 custom voice"
	::= { node23PG 25 }

pgNode23Out3Volts			OBJECT-TYPE
	SYNTAX					INTEGER
	ACCESS					read-only
	STATUS					mandatory
	DESCRIPTION			"PG Outlet 3 volts"
	::= { node23PG 26 }

pgNode23Out3Amps				OBJECT-TYPE
	SYNTAX					INTEGER
	ACCESS					read-only
	STATUS					mandatory
	DESCRIPTION			"PG Outlet 3 amps"
	::= { node23PG 27 }

pgNode23Out3Watts			OBJECT-TYPE
	SYNTAX					INTEGER
	ACCESS					read-only
	STATUS					mandatory
	DESCRIPTION			"PG Outlet 3 watts"
	::= { node23PG 28 }

pgNode23Out3State			OBJECT-TYPE
	SYNTAX					INTEGER { off(1),on(2),cycle(3) }
	ACCESS					read-only
	STATUS					mandatory
	DESCRIPTION			"PG Outlet 3 state"
	::= { node23PG 29 }

pgNode23Out3Cmd				OBJECT-TYPE
	SYNTAX					INTEGER { off(1),on(2),cycle(3) }
	ACCESS					read-write
	STATUS					mandatory
	DESCRIPTION			"PG Outlet 3 command"
	::= { node23PG 30 }

pgNode23Out4Name				OBJECT-TYPE
	SYNTAX					DisplayString
	ACCESS					read-write
	STATUS					mandatory
	DESCRIPTION			"PG Outlet 4 name"
	::= { node23PG 31 }

pgNode23Out4CustVoice	OBJECT-TYPE
	SYNTAX					DisplayString
	ACCESS					read-write
	STATUS					mandatory
	DESCRIPTION			"PG Outlet 4 custom voice"
	::= { node23PG 32 }

pgNode23Out4Volts			OBJECT-TYPE
	SYNTAX					INTEGER
	ACCESS					read-only
	STATUS					mandatory
	DESCRIPTION			"PG Outlet 4 volts"
	::= { node23PG 33 }

pgNode23Out4Amps				OBJECT-TYPE
	SYNTAX					INTEGER
	ACCESS					read-only
	STATUS					mandatory
	DESCRIPTION			"PG Outlet 4 amps"
	::= { node23PG 34 }

pgNode23Out4Watts			OBJECT-TYPE
	SYNTAX					INTEGER
	ACCESS					read-only
	STATUS					mandatory
	DESCRIPTION			"PG Outlet 4 watts"
	::= { node23PG 35 }

pgNode23Out4State			OBJECT-TYPE
	SYNTAX					INTEGER { off(1),on(2),cycle(3) }
	ACCESS					read-only
	STATUS					mandatory
	DESCRIPTION			"PG Outlet 4 state"
	::= { node23PG 36 }

pgNode23Out4Cmd				OBJECT-TYPE
	SYNTAX					INTEGER { off(1),on(2),cycle(3) }
	ACCESS					read-write
	STATUS					mandatory
	DESCRIPTION			"PG Outlet 4 command"
	::= { node23PG 37 }

pgNode23Out5Name				OBJECT-TYPE
	SYNTAX					DisplayString
	ACCESS					read-write
	STATUS					mandatory
	DESCRIPTION			"PG Outlet 5 name"
	::= { node23PG 38 }

pgNode23Out5CustVoice	OBJECT-TYPE
	SYNTAX					DisplayString
	ACCESS					read-write
	STATUS					mandatory
	DESCRIPTION			"PG Outlet 5 custom voice"
	::= { node23PG 39 }

pgNode23Out5Volts			OBJECT-TYPE
	SYNTAX					INTEGER
	ACCESS					read-only
	STATUS					mandatory
	DESCRIPTION			"PG Outlet 5 volts"
	::= { node23PG 40 }

pgNode23Out5Amps				OBJECT-TYPE
	SYNTAX					INTEGER
	ACCESS					read-only
	STATUS					mandatory
	DESCRIPTION			"PG Outlet 5 amps"
	::= { node23PG 41 }

pgNode23Out5Watts			OBJECT-TYPE
	SYNTAX					INTEGER
	ACCESS					read-only
	STATUS					mandatory
	DESCRIPTION			"PG Outlet 5 watts"
	::= { node23PG 42 }

pgNode23Out5State			OBJECT-TYPE
	SYNTAX					INTEGER { off(1),on(2),cycle(3) }
	ACCESS					read-only
	STATUS					mandatory
	DESCRIPTION			"PG Outlet 5 state"
	::= { node23PG 43 }

pgNode23Out5Cmd				OBJECT-TYPE
	SYNTAX					INTEGER { off(1),on(2),cycle(3) }
	ACCESS					read-write
	STATUS					mandatory
	DESCRIPTION			"PG Outlet 5 command"
	::= { node23PG 44 }

pgNode23Out6Name				OBJECT-TYPE
	SYNTAX					DisplayString
	ACCESS					read-write
	STATUS					mandatory
	DESCRIPTION			"PG Outlet 6 name"
	::= { node23PG 45 }

pgNode23Out6CustVoice	OBJECT-TYPE
	SYNTAX					DisplayString
	ACCESS					read-write
	STATUS					mandatory
	DESCRIPTION			"PG Outlet 6 custom voice"
	::= { node23PG 46 }

pgNode23Out6Volts			OBJECT-TYPE
	SYNTAX					INTEGER
	ACCESS					read-only
	STATUS					mandatory
	DESCRIPTION			"PG Outlet 6 volts"
	::= { node23PG 47 }

pgNode23Out6Amps				OBJECT-TYPE
	SYNTAX					INTEGER
	ACCESS					read-only
	STATUS					mandatory
	DESCRIPTION			"PG Outlet 6 amps"
	::= { node23PG 48 }

pgNode23Out6Watts			OBJECT-TYPE
	SYNTAX					INTEGER
	ACCESS					read-only
	STATUS					mandatory
	DESCRIPTION			"PG Outlet 6 watts"
	::= { node23PG 49 }

pgNode23Out6State			OBJECT-TYPE
	SYNTAX					INTEGER { off(1),on(2),cycle(3) }
	ACCESS					read-only
	STATUS					mandatory
	DESCRIPTION			"PG Outlet 6 state"
	::= { node23PG 50 }

pgNode23Out6Cmd				OBJECT-TYPE
	SYNTAX					INTEGER { off(1),on(2),cycle(3) }
	ACCESS					read-write
	STATUS					mandatory
	DESCRIPTION			"PG Outlet 6 command"
	::= { node23PG 51 }

pgNode23Out7Name				OBJECT-TYPE
	SYNTAX					DisplayString
	ACCESS					read-write
	STATUS					mandatory
	DESCRIPTION			"PG Outlet 7 name"
	::= { node23PG 52 }

pgNode23Out7CustVoice	OBJECT-TYPE
	SYNTAX					DisplayString
	ACCESS					read-write
	STATUS					mandatory
	DESCRIPTION			"PG Outlet 7 custom voice"
	::= { node23PG 53 }

pgNode23Out7Volts			OBJECT-TYPE
	SYNTAX					INTEGER
	ACCESS					read-only
	STATUS					mandatory
	DESCRIPTION			"PG Outlet 7 volts"
	::= { node23PG 54 }

pgNode23Out7Amps				OBJECT-TYPE
	SYNTAX					INTEGER
	ACCESS					read-only
	STATUS					mandatory
	DESCRIPTION			"PG Outlet 7 amps"
	::= { node23PG 55 }

pgNode23Out7Watts			OBJECT-TYPE
	SYNTAX					INTEGER
	ACCESS					read-only
	STATUS					mandatory
	DESCRIPTION			"PG Outlet 7 watts"
	::= { node23PG 56 }

pgNode23Out7State			OBJECT-TYPE
	SYNTAX					INTEGER { off(1),on(2),cycle(3) }
	ACCESS					read-only
	STATUS					mandatory
	DESCRIPTION			"PG Outlet 7 state"
	::= { node23PG 57 }

pgNode23Out7Cmd				OBJECT-TYPE
	SYNTAX					INTEGER { off(1),on(2),cycle(3) }
	ACCESS					read-write
	STATUS					mandatory
	DESCRIPTION			"PG Outlet 7 command"
	::= { node23PG 58 }

pgNode23Out8Name				OBJECT-TYPE
	SYNTAX					DisplayString
	ACCESS					read-write
	STATUS					mandatory
	DESCRIPTION			"PG Outlet 8 name"
	::= { node23PG 59 }

pgNode23Out8CustVoice	OBJECT-TYPE
	SYNTAX					DisplayString
	ACCESS					read-write
	STATUS					mandatory
	DESCRIPTION			"PG Outlet 8 custom voice"
	::= { node23PG 60 }

pgNode23Out8Volts			OBJECT-TYPE
	SYNTAX					INTEGER
	ACCESS					read-only
	STATUS					mandatory
	DESCRIPTION			"PG Outlet 8 volts"
	::= { node23PG 61 }

pgNode23Out8Amps				OBJECT-TYPE
	SYNTAX					INTEGER
	ACCESS					read-only
	STATUS					mandatory
	DESCRIPTION			"PG Outlet 8 amps"
	::= { node23PG 62 }

pgNode23Out8Watts			OBJECT-TYPE
	SYNTAX					INTEGER
	ACCESS					read-only
	STATUS					mandatory
	DESCRIPTION			"PG Outlet 8 watts"
	::= { node23PG 63 }

pgNode23Out8State			OBJECT-TYPE
	SYNTAX					INTEGER { off(1),on(2),cycle(3) }
	ACCESS					read-only
	STATUS					mandatory
	DESCRIPTION			"PG Outlet 8 state"
	::= { node23PG 64 }

pgNode23Out8Cmd				OBJECT-TYPE
	SYNTAX					INTEGER { off(1),on(2),cycle(3) }
	ACCESS					read-write
	STATUS					mandatory
	DESCRIPTION			"PG Outlet 8 command"
	::= { node23PG 65 }

pgNode24InUse					OBJECT-TYPE
	SYNTAX					INTEGER { false(1),true(2) }
	ACCESS					read-only
	STATUS					mandatory
	DESCRIPTION			"PG in use"
	::= { node24PG 1 }

pgNode24Status					OBJECT-TYPE
	SYNTAX					INTEGER { normal(1),pending(2), trouble(3) }
	ACCESS					read-only
	STATUS					mandatory
	DESCRIPTION			"PG status"
	::= { node24PG 2 }

pgNode24StatusSupport	OBJECT-TYPE
	SYNTAX					INTEGER { true1(1),false(2) }
	ACCESS					read-only
	STATUS					mandatory
	DESCRIPTION			"PG status support level"
	::= { node24PG 3 }

pgNode24Ver						OBJECT-TYPE
	SYNTAX					INTEGER { pgate1(1),pgate2(2) }
	ACCESS					read-only
	STATUS					mandatory
	DESCRIPTION			"PG version"
	::= { node24PG 4 }

pgNode24Volts					OBJECT-TYPE
	SYNTAX					INTEGER
	ACCESS					read-only
	STATUS					mandatory
	DESCRIPTION			"PG voltage"
	::= { node24PG 5 }

pgNode24Amps						OBJECT-TYPE
	SYNTAX					INTEGER
	ACCESS					read-only
	STATUS					mandatory
	DESCRIPTION			"PG amps"
	::= { node24PG 6 }

pgNode24Watts					OBJECT-TYPE
	SYNTAX					INTEGER
	ACCESS					read-only
	STATUS					mandatory
	DESCRIPTION			"PG Watts"
	::= { node24PG 7 }

pgNode24Name						OBJECT-TYPE
	SYNTAX					DisplayString
	ACCESS					read-write
	STATUS					mandatory
	DESCRIPTION			"PG name"
	::= { node24PG 8 }

pgNode24CustVoice			OBJECT-TYPE
	SYNTAX					DisplayString
	ACCESS					read-write
	STATUS					mandatory
	DESCRIPTION			"PG custom voice"
	::= { node24PG 9 }

pgNode24Out1Name				OBJECT-TYPE
	SYNTAX					DisplayString
	ACCESS					read-write
	STATUS					mandatory
	DESCRIPTION			"PG Outlet 1 name"
	::= { node24PG 10 }

pgNode24Out1CustVoice	OBJECT-TYPE
	SYNTAX					DisplayString
	ACCESS					read-write
	STATUS					mandatory
	DESCRIPTION			"PG Outlet 1 custom voice"
	::= { node24PG 11 }

pgNode24Out1Volts			OBJECT-TYPE
	SYNTAX					INTEGER
	ACCESS					read-only
	STATUS					mandatory
	DESCRIPTION			"PG Outlet 1 volts"
	::= { node24PG 12 }

pgNode24Out1Amps				OBJECT-TYPE
	SYNTAX					INTEGER
	ACCESS					read-only
	STATUS					mandatory
	DESCRIPTION			"PG Outlet 1 amps"
	::= { node24PG 13 }

pgNode24Out1Watts			OBJECT-TYPE
	SYNTAX					INTEGER
	ACCESS					read-only
	STATUS					mandatory
	DESCRIPTION			"PG Outlet 1 watts"
	::= { node24PG 14 }

pgNode24Out1State			OBJECT-TYPE
	SYNTAX					INTEGER { off(1),on(2),cycle(3) }
	ACCESS					read-only
	STATUS					mandatory
	DESCRIPTION			"PG Outlet 1 state"
	::= { node24PG 15 }

pgNode24Out1Cmd				OBJECT-TYPE
	SYNTAX					INTEGER { off(1),on(2),cycle(3) }
	ACCESS					read-write
	STATUS					mandatory
	DESCRIPTION			"PG Outlet 1 command"
	::= { node24PG 16 }

pgNode24Out2Name				OBJECT-TYPE
	SYNTAX					DisplayString
	ACCESS					read-write
	STATUS					mandatory
	DESCRIPTION			"PG Outlet 2 name"
	::= { node24PG 17 }

pgNode24Out2CustVoice	OBJECT-TYPE
	SYNTAX					DisplayString
	ACCESS					read-write
	STATUS					mandatory
	DESCRIPTION			"PG Outlet 2 custom voice"
	::= { node24PG 18 }

pgNode24Out2Volts			OBJECT-TYPE
	SYNTAX					INTEGER
	ACCESS					read-only
	STATUS					mandatory
	DESCRIPTION			"PG Outlet 2 volts"
	::= { node24PG 19 }

pgNode24Out2Amps				OBJECT-TYPE
	SYNTAX					INTEGER
	ACCESS					read-only
	STATUS					mandatory
	DESCRIPTION			"PG Outlet 2 amps"
	::= { node24PG 20 }

pgNode24Out2Watts			OBJECT-TYPE
	SYNTAX					INTEGER
	ACCESS					read-only
	STATUS					mandatory
	DESCRIPTION			"PG Outlet 2 watts"
	::= { node24PG 21 }

pgNode24Out2State			OBJECT-TYPE
	SYNTAX					INTEGER { off(1),on(2),cycle(3) }
	ACCESS					read-only
	STATUS					mandatory
	DESCRIPTION			"PG Outlet 2 state"
	::= { node24PG 22 }

pgNode24Out2Cmd				OBJECT-TYPE
	SYNTAX					INTEGER { off(1),on(2),cycle(3) }
	ACCESS					read-write
	STATUS					mandatory
	DESCRIPTION			"PG Outlet 2 command"
	::= { node24PG 23 }

pgNode24Out3Name				OBJECT-TYPE
	SYNTAX					DisplayString
	ACCESS					read-write
	STATUS					mandatory
	DESCRIPTION			"PG Outlet 3 name"
	::= { node24PG 24 }

pgNode24Out3CustVoice	OBJECT-TYPE
	SYNTAX					DisplayString
	ACCESS					read-write
	STATUS					mandatory
	DESCRIPTION			"PG Outlet 3 custom voice"
	::= { node24PG 25 }

pgNode24Out3Volts			OBJECT-TYPE
	SYNTAX					INTEGER
	ACCESS					read-only
	STATUS					mandatory
	DESCRIPTION			"PG Outlet 3 volts"
	::= { node24PG 26 }

pgNode24Out3Amps				OBJECT-TYPE
	SYNTAX					INTEGER
	ACCESS					read-only
	STATUS					mandatory
	DESCRIPTION			"PG Outlet 3 amps"
	::= { node24PG 27 }

pgNode24Out3Watts			OBJECT-TYPE
	SYNTAX					INTEGER
	ACCESS					read-only
	STATUS					mandatory
	DESCRIPTION			"PG Outlet 3 watts"
	::= { node24PG 28 }

pgNode24Out3State			OBJECT-TYPE
	SYNTAX					INTEGER { off(1),on(2),cycle(3) }
	ACCESS					read-only
	STATUS					mandatory
	DESCRIPTION			"PG Outlet 3 state"
	::= { node24PG 29 }

pgNode24Out3Cmd				OBJECT-TYPE
	SYNTAX					INTEGER { off(1),on(2),cycle(3) }
	ACCESS					read-write
	STATUS					mandatory
	DESCRIPTION			"PG Outlet 3 command"
	::= { node24PG 30 }

pgNode24Out4Name				OBJECT-TYPE
	SYNTAX					DisplayString
	ACCESS					read-write
	STATUS					mandatory
	DESCRIPTION			"PG Outlet 4 name"
	::= { node24PG 31 }

pgNode24Out4CustVoice	OBJECT-TYPE
	SYNTAX					DisplayString
	ACCESS					read-write
	STATUS					mandatory
	DESCRIPTION			"PG Outlet 4 custom voice"
	::= { node24PG 32 }

pgNode24Out4Volts			OBJECT-TYPE
	SYNTAX					INTEGER
	ACCESS					read-only
	STATUS					mandatory
	DESCRIPTION			"PG Outlet 4 volts"
	::= { node24PG 33 }

pgNode24Out4Amps				OBJECT-TYPE
	SYNTAX					INTEGER
	ACCESS					read-only
	STATUS					mandatory
	DESCRIPTION			"PG Outlet 4 amps"
	::= { node24PG 34 }

pgNode24Out4Watts			OBJECT-TYPE
	SYNTAX					INTEGER
	ACCESS					read-only
	STATUS					mandatory
	DESCRIPTION			"PG Outlet 4 watts"
	::= { node24PG 35 }

pgNode24Out4State			OBJECT-TYPE
	SYNTAX					INTEGER { off(1),on(2),cycle(3) }
	ACCESS					read-only
	STATUS					mandatory
	DESCRIPTION			"PG Outlet 4 state"
	::= { node24PG 36 }

pgNode24Out4Cmd				OBJECT-TYPE
	SYNTAX					INTEGER { off(1),on(2),cycle(3) }
	ACCESS					read-write
	STATUS					mandatory
	DESCRIPTION			"PG Outlet 4 command"
	::= { node24PG 37 }

pgNode24Out5Name				OBJECT-TYPE
	SYNTAX					DisplayString
	ACCESS					read-write
	STATUS					mandatory
	DESCRIPTION			"PG Outlet 5 name"
	::= { node24PG 38 }

pgNode24Out5CustVoice	OBJECT-TYPE
	SYNTAX					DisplayString
	ACCESS					read-write
	STATUS					mandatory
	DESCRIPTION			"PG Outlet 5 custom voice"
	::= { node24PG 39 }

pgNode24Out5Volts			OBJECT-TYPE
	SYNTAX					INTEGER
	ACCESS					read-only
	STATUS					mandatory
	DESCRIPTION			"PG Outlet 5 volts"
	::= { node24PG 40 }

pgNode24Out5Amps				OBJECT-TYPE
	SYNTAX					INTEGER
	ACCESS					read-only
	STATUS					mandatory
	DESCRIPTION			"PG Outlet 5 amps"
	::= { node24PG 41 }

pgNode24Out5Watts			OBJECT-TYPE
	SYNTAX					INTEGER
	ACCESS					read-only
	STATUS					mandatory
	DESCRIPTION			"PG Outlet 5 watts"
	::= { node24PG 42 }

pgNode24Out5State			OBJECT-TYPE
	SYNTAX					INTEGER { off(1),on(2),cycle(3) }
	ACCESS					read-only
	STATUS					mandatory
	DESCRIPTION			"PG Outlet 5 state"
	::= { node24PG 43 }

pgNode24Out5Cmd				OBJECT-TYPE
	SYNTAX					INTEGER { off(1),on(2),cycle(3) }
	ACCESS					read-write
	STATUS					mandatory
	DESCRIPTION			"PG Outlet 5 command"
	::= { node24PG 44 }

pgNode24Out6Name				OBJECT-TYPE
	SYNTAX					DisplayString
	ACCESS					read-write
	STATUS					mandatory
	DESCRIPTION			"PG Outlet 6 name"
	::= { node24PG 45 }

pgNode24Out6CustVoice	OBJECT-TYPE
	SYNTAX					DisplayString
	ACCESS					read-write
	STATUS					mandatory
	DESCRIPTION			"PG Outlet 6 custom voice"
	::= { node24PG 46 }

pgNode24Out6Volts			OBJECT-TYPE
	SYNTAX					INTEGER
	ACCESS					read-only
	STATUS					mandatory
	DESCRIPTION			"PG Outlet 6 volts"
	::= { node24PG 47 }

pgNode24Out6Amps				OBJECT-TYPE
	SYNTAX					INTEGER
	ACCESS					read-only
	STATUS					mandatory
	DESCRIPTION			"PG Outlet 6 amps"
	::= { node24PG 48 }

pgNode24Out6Watts			OBJECT-TYPE
	SYNTAX					INTEGER
	ACCESS					read-only
	STATUS					mandatory
	DESCRIPTION			"PG Outlet 6 watts"
	::= { node24PG 49 }

pgNode24Out6State			OBJECT-TYPE
	SYNTAX					INTEGER { off(1),on(2),cycle(3) }
	ACCESS					read-only
	STATUS					mandatory
	DESCRIPTION			"PG Outlet 6 state"
	::= { node24PG 50 }

pgNode24Out6Cmd				OBJECT-TYPE
	SYNTAX					INTEGER { off(1),on(2),cycle(3) }
	ACCESS					read-write
	STATUS					mandatory
	DESCRIPTION			"PG Outlet 6 command"
	::= { node24PG 51 }

pgNode24Out7Name				OBJECT-TYPE
	SYNTAX					DisplayString
	ACCESS					read-write
	STATUS					mandatory
	DESCRIPTION			"PG Outlet 7 name"
	::= { node24PG 52 }

pgNode24Out7CustVoice	OBJECT-TYPE
	SYNTAX					DisplayString
	ACCESS					read-write
	STATUS					mandatory
	DESCRIPTION			"PG Outlet 7 custom voice"
	::= { node24PG 53 }

pgNode24Out7Volts			OBJECT-TYPE
	SYNTAX					INTEGER
	ACCESS					read-only
	STATUS					mandatory
	DESCRIPTION			"PG Outlet 7 volts"
	::= { node24PG 54 }

pgNode24Out7Amps				OBJECT-TYPE
	SYNTAX					INTEGER
	ACCESS					read-only
	STATUS					mandatory
	DESCRIPTION			"PG Outlet 7 amps"
	::= { node24PG 55 }

pgNode24Out7Watts			OBJECT-TYPE
	SYNTAX					INTEGER
	ACCESS					read-only
	STATUS					mandatory
	DESCRIPTION			"PG Outlet 7 watts"
	::= { node24PG 56 }

pgNode24Out7State			OBJECT-TYPE
	SYNTAX					INTEGER { off(1),on(2),cycle(3) }
	ACCESS					read-only
	STATUS					mandatory
	DESCRIPTION			"PG Outlet 7 state"
	::= { node24PG 57 }

pgNode24Out7Cmd				OBJECT-TYPE
	SYNTAX					INTEGER { off(1),on(2),cycle(3) }
	ACCESS					read-write
	STATUS					mandatory
	DESCRIPTION			"PG Outlet 7 command"
	::= { node24PG 58 }

pgNode24Out8Name				OBJECT-TYPE
	SYNTAX					DisplayString
	ACCESS					read-write
	STATUS					mandatory
	DESCRIPTION			"PG Outlet 8 name"
	::= { node24PG 59 }

pgNode24Out8CustVoice	OBJECT-TYPE
	SYNTAX					DisplayString
	ACCESS					read-write
	STATUS					mandatory
	DESCRIPTION			"PG Outlet 8 custom voice"
	::= { node24PG 60 }

pgNode24Out8Volts			OBJECT-TYPE
	SYNTAX					INTEGER
	ACCESS					read-only
	STATUS					mandatory
	DESCRIPTION			"PG Outlet 8 volts"
	::= { node24PG 61 }

pgNode24Out8Amps				OBJECT-TYPE
	SYNTAX					INTEGER
	ACCESS					read-only
	STATUS					mandatory
	DESCRIPTION			"PG Outlet 8 amps"
	::= { node24PG 62 }

pgNode24Out8Watts			OBJECT-TYPE
	SYNTAX					INTEGER
	ACCESS					read-only
	STATUS					mandatory
	DESCRIPTION			"PG Outlet 8 watts"
	::= { node24PG 63 }

pgNode24Out8State			OBJECT-TYPE
	SYNTAX					INTEGER { off(1),on(2),cycle(3) }
	ACCESS					read-only
	STATUS					mandatory
	DESCRIPTION			"PG Outlet 8 state"
	::= { node24PG 64 }

pgNode24Out8Cmd				OBJECT-TYPE
	SYNTAX					INTEGER { off(1),on(2),cycle(3) }
	ACCESS					read-write
	STATUS					mandatory
	DESCRIPTION			"PG Outlet 8 command"
	::= { node24PG 65 }

pgNode25InUse					OBJECT-TYPE
	SYNTAX					INTEGER { false(1),true(2) }
	ACCESS					read-only
	STATUS					mandatory
	DESCRIPTION			"PG in use"
	::= { node25PG 1 }

pgNode25Status					OBJECT-TYPE
	SYNTAX					INTEGER { normal(1),pending(2), trouble(3) }
	ACCESS					read-only
	STATUS					mandatory
	DESCRIPTION			"PG status"
	::= { node25PG 2 }

pgNode25StatusSupport	OBJECT-TYPE
	SYNTAX					INTEGER { true1(1),false(2) }
	ACCESS					read-only
	STATUS					mandatory
	DESCRIPTION			"PG status support level"
	::= { node25PG 3 }

pgNode25Ver						OBJECT-TYPE
	SYNTAX					INTEGER { pgate1(1),pgate2(2) }
	ACCESS					read-only
	STATUS					mandatory
	DESCRIPTION			"PG version"
	::= { node25PG 4 }

pgNode25Volts					OBJECT-TYPE
	SYNTAX					INTEGER
	ACCESS					read-only
	STATUS					mandatory
	DESCRIPTION			"PG voltage"
	::= { node25PG 5 }

pgNode25Amps						OBJECT-TYPE
	SYNTAX					INTEGER
	ACCESS					read-only
	STATUS					mandatory
	DESCRIPTION			"PG amps"
	::= { node25PG 6 }

pgNode25Watts					OBJECT-TYPE
	SYNTAX					INTEGER
	ACCESS					read-only
	STATUS					mandatory
	DESCRIPTION			"PG Watts"
	::= { node25PG 7 }

pgNode25Name						OBJECT-TYPE
	SYNTAX					DisplayString
	ACCESS					read-write
	STATUS					mandatory
	DESCRIPTION			"PG name"
	::= { node25PG 8 }

pgNode25CustVoice			OBJECT-TYPE
	SYNTAX					DisplayString
	ACCESS					read-write
	STATUS					mandatory
	DESCRIPTION			"PG custom voice"
	::= { node25PG 9 }

pgNode25Out1Name				OBJECT-TYPE
	SYNTAX					DisplayString
	ACCESS					read-write
	STATUS					mandatory
	DESCRIPTION			"PG Outlet 1 name"
	::= { node25PG 10 }

pgNode25Out1CustVoice	OBJECT-TYPE
	SYNTAX					DisplayString
	ACCESS					read-write
	STATUS					mandatory
	DESCRIPTION			"PG Outlet 1 custom voice"
	::= { node25PG 11 }

pgNode25Out1Volts			OBJECT-TYPE
	SYNTAX					INTEGER
	ACCESS					read-only
	STATUS					mandatory
	DESCRIPTION			"PG Outlet 1 volts"
	::= { node25PG 12 }

pgNode25Out1Amps				OBJECT-TYPE
	SYNTAX					INTEGER
	ACCESS					read-only
	STATUS					mandatory
	DESCRIPTION			"PG Outlet 1 amps"
	::= { node25PG 13 }

pgNode25Out1Watts			OBJECT-TYPE
	SYNTAX					INTEGER
	ACCESS					read-only
	STATUS					mandatory
	DESCRIPTION			"PG Outlet 1 watts"
	::= { node25PG 14 }

pgNode25Out1State			OBJECT-TYPE
	SYNTAX					INTEGER { off(1),on(2),cycle(3) }
	ACCESS					read-only
	STATUS					mandatory
	DESCRIPTION			"PG Outlet 1 state"
	::= { node25PG 15 }

pgNode25Out1Cmd				OBJECT-TYPE
	SYNTAX					INTEGER { off(1),on(2),cycle(3) }
	ACCESS					read-write
	STATUS					mandatory
	DESCRIPTION			"PG Outlet 1 command"
	::= { node25PG 16 }

pgNode25Out2Name				OBJECT-TYPE
	SYNTAX					DisplayString
	ACCESS					read-write
	STATUS					mandatory
	DESCRIPTION			"PG Outlet 2 name"
	::= { node25PG 17 }

pgNode25Out2CustVoice	OBJECT-TYPE
	SYNTAX					DisplayString
	ACCESS					read-write
	STATUS					mandatory
	DESCRIPTION			"PG Outlet 2 custom voice"
	::= { node25PG 18 }

pgNode25Out2Volts			OBJECT-TYPE
	SYNTAX					INTEGER
	ACCESS					read-only
	STATUS					mandatory
	DESCRIPTION			"PG Outlet 2 volts"
	::= { node25PG 19 }

pgNode25Out2Amps				OBJECT-TYPE
	SYNTAX					INTEGER
	ACCESS					read-only
	STATUS					mandatory
	DESCRIPTION			"PG Outlet 2 amps"
	::= { node25PG 20 }

pgNode25Out2Watts			OBJECT-TYPE
	SYNTAX					INTEGER
	ACCESS					read-only
	STATUS					mandatory
	DESCRIPTION			"PG Outlet 2 watts"
	::= { node25PG 21 }

pgNode25Out2State			OBJECT-TYPE
	SYNTAX					INTEGER { off(1),on(2),cycle(3) }
	ACCESS					read-only
	STATUS					mandatory
	DESCRIPTION			"PG Outlet 2 state"
	::= { node25PG 22 }

pgNode25Out2Cmd				OBJECT-TYPE
	SYNTAX					INTEGER { off(1),on(2),cycle(3) }
	ACCESS					read-write
	STATUS					mandatory
	DESCRIPTION			"PG Outlet 2 command"
	::= { node25PG 23 }

pgNode25Out3Name				OBJECT-TYPE
	SYNTAX					DisplayString
	ACCESS					read-write
	STATUS					mandatory
	DESCRIPTION			"PG Outlet 3 name"
	::= { node25PG 24 }

pgNode25Out3CustVoice	OBJECT-TYPE
	SYNTAX					DisplayString
	ACCESS					read-write
	STATUS					mandatory
	DESCRIPTION			"PG Outlet 3 custom voice"
	::= { node25PG 25 }

pgNode25Out3Volts			OBJECT-TYPE
	SYNTAX					INTEGER
	ACCESS					read-only
	STATUS					mandatory
	DESCRIPTION			"PG Outlet 3 volts"
	::= { node25PG 26 }

pgNode25Out3Amps				OBJECT-TYPE
	SYNTAX					INTEGER
	ACCESS					read-only
	STATUS					mandatory
	DESCRIPTION			"PG Outlet 3 amps"
	::= { node25PG 27 }

pgNode25Out3Watts			OBJECT-TYPE
	SYNTAX					INTEGER
	ACCESS					read-only
	STATUS					mandatory
	DESCRIPTION			"PG Outlet 3 watts"
	::= { node25PG 28 }

pgNode25Out3State			OBJECT-TYPE
	SYNTAX					INTEGER { off(1),on(2),cycle(3) }
	ACCESS					read-only
	STATUS					mandatory
	DESCRIPTION			"PG Outlet 3 state"
	::= { node25PG 29 }

pgNode25Out3Cmd				OBJECT-TYPE
	SYNTAX					INTEGER { off(1),on(2),cycle(3) }
	ACCESS					read-write
	STATUS					mandatory
	DESCRIPTION			"PG Outlet 3 command"
	::= { node25PG 30 }

pgNode25Out4Name				OBJECT-TYPE
	SYNTAX					DisplayString
	ACCESS					read-write
	STATUS					mandatory
	DESCRIPTION			"PG Outlet 4 name"
	::= { node25PG 31 }

pgNode25Out4CustVoice	OBJECT-TYPE
	SYNTAX					DisplayString
	ACCESS					read-write
	STATUS					mandatory
	DESCRIPTION			"PG Outlet 4 custom voice"
	::= { node25PG 32 }

pgNode25Out4Volts			OBJECT-TYPE
	SYNTAX					INTEGER
	ACCESS					read-only
	STATUS					mandatory
	DESCRIPTION			"PG Outlet 4 volts"
	::= { node25PG 33 }

pgNode25Out4Amps				OBJECT-TYPE
	SYNTAX					INTEGER
	ACCESS					read-only
	STATUS					mandatory
	DESCRIPTION			"PG Outlet 4 amps"
	::= { node25PG 34 }

pgNode25Out4Watts			OBJECT-TYPE
	SYNTAX					INTEGER
	ACCESS					read-only
	STATUS					mandatory
	DESCRIPTION			"PG Outlet 4 watts"
	::= { node25PG 35 }

pgNode25Out4State			OBJECT-TYPE
	SYNTAX					INTEGER { off(1),on(2),cycle(3) }
	ACCESS					read-only
	STATUS					mandatory
	DESCRIPTION			"PG Outlet 4 state"
	::= { node25PG 36 }

pgNode25Out4Cmd				OBJECT-TYPE
	SYNTAX					INTEGER { off(1),on(2),cycle(3) }
	ACCESS					read-write
	STATUS					mandatory
	DESCRIPTION			"PG Outlet 4 command"
	::= { node25PG 37 }

pgNode25Out5Name				OBJECT-TYPE
	SYNTAX					DisplayString
	ACCESS					read-write
	STATUS					mandatory
	DESCRIPTION			"PG Outlet 5 name"
	::= { node25PG 38 }

pgNode25Out5CustVoice	OBJECT-TYPE
	SYNTAX					DisplayString
	ACCESS					read-write
	STATUS					mandatory
	DESCRIPTION			"PG Outlet 5 custom voice"
	::= { node25PG 39 }

pgNode25Out5Volts			OBJECT-TYPE
	SYNTAX					INTEGER
	ACCESS					read-only
	STATUS					mandatory
	DESCRIPTION			"PG Outlet 5 volts"
	::= { node25PG 40 }

pgNode25Out5Amps				OBJECT-TYPE
	SYNTAX					INTEGER
	ACCESS					read-only
	STATUS					mandatory
	DESCRIPTION			"PG Outlet 5 amps"
	::= { node25PG 41 }

pgNode25Out5Watts			OBJECT-TYPE
	SYNTAX					INTEGER
	ACCESS					read-only
	STATUS					mandatory
	DESCRIPTION			"PG Outlet 5 watts"
	::= { node25PG 42 }

pgNode25Out5State			OBJECT-TYPE
	SYNTAX					INTEGER { off(1),on(2),cycle(3) }
	ACCESS					read-only
	STATUS					mandatory
	DESCRIPTION			"PG Outlet 5 state"
	::= { node25PG 43 }

pgNode25Out5Cmd				OBJECT-TYPE
	SYNTAX					INTEGER { off(1),on(2),cycle(3) }
	ACCESS					read-write
	STATUS					mandatory
	DESCRIPTION			"PG Outlet 5 command"
	::= { node25PG 44 }

pgNode25Out6Name				OBJECT-TYPE
	SYNTAX					DisplayString
	ACCESS					read-write
	STATUS					mandatory
	DESCRIPTION			"PG Outlet 6 name"
	::= { node25PG 45 }

pgNode25Out6CustVoice	OBJECT-TYPE
	SYNTAX					DisplayString
	ACCESS					read-write
	STATUS					mandatory
	DESCRIPTION			"PG Outlet 6 custom voice"
	::= { node25PG 46 }

pgNode25Out6Volts			OBJECT-TYPE
	SYNTAX					INTEGER
	ACCESS					read-only
	STATUS					mandatory
	DESCRIPTION			"PG Outlet 6 volts"
	::= { node25PG 47 }

pgNode25Out6Amps				OBJECT-TYPE
	SYNTAX					INTEGER
	ACCESS					read-only
	STATUS					mandatory
	DESCRIPTION			"PG Outlet 6 amps"
	::= { node25PG 48 }

pgNode25Out6Watts			OBJECT-TYPE
	SYNTAX					INTEGER
	ACCESS					read-only
	STATUS					mandatory
	DESCRIPTION			"PG Outlet 6 watts"
	::= { node25PG 49 }

pgNode25Out6State			OBJECT-TYPE
	SYNTAX					INTEGER { off(1),on(2),cycle(3) }
	ACCESS					read-only
	STATUS					mandatory
	DESCRIPTION			"PG Outlet 6 state"
	::= { node25PG 50 }

pgNode25Out6Cmd				OBJECT-TYPE
	SYNTAX					INTEGER { off(1),on(2),cycle(3) }
	ACCESS					read-write
	STATUS					mandatory
	DESCRIPTION			"PG Outlet 6 command"
	::= { node25PG 51 }

pgNode25Out7Name				OBJECT-TYPE
	SYNTAX					DisplayString
	ACCESS					read-write
	STATUS					mandatory
	DESCRIPTION			"PG Outlet 7 name"
	::= { node25PG 52 }

pgNode25Out7CustVoice	OBJECT-TYPE
	SYNTAX					DisplayString
	ACCESS					read-write
	STATUS					mandatory
	DESCRIPTION			"PG Outlet 7 custom voice"
	::= { node25PG 53 }

pgNode25Out7Volts			OBJECT-TYPE
	SYNTAX					INTEGER
	ACCESS					read-only
	STATUS					mandatory
	DESCRIPTION			"PG Outlet 7 volts"
	::= { node25PG 54 }

pgNode25Out7Amps				OBJECT-TYPE
	SYNTAX					INTEGER
	ACCESS					read-only
	STATUS					mandatory
	DESCRIPTION			"PG Outlet 7 amps"
	::= { node25PG 55 }

pgNode25Out7Watts			OBJECT-TYPE
	SYNTAX					INTEGER
	ACCESS					read-only
	STATUS					mandatory
	DESCRIPTION			"PG Outlet 7 watts"
	::= { node25PG 56 }

pgNode25Out7State			OBJECT-TYPE
	SYNTAX					INTEGER { off(1),on(2),cycle(3) }
	ACCESS					read-only
	STATUS					mandatory
	DESCRIPTION			"PG Outlet 7 state"
	::= { node25PG 57 }

pgNode25Out7Cmd				OBJECT-TYPE
	SYNTAX					INTEGER { off(1),on(2),cycle(3) }
	ACCESS					read-write
	STATUS					mandatory
	DESCRIPTION			"PG Outlet 7 command"
	::= { node25PG 58 }

pgNode25Out8Name				OBJECT-TYPE
	SYNTAX					DisplayString
	ACCESS					read-write
	STATUS					mandatory
	DESCRIPTION			"PG Outlet 8 name"
	::= { node25PG 59 }

pgNode25Out8CustVoice	OBJECT-TYPE
	SYNTAX					DisplayString
	ACCESS					read-write
	STATUS					mandatory
	DESCRIPTION			"PG Outlet 8 custom voice"
	::= { node25PG 60 }

pgNode25Out8Volts			OBJECT-TYPE
	SYNTAX					INTEGER
	ACCESS					read-only
	STATUS					mandatory
	DESCRIPTION			"PG Outlet 8 volts"
	::= { node25PG 61 }

pgNode25Out8Amps				OBJECT-TYPE
	SYNTAX					INTEGER
	ACCESS					read-only
	STATUS					mandatory
	DESCRIPTION			"PG Outlet 8 amps"
	::= { node25PG 62 }

pgNode25Out8Watts			OBJECT-TYPE
	SYNTAX					INTEGER
	ACCESS					read-only
	STATUS					mandatory
	DESCRIPTION			"PG Outlet 8 watts"
	::= { node25PG 63 }

pgNode25Out8State			OBJECT-TYPE
	SYNTAX					INTEGER { off(1),on(2),cycle(3) }
	ACCESS					read-only
	STATUS					mandatory
	DESCRIPTION			"PG Outlet 8 state"
	::= { node25PG 64 }

pgNode25Out8Cmd				OBJECT-TYPE
	SYNTAX					INTEGER { off(1),on(2),cycle(3) }
	ACCESS					read-write
	STATUS					mandatory
	DESCRIPTION			"PG Outlet 8 command"
	::= { node25PG 65 }

pgNode26InUse					OBJECT-TYPE
	SYNTAX					INTEGER { false(1),true(2) }
	ACCESS					read-only
	STATUS					mandatory
	DESCRIPTION			"PG in use"
	::= { node26PG 1 }

pgNode26Status					OBJECT-TYPE
	SYNTAX					INTEGER { normal(1),pending(2), trouble(3) }
	ACCESS					read-only
	STATUS					mandatory
	DESCRIPTION			"PG status"
	::= { node26PG 2 }

pgNode26StatusSupport	OBJECT-TYPE
	SYNTAX					INTEGER { true1(1),false(2) }
	ACCESS					read-only
	STATUS					mandatory
	DESCRIPTION			"PG status support level"
	::= { node26PG 3 }

pgNode26Ver						OBJECT-TYPE
	SYNTAX					INTEGER { pgate1(1),pgate2(2) }
	ACCESS					read-only
	STATUS					mandatory
	DESCRIPTION			"PG version"
	::= { node26PG 4 }

pgNode26Volts					OBJECT-TYPE
	SYNTAX					INTEGER
	ACCESS					read-only
	STATUS					mandatory
	DESCRIPTION			"PG voltage"
	::= { node26PG 5 }

pgNode26Amps						OBJECT-TYPE
	SYNTAX					INTEGER
	ACCESS					read-only
	STATUS					mandatory
	DESCRIPTION			"PG amps"
	::= { node26PG 6 }

pgNode26Watts					OBJECT-TYPE
	SYNTAX					INTEGER
	ACCESS					read-only
	STATUS					mandatory
	DESCRIPTION			"PG Watts"
	::= { node26PG 7 }

pgNode26Name						OBJECT-TYPE
	SYNTAX					DisplayString
	ACCESS					read-write
	STATUS					mandatory
	DESCRIPTION			"PG name"
	::= { node26PG 8 }

pgNode26CustVoice			OBJECT-TYPE
	SYNTAX					DisplayString
	ACCESS					read-write
	STATUS					mandatory
	DESCRIPTION			"PG custom voice"
	::= { node26PG 9 }

pgNode26Out1Name				OBJECT-TYPE
	SYNTAX					DisplayString
	ACCESS					read-write
	STATUS					mandatory
	DESCRIPTION			"PG Outlet 1 name"
	::= { node26PG 10 }

pgNode26Out1CustVoice	OBJECT-TYPE
	SYNTAX					DisplayString
	ACCESS					read-write
	STATUS					mandatory
	DESCRIPTION			"PG Outlet 1 custom voice"
	::= { node26PG 11 }

pgNode26Out1Volts			OBJECT-TYPE
	SYNTAX					INTEGER
	ACCESS					read-only
	STATUS					mandatory
	DESCRIPTION			"PG Outlet 1 volts"
	::= { node26PG 12 }

pgNode26Out1Amps				OBJECT-TYPE
	SYNTAX					INTEGER
	ACCESS					read-only
	STATUS					mandatory
	DESCRIPTION			"PG Outlet 1 amps"
	::= { node26PG 13 }

pgNode26Out1Watts			OBJECT-TYPE
	SYNTAX					INTEGER
	ACCESS					read-only
	STATUS					mandatory
	DESCRIPTION			"PG Outlet 1 watts"
	::= { node26PG 14 }

pgNode26Out1State			OBJECT-TYPE
	SYNTAX					INTEGER { off(1),on(2),cycle(3) }
	ACCESS					read-only
	STATUS					mandatory
	DESCRIPTION			"PG Outlet 1 state"
	::= { node26PG 15 }

pgNode26Out1Cmd				OBJECT-TYPE
	SYNTAX					INTEGER { off(1),on(2),cycle(3) }
	ACCESS					read-write
	STATUS					mandatory
	DESCRIPTION			"PG Outlet 1 command"
	::= { node26PG 16 }

pgNode26Out2Name				OBJECT-TYPE
	SYNTAX					DisplayString
	ACCESS					read-write
	STATUS					mandatory
	DESCRIPTION			"PG Outlet 2 name"
	::= { node26PG 17 }

pgNode26Out2CustVoice	OBJECT-TYPE
	SYNTAX					DisplayString
	ACCESS					read-write
	STATUS					mandatory
	DESCRIPTION			"PG Outlet 2 custom voice"
	::= { node26PG 18 }

pgNode26Out2Volts			OBJECT-TYPE
	SYNTAX					INTEGER
	ACCESS					read-only
	STATUS					mandatory
	DESCRIPTION			"PG Outlet 2 volts"
	::= { node26PG 19 }

pgNode26Out2Amps				OBJECT-TYPE
	SYNTAX					INTEGER
	ACCESS					read-only
	STATUS					mandatory
	DESCRIPTION			"PG Outlet 2 amps"
	::= { node26PG 20 }

pgNode26Out2Watts			OBJECT-TYPE
	SYNTAX					INTEGER
	ACCESS					read-only
	STATUS					mandatory
	DESCRIPTION			"PG Outlet 2 watts"
	::= { node26PG 21 }

pgNode26Out2State			OBJECT-TYPE
	SYNTAX					INTEGER { off(1),on(2),cycle(3) }
	ACCESS					read-only
	STATUS					mandatory
	DESCRIPTION			"PG Outlet 2 state"
	::= { node26PG 22 }

pgNode26Out2Cmd				OBJECT-TYPE
	SYNTAX					INTEGER { off(1),on(2),cycle(3) }
	ACCESS					read-write
	STATUS					mandatory
	DESCRIPTION			"PG Outlet 2 command"
	::= { node26PG 23 }

pgNode26Out3Name				OBJECT-TYPE
	SYNTAX					DisplayString
	ACCESS					read-write
	STATUS					mandatory
	DESCRIPTION			"PG Outlet 3 name"
	::= { node26PG 24 }

pgNode26Out3CustVoice	OBJECT-TYPE
	SYNTAX					DisplayString
	ACCESS					read-write
	STATUS					mandatory
	DESCRIPTION			"PG Outlet 3 custom voice"
	::= { node26PG 25 }

pgNode26Out3Volts			OBJECT-TYPE
	SYNTAX					INTEGER
	ACCESS					read-only
	STATUS					mandatory
	DESCRIPTION			"PG Outlet 3 volts"
	::= { node26PG 26 }

pgNode26Out3Amps				OBJECT-TYPE
	SYNTAX					INTEGER
	ACCESS					read-only
	STATUS					mandatory
	DESCRIPTION			"PG Outlet 3 amps"
	::= { node26PG 27 }

pgNode26Out3Watts			OBJECT-TYPE
	SYNTAX					INTEGER
	ACCESS					read-only
	STATUS					mandatory
	DESCRIPTION			"PG Outlet 3 watts"
	::= { node26PG 28 }

pgNode26Out3State			OBJECT-TYPE
	SYNTAX					INTEGER { off(1),on(2),cycle(3) }
	ACCESS					read-only
	STATUS					mandatory
	DESCRIPTION			"PG Outlet 3 state"
	::= { node26PG 29 }

pgNode26Out3Cmd				OBJECT-TYPE
	SYNTAX					INTEGER { off(1),on(2),cycle(3) }
	ACCESS					read-write
	STATUS					mandatory
	DESCRIPTION			"PG Outlet 3 command"
	::= { node26PG 30 }

pgNode26Out4Name				OBJECT-TYPE
	SYNTAX					DisplayString
	ACCESS					read-write
	STATUS					mandatory
	DESCRIPTION			"PG Outlet 4 name"
	::= { node26PG 31 }

pgNode26Out4CustVoice	OBJECT-TYPE
	SYNTAX					DisplayString
	ACCESS					read-write
	STATUS					mandatory
	DESCRIPTION			"PG Outlet 4 custom voice"
	::= { node26PG 32 }

pgNode26Out4Volts			OBJECT-TYPE
	SYNTAX					INTEGER
	ACCESS					read-only
	STATUS					mandatory
	DESCRIPTION			"PG Outlet 4 volts"
	::= { node26PG 33 }

pgNode26Out4Amps				OBJECT-TYPE
	SYNTAX					INTEGER
	ACCESS					read-only
	STATUS					mandatory
	DESCRIPTION			"PG Outlet 4 amps"
	::= { node26PG 34 }

pgNode26Out4Watts			OBJECT-TYPE
	SYNTAX					INTEGER
	ACCESS					read-only
	STATUS					mandatory
	DESCRIPTION			"PG Outlet 4 watts"
	::= { node26PG 35 }

pgNode26Out4State			OBJECT-TYPE
	SYNTAX					INTEGER { off(1),on(2),cycle(3) }
	ACCESS					read-only
	STATUS					mandatory
	DESCRIPTION			"PG Outlet 4 state"
	::= { node26PG 36 }

pgNode26Out4Cmd				OBJECT-TYPE
	SYNTAX					INTEGER { off(1),on(2),cycle(3) }
	ACCESS					read-write
	STATUS					mandatory
	DESCRIPTION			"PG Outlet 4 command"
	::= { node26PG 37 }

pgNode26Out5Name				OBJECT-TYPE
	SYNTAX					DisplayString
	ACCESS					read-write
	STATUS					mandatory
	DESCRIPTION			"PG Outlet 5 name"
	::= { node26PG 38 }

pgNode26Out5CustVoice	OBJECT-TYPE
	SYNTAX					DisplayString
	ACCESS					read-write
	STATUS					mandatory
	DESCRIPTION			"PG Outlet 5 custom voice"
	::= { node26PG 39 }

pgNode26Out5Volts			OBJECT-TYPE
	SYNTAX					INTEGER
	ACCESS					read-only
	STATUS					mandatory
	DESCRIPTION			"PG Outlet 5 volts"
	::= { node26PG 40 }

pgNode26Out5Amps				OBJECT-TYPE
	SYNTAX					INTEGER
	ACCESS					read-only
	STATUS					mandatory
	DESCRIPTION			"PG Outlet 5 amps"
	::= { node26PG 41 }

pgNode26Out5Watts			OBJECT-TYPE
	SYNTAX					INTEGER
	ACCESS					read-only
	STATUS					mandatory
	DESCRIPTION			"PG Outlet 5 watts"
	::= { node26PG 42 }

pgNode26Out5State			OBJECT-TYPE
	SYNTAX					INTEGER { off(1),on(2),cycle(3) }
	ACCESS					read-only
	STATUS					mandatory
	DESCRIPTION			"PG Outlet 5 state"
	::= { node26PG 43 }

pgNode26Out5Cmd				OBJECT-TYPE
	SYNTAX					INTEGER { off(1),on(2),cycle(3) }
	ACCESS					read-write
	STATUS					mandatory
	DESCRIPTION			"PG Outlet 5 command"
	::= { node26PG 44 }

pgNode26Out6Name				OBJECT-TYPE
	SYNTAX					DisplayString
	ACCESS					read-write
	STATUS					mandatory
	DESCRIPTION			"PG Outlet 6 name"
	::= { node26PG 45 }

pgNode26Out6CustVoice	OBJECT-TYPE
	SYNTAX					DisplayString
	ACCESS					read-write
	STATUS					mandatory
	DESCRIPTION			"PG Outlet 6 custom voice"
	::= { node26PG 46 }

pgNode26Out6Volts			OBJECT-TYPE
	SYNTAX					INTEGER
	ACCESS					read-only
	STATUS					mandatory
	DESCRIPTION			"PG Outlet 6 volts"
	::= { node26PG 47 }

pgNode26Out6Amps				OBJECT-TYPE
	SYNTAX					INTEGER
	ACCESS					read-only
	STATUS					mandatory
	DESCRIPTION			"PG Outlet 6 amps"
	::= { node26PG 48 }

pgNode26Out6Watts			OBJECT-TYPE
	SYNTAX					INTEGER
	ACCESS					read-only
	STATUS					mandatory
	DESCRIPTION			"PG Outlet 6 watts"
	::= { node26PG 49 }

pgNode26Out6State			OBJECT-TYPE
	SYNTAX					INTEGER { off(1),on(2),cycle(3) }
	ACCESS					read-only
	STATUS					mandatory
	DESCRIPTION			"PG Outlet 6 state"
	::= { node26PG 50 }

pgNode26Out6Cmd				OBJECT-TYPE
	SYNTAX					INTEGER { off(1),on(2),cycle(3) }
	ACCESS					read-write
	STATUS					mandatory
	DESCRIPTION			"PG Outlet 6 command"
	::= { node26PG 51 }

pgNode26Out7Name				OBJECT-TYPE
	SYNTAX					DisplayString
	ACCESS					read-write
	STATUS					mandatory
	DESCRIPTION			"PG Outlet 7 name"
	::= { node26PG 52 }

pgNode26Out7CustVoice	OBJECT-TYPE
	SYNTAX					DisplayString
	ACCESS					read-write
	STATUS					mandatory
	DESCRIPTION			"PG Outlet 7 custom voice"
	::= { node26PG 53 }

pgNode26Out7Volts			OBJECT-TYPE
	SYNTAX					INTEGER
	ACCESS					read-only
	STATUS					mandatory
	DESCRIPTION			"PG Outlet 7 volts"
	::= { node26PG 54 }

pgNode26Out7Amps				OBJECT-TYPE
	SYNTAX					INTEGER
	ACCESS					read-only
	STATUS					mandatory
	DESCRIPTION			"PG Outlet 7 amps"
	::= { node26PG 55 }

pgNode26Out7Watts			OBJECT-TYPE
	SYNTAX					INTEGER
	ACCESS					read-only
	STATUS					mandatory
	DESCRIPTION			"PG Outlet 7 watts"
	::= { node26PG 56 }

pgNode26Out7State			OBJECT-TYPE
	SYNTAX					INTEGER { off(1),on(2),cycle(3) }
	ACCESS					read-only
	STATUS					mandatory
	DESCRIPTION			"PG Outlet 7 state"
	::= { node26PG 57 }

pgNode26Out7Cmd				OBJECT-TYPE
	SYNTAX					INTEGER { off(1),on(2),cycle(3) }
	ACCESS					read-write
	STATUS					mandatory
	DESCRIPTION			"PG Outlet 7 command"
	::= { node26PG 58 }

pgNode26Out8Name				OBJECT-TYPE
	SYNTAX					DisplayString
	ACCESS					read-write
	STATUS					mandatory
	DESCRIPTION			"PG Outlet 8 name"
	::= { node26PG 59 }

pgNode26Out8CustVoice	OBJECT-TYPE
	SYNTAX					DisplayString
	ACCESS					read-write
	STATUS					mandatory
	DESCRIPTION			"PG Outlet 8 custom voice"
	::= { node26PG 60 }

pgNode26Out8Volts			OBJECT-TYPE
	SYNTAX					INTEGER
	ACCESS					read-only
	STATUS					mandatory
	DESCRIPTION			"PG Outlet 8 volts"
	::= { node26PG 61 }

pgNode26Out8Amps				OBJECT-TYPE
	SYNTAX					INTEGER
	ACCESS					read-only
	STATUS					mandatory
	DESCRIPTION			"PG Outlet 8 amps"
	::= { node26PG 62 }

pgNode26Out8Watts			OBJECT-TYPE
	SYNTAX					INTEGER
	ACCESS					read-only
	STATUS					mandatory
	DESCRIPTION			"PG Outlet 8 watts"
	::= { node26PG 63 }

pgNode26Out8State			OBJECT-TYPE
	SYNTAX					INTEGER { off(1),on(2),cycle(3) }
	ACCESS					read-only
	STATUS					mandatory
	DESCRIPTION			"PG Outlet 8 state"
	::= { node26PG 64 }

pgNode26Out8Cmd				OBJECT-TYPE
	SYNTAX					INTEGER { off(1),on(2),cycle(3) }
	ACCESS					read-write
	STATUS					mandatory
	DESCRIPTION			"PG Outlet 8 command"
	::= { node26PG 65 }

pgNode27InUse					OBJECT-TYPE
	SYNTAX					INTEGER { false(1),true(2) }
	ACCESS					read-only
	STATUS					mandatory
	DESCRIPTION			"PG in use"
	::= { node27PG 1 }

pgNode27Status					OBJECT-TYPE
	SYNTAX					INTEGER { normal(1),pending(2), trouble(3) }
	ACCESS					read-only
	STATUS					mandatory
	DESCRIPTION			"PG status"
	::= { node27PG 2 }

pgNode27StatusSupport	OBJECT-TYPE
	SYNTAX					INTEGER { true1(1),false(2) }
	ACCESS					read-only
	STATUS					mandatory
	DESCRIPTION			"PG status support level"
	::= { node27PG 3 }

pgNode27Ver						OBJECT-TYPE
	SYNTAX					INTEGER { pgate1(1),pgate2(2) }
	ACCESS					read-only
	STATUS					mandatory
	DESCRIPTION			"PG version"
	::= { node27PG 4 }

pgNode27Volts					OBJECT-TYPE
	SYNTAX					INTEGER
	ACCESS					read-only
	STATUS					mandatory
	DESCRIPTION			"PG voltage"
	::= { node27PG 5 }

pgNode27Amps						OBJECT-TYPE
	SYNTAX					INTEGER
	ACCESS					read-only
	STATUS					mandatory
	DESCRIPTION			"PG amps"
	::= { node27PG 6 }

pgNode27Watts					OBJECT-TYPE
	SYNTAX					INTEGER
	ACCESS					read-only
	STATUS					mandatory
	DESCRIPTION			"PG Watts"
	::= { node27PG 7 }

pgNode27Name						OBJECT-TYPE
	SYNTAX					DisplayString
	ACCESS					read-write
	STATUS					mandatory
	DESCRIPTION			"PG name"
	::= { node27PG 8 }

pgNode27CustVoice			OBJECT-TYPE
	SYNTAX					DisplayString
	ACCESS					read-write
	STATUS					mandatory
	DESCRIPTION			"PG custom voice"
	::= { node27PG 9 }

pgNode27Out1Name				OBJECT-TYPE
	SYNTAX					DisplayString
	ACCESS					read-write
	STATUS					mandatory
	DESCRIPTION			"PG Outlet 1 name"
	::= { node27PG 10 }

pgNode27Out1CustVoice	OBJECT-TYPE
	SYNTAX					DisplayString
	ACCESS					read-write
	STATUS					mandatory
	DESCRIPTION			"PG Outlet 1 custom voice"
	::= { node27PG 11 }

pgNode27Out1Volts			OBJECT-TYPE
	SYNTAX					INTEGER
	ACCESS					read-only
	STATUS					mandatory
	DESCRIPTION			"PG Outlet 1 volts"
	::= { node27PG 12 }

pgNode27Out1Amps				OBJECT-TYPE
	SYNTAX					INTEGER
	ACCESS					read-only
	STATUS					mandatory
	DESCRIPTION			"PG Outlet 1 amps"
	::= { node27PG 13 }

pgNode27Out1Watts			OBJECT-TYPE
	SYNTAX					INTEGER
	ACCESS					read-only
	STATUS					mandatory
	DESCRIPTION			"PG Outlet 1 watts"
	::= { node27PG 14 }

pgNode27Out1State			OBJECT-TYPE
	SYNTAX					INTEGER { off(1),on(2),cycle(3) }
	ACCESS					read-only
	STATUS					mandatory
	DESCRIPTION			"PG Outlet 1 state"
	::= { node27PG 15 }

pgNode27Out1Cmd				OBJECT-TYPE
	SYNTAX					INTEGER { off(1),on(2),cycle(3) }
	ACCESS					read-write
	STATUS					mandatory
	DESCRIPTION			"PG Outlet 1 command"
	::= { node27PG 16 }

pgNode27Out2Name				OBJECT-TYPE
	SYNTAX					DisplayString
	ACCESS					read-write
	STATUS					mandatory
	DESCRIPTION			"PG Outlet 2 name"
	::= { node27PG 17 }

pgNode27Out2CustVoice	OBJECT-TYPE
	SYNTAX					DisplayString
	ACCESS					read-write
	STATUS					mandatory
	DESCRIPTION			"PG Outlet 2 custom voice"
	::= { node27PG 18 }

pgNode27Out2Volts			OBJECT-TYPE
	SYNTAX					INTEGER
	ACCESS					read-only
	STATUS					mandatory
	DESCRIPTION			"PG Outlet 2 volts"
	::= { node27PG 19 }

pgNode27Out2Amps				OBJECT-TYPE
	SYNTAX					INTEGER
	ACCESS					read-only
	STATUS					mandatory
	DESCRIPTION			"PG Outlet 2 amps"
	::= { node27PG 20 }

pgNode27Out2Watts			OBJECT-TYPE
	SYNTAX					INTEGER
	ACCESS					read-only
	STATUS					mandatory
	DESCRIPTION			"PG Outlet 2 watts"
	::= { node27PG 21 }

pgNode27Out2State			OBJECT-TYPE
	SYNTAX					INTEGER { off(1),on(2),cycle(3) }
	ACCESS					read-only
	STATUS					mandatory
	DESCRIPTION			"PG Outlet 2 state"
	::= { node27PG 22 }

pgNode27Out2Cmd				OBJECT-TYPE
	SYNTAX					INTEGER { off(1),on(2),cycle(3) }
	ACCESS					read-write
	STATUS					mandatory
	DESCRIPTION			"PG Outlet 2 command"
	::= { node27PG 23 }

pgNode27Out3Name				OBJECT-TYPE
	SYNTAX					DisplayString
	ACCESS					read-write
	STATUS					mandatory
	DESCRIPTION			"PG Outlet 3 name"
	::= { node27PG 24 }

pgNode27Out3CustVoice	OBJECT-TYPE
	SYNTAX					DisplayString
	ACCESS					read-write
	STATUS					mandatory
	DESCRIPTION			"PG Outlet 3 custom voice"
	::= { node27PG 25 }

pgNode27Out3Volts			OBJECT-TYPE
	SYNTAX					INTEGER
	ACCESS					read-only
	STATUS					mandatory
	DESCRIPTION			"PG Outlet 3 volts"
	::= { node27PG 26 }

pgNode27Out3Amps				OBJECT-TYPE
	SYNTAX					INTEGER
	ACCESS					read-only
	STATUS					mandatory
	DESCRIPTION			"PG Outlet 3 amps"
	::= { node27PG 27 }

pgNode27Out3Watts			OBJECT-TYPE
	SYNTAX					INTEGER
	ACCESS					read-only
	STATUS					mandatory
	DESCRIPTION			"PG Outlet 3 watts"
	::= { node27PG 28 }

pgNode27Out3State			OBJECT-TYPE
	SYNTAX					INTEGER { off(1),on(2),cycle(3) }
	ACCESS					read-only
	STATUS					mandatory
	DESCRIPTION			"PG Outlet 3 state"
	::= { node27PG 29 }

pgNode27Out3Cmd				OBJECT-TYPE
	SYNTAX					INTEGER { off(1),on(2),cycle(3) }
	ACCESS					read-write
	STATUS					mandatory
	DESCRIPTION			"PG Outlet 3 command"
	::= { node27PG 30 }

pgNode27Out4Name				OBJECT-TYPE
	SYNTAX					DisplayString
	ACCESS					read-write
	STATUS					mandatory
	DESCRIPTION			"PG Outlet 4 name"
	::= { node27PG 31 }

pgNode27Out4CustVoice	OBJECT-TYPE
	SYNTAX					DisplayString
	ACCESS					read-write
	STATUS					mandatory
	DESCRIPTION			"PG Outlet 4 custom voice"
	::= { node27PG 32 }

pgNode27Out4Volts			OBJECT-TYPE
	SYNTAX					INTEGER
	ACCESS					read-only
	STATUS					mandatory
	DESCRIPTION			"PG Outlet 4 volts"
	::= { node27PG 33 }

pgNode27Out4Amps				OBJECT-TYPE
	SYNTAX					INTEGER
	ACCESS					read-only
	STATUS					mandatory
	DESCRIPTION			"PG Outlet 4 amps"
	::= { node27PG 34 }

pgNode27Out4Watts			OBJECT-TYPE
	SYNTAX					INTEGER
	ACCESS					read-only
	STATUS					mandatory
	DESCRIPTION			"PG Outlet 4 watts"
	::= { node27PG 35 }

pgNode27Out4State			OBJECT-TYPE
	SYNTAX					INTEGER { off(1),on(2),cycle(3) }
	ACCESS					read-only
	STATUS					mandatory
	DESCRIPTION			"PG Outlet 4 state"
	::= { node27PG 36 }

pgNode27Out4Cmd				OBJECT-TYPE
	SYNTAX					INTEGER { off(1),on(2),cycle(3) }
	ACCESS					read-write
	STATUS					mandatory
	DESCRIPTION			"PG Outlet 4 command"
	::= { node27PG 37 }

pgNode27Out5Name				OBJECT-TYPE
	SYNTAX					DisplayString
	ACCESS					read-write
	STATUS					mandatory
	DESCRIPTION			"PG Outlet 5 name"
	::= { node27PG 38 }

pgNode27Out5CustVoice	OBJECT-TYPE
	SYNTAX					DisplayString
	ACCESS					read-write
	STATUS					mandatory
	DESCRIPTION			"PG Outlet 5 custom voice"
	::= { node27PG 39 }

pgNode27Out5Volts			OBJECT-TYPE
	SYNTAX					INTEGER
	ACCESS					read-only
	STATUS					mandatory
	DESCRIPTION			"PG Outlet 5 volts"
	::= { node27PG 40 }

pgNode27Out5Amps				OBJECT-TYPE
	SYNTAX					INTEGER
	ACCESS					read-only
	STATUS					mandatory
	DESCRIPTION			"PG Outlet 5 amps"
	::= { node27PG 41 }

pgNode27Out5Watts			OBJECT-TYPE
	SYNTAX					INTEGER
	ACCESS					read-only
	STATUS					mandatory
	DESCRIPTION			"PG Outlet 5 watts"
	::= { node27PG 42 }

pgNode27Out5State			OBJECT-TYPE
	SYNTAX					INTEGER { off(1),on(2),cycle(3) }
	ACCESS					read-only
	STATUS					mandatory
	DESCRIPTION			"PG Outlet 5 state"
	::= { node27PG 43 }

pgNode27Out5Cmd				OBJECT-TYPE
	SYNTAX					INTEGER { off(1),on(2),cycle(3) }
	ACCESS					read-write
	STATUS					mandatory
	DESCRIPTION			"PG Outlet 5 command"
	::= { node27PG 44 }

pgNode27Out6Name				OBJECT-TYPE
	SYNTAX					DisplayString
	ACCESS					read-write
	STATUS					mandatory
	DESCRIPTION			"PG Outlet 6 name"
	::= { node27PG 45 }

pgNode27Out6CustVoice	OBJECT-TYPE
	SYNTAX					DisplayString
	ACCESS					read-write
	STATUS					mandatory
	DESCRIPTION			"PG Outlet 6 custom voice"
	::= { node27PG 46 }

pgNode27Out6Volts			OBJECT-TYPE
	SYNTAX					INTEGER
	ACCESS					read-only
	STATUS					mandatory
	DESCRIPTION			"PG Outlet 6 volts"
	::= { node27PG 47 }

pgNode27Out6Amps				OBJECT-TYPE
	SYNTAX					INTEGER
	ACCESS					read-only
	STATUS					mandatory
	DESCRIPTION			"PG Outlet 6 amps"
	::= { node27PG 48 }

pgNode27Out6Watts			OBJECT-TYPE
	SYNTAX					INTEGER
	ACCESS					read-only
	STATUS					mandatory
	DESCRIPTION			"PG Outlet 6 watts"
	::= { node27PG 49 }

pgNode27Out6State			OBJECT-TYPE
	SYNTAX					INTEGER { off(1),on(2),cycle(3) }
	ACCESS					read-only
	STATUS					mandatory
	DESCRIPTION			"PG Outlet 6 state"
	::= { node27PG 50 }

pgNode27Out6Cmd				OBJECT-TYPE
	SYNTAX					INTEGER { off(1),on(2),cycle(3) }
	ACCESS					read-write
	STATUS					mandatory
	DESCRIPTION			"PG Outlet 6 command"
	::= { node27PG 51 }

pgNode27Out7Name				OBJECT-TYPE
	SYNTAX					DisplayString
	ACCESS					read-write
	STATUS					mandatory
	DESCRIPTION			"PG Outlet 7 name"
	::= { node27PG 52 }

pgNode27Out7CustVoice	OBJECT-TYPE
	SYNTAX					DisplayString
	ACCESS					read-write
	STATUS					mandatory
	DESCRIPTION			"PG Outlet 7 custom voice"
	::= { node27PG 53 }

pgNode27Out7Volts			OBJECT-TYPE
	SYNTAX					INTEGER
	ACCESS					read-only
	STATUS					mandatory
	DESCRIPTION			"PG Outlet 7 volts"
	::= { node27PG 54 }

pgNode27Out7Amps				OBJECT-TYPE
	SYNTAX					INTEGER
	ACCESS					read-only
	STATUS					mandatory
	DESCRIPTION			"PG Outlet 7 amps"
	::= { node27PG 55 }

pgNode27Out7Watts			OBJECT-TYPE
	SYNTAX					INTEGER
	ACCESS					read-only
	STATUS					mandatory
	DESCRIPTION			"PG Outlet 7 watts"
	::= { node27PG 56 }

pgNode27Out7State			OBJECT-TYPE
	SYNTAX					INTEGER { off(1),on(2),cycle(3) }
	ACCESS					read-only
	STATUS					mandatory
	DESCRIPTION			"PG Outlet 7 state"
	::= { node27PG 57 }

pgNode27Out7Cmd				OBJECT-TYPE
	SYNTAX					INTEGER { off(1),on(2),cycle(3) }
	ACCESS					read-write
	STATUS					mandatory
	DESCRIPTION			"PG Outlet 7 command"
	::= { node27PG 58 }

pgNode27Out8Name				OBJECT-TYPE
	SYNTAX					DisplayString
	ACCESS					read-write
	STATUS					mandatory
	DESCRIPTION			"PG Outlet 8 name"
	::= { node27PG 59 }

pgNode27Out8CustVoice	OBJECT-TYPE
	SYNTAX					DisplayString
	ACCESS					read-write
	STATUS					mandatory
	DESCRIPTION			"PG Outlet 8 custom voice"
	::= { node27PG 60 }

pgNode27Out8Volts			OBJECT-TYPE
	SYNTAX					INTEGER
	ACCESS					read-only
	STATUS					mandatory
	DESCRIPTION			"PG Outlet 8 volts"
	::= { node27PG 61 }

pgNode27Out8Amps				OBJECT-TYPE
	SYNTAX					INTEGER
	ACCESS					read-only
	STATUS					mandatory
	DESCRIPTION			"PG Outlet 8 amps"
	::= { node27PG 62 }

pgNode27Out8Watts			OBJECT-TYPE
	SYNTAX					INTEGER
	ACCESS					read-only
	STATUS					mandatory
	DESCRIPTION			"PG Outlet 8 watts"
	::= { node27PG 63 }

pgNode27Out8State			OBJECT-TYPE
	SYNTAX					INTEGER { off(1),on(2),cycle(3) }
	ACCESS					read-only
	STATUS					mandatory
	DESCRIPTION			"PG Outlet 8 state"
	::= { node27PG 64 }

pgNode27Out8Cmd				OBJECT-TYPE
	SYNTAX					INTEGER { off(1),on(2),cycle(3) }
	ACCESS					read-write
	STATUS					mandatory
	DESCRIPTION			"PG Outlet 8 command"
	::= { node27PG 65 }

pgNode28InUse					OBJECT-TYPE
	SYNTAX					INTEGER { false(1),true(2) }
	ACCESS					read-only
	STATUS					mandatory
	DESCRIPTION			"PG in use"
	::= { node28PG 1 }

pgNode28Status					OBJECT-TYPE
	SYNTAX					INTEGER { normal(1),pending(2), trouble(3) }
	ACCESS					read-only
	STATUS					mandatory
	DESCRIPTION			"PG status"
	::= { node28PG 2 }

pgNode28StatusSupport	OBJECT-TYPE
	SYNTAX					INTEGER { true1(1),false(2) }
	ACCESS					read-only
	STATUS					mandatory
	DESCRIPTION			"PG status support level"
	::= { node28PG 3 }

pgNode28Ver						OBJECT-TYPE
	SYNTAX					INTEGER { pgate1(1),pgate2(2) }
	ACCESS					read-only
	STATUS					mandatory
	DESCRIPTION			"PG version"
	::= { node28PG 4 }

pgNode28Volts					OBJECT-TYPE
	SYNTAX					INTEGER
	ACCESS					read-only
	STATUS					mandatory
	DESCRIPTION			"PG voltage"
	::= { node28PG 5 }

pgNode28Amps						OBJECT-TYPE
	SYNTAX					INTEGER
	ACCESS					read-only
	STATUS					mandatory
	DESCRIPTION			"PG amps"
	::= { node28PG 6 }

pgNode28Watts					OBJECT-TYPE
	SYNTAX					INTEGER
	ACCESS					read-only
	STATUS					mandatory
	DESCRIPTION			"PG Watts"
	::= { node28PG 7 }

pgNode28Name						OBJECT-TYPE
	SYNTAX					DisplayString
	ACCESS					read-write
	STATUS					mandatory
	DESCRIPTION			"PG name"
	::= { node28PG 8 }

pgNode28CustVoice			OBJECT-TYPE
	SYNTAX					DisplayString
	ACCESS					read-write
	STATUS					mandatory
	DESCRIPTION			"PG custom voice"
	::= { node28PG 9 }

pgNode28Out1Name				OBJECT-TYPE
	SYNTAX					DisplayString
	ACCESS					read-write
	STATUS					mandatory
	DESCRIPTION			"PG Outlet 1 name"
	::= { node28PG 10 }

pgNode28Out1CustVoice	OBJECT-TYPE
	SYNTAX					DisplayString
	ACCESS					read-write
	STATUS					mandatory
	DESCRIPTION			"PG Outlet 1 custom voice"
	::= { node28PG 11 }

pgNode28Out1Volts			OBJECT-TYPE
	SYNTAX					INTEGER
	ACCESS					read-only
	STATUS					mandatory
	DESCRIPTION			"PG Outlet 1 volts"
	::= { node28PG 12 }

pgNode28Out1Amps				OBJECT-TYPE
	SYNTAX					INTEGER
	ACCESS					read-only
	STATUS					mandatory
	DESCRIPTION			"PG Outlet 1 amps"
	::= { node28PG 13 }

pgNode28Out1Watts			OBJECT-TYPE
	SYNTAX					INTEGER
	ACCESS					read-only
	STATUS					mandatory
	DESCRIPTION			"PG Outlet 1 watts"
	::= { node28PG 14 }

pgNode28Out1State			OBJECT-TYPE
	SYNTAX					INTEGER { off(1),on(2),cycle(3) }
	ACCESS					read-only
	STATUS					mandatory
	DESCRIPTION			"PG Outlet 1 state"
	::= { node28PG 15 }

pgNode28Out1Cmd				OBJECT-TYPE
	SYNTAX					INTEGER { off(1),on(2),cycle(3) }
	ACCESS					read-write
	STATUS					mandatory
	DESCRIPTION			"PG Outlet 1 command"
	::= { node28PG 16 }

pgNode28Out2Name				OBJECT-TYPE
	SYNTAX					DisplayString
	ACCESS					read-write
	STATUS					mandatory
	DESCRIPTION			"PG Outlet 2 name"
	::= { node28PG 17 }

pgNode28Out2CustVoice	OBJECT-TYPE
	SYNTAX					DisplayString
	ACCESS					read-write
	STATUS					mandatory
	DESCRIPTION			"PG Outlet 2 custom voice"
	::= { node28PG 18 }

pgNode28Out2Volts			OBJECT-TYPE
	SYNTAX					INTEGER
	ACCESS					read-only
	STATUS					mandatory
	DESCRIPTION			"PG Outlet 2 volts"
	::= { node28PG 19 }

pgNode28Out2Amps				OBJECT-TYPE
	SYNTAX					INTEGER
	ACCESS					read-only
	STATUS					mandatory
	DESCRIPTION			"PG Outlet 2 amps"
	::= { node28PG 20 }

pgNode28Out2Watts			OBJECT-TYPE
	SYNTAX					INTEGER
	ACCESS					read-only
	STATUS					mandatory
	DESCRIPTION			"PG Outlet 2 watts"
	::= { node28PG 21 }

pgNode28Out2State			OBJECT-TYPE
	SYNTAX					INTEGER { off(1),on(2),cycle(3) }
	ACCESS					read-only
	STATUS					mandatory
	DESCRIPTION			"PG Outlet 2 state"
	::= { node28PG 22 }

pgNode28Out2Cmd				OBJECT-TYPE
	SYNTAX					INTEGER { off(1),on(2),cycle(3) }
	ACCESS					read-write
	STATUS					mandatory
	DESCRIPTION			"PG Outlet 2 command"
	::= { node28PG 23 }

pgNode28Out3Name				OBJECT-TYPE
	SYNTAX					DisplayString
	ACCESS					read-write
	STATUS					mandatory
	DESCRIPTION			"PG Outlet 3 name"
	::= { node28PG 24 }

pgNode28Out3CustVoice	OBJECT-TYPE
	SYNTAX					DisplayString
	ACCESS					read-write
	STATUS					mandatory
	DESCRIPTION			"PG Outlet 3 custom voice"
	::= { node28PG 25 }

pgNode28Out3Volts			OBJECT-TYPE
	SYNTAX					INTEGER
	ACCESS					read-only
	STATUS					mandatory
	DESCRIPTION			"PG Outlet 3 volts"
	::= { node28PG 26 }

pgNode28Out3Amps				OBJECT-TYPE
	SYNTAX					INTEGER
	ACCESS					read-only
	STATUS					mandatory
	DESCRIPTION			"PG Outlet 3 amps"
	::= { node28PG 27 }

pgNode28Out3Watts			OBJECT-TYPE
	SYNTAX					INTEGER
	ACCESS					read-only
	STATUS					mandatory
	DESCRIPTION			"PG Outlet 3 watts"
	::= { node28PG 28 }

pgNode28Out3State			OBJECT-TYPE
	SYNTAX					INTEGER { off(1),on(2),cycle(3) }
	ACCESS					read-only
	STATUS					mandatory
	DESCRIPTION			"PG Outlet 3 state"
	::= { node28PG 29 }

pgNode28Out3Cmd				OBJECT-TYPE
	SYNTAX					INTEGER { off(1),on(2),cycle(3) }
	ACCESS					read-write
	STATUS					mandatory
	DESCRIPTION			"PG Outlet 3 command"
	::= { node28PG 30 }

pgNode28Out4Name				OBJECT-TYPE
	SYNTAX					DisplayString
	ACCESS					read-write
	STATUS					mandatory
	DESCRIPTION			"PG Outlet 4 name"
	::= { node28PG 31 }

pgNode28Out4CustVoice	OBJECT-TYPE
	SYNTAX					DisplayString
	ACCESS					read-write
	STATUS					mandatory
	DESCRIPTION			"PG Outlet 4 custom voice"
	::= { node28PG 32 }

pgNode28Out4Volts			OBJECT-TYPE
	SYNTAX					INTEGER
	ACCESS					read-only
	STATUS					mandatory
	DESCRIPTION			"PG Outlet 4 volts"
	::= { node28PG 33 }

pgNode28Out4Amps				OBJECT-TYPE
	SYNTAX					INTEGER
	ACCESS					read-only
	STATUS					mandatory
	DESCRIPTION			"PG Outlet 4 amps"
	::= { node28PG 34 }

pgNode28Out4Watts			OBJECT-TYPE
	SYNTAX					INTEGER
	ACCESS					read-only
	STATUS					mandatory
	DESCRIPTION			"PG Outlet 4 watts"
	::= { node28PG 35 }

pgNode28Out4State			OBJECT-TYPE
	SYNTAX					INTEGER { off(1),on(2),cycle(3) }
	ACCESS					read-only
	STATUS					mandatory
	DESCRIPTION			"PG Outlet 4 state"
	::= { node28PG 36 }

pgNode28Out4Cmd				OBJECT-TYPE
	SYNTAX					INTEGER { off(1),on(2),cycle(3) }
	ACCESS					read-write
	STATUS					mandatory
	DESCRIPTION			"PG Outlet 4 command"
	::= { node28PG 37 }

pgNode28Out5Name				OBJECT-TYPE
	SYNTAX					DisplayString
	ACCESS					read-write
	STATUS					mandatory
	DESCRIPTION			"PG Outlet 5 name"
	::= { node28PG 38 }

pgNode28Out5CustVoice	OBJECT-TYPE
	SYNTAX					DisplayString
	ACCESS					read-write
	STATUS					mandatory
	DESCRIPTION			"PG Outlet 5 custom voice"
	::= { node28PG 39 }

pgNode28Out5Volts			OBJECT-TYPE
	SYNTAX					INTEGER
	ACCESS					read-only
	STATUS					mandatory
	DESCRIPTION			"PG Outlet 5 volts"
	::= { node28PG 40 }

pgNode28Out5Amps				OBJECT-TYPE
	SYNTAX					INTEGER
	ACCESS					read-only
	STATUS					mandatory
	DESCRIPTION			"PG Outlet 5 amps"
	::= { node28PG 41 }

pgNode28Out5Watts			OBJECT-TYPE
	SYNTAX					INTEGER
	ACCESS					read-only
	STATUS					mandatory
	DESCRIPTION			"PG Outlet 5 watts"
	::= { node28PG 42 }

pgNode28Out5State			OBJECT-TYPE
	SYNTAX					INTEGER { off(1),on(2),cycle(3) }
	ACCESS					read-only
	STATUS					mandatory
	DESCRIPTION			"PG Outlet 5 state"
	::= { node28PG 43 }

pgNode28Out5Cmd				OBJECT-TYPE
	SYNTAX					INTEGER { off(1),on(2),cycle(3) }
	ACCESS					read-write
	STATUS					mandatory
	DESCRIPTION			"PG Outlet 5 command"
	::= { node28PG 44 }

pgNode28Out6Name				OBJECT-TYPE
	SYNTAX					DisplayString
	ACCESS					read-write
	STATUS					mandatory
	DESCRIPTION			"PG Outlet 6 name"
	::= { node28PG 45 }

pgNode28Out6CustVoice	OBJECT-TYPE
	SYNTAX					DisplayString
	ACCESS					read-write
	STATUS					mandatory
	DESCRIPTION			"PG Outlet 6 custom voice"
	::= { node28PG 46 }

pgNode28Out6Volts			OBJECT-TYPE
	SYNTAX					INTEGER
	ACCESS					read-only
	STATUS					mandatory
	DESCRIPTION			"PG Outlet 6 volts"
	::= { node28PG 47 }

pgNode28Out6Amps				OBJECT-TYPE
	SYNTAX					INTEGER
	ACCESS					read-only
	STATUS					mandatory
	DESCRIPTION			"PG Outlet 6 amps"
	::= { node28PG 48 }

pgNode28Out6Watts			OBJECT-TYPE
	SYNTAX					INTEGER
	ACCESS					read-only
	STATUS					mandatory
	DESCRIPTION			"PG Outlet 6 watts"
	::= { node28PG 49 }

pgNode28Out6State			OBJECT-TYPE
	SYNTAX					INTEGER { off(1),on(2),cycle(3) }
	ACCESS					read-only
	STATUS					mandatory
	DESCRIPTION			"PG Outlet 6 state"
	::= { node28PG 50 }

pgNode28Out6Cmd				OBJECT-TYPE
	SYNTAX					INTEGER { off(1),on(2),cycle(3) }
	ACCESS					read-write
	STATUS					mandatory
	DESCRIPTION			"PG Outlet 6 command"
	::= { node28PG 51 }

pgNode28Out7Name				OBJECT-TYPE
	SYNTAX					DisplayString
	ACCESS					read-write
	STATUS					mandatory
	DESCRIPTION			"PG Outlet 7 name"
	::= { node28PG 52 }

pgNode28Out7CustVoice	OBJECT-TYPE
	SYNTAX					DisplayString
	ACCESS					read-write
	STATUS					mandatory
	DESCRIPTION			"PG Outlet 7 custom voice"
	::= { node28PG 53 }

pgNode28Out7Volts			OBJECT-TYPE
	SYNTAX					INTEGER
	ACCESS					read-only
	STATUS					mandatory
	DESCRIPTION			"PG Outlet 7 volts"
	::= { node28PG 54 }

pgNode28Out7Amps				OBJECT-TYPE
	SYNTAX					INTEGER
	ACCESS					read-only
	STATUS					mandatory
	DESCRIPTION			"PG Outlet 7 amps"
	::= { node28PG 55 }

pgNode28Out7Watts			OBJECT-TYPE
	SYNTAX					INTEGER
	ACCESS					read-only
	STATUS					mandatory
	DESCRIPTION			"PG Outlet 7 watts"
	::= { node28PG 56 }

pgNode28Out7State			OBJECT-TYPE
	SYNTAX					INTEGER { off(1),on(2),cycle(3) }
	ACCESS					read-only
	STATUS					mandatory
	DESCRIPTION			"PG Outlet 7 state"
	::= { node28PG 57 }

pgNode28Out7Cmd				OBJECT-TYPE
	SYNTAX					INTEGER { off(1),on(2),cycle(3) }
	ACCESS					read-write
	STATUS					mandatory
	DESCRIPTION			"PG Outlet 7 command"
	::= { node28PG 58 }

pgNode28Out8Name				OBJECT-TYPE
	SYNTAX					DisplayString
	ACCESS					read-write
	STATUS					mandatory
	DESCRIPTION			"PG Outlet 8 name"
	::= { node28PG 59 }

pgNode28Out8CustVoice	OBJECT-TYPE
	SYNTAX					DisplayString
	ACCESS					read-write
	STATUS					mandatory
	DESCRIPTION			"PG Outlet 8 custom voice"
	::= { node28PG 60 }

pgNode28Out8Volts			OBJECT-TYPE
	SYNTAX					INTEGER
	ACCESS					read-only
	STATUS					mandatory
	DESCRIPTION			"PG Outlet 8 volts"
	::= { node28PG 61 }

pgNode28Out8Amps				OBJECT-TYPE
	SYNTAX					INTEGER
	ACCESS					read-only
	STATUS					mandatory
	DESCRIPTION			"PG Outlet 8 amps"
	::= { node28PG 62 }

pgNode28Out8Watts			OBJECT-TYPE
	SYNTAX					INTEGER
	ACCESS					read-only
	STATUS					mandatory
	DESCRIPTION			"PG Outlet 8 watts"
	::= { node28PG 63 }

pgNode28Out8State			OBJECT-TYPE
	SYNTAX					INTEGER { off(1),on(2),cycle(3) }
	ACCESS					read-only
	STATUS					mandatory
	DESCRIPTION			"PG Outlet 8 state"
	::= { node28PG 64 }

pgNode28Out8Cmd				OBJECT-TYPE
	SYNTAX					INTEGER { off(1),on(2),cycle(3) }
	ACCESS					read-write
	STATUS					mandatory
	DESCRIPTION			"PG Outlet 8 command"
	::= { node28PG 65 }

pgNode29InUse					OBJECT-TYPE
	SYNTAX					INTEGER { false(1),true(2) }
	ACCESS					read-only
	STATUS					mandatory
	DESCRIPTION			"PG in use"
	::= { node29PG 1 }

pgNode29Status					OBJECT-TYPE
	SYNTAX					INTEGER { normal(1),pending(2), trouble(3) }
	ACCESS					read-only
	STATUS					mandatory
	DESCRIPTION			"PG status"
	::= { node29PG 2 }

pgNode29StatusSupport	OBJECT-TYPE
	SYNTAX					INTEGER { true1(1),false(2) }
	ACCESS					read-only
	STATUS					mandatory
	DESCRIPTION			"PG status support level"
	::= { node29PG 3 }

pgNode29Ver						OBJECT-TYPE
	SYNTAX					INTEGER { pgate1(1),pgate2(2) }
	ACCESS					read-only
	STATUS					mandatory
	DESCRIPTION			"PG version"
	::= { node29PG 4 }

pgNode29Volts					OBJECT-TYPE
	SYNTAX					INTEGER
	ACCESS					read-only
	STATUS					mandatory
	DESCRIPTION			"PG voltage"
	::= { node29PG 5 }

pgNode29Amps						OBJECT-TYPE
	SYNTAX					INTEGER
	ACCESS					read-only
	STATUS					mandatory
	DESCRIPTION			"PG amps"
	::= { node29PG 6 }

pgNode29Watts					OBJECT-TYPE
	SYNTAX					INTEGER
	ACCESS					read-only
	STATUS					mandatory
	DESCRIPTION			"PG Watts"
	::= { node29PG 7 }

pgNode29Name						OBJECT-TYPE
	SYNTAX					DisplayString
	ACCESS					read-write
	STATUS					mandatory
	DESCRIPTION			"PG name"
	::= { node29PG 8 }

pgNode29CustVoice			OBJECT-TYPE
	SYNTAX					DisplayString
	ACCESS					read-write
	STATUS					mandatory
	DESCRIPTION			"PG custom voice"
	::= { node29PG 9 }

pgNode29Out1Name				OBJECT-TYPE
	SYNTAX					DisplayString
	ACCESS					read-write
	STATUS					mandatory
	DESCRIPTION			"PG Outlet 1 name"
	::= { node29PG 10 }

pgNode29Out1CustVoice	OBJECT-TYPE
	SYNTAX					DisplayString
	ACCESS					read-write
	STATUS					mandatory
	DESCRIPTION			"PG Outlet 1 custom voice"
	::= { node29PG 11 }

pgNode29Out1Volts			OBJECT-TYPE
	SYNTAX					INTEGER
	ACCESS					read-only
	STATUS					mandatory
	DESCRIPTION			"PG Outlet 1 volts"
	::= { node29PG 12 }

pgNode29Out1Amps				OBJECT-TYPE
	SYNTAX					INTEGER
	ACCESS					read-only
	STATUS					mandatory
	DESCRIPTION			"PG Outlet 1 amps"
	::= { node29PG 13 }

pgNode29Out1Watts			OBJECT-TYPE
	SYNTAX					INTEGER
	ACCESS					read-only
	STATUS					mandatory
	DESCRIPTION			"PG Outlet 1 watts"
	::= { node29PG 14 }

pgNode29Out1State			OBJECT-TYPE
	SYNTAX					INTEGER { off(1),on(2),cycle(3) }
	ACCESS					read-only
	STATUS					mandatory
	DESCRIPTION			"PG Outlet 1 state"
	::= { node29PG 15 }

pgNode29Out1Cmd				OBJECT-TYPE
	SYNTAX					INTEGER { off(1),on(2),cycle(3) }
	ACCESS					read-write
	STATUS					mandatory
	DESCRIPTION			"PG Outlet 1 command"
	::= { node29PG 16 }

pgNode29Out2Name				OBJECT-TYPE
	SYNTAX					DisplayString
	ACCESS					read-write
	STATUS					mandatory
	DESCRIPTION			"PG Outlet 2 name"
	::= { node29PG 17 }

pgNode29Out2CustVoice	OBJECT-TYPE
	SYNTAX					DisplayString
	ACCESS					read-write
	STATUS					mandatory
	DESCRIPTION			"PG Outlet 2 custom voice"
	::= { node29PG 18 }

pgNode29Out2Volts			OBJECT-TYPE
	SYNTAX					INTEGER
	ACCESS					read-only
	STATUS					mandatory
	DESCRIPTION			"PG Outlet 2 volts"
	::= { node29PG 19 }

pgNode29Out2Amps				OBJECT-TYPE
	SYNTAX					INTEGER
	ACCESS					read-only
	STATUS					mandatory
	DESCRIPTION			"PG Outlet 2 amps"
	::= { node29PG 20 }

pgNode29Out2Watts			OBJECT-TYPE
	SYNTAX					INTEGER
	ACCESS					read-only
	STATUS					mandatory
	DESCRIPTION			"PG Outlet 2 watts"
	::= { node29PG 21 }

pgNode29Out2State			OBJECT-TYPE
	SYNTAX					INTEGER { off(1),on(2),cycle(3) }
	ACCESS					read-only
	STATUS					mandatory
	DESCRIPTION			"PG Outlet 2 state"
	::= { node29PG 22 }

pgNode29Out2Cmd				OBJECT-TYPE
	SYNTAX					INTEGER { off(1),on(2),cycle(3) }
	ACCESS					read-write
	STATUS					mandatory
	DESCRIPTION			"PG Outlet 2 command"
	::= { node29PG 23 }

pgNode29Out3Name				OBJECT-TYPE
	SYNTAX					DisplayString
	ACCESS					read-write
	STATUS					mandatory
	DESCRIPTION			"PG Outlet 3 name"
	::= { node29PG 24 }

pgNode29Out3CustVoice	OBJECT-TYPE
	SYNTAX					DisplayString
	ACCESS					read-write
	STATUS					mandatory
	DESCRIPTION			"PG Outlet 3 custom voice"
	::= { node29PG 25 }

pgNode29Out3Volts			OBJECT-TYPE
	SYNTAX					INTEGER
	ACCESS					read-only
	STATUS					mandatory
	DESCRIPTION			"PG Outlet 3 volts"
	::= { node29PG 26 }

pgNode29Out3Amps				OBJECT-TYPE
	SYNTAX					INTEGER
	ACCESS					read-only
	STATUS					mandatory
	DESCRIPTION			"PG Outlet 3 amps"
	::= { node29PG 27 }

pgNode29Out3Watts			OBJECT-TYPE
	SYNTAX					INTEGER
	ACCESS					read-only
	STATUS					mandatory
	DESCRIPTION			"PG Outlet 3 watts"
	::= { node29PG 28 }

pgNode29Out3State			OBJECT-TYPE
	SYNTAX					INTEGER { off(1),on(2),cycle(3) }
	ACCESS					read-only
	STATUS					mandatory
	DESCRIPTION			"PG Outlet 3 state"
	::= { node29PG 29 }

pgNode29Out3Cmd				OBJECT-TYPE
	SYNTAX					INTEGER { off(1),on(2),cycle(3) }
	ACCESS					read-write
	STATUS					mandatory
	DESCRIPTION			"PG Outlet 3 command"
	::= { node29PG 30 }

pgNode29Out4Name				OBJECT-TYPE
	SYNTAX					DisplayString
	ACCESS					read-write
	STATUS					mandatory
	DESCRIPTION			"PG Outlet 4 name"
	::= { node29PG 31 }

pgNode29Out4CustVoice	OBJECT-TYPE
	SYNTAX					DisplayString
	ACCESS					read-write
	STATUS					mandatory
	DESCRIPTION			"PG Outlet 4 custom voice"
	::= { node29PG 32 }

pgNode29Out4Volts			OBJECT-TYPE
	SYNTAX					INTEGER
	ACCESS					read-only
	STATUS					mandatory
	DESCRIPTION			"PG Outlet 4 volts"
	::= { node29PG 33 }

pgNode29Out4Amps				OBJECT-TYPE
	SYNTAX					INTEGER
	ACCESS					read-only
	STATUS					mandatory
	DESCRIPTION			"PG Outlet 4 amps"
	::= { node29PG 34 }

pgNode29Out4Watts			OBJECT-TYPE
	SYNTAX					INTEGER
	ACCESS					read-only
	STATUS					mandatory
	DESCRIPTION			"PG Outlet 4 watts"
	::= { node29PG 35 }

pgNode29Out4State			OBJECT-TYPE
	SYNTAX					INTEGER { off(1),on(2),cycle(3) }
	ACCESS					read-only
	STATUS					mandatory
	DESCRIPTION			"PG Outlet 4 state"
	::= { node29PG 36 }

pgNode29Out4Cmd				OBJECT-TYPE
	SYNTAX					INTEGER { off(1),on(2),cycle(3) }
	ACCESS					read-write
	STATUS					mandatory
	DESCRIPTION			"PG Outlet 4 command"
	::= { node29PG 37 }

pgNode29Out5Name				OBJECT-TYPE
	SYNTAX					DisplayString
	ACCESS					read-write
	STATUS					mandatory
	DESCRIPTION			"PG Outlet 5 name"
	::= { node29PG 38 }

pgNode29Out5CustVoice	OBJECT-TYPE
	SYNTAX					DisplayString
	ACCESS					read-write
	STATUS					mandatory
	DESCRIPTION			"PG Outlet 5 custom voice"
	::= { node29PG 39 }

pgNode29Out5Volts			OBJECT-TYPE
	SYNTAX					INTEGER
	ACCESS					read-only
	STATUS					mandatory
	DESCRIPTION			"PG Outlet 5 volts"
	::= { node29PG 40 }

pgNode29Out5Amps				OBJECT-TYPE
	SYNTAX					INTEGER
	ACCESS					read-only
	STATUS					mandatory
	DESCRIPTION			"PG Outlet 5 amps"
	::= { node29PG 41 }

pgNode29Out5Watts			OBJECT-TYPE
	SYNTAX					INTEGER
	ACCESS					read-only
	STATUS					mandatory
	DESCRIPTION			"PG Outlet 5 watts"
	::= { node29PG 42 }

pgNode29Out5State			OBJECT-TYPE
	SYNTAX					INTEGER { off(1),on(2),cycle(3) }
	ACCESS					read-only
	STATUS					mandatory
	DESCRIPTION			"PG Outlet 5 state"
	::= { node29PG 43 }

pgNode29Out5Cmd				OBJECT-TYPE
	SYNTAX					INTEGER { off(1),on(2),cycle(3) }
	ACCESS					read-write
	STATUS					mandatory
	DESCRIPTION			"PG Outlet 5 command"
	::= { node29PG 44 }

pgNode29Out6Name				OBJECT-TYPE
	SYNTAX					DisplayString
	ACCESS					read-write
	STATUS					mandatory
	DESCRIPTION			"PG Outlet 6 name"
	::= { node29PG 45 }

pgNode29Out6CustVoice	OBJECT-TYPE
	SYNTAX					DisplayString
	ACCESS					read-write
	STATUS					mandatory
	DESCRIPTION			"PG Outlet 6 custom voice"
	::= { node29PG 46 }

pgNode29Out6Volts			OBJECT-TYPE
	SYNTAX					INTEGER
	ACCESS					read-only
	STATUS					mandatory
	DESCRIPTION			"PG Outlet 6 volts"
	::= { node29PG 47 }

pgNode29Out6Amps				OBJECT-TYPE
	SYNTAX					INTEGER
	ACCESS					read-only
	STATUS					mandatory
	DESCRIPTION			"PG Outlet 6 amps"
	::= { node29PG 48 }

pgNode29Out6Watts			OBJECT-TYPE
	SYNTAX					INTEGER
	ACCESS					read-only
	STATUS					mandatory
	DESCRIPTION			"PG Outlet 6 watts"
	::= { node29PG 49 }

pgNode29Out6State			OBJECT-TYPE
	SYNTAX					INTEGER { off(1),on(2),cycle(3) }
	ACCESS					read-only
	STATUS					mandatory
	DESCRIPTION			"PG Outlet 6 state"
	::= { node29PG 50 }

pgNode29Out6Cmd				OBJECT-TYPE
	SYNTAX					INTEGER { off(1),on(2),cycle(3) }
	ACCESS					read-write
	STATUS					mandatory
	DESCRIPTION			"PG Outlet 6 command"
	::= { node29PG 51 }

pgNode29Out7Name				OBJECT-TYPE
	SYNTAX					DisplayString
	ACCESS					read-write
	STATUS					mandatory
	DESCRIPTION			"PG Outlet 7 name"
	::= { node29PG 52 }

pgNode29Out7CustVoice	OBJECT-TYPE
	SYNTAX					DisplayString
	ACCESS					read-write
	STATUS					mandatory
	DESCRIPTION			"PG Outlet 7 custom voice"
	::= { node29PG 53 }

pgNode29Out7Volts			OBJECT-TYPE
	SYNTAX					INTEGER
	ACCESS					read-only
	STATUS					mandatory
	DESCRIPTION			"PG Outlet 7 volts"
	::= { node29PG 54 }

pgNode29Out7Amps				OBJECT-TYPE
	SYNTAX					INTEGER
	ACCESS					read-only
	STATUS					mandatory
	DESCRIPTION			"PG Outlet 7 amps"
	::= { node29PG 55 }

pgNode29Out7Watts			OBJECT-TYPE
	SYNTAX					INTEGER
	ACCESS					read-only
	STATUS					mandatory
	DESCRIPTION			"PG Outlet 7 watts"
	::= { node29PG 56 }

pgNode29Out7State			OBJECT-TYPE
	SYNTAX					INTEGER { off(1),on(2),cycle(3) }
	ACCESS					read-only
	STATUS					mandatory
	DESCRIPTION			"PG Outlet 7 state"
	::= { node29PG 57 }

pgNode29Out7Cmd				OBJECT-TYPE
	SYNTAX					INTEGER { off(1),on(2),cycle(3) }
	ACCESS					read-write
	STATUS					mandatory
	DESCRIPTION			"PG Outlet 7 command"
	::= { node29PG 58 }

pgNode29Out8Name				OBJECT-TYPE
	SYNTAX					DisplayString
	ACCESS					read-write
	STATUS					mandatory
	DESCRIPTION			"PG Outlet 8 name"
	::= { node29PG 59 }

pgNode29Out8CustVoice	OBJECT-TYPE
	SYNTAX					DisplayString
	ACCESS					read-write
	STATUS					mandatory
	DESCRIPTION			"PG Outlet 8 custom voice"
	::= { node29PG 60 }

pgNode29Out8Volts			OBJECT-TYPE
	SYNTAX					INTEGER
	ACCESS					read-only
	STATUS					mandatory
	DESCRIPTION			"PG Outlet 8 volts"
	::= { node29PG 61 }

pgNode29Out8Amps				OBJECT-TYPE
	SYNTAX					INTEGER
	ACCESS					read-only
	STATUS					mandatory
	DESCRIPTION			"PG Outlet 8 amps"
	::= { node29PG 62 }

pgNode29Out8Watts			OBJECT-TYPE
	SYNTAX					INTEGER
	ACCESS					read-only
	STATUS					mandatory
	DESCRIPTION			"PG Outlet 8 watts"
	::= { node29PG 63 }

pgNode29Out8State			OBJECT-TYPE
	SYNTAX					INTEGER { off(1),on(2),cycle(3) }
	ACCESS					read-only
	STATUS					mandatory
	DESCRIPTION			"PG Outlet 8 state"
	::= { node29PG 64 }

pgNode29Out8Cmd				OBJECT-TYPE
	SYNTAX					INTEGER { off(1),on(2),cycle(3) }
	ACCESS					read-write
	STATUS					mandatory
	DESCRIPTION			"PG Outlet 8 command"
	::= { node29PG 65 }

pgNode30InUse					OBJECT-TYPE
	SYNTAX					INTEGER { false(1),true(2) }
	ACCESS					read-only
	STATUS					mandatory
	DESCRIPTION			"PG in use"
	::= { node30PG 1 }

pgNode30Status					OBJECT-TYPE
	SYNTAX					INTEGER { normal(1),pending(2), trouble(3) }
	ACCESS					read-only
	STATUS					mandatory
	DESCRIPTION			"PG status"
	::= { node30PG 2 }

pgNode30StatusSupport	OBJECT-TYPE
	SYNTAX					INTEGER { true1(1),false(2) }
	ACCESS					read-only
	STATUS					mandatory
	DESCRIPTION			"PG status support level"
	::= { node30PG 3 }

pgNode30Ver						OBJECT-TYPE
	SYNTAX					INTEGER { pgate1(1),pgate2(2) }
	ACCESS					read-only
	STATUS					mandatory
	DESCRIPTION			"PG version"
	::= { node30PG 4 }

pgNode30Volts					OBJECT-TYPE
	SYNTAX					INTEGER
	ACCESS					read-only
	STATUS					mandatory
	DESCRIPTION			"PG voltage"
	::= { node30PG 5 }

pgNode30Amps						OBJECT-TYPE
	SYNTAX					INTEGER
	ACCESS					read-only
	STATUS					mandatory
	DESCRIPTION			"PG amps"
	::= { node30PG 6 }

pgNode30Watts					OBJECT-TYPE
	SYNTAX					INTEGER
	ACCESS					read-only
	STATUS					mandatory
	DESCRIPTION			"PG Watts"
	::= { node30PG 7 }

pgNode30Name						OBJECT-TYPE
	SYNTAX					DisplayString
	ACCESS					read-write
	STATUS					mandatory
	DESCRIPTION			"PG name"
	::= { node30PG 8 }

pgNode30CustVoice			OBJECT-TYPE
	SYNTAX					DisplayString
	ACCESS					read-write
	STATUS					mandatory
	DESCRIPTION			"PG custom voice"
	::= { node30PG 9 }

pgNode30Out1Name				OBJECT-TYPE
	SYNTAX					DisplayString
	ACCESS					read-write
	STATUS					mandatory
	DESCRIPTION			"PG Outlet 1 name"
	::= { node30PG 10 }

pgNode30Out1CustVoice	OBJECT-TYPE
	SYNTAX					DisplayString
	ACCESS					read-write
	STATUS					mandatory
	DESCRIPTION			"PG Outlet 1 custom voice"
	::= { node30PG 11 }

pgNode30Out1Volts			OBJECT-TYPE
	SYNTAX					INTEGER
	ACCESS					read-only
	STATUS					mandatory
	DESCRIPTION			"PG Outlet 1 volts"
	::= { node30PG 12 }

pgNode30Out1Amps				OBJECT-TYPE
	SYNTAX					INTEGER
	ACCESS					read-only
	STATUS					mandatory
	DESCRIPTION			"PG Outlet 1 amps"
	::= { node30PG 13 }

pgNode30Out1Watts			OBJECT-TYPE
	SYNTAX					INTEGER
	ACCESS					read-only
	STATUS					mandatory
	DESCRIPTION			"PG Outlet 1 watts"
	::= { node30PG 14 }

pgNode30Out1State			OBJECT-TYPE
	SYNTAX					INTEGER { off(1),on(2),cycle(3) }
	ACCESS					read-only
	STATUS					mandatory
	DESCRIPTION			"PG Outlet 1 state"
	::= { node30PG 15 }

pgNode30Out1Cmd				OBJECT-TYPE
	SYNTAX					INTEGER { off(1),on(2),cycle(3) }
	ACCESS					read-write
	STATUS					mandatory
	DESCRIPTION			"PG Outlet 1 command"
	::= { node30PG 16 }

pgNode30Out2Name				OBJECT-TYPE
	SYNTAX					DisplayString
	ACCESS					read-write
	STATUS					mandatory
	DESCRIPTION			"PG Outlet 2 name"
	::= { node30PG 17 }

pgNode30Out2CustVoice	OBJECT-TYPE
	SYNTAX					DisplayString
	ACCESS					read-write
	STATUS					mandatory
	DESCRIPTION			"PG Outlet 2 custom voice"
	::= { node30PG 18 }

pgNode30Out2Volts			OBJECT-TYPE
	SYNTAX					INTEGER
	ACCESS					read-only
	STATUS					mandatory
	DESCRIPTION			"PG Outlet 2 volts"
	::= { node30PG 19 }

pgNode30Out2Amps				OBJECT-TYPE
	SYNTAX					INTEGER
	ACCESS					read-only
	STATUS					mandatory
	DESCRIPTION			"PG Outlet 2 amps"
	::= { node30PG 20 }

pgNode30Out2Watts			OBJECT-TYPE
	SYNTAX					INTEGER
	ACCESS					read-only
	STATUS					mandatory
	DESCRIPTION			"PG Outlet 2 watts"
	::= { node30PG 21 }

pgNode30Out2State			OBJECT-TYPE
	SYNTAX					INTEGER { off(1),on(2),cycle(3) }
	ACCESS					read-only
	STATUS					mandatory
	DESCRIPTION			"PG Outlet 2 state"
	::= { node30PG 22 }

pgNode30Out2Cmd				OBJECT-TYPE
	SYNTAX					INTEGER { off(1),on(2),cycle(3) }
	ACCESS					read-write
	STATUS					mandatory
	DESCRIPTION			"PG Outlet 2 command"
	::= { node30PG 23 }

pgNode30Out3Name				OBJECT-TYPE
	SYNTAX					DisplayString
	ACCESS					read-write
	STATUS					mandatory
	DESCRIPTION			"PG Outlet 3 name"
	::= { node30PG 24 }

pgNode30Out3CustVoice	OBJECT-TYPE
	SYNTAX					DisplayString
	ACCESS					read-write
	STATUS					mandatory
	DESCRIPTION			"PG Outlet 3 custom voice"
	::= { node30PG 25 }

pgNode30Out3Volts			OBJECT-TYPE
	SYNTAX					INTEGER
	ACCESS					read-only
	STATUS					mandatory
	DESCRIPTION			"PG Outlet 3 volts"
	::= { node30PG 26 }

pgNode30Out3Amps				OBJECT-TYPE
	SYNTAX					INTEGER
	ACCESS					read-only
	STATUS					mandatory
	DESCRIPTION			"PG Outlet 3 amps"
	::= { node30PG 27 }

pgNode30Out3Watts			OBJECT-TYPE
	SYNTAX					INTEGER
	ACCESS					read-only
	STATUS					mandatory
	DESCRIPTION			"PG Outlet 3 watts"
	::= { node30PG 28 }

pgNode30Out3State			OBJECT-TYPE
	SYNTAX					INTEGER { off(1),on(2),cycle(3) }
	ACCESS					read-only
	STATUS					mandatory
	DESCRIPTION			"PG Outlet 3 state"
	::= { node30PG 29 }

pgNode30Out3Cmd				OBJECT-TYPE
	SYNTAX					INTEGER { off(1),on(2),cycle(3) }
	ACCESS					read-write
	STATUS					mandatory
	DESCRIPTION			"PG Outlet 3 command"
	::= { node30PG 30 }

pgNode30Out4Name				OBJECT-TYPE
	SYNTAX					DisplayString
	ACCESS					read-write
	STATUS					mandatory
	DESCRIPTION			"PG Outlet 4 name"
	::= { node30PG 31 }

pgNode30Out4CustVoice	OBJECT-TYPE
	SYNTAX					DisplayString
	ACCESS					read-write
	STATUS					mandatory
	DESCRIPTION			"PG Outlet 4 custom voice"
	::= { node30PG 32 }

pgNode30Out4Volts			OBJECT-TYPE
	SYNTAX					INTEGER
	ACCESS					read-only
	STATUS					mandatory
	DESCRIPTION			"PG Outlet 4 volts"
	::= { node30PG 33 }

pgNode30Out4Amps				OBJECT-TYPE
	SYNTAX					INTEGER
	ACCESS					read-only
	STATUS					mandatory
	DESCRIPTION			"PG Outlet 4 amps"
	::= { node30PG 34 }

pgNode30Out4Watts			OBJECT-TYPE
	SYNTAX					INTEGER
	ACCESS					read-only
	STATUS					mandatory
	DESCRIPTION			"PG Outlet 4 watts"
	::= { node30PG 35 }

pgNode30Out4State			OBJECT-TYPE
	SYNTAX					INTEGER { off(1),on(2),cycle(3) }
	ACCESS					read-only
	STATUS					mandatory
	DESCRIPTION			"PG Outlet 4 state"
	::= { node30PG 36 }

pgNode30Out4Cmd				OBJECT-TYPE
	SYNTAX					INTEGER { off(1),on(2),cycle(3) }
	ACCESS					read-write
	STATUS					mandatory
	DESCRIPTION			"PG Outlet 4 command"
	::= { node30PG 37 }

pgNode30Out5Name				OBJECT-TYPE
	SYNTAX					DisplayString
	ACCESS					read-write
	STATUS					mandatory
	DESCRIPTION			"PG Outlet 5 name"
	::= { node30PG 38 }

pgNode30Out5CustVoice	OBJECT-TYPE
	SYNTAX					DisplayString
	ACCESS					read-write
	STATUS					mandatory
	DESCRIPTION			"PG Outlet 5 custom voice"
	::= { node30PG 39 }

pgNode30Out5Volts			OBJECT-TYPE
	SYNTAX					INTEGER
	ACCESS					read-only
	STATUS					mandatory
	DESCRIPTION			"PG Outlet 5 volts"
	::= { node30PG 40 }

pgNode30Out5Amps				OBJECT-TYPE
	SYNTAX					INTEGER
	ACCESS					read-only
	STATUS					mandatory
	DESCRIPTION			"PG Outlet 5 amps"
	::= { node30PG 41 }

pgNode30Out5Watts			OBJECT-TYPE
	SYNTAX					INTEGER
	ACCESS					read-only
	STATUS					mandatory
	DESCRIPTION			"PG Outlet 5 watts"
	::= { node30PG 42 }

pgNode30Out5State			OBJECT-TYPE
	SYNTAX					INTEGER { off(1),on(2),cycle(3) }
	ACCESS					read-only
	STATUS					mandatory
	DESCRIPTION			"PG Outlet 5 state"
	::= { node30PG 43 }

pgNode30Out5Cmd				OBJECT-TYPE
	SYNTAX					INTEGER { off(1),on(2),cycle(3) }
	ACCESS					read-write
	STATUS					mandatory
	DESCRIPTION			"PG Outlet 5 command"
	::= { node30PG 44 }

pgNode30Out6Name				OBJECT-TYPE
	SYNTAX					DisplayString
	ACCESS					read-write
	STATUS					mandatory
	DESCRIPTION			"PG Outlet 6 name"
	::= { node30PG 45 }

pgNode30Out6CustVoice	OBJECT-TYPE
	SYNTAX					DisplayString
	ACCESS					read-write
	STATUS					mandatory
	DESCRIPTION			"PG Outlet 6 custom voice"
	::= { node30PG 46 }

pgNode30Out6Volts			OBJECT-TYPE
	SYNTAX					INTEGER
	ACCESS					read-only
	STATUS					mandatory
	DESCRIPTION			"PG Outlet 6 volts"
	::= { node30PG 47 }

pgNode30Out6Amps				OBJECT-TYPE
	SYNTAX					INTEGER
	ACCESS					read-only
	STATUS					mandatory
	DESCRIPTION			"PG Outlet 6 amps"
	::= { node30PG 48 }

pgNode30Out6Watts			OBJECT-TYPE
	SYNTAX					INTEGER
	ACCESS					read-only
	STATUS					mandatory
	DESCRIPTION			"PG Outlet 6 watts"
	::= { node30PG 49 }

pgNode30Out6State			OBJECT-TYPE
	SYNTAX					INTEGER { off(1),on(2),cycle(3) }
	ACCESS					read-only
	STATUS					mandatory
	DESCRIPTION			"PG Outlet 6 state"
	::= { node30PG 50 }

pgNode30Out6Cmd				OBJECT-TYPE
	SYNTAX					INTEGER { off(1),on(2),cycle(3) }
	ACCESS					read-write
	STATUS					mandatory
	DESCRIPTION			"PG Outlet 6 command"
	::= { node30PG 51 }

pgNode30Out7Name				OBJECT-TYPE
	SYNTAX					DisplayString
	ACCESS					read-write
	STATUS					mandatory
	DESCRIPTION			"PG Outlet 7 name"
	::= { node30PG 52 }

pgNode30Out7CustVoice	OBJECT-TYPE
	SYNTAX					DisplayString
	ACCESS					read-write
	STATUS					mandatory
	DESCRIPTION			"PG Outlet 7 custom voice"
	::= { node30PG 53 }

pgNode30Out7Volts			OBJECT-TYPE
	SYNTAX					INTEGER
	ACCESS					read-only
	STATUS					mandatory
	DESCRIPTION			"PG Outlet 7 volts"
	::= { node30PG 54 }

pgNode30Out7Amps				OBJECT-TYPE
	SYNTAX					INTEGER
	ACCESS					read-only
	STATUS					mandatory
	DESCRIPTION			"PG Outlet 7 amps"
	::= { node30PG 55 }

pgNode30Out7Watts			OBJECT-TYPE
	SYNTAX					INTEGER
	ACCESS					read-only
	STATUS					mandatory
	DESCRIPTION			"PG Outlet 7 watts"
	::= { node30PG 56 }

pgNode30Out7State			OBJECT-TYPE
	SYNTAX					INTEGER { off(1),on(2),cycle(3) }
	ACCESS					read-only
	STATUS					mandatory
	DESCRIPTION			"PG Outlet 7 state"
	::= { node30PG 57 }

pgNode30Out7Cmd				OBJECT-TYPE
	SYNTAX					INTEGER { off(1),on(2),cycle(3) }
	ACCESS					read-write
	STATUS					mandatory
	DESCRIPTION			"PG Outlet 7 command"
	::= { node30PG 58 }

pgNode30Out8Name				OBJECT-TYPE
	SYNTAX					DisplayString
	ACCESS					read-write
	STATUS					mandatory
	DESCRIPTION			"PG Outlet 8 name"
	::= { node30PG 59 }

pgNode30Out8CustVoice	OBJECT-TYPE
	SYNTAX					DisplayString
	ACCESS					read-write
	STATUS					mandatory
	DESCRIPTION			"PG Outlet 8 custom voice"
	::= { node30PG 60 }

pgNode30Out8Volts			OBJECT-TYPE
	SYNTAX					INTEGER
	ACCESS					read-only
	STATUS					mandatory
	DESCRIPTION			"PG Outlet 8 volts"
	::= { node30PG 61 }

pgNode30Out8Amps				OBJECT-TYPE
	SYNTAX					INTEGER
	ACCESS					read-only
	STATUS					mandatory
	DESCRIPTION			"PG Outlet 8 amps"
	::= { node30PG 62 }

pgNode30Out8Watts			OBJECT-TYPE
	SYNTAX					INTEGER
	ACCESS					read-only
	STATUS					mandatory
	DESCRIPTION			"PG Outlet 8 watts"
	::= { node30PG 63 }

pgNode30Out8State			OBJECT-TYPE
	SYNTAX					INTEGER { off(1),on(2),cycle(3) }
	ACCESS					read-only
	STATUS					mandatory
	DESCRIPTION			"PG Outlet 8 state"
	::= { node30PG 64 }

pgNode30Out8Cmd				OBJECT-TYPE
	SYNTAX					INTEGER { off(1),on(2),cycle(3) }
	ACCESS					read-write
	STATUS					mandatory
	DESCRIPTION			"PG Outlet 8 command"
	::= { node30PG 65 }

pgNode31InUse					OBJECT-TYPE
	SYNTAX					INTEGER { false(1),true(2) }
	ACCESS					read-only
	STATUS					mandatory
	DESCRIPTION			"PG in use"
	::= { node31PG 1 }

pgNode31Status					OBJECT-TYPE
	SYNTAX					INTEGER { normal(1),pending(2), trouble(3) }
	ACCESS					read-only
	STATUS					mandatory
	DESCRIPTION			"PG status"
	::= { node31PG 2 }

pgNode31StatusSupport	OBJECT-TYPE
	SYNTAX					INTEGER { true1(1),false(2) }
	ACCESS					read-only
	STATUS					mandatory
	DESCRIPTION			"PG status support level"
	::= { node31PG 3 }

pgNode31Ver						OBJECT-TYPE
	SYNTAX					INTEGER { pgate1(1),pgate2(2) }
	ACCESS					read-only
	STATUS					mandatory
	DESCRIPTION			"PG version"
	::= { node31PG 4 }

pgNode31Volts					OBJECT-TYPE
	SYNTAX					INTEGER
	ACCESS					read-only
	STATUS					mandatory
	DESCRIPTION			"PG voltage"
	::= { node31PG 5 }

pgNode31Amps						OBJECT-TYPE
	SYNTAX					INTEGER
	ACCESS					read-only
	STATUS					mandatory
	DESCRIPTION			"PG amps"
	::= { node31PG 6 }

pgNode31Watts					OBJECT-TYPE
	SYNTAX					INTEGER
	ACCESS					read-only
	STATUS					mandatory
	DESCRIPTION			"PG Watts"
	::= { node31PG 7 }

pgNode31Name						OBJECT-TYPE
	SYNTAX					DisplayString
	ACCESS					read-write
	STATUS					mandatory
	DESCRIPTION			"PG name"
	::= { node31PG 8 }

pgNode31CustVoice			OBJECT-TYPE
	SYNTAX					DisplayString
	ACCESS					read-write
	STATUS					mandatory
	DESCRIPTION			"PG custom voice"
	::= { node31PG 9 }

pgNode31Out1Name				OBJECT-TYPE
	SYNTAX					DisplayString
	ACCESS					read-write
	STATUS					mandatory
	DESCRIPTION			"PG Outlet 1 name"
	::= { node31PG 10 }

pgNode31Out1CustVoice	OBJECT-TYPE
	SYNTAX					DisplayString
	ACCESS					read-write
	STATUS					mandatory
	DESCRIPTION			"PG Outlet 1 custom voice"
	::= { node31PG 11 }

pgNode31Out1Volts			OBJECT-TYPE
	SYNTAX					INTEGER
	ACCESS					read-only
	STATUS					mandatory
	DESCRIPTION			"PG Outlet 1 volts"
	::= { node31PG 12 }

pgNode31Out1Amps				OBJECT-TYPE
	SYNTAX					INTEGER
	ACCESS					read-only
	STATUS					mandatory
	DESCRIPTION			"PG Outlet 1 amps"
	::= { node31PG 13 }

pgNode31Out1Watts			OBJECT-TYPE
	SYNTAX					INTEGER
	ACCESS					read-only
	STATUS					mandatory
	DESCRIPTION			"PG Outlet 1 watts"
	::= { node31PG 14 }

pgNode31Out1State			OBJECT-TYPE
	SYNTAX					INTEGER { off(1),on(2),cycle(3) }
	ACCESS					read-only
	STATUS					mandatory
	DESCRIPTION			"PG Outlet 1 state"
	::= { node31PG 15 }

pgNode31Out1Cmd				OBJECT-TYPE
	SYNTAX					INTEGER { off(1),on(2),cycle(3) }
	ACCESS					read-write
	STATUS					mandatory
	DESCRIPTION			"PG Outlet 1 command"
	::= { node31PG 16 }

pgNode31Out2Name				OBJECT-TYPE
	SYNTAX					DisplayString
	ACCESS					read-write
	STATUS					mandatory
	DESCRIPTION			"PG Outlet 2 name"
	::= { node31PG 17 }

pgNode31Out2CustVoice	OBJECT-TYPE
	SYNTAX					DisplayString
	ACCESS					read-write
	STATUS					mandatory
	DESCRIPTION			"PG Outlet 2 custom voice"
	::= { node31PG 18 }

pgNode31Out2Volts			OBJECT-TYPE
	SYNTAX					INTEGER
	ACCESS					read-only
	STATUS					mandatory
	DESCRIPTION			"PG Outlet 2 volts"
	::= { node31PG 19 }

pgNode31Out2Amps				OBJECT-TYPE
	SYNTAX					INTEGER
	ACCESS					read-only
	STATUS					mandatory
	DESCRIPTION			"PG Outlet 2 amps"
	::= { node31PG 20 }

pgNode31Out2Watts			OBJECT-TYPE
	SYNTAX					INTEGER
	ACCESS					read-only
	STATUS					mandatory
	DESCRIPTION			"PG Outlet 2 watts"
	::= { node31PG 21 }

pgNode31Out2State			OBJECT-TYPE
	SYNTAX					INTEGER { off(1),on(2),cycle(3) }
	ACCESS					read-only
	STATUS					mandatory
	DESCRIPTION			"PG Outlet 2 state"
	::= { node31PG 22 }

pgNode31Out2Cmd				OBJECT-TYPE
	SYNTAX					INTEGER { off(1),on(2),cycle(3) }
	ACCESS					read-write
	STATUS					mandatory
	DESCRIPTION			"PG Outlet 2 command"
	::= { node31PG 23 }

pgNode31Out3Name				OBJECT-TYPE
	SYNTAX					DisplayString
	ACCESS					read-write
	STATUS					mandatory
	DESCRIPTION			"PG Outlet 3 name"
	::= { node31PG 24 }

pgNode31Out3CustVoice	OBJECT-TYPE
	SYNTAX					DisplayString
	ACCESS					read-write
	STATUS					mandatory
	DESCRIPTION			"PG Outlet 3 custom voice"
	::= { node31PG 25 }

pgNode31Out3Volts			OBJECT-TYPE
	SYNTAX					INTEGER
	ACCESS					read-only
	STATUS					mandatory
	DESCRIPTION			"PG Outlet 3 volts"
	::= { node31PG 26 }

pgNode31Out3Amps				OBJECT-TYPE
	SYNTAX					INTEGER
	ACCESS					read-only
	STATUS					mandatory
	DESCRIPTION			"PG Outlet 3 amps"
	::= { node31PG 27 }

pgNode31Out3Watts			OBJECT-TYPE
	SYNTAX					INTEGER
	ACCESS					read-only
	STATUS					mandatory
	DESCRIPTION			"PG Outlet 3 watts"
	::= { node31PG 28 }

pgNode31Out3State			OBJECT-TYPE
	SYNTAX					INTEGER { off(1),on(2),cycle(3) }
	ACCESS					read-only
	STATUS					mandatory
	DESCRIPTION			"PG Outlet 3 state"
	::= { node31PG 29 }

pgNode31Out3Cmd				OBJECT-TYPE
	SYNTAX					INTEGER { off(1),on(2),cycle(3) }
	ACCESS					read-write
	STATUS					mandatory
	DESCRIPTION			"PG Outlet 3 command"
	::= { node31PG 30 }

pgNode31Out4Name				OBJECT-TYPE
	SYNTAX					DisplayString
	ACCESS					read-write
	STATUS					mandatory
	DESCRIPTION			"PG Outlet 4 name"
	::= { node31PG 31 }

pgNode31Out4CustVoice	OBJECT-TYPE
	SYNTAX					DisplayString
	ACCESS					read-write
	STATUS					mandatory
	DESCRIPTION			"PG Outlet 4 custom voice"
	::= { node31PG 32 }

pgNode31Out4Volts			OBJECT-TYPE
	SYNTAX					INTEGER
	ACCESS					read-only
	STATUS					mandatory
	DESCRIPTION			"PG Outlet 4 volts"
	::= { node31PG 33 }

pgNode31Out4Amps				OBJECT-TYPE
	SYNTAX					INTEGER
	ACCESS					read-only
	STATUS					mandatory
	DESCRIPTION			"PG Outlet 4 amps"
	::= { node31PG 34 }

pgNode31Out4Watts			OBJECT-TYPE
	SYNTAX					INTEGER
	ACCESS					read-only
	STATUS					mandatory
	DESCRIPTION			"PG Outlet 4 watts"
	::= { node31PG 35 }

pgNode31Out4State			OBJECT-TYPE
	SYNTAX					INTEGER { off(1),on(2),cycle(3) }
	ACCESS					read-only
	STATUS					mandatory
	DESCRIPTION			"PG Outlet 4 state"
	::= { node31PG 36 }

pgNode31Out4Cmd				OBJECT-TYPE
	SYNTAX					INTEGER { off(1),on(2),cycle(3) }
	ACCESS					read-write
	STATUS					mandatory
	DESCRIPTION			"PG Outlet 4 command"
	::= { node31PG 37 }

pgNode31Out5Name				OBJECT-TYPE
	SYNTAX					DisplayString
	ACCESS					read-write
	STATUS					mandatory
	DESCRIPTION			"PG Outlet 5 name"
	::= { node31PG 38 }

pgNode31Out5CustVoice	OBJECT-TYPE
	SYNTAX					DisplayString
	ACCESS					read-write
	STATUS					mandatory
	DESCRIPTION			"PG Outlet 5 custom voice"
	::= { node31PG 39 }

pgNode31Out5Volts			OBJECT-TYPE
	SYNTAX					INTEGER
	ACCESS					read-only
	STATUS					mandatory
	DESCRIPTION			"PG Outlet 5 volts"
	::= { node31PG 40 }

pgNode31Out5Amps				OBJECT-TYPE
	SYNTAX					INTEGER
	ACCESS					read-only
	STATUS					mandatory
	DESCRIPTION			"PG Outlet 5 amps"
	::= { node31PG 41 }

pgNode31Out5Watts			OBJECT-TYPE
	SYNTAX					INTEGER
	ACCESS					read-only
	STATUS					mandatory
	DESCRIPTION			"PG Outlet 5 watts"
	::= { node31PG 42 }

pgNode31Out5State			OBJECT-TYPE
	SYNTAX					INTEGER { off(1),on(2),cycle(3) }
	ACCESS					read-only
	STATUS					mandatory
	DESCRIPTION			"PG Outlet 5 state"
	::= { node31PG 43 }

pgNode31Out5Cmd				OBJECT-TYPE
	SYNTAX					INTEGER { off(1),on(2),cycle(3) }
	ACCESS					read-write
	STATUS					mandatory
	DESCRIPTION			"PG Outlet 5 command"
	::= { node31PG 44 }

pgNode31Out6Name				OBJECT-TYPE
	SYNTAX					DisplayString
	ACCESS					read-write
	STATUS					mandatory
	DESCRIPTION			"PG Outlet 6 name"
	::= { node31PG 45 }

pgNode31Out6CustVoice	OBJECT-TYPE
	SYNTAX					DisplayString
	ACCESS					read-write
	STATUS					mandatory
	DESCRIPTION			"PG Outlet 6 custom voice"
	::= { node31PG 46 }

pgNode31Out6Volts			OBJECT-TYPE
	SYNTAX					INTEGER
	ACCESS					read-only
	STATUS					mandatory
	DESCRIPTION			"PG Outlet 6 volts"
	::= { node31PG 47 }

pgNode31Out6Amps				OBJECT-TYPE
	SYNTAX					INTEGER
	ACCESS					read-only
	STATUS					mandatory
	DESCRIPTION			"PG Outlet 6 amps"
	::= { node31PG 48 }

pgNode31Out6Watts			OBJECT-TYPE
	SYNTAX					INTEGER
	ACCESS					read-only
	STATUS					mandatory
	DESCRIPTION			"PG Outlet 6 watts"
	::= { node31PG 49 }

pgNode31Out6State			OBJECT-TYPE
	SYNTAX					INTEGER { off(1),on(2),cycle(3) }
	ACCESS					read-only
	STATUS					mandatory
	DESCRIPTION			"PG Outlet 6 state"
	::= { node31PG 50 }

pgNode31Out6Cmd				OBJECT-TYPE
	SYNTAX					INTEGER { off(1),on(2),cycle(3) }
	ACCESS					read-write
	STATUS					mandatory
	DESCRIPTION			"PG Outlet 6 command"
	::= { node31PG 51 }

pgNode31Out7Name				OBJECT-TYPE
	SYNTAX					DisplayString
	ACCESS					read-write
	STATUS					mandatory
	DESCRIPTION			"PG Outlet 7 name"
	::= { node31PG 52 }

pgNode31Out7CustVoice	OBJECT-TYPE
	SYNTAX					DisplayString
	ACCESS					read-write
	STATUS					mandatory
	DESCRIPTION			"PG Outlet 7 custom voice"
	::= { node31PG 53 }

pgNode31Out7Volts			OBJECT-TYPE
	SYNTAX					INTEGER
	ACCESS					read-only
	STATUS					mandatory
	DESCRIPTION			"PG Outlet 7 volts"
	::= { node31PG 54 }

pgNode31Out7Amps				OBJECT-TYPE
	SYNTAX					INTEGER
	ACCESS					read-only
	STATUS					mandatory
	DESCRIPTION			"PG Outlet 7 amps"
	::= { node31PG 55 }

pgNode31Out7Watts			OBJECT-TYPE
	SYNTAX					INTEGER
	ACCESS					read-only
	STATUS					mandatory
	DESCRIPTION			"PG Outlet 7 watts"
	::= { node31PG 56 }

pgNode31Out7State			OBJECT-TYPE
	SYNTAX					INTEGER { off(1),on(2),cycle(3) }
	ACCESS					read-only
	STATUS					mandatory
	DESCRIPTION			"PG Outlet 7 state"
	::= { node31PG 57 }

pgNode31Out7Cmd				OBJECT-TYPE
	SYNTAX					INTEGER { off(1),on(2),cycle(3) }
	ACCESS					read-write
	STATUS					mandatory
	DESCRIPTION			"PG Outlet 7 command"
	::= { node31PG 58 }

pgNode31Out8Name				OBJECT-TYPE
	SYNTAX					DisplayString
	ACCESS					read-write
	STATUS					mandatory
	DESCRIPTION			"PG Outlet 8 name"
	::= { node31PG 59 }

pgNode31Out8CustVoice	OBJECT-TYPE
	SYNTAX					DisplayString
	ACCESS					read-write
	STATUS					mandatory
	DESCRIPTION			"PG Outlet 8 custom voice"
	::= { node31PG 60 }

pgNode31Out8Volts			OBJECT-TYPE
	SYNTAX					INTEGER
	ACCESS					read-only
	STATUS					mandatory
	DESCRIPTION			"PG Outlet 8 volts"
	::= { node31PG 61 }

pgNode31Out8Amps				OBJECT-TYPE
	SYNTAX					INTEGER
	ACCESS					read-only
	STATUS					mandatory
	DESCRIPTION			"PG Outlet 8 amps"
	::= { node31PG 62 }

pgNode31Out8Watts			OBJECT-TYPE
	SYNTAX					INTEGER
	ACCESS					read-only
	STATUS					mandatory
	DESCRIPTION			"PG Outlet 8 watts"
	::= { node31PG 63 }

pgNode31Out8State			OBJECT-TYPE
	SYNTAX					INTEGER { off(1),on(2),cycle(3) }
	ACCESS					read-only
	STATUS					mandatory
	DESCRIPTION			"PG Outlet 8 state"
	::= { node31PG 64 }

pgNode31Out8Cmd				OBJECT-TYPE
	SYNTAX					INTEGER { off(1),on(2),cycle(3) }
	ACCESS					read-write
	STATUS					mandatory
	DESCRIPTION			"PG Outlet 8 command"
	::= { node31PG 65 }


--	Diags

diag1LinuxVer			OBJECT-TYPE
	SYNTAX					DisplayString
	ACCESS					read-only
	STATUS					mandatory
	DESCRIPTION			"Linux OS version"
	::= { hostDiags 1 }

diag1FirmwareVer	OBJECT-TYPE
	SYNTAX					DisplayString
	ACCESS					read-only
	STATUS					mandatory
	DESCRIPTION			"Firmware version"
	::= { hostDiags 2 }

diag1Diskfree			OBJECT-TYPE
	SYNTAX					INTEGER
	ACCESS					read-only
	STATUS					mandatory
	DESCRIPTION			"Persistant storage free"
	::= { hostDiags 3 }

diag1Uptime				OBJECT-TYPE
	SYNTAX					INTEGER
	ACCESS					read-only
	STATUS					mandatory
	DESCRIPTION			"Time since last boot"
	::= { hostDiags 4 }

diag1Ramused			OBJECT-TYPE
	SYNTAX					INTEGER
	ACCESS					read-only
	STATUS					mandatory
	DESCRIPTION			"Ram used"
	::= { hostDiags 5 }

diag1AckTimeouts	OBJECT-TYPE
	SYNTAX					INTEGER
	ACCESS					read-only
	STATUS					mandatory
	DESCRIPTION			"Node Ack timeouts"
	::= { hostDiags 6 }

diag1PackRecv			OBJECT-TYPE
	SYNTAX					INTEGER
	ACCESS					read-only
	STATUS					mandatory
	DESCRIPTION			"Node packet recvs"
	::= { hostDiags 7 }

diag1PackTrans		OBJECT-TYPE
	SYNTAX					INTEGER
	ACCESS					read-only
	STATUS					mandatory
	DESCRIPTION			"Node packet xmits"
	::= { hostDiags 8 }

diag1PackErrors		OBJECT-TYPE
	SYNTAX					INTEGER
	ACCESS					read-only
	STATUS					mandatory
	DESCRIPTION			"Node packet errors"
	::= { hostDiags 9 }

diag1ErrorMask		OBJECT-TYPE
	SYNTAX					INTEGER
	ACCESS					read-only
	STATUS					mandatory
	DESCRIPTION			"Node error flags"
	::= { hostDiags 10 }

diag1ClockTimeouts	OBJECT-TYPE
	SYNTAX					INTEGER
	ACCESS					read-only
	STATUS					mandatory
	DESCRIPTION			"Node clock timeouts"
	::= { hostDiags 11 }

diag2LinuxVer			OBJECT-TYPE
	SYNTAX					DisplayString
	ACCESS					read-only
	STATUS					mandatory
	DESCRIPTION			"Linux OS version"
	::= { node1Diags 1 }

diag2FirmwareVer	OBJECT-TYPE
	SYNTAX					DisplayString
	ACCESS					read-only
	STATUS					mandatory
	DESCRIPTION			"Firmware version"
	::= { node1Diags 2 }

diag2Diskfree			OBJECT-TYPE
	SYNTAX					INTEGER
	ACCESS					read-only
	STATUS					mandatory
	DESCRIPTION			"Persistant storage free"
	::= { node1Diags 3 }

diag2Uptime				OBJECT-TYPE
	SYNTAX					INTEGER
	ACCESS					read-only
	STATUS					mandatory
	DESCRIPTION			"Time since last boot"
	::= { node1Diags 4 }

diag2Ramused			OBJECT-TYPE
	SYNTAX					INTEGER
	ACCESS					read-only
	STATUS					mandatory
	DESCRIPTION			"Ram used"
	::= { node1Diags 5 }

diag2AckTimeouts	OBJECT-TYPE
	SYNTAX					INTEGER
	ACCESS					read-only
	STATUS					mandatory
	DESCRIPTION			"Node Ack timeouts"
	::= { node1Diags 6 }

diag2PackRecv			OBJECT-TYPE
	SYNTAX					INTEGER
	ACCESS					read-only
	STATUS					mandatory
	DESCRIPTION			"Node packet recvs"
	::= { node1Diags 7 }

diag2PackTrans		OBJECT-TYPE
	SYNTAX					INTEGER
	ACCESS					read-only
	STATUS					mandatory
	DESCRIPTION			"Node packet xmits"
	::= { node1Diags 8 }

diag2PackErrors		OBJECT-TYPE
	SYNTAX					INTEGER
	ACCESS					read-only
	STATUS					mandatory
	DESCRIPTION			"Node packet errors"
	::= { node1Diags 9 }

diag2ErrorMask		OBJECT-TYPE
	SYNTAX					INTEGER
	ACCESS					read-only
	STATUS					mandatory
	DESCRIPTION			"Node error flags"
	::= { node1Diags 10 }

diag2ClockTimeouts	OBJECT-TYPE
	SYNTAX					INTEGER
	ACCESS					read-only
	STATUS					mandatory
	DESCRIPTION			"Node clock timeouts"
	::= { node1Diags 11 }

diag3LinuxVer			OBJECT-TYPE
	SYNTAX					DisplayString
	ACCESS					read-only
	STATUS					mandatory
	DESCRIPTION			"Linux OS version"
	::= { node2Diags 1 }

diag3FirmwareVer	OBJECT-TYPE
	SYNTAX					DisplayString
	ACCESS					read-only
	STATUS					mandatory
	DESCRIPTION			"Firmware version"
	::= { node2Diags 2 }

diag3Diskfree			OBJECT-TYPE
	SYNTAX					INTEGER
	ACCESS					read-only
	STATUS					mandatory
	DESCRIPTION			"Persistant storage free"
	::= { node2Diags 3 }

diag3Uptime				OBJECT-TYPE
	SYNTAX					INTEGER
	ACCESS					read-only
	STATUS					mandatory
	DESCRIPTION			"Time since last boot"
	::= { node2Diags 4 }

diag3Ramused			OBJECT-TYPE
	SYNTAX					INTEGER
	ACCESS					read-only
	STATUS					mandatory
	DESCRIPTION			"Ram used"
	::= { node2Diags 5 }

diag3AckTimeouts	OBJECT-TYPE
	SYNTAX					INTEGER
	ACCESS					read-only
	STATUS					mandatory
	DESCRIPTION			"Node Ack timeouts"
	::= { node2Diags 6 }

diag3PackRecv			OBJECT-TYPE
	SYNTAX					INTEGER
	ACCESS					read-only
	STATUS					mandatory
	DESCRIPTION			"Node packet recvs"
	::= { node2Diags 7 }

diag3PackTrans		OBJECT-TYPE
	SYNTAX					INTEGER
	ACCESS					read-only
	STATUS					mandatory
	DESCRIPTION			"Node packet xmits"
	::= { node2Diags 8 }

diag3PackErrors		OBJECT-TYPE
	SYNTAX					INTEGER
	ACCESS					read-only
	STATUS					mandatory
	DESCRIPTION			"Node packet errors"
	::= { node2Diags 9 }

diag3ErrorMask		OBJECT-TYPE
	SYNTAX					INTEGER
	ACCESS					read-only
	STATUS					mandatory
	DESCRIPTION			"Node error flags"
	::= { node2Diags 10 }

diag3ClockTimeouts	OBJECT-TYPE
	SYNTAX					INTEGER
	ACCESS					read-only
	STATUS					mandatory
	DESCRIPTION			"Node clock timeouts"
	::= { node2Diags 11 }

diag4LinuxVer			OBJECT-TYPE
	SYNTAX					DisplayString
	ACCESS					read-only
	STATUS					mandatory
	DESCRIPTION			"Linux OS version"
	::= { node3Diags 1 }

diag4FirmwareVer	OBJECT-TYPE
	SYNTAX					DisplayString
	ACCESS					read-only
	STATUS					mandatory
	DESCRIPTION			"Firmware version"
	::= { node3Diags 2 }

diag4Diskfree			OBJECT-TYPE
	SYNTAX					INTEGER
	ACCESS					read-only
	STATUS					mandatory
	DESCRIPTION			"Persistant storage free"
	::= { node3Diags 3 }

diag4Uptime				OBJECT-TYPE
	SYNTAX					INTEGER
	ACCESS					read-only
	STATUS					mandatory
	DESCRIPTION			"Time since last boot"
	::= { node3Diags 4 }

diag4Ramused			OBJECT-TYPE
	SYNTAX					INTEGER
	ACCESS					read-only
	STATUS					mandatory
	DESCRIPTION			"Ram used"
	::= { node3Diags 5 }

diag4AckTimeouts	OBJECT-TYPE
	SYNTAX					INTEGER
	ACCESS					read-only
	STATUS					mandatory
	DESCRIPTION			"Node Ack timeouts"
	::= { node3Diags 6 }

diag4PackRecv			OBJECT-TYPE
	SYNTAX					INTEGER
	ACCESS					read-only
	STATUS					mandatory
	DESCRIPTION			"Node packet recvs"
	::= { node3Diags 7 }

diag4PackTrans		OBJECT-TYPE
	SYNTAX					INTEGER
	ACCESS					read-only
	STATUS					mandatory
	DESCRIPTION			"Node packet xmits"
	::= { node3Diags 8 }

diag4PackErrors		OBJECT-TYPE
	SYNTAX					INTEGER
	ACCESS					read-only
	STATUS					mandatory
	DESCRIPTION			"Node packet errors"
	::= { node3Diags 9 }

diag4ErrorMask		OBJECT-TYPE
	SYNTAX					INTEGER
	ACCESS					read-only
	STATUS					mandatory
	DESCRIPTION			"Node error flags"
	::= { node3Diags 10 }

diag4ClockTimeouts	OBJECT-TYPE
	SYNTAX					INTEGER
	ACCESS					read-only
	STATUS					mandatory
	DESCRIPTION			"Node clock timeouts"
	::= { node3Diags 11 }

diag5LinuxVer			OBJECT-TYPE
	SYNTAX					DisplayString
	ACCESS					read-only
	STATUS					mandatory
	DESCRIPTION			"Linux OS version"
	::= { node4Diags 1 }

diag5FirmwareVer	OBJECT-TYPE
	SYNTAX					DisplayString
	ACCESS					read-only
	STATUS					mandatory
	DESCRIPTION			"Firmware version"
	::= { node4Diags 2 }

diag5Diskfree			OBJECT-TYPE
	SYNTAX					INTEGER
	ACCESS					read-only
	STATUS					mandatory
	DESCRIPTION			"Persistant storage free"
	::= { node4Diags 3 }

diag5Uptime				OBJECT-TYPE
	SYNTAX					INTEGER
	ACCESS					read-only
	STATUS					mandatory
	DESCRIPTION			"Time since last boot"
	::= { node4Diags 4 }

diag5Ramused			OBJECT-TYPE
	SYNTAX					INTEGER
	ACCESS					read-only
	STATUS					mandatory
	DESCRIPTION			"Ram used"
	::= { node4Diags 5 }

diag5AckTimeouts	OBJECT-TYPE
	SYNTAX					INTEGER
	ACCESS					read-only
	STATUS					mandatory
	DESCRIPTION			"Node Ack timeouts"
	::= { node4Diags 6 }

diag5PackRecv			OBJECT-TYPE
	SYNTAX					INTEGER
	ACCESS					read-only
	STATUS					mandatory
	DESCRIPTION			"Node packet recvs"
	::= { node4Diags 7 }

diag5PackTrans		OBJECT-TYPE
	SYNTAX					INTEGER
	ACCESS					read-only
	STATUS					mandatory
	DESCRIPTION			"Node packet xmits"
	::= { node4Diags 8 }

diag5PackErrors		OBJECT-TYPE
	SYNTAX					INTEGER
	ACCESS					read-only
	STATUS					mandatory
	DESCRIPTION			"Node packet errors"
	::= { node4Diags 9 }

diag5ErrorMask		OBJECT-TYPE
	SYNTAX					INTEGER
	ACCESS					read-only
	STATUS					mandatory
	DESCRIPTION			"Node error flags"
	::= { node4Diags 10 }

diag5ClockTimeouts	OBJECT-TYPE
	SYNTAX					INTEGER
	ACCESS					read-only
	STATUS					mandatory
	DESCRIPTION			"Node clock timeouts"
	::= { node4Diags 11 }

diag6LinuxVer			OBJECT-TYPE
	SYNTAX					DisplayString
	ACCESS					read-only
	STATUS					mandatory
	DESCRIPTION			"Linux OS version"
	::= { node5Diags 1 }

diag6FirmwareVer	OBJECT-TYPE
	SYNTAX					DisplayString
	ACCESS					read-only
	STATUS					mandatory
	DESCRIPTION			"Firmware version"
	::= { node5Diags 2 }

diag6Diskfree			OBJECT-TYPE
	SYNTAX					INTEGER
	ACCESS					read-only
	STATUS					mandatory
	DESCRIPTION			"Persistant storage free"
	::= { node5Diags 3 }

diag6Uptime				OBJECT-TYPE
	SYNTAX					INTEGER
	ACCESS					read-only
	STATUS					mandatory
	DESCRIPTION			"Time since last boot"
	::= { node5Diags 4 }

diag6Ramused			OBJECT-TYPE
	SYNTAX					INTEGER
	ACCESS					read-only
	STATUS					mandatory
	DESCRIPTION			"Ram used"
	::= { node5Diags 5 }

diag6AckTimeouts	OBJECT-TYPE
	SYNTAX					INTEGER
	ACCESS					read-only
	STATUS					mandatory
	DESCRIPTION			"Node Ack timeouts"
	::= { node5Diags 6 }

diag6PackRecv			OBJECT-TYPE
	SYNTAX					INTEGER
	ACCESS					read-only
	STATUS					mandatory
	DESCRIPTION			"Node packet recvs"
	::= { node5Diags 7 }

diag6PackTrans		OBJECT-TYPE
	SYNTAX					INTEGER
	ACCESS					read-only
	STATUS					mandatory
	DESCRIPTION			"Node packet xmits"
	::= { node5Diags 8 }

diag6PackErrors		OBJECT-TYPE
	SYNTAX					INTEGER
	ACCESS					read-only
	STATUS					mandatory
	DESCRIPTION			"Node packet errors"
	::= { node5Diags 9 }

diag6ErrorMask		OBJECT-TYPE
	SYNTAX					INTEGER
	ACCESS					read-only
	STATUS					mandatory
	DESCRIPTION			"Node error flags"
	::= { node5Diags 10 }

diag6ClockTimeouts	OBJECT-TYPE
	SYNTAX					INTEGER
	ACCESS					read-only
	STATUS					mandatory
	DESCRIPTION			"Node clock timeouts"
	::= { node5Diags 11 }

diag7LinuxVer			OBJECT-TYPE
	SYNTAX					DisplayString
	ACCESS					read-only
	STATUS					mandatory
	DESCRIPTION			"Linux OS version"
	::= { node6Diags 1 }

diag7FirmwareVer	OBJECT-TYPE
	SYNTAX					DisplayString
	ACCESS					read-only
	STATUS					mandatory
	DESCRIPTION			"Firmware version"
	::= { node6Diags 2 }

diag7Diskfree			OBJECT-TYPE
	SYNTAX					INTEGER
	ACCESS					read-only
	STATUS					mandatory
	DESCRIPTION			"Persistant storage free"
	::= { node6Diags 3 }

diag7Uptime				OBJECT-TYPE
	SYNTAX					INTEGER
	ACCESS					read-only
	STATUS					mandatory
	DESCRIPTION			"Time since last boot"
	::= { node6Diags 4 }

diag7Ramused			OBJECT-TYPE
	SYNTAX					INTEGER
	ACCESS					read-only
	STATUS					mandatory
	DESCRIPTION			"Ram used"
	::= { node6Diags 5 }

diag7AckTimeouts	OBJECT-TYPE
	SYNTAX					INTEGER
	ACCESS					read-only
	STATUS					mandatory
	DESCRIPTION			"Node Ack timeouts"
	::= { node6Diags 6 }

diag7PackRecv			OBJECT-TYPE
	SYNTAX					INTEGER
	ACCESS					read-only
	STATUS					mandatory
	DESCRIPTION			"Node packet recvs"
	::= { node6Diags 7 }

diag7PackTrans		OBJECT-TYPE
	SYNTAX					INTEGER
	ACCESS					read-only
	STATUS					mandatory
	DESCRIPTION			"Node packet xmits"
	::= { node6Diags 8 }

diag7PackErrors		OBJECT-TYPE
	SYNTAX					INTEGER
	ACCESS					read-only
	STATUS					mandatory
	DESCRIPTION			"Node packet errors"
	::= { node6Diags 9 }

diag7ErrorMask		OBJECT-TYPE
	SYNTAX					INTEGER
	ACCESS					read-only
	STATUS					mandatory
	DESCRIPTION			"Node error flags"
	::= { node6Diags 10 }

diag7ClockTimeouts	OBJECT-TYPE
	SYNTAX					INTEGER
	ACCESS					read-only
	STATUS					mandatory
	DESCRIPTION			"Node clock timeouts"
	::= { node6Diags 11 }

diag8LinuxVer			OBJECT-TYPE
	SYNTAX					DisplayString
	ACCESS					read-only
	STATUS					mandatory
	DESCRIPTION			"Linux OS version"
	::= { node7Diags 1 }

diag8FirmwareVer	OBJECT-TYPE
	SYNTAX					DisplayString
	ACCESS					read-only
	STATUS					mandatory
	DESCRIPTION			"Firmware version"
	::= { node7Diags 2 }

diag8Diskfree			OBJECT-TYPE
	SYNTAX					INTEGER
	ACCESS					read-only
	STATUS					mandatory
	DESCRIPTION			"Persistant storage free"
	::= { node7Diags 3 }

diag8Uptime				OBJECT-TYPE
	SYNTAX					INTEGER
	ACCESS					read-only
	STATUS					mandatory
	DESCRIPTION			"Time since last boot"
	::= { node7Diags 4 }

diag8Ramused			OBJECT-TYPE
	SYNTAX					INTEGER
	ACCESS					read-only
	STATUS					mandatory
	DESCRIPTION			"Ram used"
	::= { node7Diags 5 }

diag8AckTimeouts	OBJECT-TYPE
	SYNTAX					INTEGER
	ACCESS					read-only
	STATUS					mandatory
	DESCRIPTION			"Node Ack timeouts"
	::= { node7Diags 6 }

diag8PackRecv			OBJECT-TYPE
	SYNTAX					INTEGER
	ACCESS					read-only
	STATUS					mandatory
	DESCRIPTION			"Node packet recvs"
	::= { node7Diags 7 }

diag8PackTrans		OBJECT-TYPE
	SYNTAX					INTEGER
	ACCESS					read-only
	STATUS					mandatory
	DESCRIPTION			"Node packet xmits"
	::= { node7Diags 8 }

diag8PackErrors		OBJECT-TYPE
	SYNTAX					INTEGER
	ACCESS					read-only
	STATUS					mandatory
	DESCRIPTION			"Node packet errors"
	::= { node7Diags 9 }

diag8ErrorMask		OBJECT-TYPE
	SYNTAX					INTEGER
	ACCESS					read-only
	STATUS					mandatory
	DESCRIPTION			"Node error flags"
	::= { node7Diags 10 }

diag8ClockTimeouts	OBJECT-TYPE
	SYNTAX					INTEGER
	ACCESS					read-only
	STATUS					mandatory
	DESCRIPTION			"Node clock timeouts"
	::= { node7Diags 11 }

diag9LinuxVer			OBJECT-TYPE
	SYNTAX					DisplayString
	ACCESS					read-only
	STATUS					mandatory
	DESCRIPTION			"Linux OS version"
	::= { node8Diags 1 }

diag9FirmwareVer	OBJECT-TYPE
	SYNTAX					DisplayString
	ACCESS					read-only
	STATUS					mandatory
	DESCRIPTION			"Firmware version"
	::= { node8Diags 2 }

diag9Diskfree			OBJECT-TYPE
	SYNTAX					INTEGER
	ACCESS					read-only
	STATUS					mandatory
	DESCRIPTION			"Persistant storage free"
	::= { node8Diags 3 }

diag9Uptime				OBJECT-TYPE
	SYNTAX					INTEGER
	ACCESS					read-only
	STATUS					mandatory
	DESCRIPTION			"Time since last boot"
	::= { node8Diags 4 }

diag9Ramused			OBJECT-TYPE
	SYNTAX					INTEGER
	ACCESS					read-only
	STATUS					mandatory
	DESCRIPTION			"Ram used"
	::= { node8Diags 5 }

diag9AckTimeouts	OBJECT-TYPE
	SYNTAX					INTEGER
	ACCESS					read-only
	STATUS					mandatory
	DESCRIPTION			"Node Ack timeouts"
	::= { node8Diags 6 }

diag9PackRecv			OBJECT-TYPE
	SYNTAX					INTEGER
	ACCESS					read-only
	STATUS					mandatory
	DESCRIPTION			"Node packet recvs"
	::= { node8Diags 7 }

diag9PackTrans		OBJECT-TYPE
	SYNTAX					INTEGER
	ACCESS					read-only
	STATUS					mandatory
	DESCRIPTION			"Node packet xmits"
	::= { node8Diags 8 }

diag9PackErrors		OBJECT-TYPE
	SYNTAX					INTEGER
	ACCESS					read-only
	STATUS					mandatory
	DESCRIPTION			"Node packet errors"
	::= { node8Diags 9 }

diag9ErrorMask		OBJECT-TYPE
	SYNTAX					INTEGER
	ACCESS					read-only
	STATUS					mandatory
	DESCRIPTION			"Node error flags"
	::= { node8Diags 10 }

diag9ClockTimeouts	OBJECT-TYPE
	SYNTAX					INTEGER
	ACCESS					read-only
	STATUS					mandatory
	DESCRIPTION			"Node clock timeouts"
	::= { node8Diags 11 }

diag10LinuxVer			OBJECT-TYPE
	SYNTAX					DisplayString
	ACCESS					read-only
	STATUS					mandatory
	DESCRIPTION			"Linux OS version"
	::= { node9Diags 1 }

diag10FirmwareVer	OBJECT-TYPE
	SYNTAX					DisplayString
	ACCESS					read-only
	STATUS					mandatory
	DESCRIPTION			"Firmware version"
	::= { node9Diags 2 }

diag10Diskfree			OBJECT-TYPE
	SYNTAX					INTEGER
	ACCESS					read-only
	STATUS					mandatory
	DESCRIPTION			"Persistant storage free"
	::= { node9Diags 3 }

diag10Uptime				OBJECT-TYPE
	SYNTAX					INTEGER
	ACCESS					read-only
	STATUS					mandatory
	DESCRIPTION			"Time since last boot"
	::= { node9Diags 4 }

diag10Ramused			OBJECT-TYPE
	SYNTAX					INTEGER
	ACCESS					read-only
	STATUS					mandatory
	DESCRIPTION			"Ram used"
	::= { node9Diags 5 }

diag10AckTimeouts	OBJECT-TYPE
	SYNTAX					INTEGER
	ACCESS					read-only
	STATUS					mandatory
	DESCRIPTION			"Node Ack timeouts"
	::= { node9Diags 6 }

diag10PackRecv			OBJECT-TYPE
	SYNTAX					INTEGER
	ACCESS					read-only
	STATUS					mandatory
	DESCRIPTION			"Node packet recvs"
	::= { node9Diags 7 }

diag10PackTrans		OBJECT-TYPE
	SYNTAX					INTEGER
	ACCESS					read-only
	STATUS					mandatory
	DESCRIPTION			"Node packet xmits"
	::= { node9Diags 8 }

diag10PackErrors		OBJECT-TYPE
	SYNTAX					INTEGER
	ACCESS					read-only
	STATUS					mandatory
	DESCRIPTION			"Node packet errors"
	::= { node9Diags 9 }

diag10ErrorMask		OBJECT-TYPE
	SYNTAX					INTEGER
	ACCESS					read-only
	STATUS					mandatory
	DESCRIPTION			"Node error flags"
	::= { node9Diags 10 }

diag10ClockTimeouts	OBJECT-TYPE
	SYNTAX					INTEGER
	ACCESS					read-only
	STATUS					mandatory
	DESCRIPTION			"Node clock timeouts"
	::= { node9Diags 11 }

diag11LinuxVer			OBJECT-TYPE
	SYNTAX					DisplayString
	ACCESS					read-only
	STATUS					mandatory
	DESCRIPTION			"Linux OS version"
	::= { node10Diags 1 }

diag11FirmwareVer	OBJECT-TYPE
	SYNTAX					DisplayString
	ACCESS					read-only
	STATUS					mandatory
	DESCRIPTION			"Firmware version"
	::= { node10Diags 2 }

diag11Diskfree			OBJECT-TYPE
	SYNTAX					INTEGER
	ACCESS					read-only
	STATUS					mandatory
	DESCRIPTION			"Persistant storage free"
	::= { node10Diags 3 }

diag11Uptime				OBJECT-TYPE
	SYNTAX					INTEGER
	ACCESS					read-only
	STATUS					mandatory
	DESCRIPTION			"Time since last boot"
	::= { node10Diags 4 }

diag11Ramused			OBJECT-TYPE
	SYNTAX					INTEGER
	ACCESS					read-only
	STATUS					mandatory
	DESCRIPTION			"Ram used"
	::= { node10Diags 5 }

diag11AckTimeouts	OBJECT-TYPE
	SYNTAX					INTEGER
	ACCESS					read-only
	STATUS					mandatory
	DESCRIPTION			"Node Ack timeouts"
	::= { node10Diags 6 }

diag11PackRecv			OBJECT-TYPE
	SYNTAX					INTEGER
	ACCESS					read-only
	STATUS					mandatory
	DESCRIPTION			"Node packet recvs"
	::= { node10Diags 7 }

diag11PackTrans		OBJECT-TYPE
	SYNTAX					INTEGER
	ACCESS					read-only
	STATUS					mandatory
	DESCRIPTION			"Node packet xmits"
	::= { node10Diags 8 }

diag11PackErrors		OBJECT-TYPE
	SYNTAX					INTEGER
	ACCESS					read-only
	STATUS					mandatory
	DESCRIPTION			"Node packet errors"
	::= { node10Diags 9 }

diag11ErrorMask		OBJECT-TYPE
	SYNTAX					INTEGER
	ACCESS					read-only
	STATUS					mandatory
	DESCRIPTION			"Node error flags"
	::= { node10Diags 10 }

diag11ClockTimeouts	OBJECT-TYPE
	SYNTAX					INTEGER
	ACCESS					read-only
	STATUS					mandatory
	DESCRIPTION			"Node clock timeouts"
	::= { node10Diags 11 }

diag12LinuxVer			OBJECT-TYPE
	SYNTAX					DisplayString
	ACCESS					read-only
	STATUS					mandatory
	DESCRIPTION			"Linux OS version"
	::= { node11Diags 1 }

diag12FirmwareVer	OBJECT-TYPE
	SYNTAX					DisplayString
	ACCESS					read-only
	STATUS					mandatory
	DESCRIPTION			"Firmware version"
	::= { node11Diags 2 }

diag12Diskfree			OBJECT-TYPE
	SYNTAX					INTEGER
	ACCESS					read-only
	STATUS					mandatory
	DESCRIPTION			"Persistant storage free"
	::= { node11Diags 3 }

diag12Uptime				OBJECT-TYPE
	SYNTAX					INTEGER
	ACCESS					read-only
	STATUS					mandatory
	DESCRIPTION			"Time since last boot"
	::= { node11Diags 4 }

diag12Ramused			OBJECT-TYPE
	SYNTAX					INTEGER
	ACCESS					read-only
	STATUS					mandatory
	DESCRIPTION			"Ram used"
	::= { node11Diags 5 }

diag12AckTimeouts	OBJECT-TYPE
	SYNTAX					INTEGER
	ACCESS					read-only
	STATUS					mandatory
	DESCRIPTION			"Node Ack timeouts"
	::= { node11Diags 6 }

diag12PackRecv			OBJECT-TYPE
	SYNTAX					INTEGER
	ACCESS					read-only
	STATUS					mandatory
	DESCRIPTION			"Node packet recvs"
	::= { node11Diags 7 }

diag12PackTrans		OBJECT-TYPE
	SYNTAX					INTEGER
	ACCESS					read-only
	STATUS					mandatory
	DESCRIPTION			"Node packet xmits"
	::= { node11Diags 8 }

diag12PackErrors		OBJECT-TYPE
	SYNTAX					INTEGER
	ACCESS					read-only
	STATUS					mandatory
	DESCRIPTION			"Node packet errors"
	::= { node11Diags 9 }

diag12ErrorMask		OBJECT-TYPE
	SYNTAX					INTEGER
	ACCESS					read-only
	STATUS					mandatory
	DESCRIPTION			"Node error flags"
	::= { node11Diags 10 }

diag12ClockTimeouts	OBJECT-TYPE
	SYNTAX					INTEGER
	ACCESS					read-only
	STATUS					mandatory
	DESCRIPTION			"Node clock timeouts"
	::= { node11Diags 11 }

diag13LinuxVer			OBJECT-TYPE
	SYNTAX					DisplayString
	ACCESS					read-only
	STATUS					mandatory
	DESCRIPTION			"Linux OS version"
	::= { node12Diags 1 }

diag13FirmwareVer	OBJECT-TYPE
	SYNTAX					DisplayString
	ACCESS					read-only
	STATUS					mandatory
	DESCRIPTION			"Firmware version"
	::= { node12Diags 2 }

diag13Diskfree			OBJECT-TYPE
	SYNTAX					INTEGER
	ACCESS					read-only
	STATUS					mandatory
	DESCRIPTION			"Persistant storage free"
	::= { node12Diags 3 }

diag13Uptime				OBJECT-TYPE
	SYNTAX					INTEGER
	ACCESS					read-only
	STATUS					mandatory
	DESCRIPTION			"Time since last boot"
	::= { node12Diags 4 }

diag13Ramused			OBJECT-TYPE
	SYNTAX					INTEGER
	ACCESS					read-only
	STATUS					mandatory
	DESCRIPTION			"Ram used"
	::= { node12Diags 5 }

diag13AckTimeouts	OBJECT-TYPE
	SYNTAX					INTEGER
	ACCESS					read-only
	STATUS					mandatory
	DESCRIPTION			"Node Ack timeouts"
	::= { node12Diags 6 }

diag13PackRecv			OBJECT-TYPE
	SYNTAX					INTEGER
	ACCESS					read-only
	STATUS					mandatory
	DESCRIPTION			"Node packet recvs"
	::= { node12Diags 7 }

diag13PackTrans		OBJECT-TYPE
	SYNTAX					INTEGER
	ACCESS					read-only
	STATUS					mandatory
	DESCRIPTION			"Node packet xmits"
	::= { node12Diags 8 }

diag13PackErrors		OBJECT-TYPE
	SYNTAX					INTEGER
	ACCESS					read-only
	STATUS					mandatory
	DESCRIPTION			"Node packet errors"
	::= { node12Diags 9 }

diag13ErrorMask		OBJECT-TYPE
	SYNTAX					INTEGER
	ACCESS					read-only
	STATUS					mandatory
	DESCRIPTION			"Node error flags"
	::= { node12Diags 10 }

diag13ClockTimeouts	OBJECT-TYPE
	SYNTAX					INTEGER
	ACCESS					read-only
	STATUS					mandatory
	DESCRIPTION			"Node clock timeouts"
	::= { node12Diags 11 }

diag14LinuxVer			OBJECT-TYPE
	SYNTAX					DisplayString
	ACCESS					read-only
	STATUS					mandatory
	DESCRIPTION			"Linux OS version"
	::= { node13Diags 1 }

diag14FirmwareVer	OBJECT-TYPE
	SYNTAX					DisplayString
	ACCESS					read-only
	STATUS					mandatory
	DESCRIPTION			"Firmware version"
	::= { node13Diags 2 }

diag14Diskfree			OBJECT-TYPE
	SYNTAX					INTEGER
	ACCESS					read-only
	STATUS					mandatory
	DESCRIPTION			"Persistant storage free"
	::= { node13Diags 3 }

diag14Uptime				OBJECT-TYPE
	SYNTAX					INTEGER
	ACCESS					read-only
	STATUS					mandatory
	DESCRIPTION			"Time since last boot"
	::= { node13Diags 4 }

diag14Ramused			OBJECT-TYPE
	SYNTAX					INTEGER
	ACCESS					read-only
	STATUS					mandatory
	DESCRIPTION			"Ram used"
	::= { node13Diags 5 }

diag14AckTimeouts	OBJECT-TYPE
	SYNTAX					INTEGER
	ACCESS					read-only
	STATUS					mandatory
	DESCRIPTION			"Node Ack timeouts"
	::= { node13Diags 6 }

diag14PackRecv			OBJECT-TYPE
	SYNTAX					INTEGER
	ACCESS					read-only
	STATUS					mandatory
	DESCRIPTION			"Node packet recvs"
	::= { node13Diags 7 }

diag14PackTrans		OBJECT-TYPE
	SYNTAX					INTEGER
	ACCESS					read-only
	STATUS					mandatory
	DESCRIPTION			"Node packet xmits"
	::= { node13Diags 8 }

diag14PackErrors		OBJECT-TYPE
	SYNTAX					INTEGER
	ACCESS					read-only
	STATUS					mandatory
	DESCRIPTION			"Node packet errors"
	::= { node13Diags 9 }

diag14ErrorMask		OBJECT-TYPE
	SYNTAX					INTEGER
	ACCESS					read-only
	STATUS					mandatory
	DESCRIPTION			"Node error flags"
	::= { node13Diags 10 }

diag14ClockTimeouts	OBJECT-TYPE
	SYNTAX					INTEGER
	ACCESS					read-only
	STATUS					mandatory
	DESCRIPTION			"Node clock timeouts"
	::= { node13Diags 11 }

diag15LinuxVer			OBJECT-TYPE
	SYNTAX					DisplayString
	ACCESS					read-only
	STATUS					mandatory
	DESCRIPTION			"Linux OS version"
	::= { node14Diags 1 }

diag15FirmwareVer	OBJECT-TYPE
	SYNTAX					DisplayString
	ACCESS					read-only
	STATUS					mandatory
	DESCRIPTION			"Firmware version"
	::= { node14Diags 2 }

diag15Diskfree			OBJECT-TYPE
	SYNTAX					INTEGER
	ACCESS					read-only
	STATUS					mandatory
	DESCRIPTION			"Persistant storage free"
	::= { node14Diags 3 }

diag15Uptime				OBJECT-TYPE
	SYNTAX					INTEGER
	ACCESS					read-only
	STATUS					mandatory
	DESCRIPTION			"Time since last boot"
	::= { node14Diags 4 }

diag15Ramused			OBJECT-TYPE
	SYNTAX					INTEGER
	ACCESS					read-only
	STATUS					mandatory
	DESCRIPTION			"Ram used"
	::= { node14Diags 5 }

diag15AckTimeouts	OBJECT-TYPE
	SYNTAX					INTEGER
	ACCESS					read-only
	STATUS					mandatory
	DESCRIPTION			"Node Ack timeouts"
	::= { node14Diags 6 }

diag15PackRecv			OBJECT-TYPE
	SYNTAX					INTEGER
	ACCESS					read-only
	STATUS					mandatory
	DESCRIPTION			"Node packet recvs"
	::= { node14Diags 7 }

diag15PackTrans		OBJECT-TYPE
	SYNTAX					INTEGER
	ACCESS					read-only
	STATUS					mandatory
	DESCRIPTION			"Node packet xmits"
	::= { node14Diags 8 }

diag15PackErrors		OBJECT-TYPE
	SYNTAX					INTEGER
	ACCESS					read-only
	STATUS					mandatory
	DESCRIPTION			"Node packet errors"
	::= { node14Diags 9 }

diag15ErrorMask		OBJECT-TYPE
	SYNTAX					INTEGER
	ACCESS					read-only
	STATUS					mandatory
	DESCRIPTION			"Node error flags"
	::= { node14Diags 10 }

diag15ClockTimeouts	OBJECT-TYPE
	SYNTAX					INTEGER
	ACCESS					read-only
	STATUS					mandatory
	DESCRIPTION			"Node clock timeouts"
	::= { node14Diags 11 }

diag16LinuxVer			OBJECT-TYPE
	SYNTAX					DisplayString
	ACCESS					read-only
	STATUS					mandatory
	DESCRIPTION			"Linux OS version"
	::= { node15Diags 1 }

diag16FirmwareVer	OBJECT-TYPE
	SYNTAX					DisplayString
	ACCESS					read-only
	STATUS					mandatory
	DESCRIPTION			"Firmware version"
	::= { node15Diags 2 }

diag16Diskfree			OBJECT-TYPE
	SYNTAX					INTEGER
	ACCESS					read-only
	STATUS					mandatory
	DESCRIPTION			"Persistant storage free"
	::= { node15Diags 3 }

diag16Uptime				OBJECT-TYPE
	SYNTAX					INTEGER
	ACCESS					read-only
	STATUS					mandatory
	DESCRIPTION			"Time since last boot"
	::= { node15Diags 4 }

diag16Ramused			OBJECT-TYPE
	SYNTAX					INTEGER
	ACCESS					read-only
	STATUS					mandatory
	DESCRIPTION			"Ram used"
	::= { node15Diags 5 }

diag16AckTimeouts	OBJECT-TYPE
	SYNTAX					INTEGER
	ACCESS					read-only
	STATUS					mandatory
	DESCRIPTION			"Node Ack timeouts"
	::= { node15Diags 6 }

diag16PackRecv			OBJECT-TYPE
	SYNTAX					INTEGER
	ACCESS					read-only
	STATUS					mandatory
	DESCRIPTION			"Node packet recvs"
	::= { node15Diags 7 }

diag16PackTrans		OBJECT-TYPE
	SYNTAX					INTEGER
	ACCESS					read-only
	STATUS					mandatory
	DESCRIPTION			"Node packet xmits"
	::= { node15Diags 8 }

diag16PackErrors		OBJECT-TYPE
	SYNTAX					INTEGER
	ACCESS					read-only
	STATUS					mandatory
	DESCRIPTION			"Node packet errors"
	::= { node15Diags 9 }

diag16ErrorMask		OBJECT-TYPE
	SYNTAX					INTEGER
	ACCESS					read-only
	STATUS					mandatory
	DESCRIPTION			"Node error flags"
	::= { node15Diags 10 }

diag16ClockTimeouts	OBJECT-TYPE
	SYNTAX					INTEGER
	ACCESS					read-only
	STATUS					mandatory
	DESCRIPTION			"Node clock timeouts"
	::= { node15Diags 11 }

diag17LinuxVer			OBJECT-TYPE
	SYNTAX					DisplayString
	ACCESS					read-only
	STATUS					mandatory
	DESCRIPTION			"Linux OS version"
	::= { node16Diags 1 }

diag17FirmwareVer	OBJECT-TYPE
	SYNTAX					DisplayString
	ACCESS					read-only
	STATUS					mandatory
	DESCRIPTION			"Firmware version"
	::= { node16Diags 2 }

diag17Diskfree			OBJECT-TYPE
	SYNTAX					INTEGER
	ACCESS					read-only
	STATUS					mandatory
	DESCRIPTION			"Persistant storage free"
	::= { node16Diags 3 }

diag17Uptime				OBJECT-TYPE
	SYNTAX					INTEGER
	ACCESS					read-only
	STATUS					mandatory
	DESCRIPTION			"Time since last boot"
	::= { node16Diags 4 }

diag17Ramused			OBJECT-TYPE
	SYNTAX					INTEGER
	ACCESS					read-only
	STATUS					mandatory
	DESCRIPTION			"Ram used"
	::= { node16Diags 5 }

diag17AckTimeouts	OBJECT-TYPE
	SYNTAX					INTEGER
	ACCESS					read-only
	STATUS					mandatory
	DESCRIPTION			"Node Ack timeouts"
	::= { node16Diags 6 }

diag17PackRecv			OBJECT-TYPE
	SYNTAX					INTEGER
	ACCESS					read-only
	STATUS					mandatory
	DESCRIPTION			"Node packet recvs"
	::= { node16Diags 7 }

diag17PackTrans		OBJECT-TYPE
	SYNTAX					INTEGER
	ACCESS					read-only
	STATUS					mandatory
	DESCRIPTION			"Node packet xmits"
	::= { node16Diags 8 }

diag17PackErrors		OBJECT-TYPE
	SYNTAX					INTEGER
	ACCESS					read-only
	STATUS					mandatory
	DESCRIPTION			"Node packet errors"
	::= { node16Diags 9 }

diag17ErrorMask		OBJECT-TYPE
	SYNTAX					INTEGER
	ACCESS					read-only
	STATUS					mandatory
	DESCRIPTION			"Node error flags"
	::= { node16Diags 10 }

diag17ClockTimeouts	OBJECT-TYPE
	SYNTAX					INTEGER
	ACCESS					read-only
	STATUS					mandatory
	DESCRIPTION			"Node clock timeouts"
	::= { node16Diags 11 }

diag18LinuxVer			OBJECT-TYPE
	SYNTAX					DisplayString
	ACCESS					read-only
	STATUS					mandatory
	DESCRIPTION			"Linux OS version"
	::= { node17Diags 1 }

diag18FirmwareVer	OBJECT-TYPE
	SYNTAX					DisplayString
	ACCESS					read-only
	STATUS					mandatory
	DESCRIPTION			"Firmware version"
	::= { node17Diags 2 }

diag18Diskfree			OBJECT-TYPE
	SYNTAX					INTEGER
	ACCESS					read-only
	STATUS					mandatory
	DESCRIPTION			"Persistant storage free"
	::= { node17Diags 3 }

diag18Uptime				OBJECT-TYPE
	SYNTAX					INTEGER
	ACCESS					read-only
	STATUS					mandatory
	DESCRIPTION			"Time since last boot"
	::= { node17Diags 4 }

diag18Ramused			OBJECT-TYPE
	SYNTAX					INTEGER
	ACCESS					read-only
	STATUS					mandatory
	DESCRIPTION			"Ram used"
	::= { node17Diags 5 }

diag18AckTimeouts	OBJECT-TYPE
	SYNTAX					INTEGER
	ACCESS					read-only
	STATUS					mandatory
	DESCRIPTION			"Node Ack timeouts"
	::= { node17Diags 6 }

diag18PackRecv			OBJECT-TYPE
	SYNTAX					INTEGER
	ACCESS					read-only
	STATUS					mandatory
	DESCRIPTION			"Node packet recvs"
	::= { node17Diags 7 }

diag18PackTrans		OBJECT-TYPE
	SYNTAX					INTEGER
	ACCESS					read-only
	STATUS					mandatory
	DESCRIPTION			"Node packet xmits"
	::= { node17Diags 8 }

diag18PackErrors		OBJECT-TYPE
	SYNTAX					INTEGER
	ACCESS					read-only
	STATUS					mandatory
	DESCRIPTION			"Node packet errors"
	::= { node17Diags 9 }

diag18ErrorMask		OBJECT-TYPE
	SYNTAX					INTEGER
	ACCESS					read-only
	STATUS					mandatory
	DESCRIPTION			"Node error flags"
	::= { node17Diags 10 }

diag18ClockTimeouts	OBJECT-TYPE
	SYNTAX					INTEGER
	ACCESS					read-only
	STATUS					mandatory
	DESCRIPTION			"Node clock timeouts"
	::= { node17Diags 11 }

diag19LinuxVer			OBJECT-TYPE
	SYNTAX					DisplayString
	ACCESS					read-only
	STATUS					mandatory
	DESCRIPTION			"Linux OS version"
	::= { node18Diags 1 }

diag19FirmwareVer	OBJECT-TYPE
	SYNTAX					DisplayString
	ACCESS					read-only
	STATUS					mandatory
	DESCRIPTION			"Firmware version"
	::= { node18Diags 2 }

diag19Diskfree			OBJECT-TYPE
	SYNTAX					INTEGER
	ACCESS					read-only
	STATUS					mandatory
	DESCRIPTION			"Persistant storage free"
	::= { node18Diags 3 }

diag19Uptime				OBJECT-TYPE
	SYNTAX					INTEGER
	ACCESS					read-only
	STATUS					mandatory
	DESCRIPTION			"Time since last boot"
	::= { node18Diags 4 }

diag19Ramused			OBJECT-TYPE
	SYNTAX					INTEGER
	ACCESS					read-only
	STATUS					mandatory
	DESCRIPTION			"Ram used"
	::= { node18Diags 5 }

diag19AckTimeouts	OBJECT-TYPE
	SYNTAX					INTEGER
	ACCESS					read-only
	STATUS					mandatory
	DESCRIPTION			"Node Ack timeouts"
	::= { node18Diags 6 }

diag19PackRecv			OBJECT-TYPE
	SYNTAX					INTEGER
	ACCESS					read-only
	STATUS					mandatory
	DESCRIPTION			"Node packet recvs"
	::= { node18Diags 7 }

diag19PackTrans		OBJECT-TYPE
	SYNTAX					INTEGER
	ACCESS					read-only
	STATUS					mandatory
	DESCRIPTION			"Node packet xmits"
	::= { node18Diags 8 }

diag19PackErrors		OBJECT-TYPE
	SYNTAX					INTEGER
	ACCESS					read-only
	STATUS					mandatory
	DESCRIPTION			"Node packet errors"
	::= { node18Diags 9 }

diag19ErrorMask		OBJECT-TYPE
	SYNTAX					INTEGER
	ACCESS					read-only
	STATUS					mandatory
	DESCRIPTION			"Node error flags"
	::= { node18Diags 10 }

diag19ClockTimeouts	OBJECT-TYPE
	SYNTAX					INTEGER
	ACCESS					read-only
	STATUS					mandatory
	DESCRIPTION			"Node clock timeouts"
	::= { node18Diags 11 }

diag20LinuxVer			OBJECT-TYPE
	SYNTAX					DisplayString
	ACCESS					read-only
	STATUS					mandatory
	DESCRIPTION			"Linux OS version"
	::= { node19Diags 1 }

diag20FirmwareVer	OBJECT-TYPE
	SYNTAX					DisplayString
	ACCESS					read-only
	STATUS					mandatory
	DESCRIPTION			"Firmware version"
	::= { node19Diags 2 }

diag20Diskfree			OBJECT-TYPE
	SYNTAX					INTEGER
	ACCESS					read-only
	STATUS					mandatory
	DESCRIPTION			"Persistant storage free"
	::= { node19Diags 3 }

diag20Uptime				OBJECT-TYPE
	SYNTAX					INTEGER
	ACCESS					read-only
	STATUS					mandatory
	DESCRIPTION			"Time since last boot"
	::= { node19Diags 4 }

diag20Ramused			OBJECT-TYPE
	SYNTAX					INTEGER
	ACCESS					read-only
	STATUS					mandatory
	DESCRIPTION			"Ram used"
	::= { node19Diags 5 }

diag20AckTimeouts	OBJECT-TYPE
	SYNTAX					INTEGER
	ACCESS					read-only
	STATUS					mandatory
	DESCRIPTION			"Node Ack timeouts"
	::= { node19Diags 6 }

diag20PackRecv			OBJECT-TYPE
	SYNTAX					INTEGER
	ACCESS					read-only
	STATUS					mandatory
	DESCRIPTION			"Node packet recvs"
	::= { node19Diags 7 }

diag20PackTrans		OBJECT-TYPE
	SYNTAX					INTEGER
	ACCESS					read-only
	STATUS					mandatory
	DESCRIPTION			"Node packet xmits"
	::= { node19Diags 8 }

diag20PackErrors		OBJECT-TYPE
	SYNTAX					INTEGER
	ACCESS					read-only
	STATUS					mandatory
	DESCRIPTION			"Node packet errors"
	::= { node19Diags 9 }

diag20ErrorMask		OBJECT-TYPE
	SYNTAX					INTEGER
	ACCESS					read-only
	STATUS					mandatory
	DESCRIPTION			"Node error flags"
	::= { node19Diags 10 }

diag20ClockTimeouts	OBJECT-TYPE
	SYNTAX					INTEGER
	ACCESS					read-only
	STATUS					mandatory
	DESCRIPTION			"Node clock timeouts"
	::= { node19Diags 11 }

diag21LinuxVer			OBJECT-TYPE
	SYNTAX					DisplayString
	ACCESS					read-only
	STATUS					mandatory
	DESCRIPTION			"Linux OS version"
	::= { node20Diags 1 }

diag21FirmwareVer	OBJECT-TYPE
	SYNTAX					DisplayString
	ACCESS					read-only
	STATUS					mandatory
	DESCRIPTION			"Firmware version"
	::= { node20Diags 2 }

diag21Diskfree			OBJECT-TYPE
	SYNTAX					INTEGER
	ACCESS					read-only
	STATUS					mandatory
	DESCRIPTION			"Persistant storage free"
	::= { node20Diags 3 }

diag21Uptime				OBJECT-TYPE
	SYNTAX					INTEGER
	ACCESS					read-only
	STATUS					mandatory
	DESCRIPTION			"Time since last boot"
	::= { node20Diags 4 }

diag21Ramused			OBJECT-TYPE
	SYNTAX					INTEGER
	ACCESS					read-only
	STATUS					mandatory
	DESCRIPTION			"Ram used"
	::= { node20Diags 5 }

diag21AckTimeouts	OBJECT-TYPE
	SYNTAX					INTEGER
	ACCESS					read-only
	STATUS					mandatory
	DESCRIPTION			"Node Ack timeouts"
	::= { node20Diags 6 }

diag21PackRecv			OBJECT-TYPE
	SYNTAX					INTEGER
	ACCESS					read-only
	STATUS					mandatory
	DESCRIPTION			"Node packet recvs"
	::= { node20Diags 7 }

diag21PackTrans		OBJECT-TYPE
	SYNTAX					INTEGER
	ACCESS					read-only
	STATUS					mandatory
	DESCRIPTION			"Node packet xmits"
	::= { node20Diags 8 }

diag21PackErrors		OBJECT-TYPE
	SYNTAX					INTEGER
	ACCESS					read-only
	STATUS					mandatory
	DESCRIPTION			"Node packet errors"
	::= { node20Diags 9 }

diag21ErrorMask		OBJECT-TYPE
	SYNTAX					INTEGER
	ACCESS					read-only
	STATUS					mandatory
	DESCRIPTION			"Node error flags"
	::= { node20Diags 10 }

diag21ClockTimeouts	OBJECT-TYPE
	SYNTAX					INTEGER
	ACCESS					read-only
	STATUS					mandatory
	DESCRIPTION			"Node clock timeouts"
	::= { node20Diags 11 }

diag22LinuxVer			OBJECT-TYPE
	SYNTAX					DisplayString
	ACCESS					read-only
	STATUS					mandatory
	DESCRIPTION			"Linux OS version"
	::= { node21Diags 1 }

diag22FirmwareVer	OBJECT-TYPE
	SYNTAX					DisplayString
	ACCESS					read-only
	STATUS					mandatory
	DESCRIPTION			"Firmware version"
	::= { node21Diags 2 }

diag22Diskfree			OBJECT-TYPE
	SYNTAX					INTEGER
	ACCESS					read-only
	STATUS					mandatory
	DESCRIPTION			"Persistant storage free"
	::= { node21Diags 3 }

diag22Uptime				OBJECT-TYPE
	SYNTAX					INTEGER
	ACCESS					read-only
	STATUS					mandatory
	DESCRIPTION			"Time since last boot"
	::= { node21Diags 4 }

diag22Ramused			OBJECT-TYPE
	SYNTAX					INTEGER
	ACCESS					read-only
	STATUS					mandatory
	DESCRIPTION			"Ram used"
	::= { node21Diags 5 }

diag22AckTimeouts	OBJECT-TYPE
	SYNTAX					INTEGER
	ACCESS					read-only
	STATUS					mandatory
	DESCRIPTION			"Node Ack timeouts"
	::= { node21Diags 6 }

diag22PackRecv			OBJECT-TYPE
	SYNTAX					INTEGER
	ACCESS					read-only
	STATUS					mandatory
	DESCRIPTION			"Node packet recvs"
	::= { node21Diags 7 }

diag22PackTrans		OBJECT-TYPE
	SYNTAX					INTEGER
	ACCESS					read-only
	STATUS					mandatory
	DESCRIPTION			"Node packet xmits"
	::= { node21Diags 8 }

diag22PackErrors		OBJECT-TYPE
	SYNTAX					INTEGER
	ACCESS					read-only
	STATUS					mandatory
	DESCRIPTION			"Node packet errors"
	::= { node21Diags 9 }

diag22ErrorMask		OBJECT-TYPE
	SYNTAX					INTEGER
	ACCESS					read-only
	STATUS					mandatory
	DESCRIPTION			"Node error flags"
	::= { node21Diags 10 }

diag22ClockTimeouts	OBJECT-TYPE
	SYNTAX					INTEGER
	ACCESS					read-only
	STATUS					mandatory
	DESCRIPTION			"Node clock timeouts"
	::= { node21Diags 11 }

diag23LinuxVer			OBJECT-TYPE
	SYNTAX					DisplayString
	ACCESS					read-only
	STATUS					mandatory
	DESCRIPTION			"Linux OS version"
	::= { node22Diags 1 }

diag23FirmwareVer	OBJECT-TYPE
	SYNTAX					DisplayString
	ACCESS					read-only
	STATUS					mandatory
	DESCRIPTION			"Firmware version"
	::= { node22Diags 2 }

diag23Diskfree			OBJECT-TYPE
	SYNTAX					INTEGER
	ACCESS					read-only
	STATUS					mandatory
	DESCRIPTION			"Persistant storage free"
	::= { node22Diags 3 }

diag23Uptime				OBJECT-TYPE
	SYNTAX					INTEGER
	ACCESS					read-only
	STATUS					mandatory
	DESCRIPTION			"Time since last boot"
	::= { node22Diags 4 }

diag23Ramused			OBJECT-TYPE
	SYNTAX					INTEGER
	ACCESS					read-only
	STATUS					mandatory
	DESCRIPTION			"Ram used"
	::= { node22Diags 5 }

diag23AckTimeouts	OBJECT-TYPE
	SYNTAX					INTEGER
	ACCESS					read-only
	STATUS					mandatory
	DESCRIPTION			"Node Ack timeouts"
	::= { node22Diags 6 }

diag23PackRecv			OBJECT-TYPE
	SYNTAX					INTEGER
	ACCESS					read-only
	STATUS					mandatory
	DESCRIPTION			"Node packet recvs"
	::= { node22Diags 7 }

diag23PackTrans		OBJECT-TYPE
	SYNTAX					INTEGER
	ACCESS					read-only
	STATUS					mandatory
	DESCRIPTION			"Node packet xmits"
	::= { node22Diags 8 }

diag23PackErrors		OBJECT-TYPE
	SYNTAX					INTEGER
	ACCESS					read-only
	STATUS					mandatory
	DESCRIPTION			"Node packet errors"
	::= { node22Diags 9 }

diag23ErrorMask		OBJECT-TYPE
	SYNTAX					INTEGER
	ACCESS					read-only
	STATUS					mandatory
	DESCRIPTION			"Node error flags"
	::= { node22Diags 10 }

diag23ClockTimeouts	OBJECT-TYPE
	SYNTAX					INTEGER
	ACCESS					read-only
	STATUS					mandatory
	DESCRIPTION			"Node clock timeouts"
	::= { node22Diags 11 }

diag24LinuxVer			OBJECT-TYPE
	SYNTAX					DisplayString
	ACCESS					read-only
	STATUS					mandatory
	DESCRIPTION			"Linux OS version"
	::= { node23Diags 1 }

diag24FirmwareVer	OBJECT-TYPE
	SYNTAX					DisplayString
	ACCESS					read-only
	STATUS					mandatory
	DESCRIPTION			"Firmware version"
	::= { node23Diags 2 }

diag24Diskfree			OBJECT-TYPE
	SYNTAX					INTEGER
	ACCESS					read-only
	STATUS					mandatory
	DESCRIPTION			"Persistant storage free"
	::= { node23Diags 3 }

diag24Uptime				OBJECT-TYPE
	SYNTAX					INTEGER
	ACCESS					read-only
	STATUS					mandatory
	DESCRIPTION			"Time since last boot"
	::= { node23Diags 4 }

diag24Ramused			OBJECT-TYPE
	SYNTAX					INTEGER
	ACCESS					read-only
	STATUS					mandatory
	DESCRIPTION			"Ram used"
	::= { node23Diags 5 }

diag24AckTimeouts	OBJECT-TYPE
	SYNTAX					INTEGER
	ACCESS					read-only
	STATUS					mandatory
	DESCRIPTION			"Node Ack timeouts"
	::= { node23Diags 6 }

diag24PackRecv			OBJECT-TYPE
	SYNTAX					INTEGER
	ACCESS					read-only
	STATUS					mandatory
	DESCRIPTION			"Node packet recvs"
	::= { node23Diags 7 }

diag24PackTrans		OBJECT-TYPE
	SYNTAX					INTEGER
	ACCESS					read-only
	STATUS					mandatory
	DESCRIPTION			"Node packet xmits"
	::= { node23Diags 8 }

diag24PackErrors		OBJECT-TYPE
	SYNTAX					INTEGER
	ACCESS					read-only
	STATUS					mandatory
	DESCRIPTION			"Node packet errors"
	::= { node23Diags 9 }

diag24ErrorMask		OBJECT-TYPE
	SYNTAX					INTEGER
	ACCESS					read-only
	STATUS					mandatory
	DESCRIPTION			"Node error flags"
	::= { node23Diags 10 }

diag24ClockTimeouts	OBJECT-TYPE
	SYNTAX					INTEGER
	ACCESS					read-only
	STATUS					mandatory
	DESCRIPTION			"Node clock timeouts"
	::= { node23Diags 11 }

diag25LinuxVer			OBJECT-TYPE
	SYNTAX					DisplayString
	ACCESS					read-only
	STATUS					mandatory
	DESCRIPTION			"Linux OS version"
	::= { node24Diags 1 }

diag25FirmwareVer	OBJECT-TYPE
	SYNTAX					DisplayString
	ACCESS					read-only
	STATUS					mandatory
	DESCRIPTION			"Firmware version"
	::= { node24Diags 2 }

diag25Diskfree			OBJECT-TYPE
	SYNTAX					INTEGER
	ACCESS					read-only
	STATUS					mandatory
	DESCRIPTION			"Persistant storage free"
	::= { node24Diags 3 }

diag25Uptime				OBJECT-TYPE
	SYNTAX					INTEGER
	ACCESS					read-only
	STATUS					mandatory
	DESCRIPTION			"Time since last boot"
	::= { node24Diags 4 }

diag25Ramused			OBJECT-TYPE
	SYNTAX					INTEGER
	ACCESS					read-only
	STATUS					mandatory
	DESCRIPTION			"Ram used"
	::= { node24Diags 5 }

diag25AckTimeouts	OBJECT-TYPE
	SYNTAX					INTEGER
	ACCESS					read-only
	STATUS					mandatory
	DESCRIPTION			"Node Ack timeouts"
	::= { node24Diags 6 }

diag25PackRecv			OBJECT-TYPE
	SYNTAX					INTEGER
	ACCESS					read-only
	STATUS					mandatory
	DESCRIPTION			"Node packet recvs"
	::= { node24Diags 7 }

diag25PackTrans		OBJECT-TYPE
	SYNTAX					INTEGER
	ACCESS					read-only
	STATUS					mandatory
	DESCRIPTION			"Node packet xmits"
	::= { node24Diags 8 }

diag25PackErrors		OBJECT-TYPE
	SYNTAX					INTEGER
	ACCESS					read-only
	STATUS					mandatory
	DESCRIPTION			"Node packet errors"
	::= { node24Diags 9 }

diag25ErrorMask		OBJECT-TYPE
	SYNTAX					INTEGER
	ACCESS					read-only
	STATUS					mandatory
	DESCRIPTION			"Node error flags"
	::= { node24Diags 10 }

diag25ClockTimeouts	OBJECT-TYPE
	SYNTAX					INTEGER
	ACCESS					read-only
	STATUS					mandatory
	DESCRIPTION			"Node clock timeouts"
	::= { node24Diags 11 }

diag26LinuxVer			OBJECT-TYPE
	SYNTAX					DisplayString
	ACCESS					read-only
	STATUS					mandatory
	DESCRIPTION			"Linux OS version"
	::= { node25Diags 1 }

diag26FirmwareVer	OBJECT-TYPE
	SYNTAX					DisplayString
	ACCESS					read-only
	STATUS					mandatory
	DESCRIPTION			"Firmware version"
	::= { node25Diags 2 }

diag26Diskfree			OBJECT-TYPE
	SYNTAX					INTEGER
	ACCESS					read-only
	STATUS					mandatory
	DESCRIPTION			"Persistant storage free"
	::= { node25Diags 3 }

diag26Uptime				OBJECT-TYPE
	SYNTAX					INTEGER
	ACCESS					read-only
	STATUS					mandatory
	DESCRIPTION			"Time since last boot"
	::= { node25Diags 4 }

diag26Ramused			OBJECT-TYPE
	SYNTAX					INTEGER
	ACCESS					read-only
	STATUS					mandatory
	DESCRIPTION			"Ram used"
	::= { node25Diags 5 }

diag26AckTimeouts	OBJECT-TYPE
	SYNTAX					INTEGER
	ACCESS					read-only
	STATUS					mandatory
	DESCRIPTION			"Node Ack timeouts"
	::= { node25Diags 6 }

diag26PackRecv			OBJECT-TYPE
	SYNTAX					INTEGER
	ACCESS					read-only
	STATUS					mandatory
	DESCRIPTION			"Node packet recvs"
	::= { node25Diags 7 }

diag26PackTrans		OBJECT-TYPE
	SYNTAX					INTEGER
	ACCESS					read-only
	STATUS					mandatory
	DESCRIPTION			"Node packet xmits"
	::= { node25Diags 8 }

diag26PackErrors		OBJECT-TYPE
	SYNTAX					INTEGER
	ACCESS					read-only
	STATUS					mandatory
	DESCRIPTION			"Node packet errors"
	::= { node25Diags 9 }

diag26ErrorMask		OBJECT-TYPE
	SYNTAX					INTEGER
	ACCESS					read-only
	STATUS					mandatory
	DESCRIPTION			"Node error flags"
	::= { node25Diags 10 }

diag26ClockTimeouts	OBJECT-TYPE
	SYNTAX					INTEGER
	ACCESS					read-only
	STATUS					mandatory
	DESCRIPTION			"Node clock timeouts"
	::= { node25Diags 11 }

diag27LinuxVer			OBJECT-TYPE
	SYNTAX					DisplayString
	ACCESS					read-only
	STATUS					mandatory
	DESCRIPTION			"Linux OS version"
	::= { node26Diags 1 }

diag27FirmwareVer	OBJECT-TYPE
	SYNTAX					DisplayString
	ACCESS					read-only
	STATUS					mandatory
	DESCRIPTION			"Firmware version"
	::= { node26Diags 2 }

diag27Diskfree			OBJECT-TYPE
	SYNTAX					INTEGER
	ACCESS					read-only
	STATUS					mandatory
	DESCRIPTION			"Persistant storage free"
	::= { node26Diags 3 }

diag27Uptime				OBJECT-TYPE
	SYNTAX					INTEGER
	ACCESS					read-only
	STATUS					mandatory
	DESCRIPTION			"Time since last boot"
	::= { node26Diags 4 }

diag27Ramused			OBJECT-TYPE
	SYNTAX					INTEGER
	ACCESS					read-only
	STATUS					mandatory
	DESCRIPTION			"Ram used"
	::= { node26Diags 5 }

diag27AckTimeouts	OBJECT-TYPE
	SYNTAX					INTEGER
	ACCESS					read-only
	STATUS					mandatory
	DESCRIPTION			"Node Ack timeouts"
	::= { node26Diags 6 }

diag27PackRecv			OBJECT-TYPE
	SYNTAX					INTEGER
	ACCESS					read-only
	STATUS					mandatory
	DESCRIPTION			"Node packet recvs"
	::= { node26Diags 7 }

diag27PackTrans		OBJECT-TYPE
	SYNTAX					INTEGER
	ACCESS					read-only
	STATUS					mandatory
	DESCRIPTION			"Node packet xmits"
	::= { node26Diags 8 }

diag27PackErrors		OBJECT-TYPE
	SYNTAX					INTEGER
	ACCESS					read-only
	STATUS					mandatory
	DESCRIPTION			"Node packet errors"
	::= { node26Diags 9 }

diag27ErrorMask		OBJECT-TYPE
	SYNTAX					INTEGER
	ACCESS					read-only
	STATUS					mandatory
	DESCRIPTION			"Node error flags"
	::= { node26Diags 10 }

diag27ClockTimeouts	OBJECT-TYPE
	SYNTAX					INTEGER
	ACCESS					read-only
	STATUS					mandatory
	DESCRIPTION			"Node clock timeouts"
	::= { node26Diags 11 }

diag28LinuxVer			OBJECT-TYPE
	SYNTAX					DisplayString
	ACCESS					read-only
	STATUS					mandatory
	DESCRIPTION			"Linux OS version"
	::= { node27Diags 1 }

diag28FirmwareVer	OBJECT-TYPE
	SYNTAX					DisplayString
	ACCESS					read-only
	STATUS					mandatory
	DESCRIPTION			"Firmware version"
	::= { node27Diags 2 }

diag28Diskfree			OBJECT-TYPE
	SYNTAX					INTEGER
	ACCESS					read-only
	STATUS					mandatory
	DESCRIPTION			"Persistant storage free"
	::= { node27Diags 3 }

diag28Uptime				OBJECT-TYPE
	SYNTAX					INTEGER
	ACCESS					read-only
	STATUS					mandatory
	DESCRIPTION			"Time since last boot"
	::= { node27Diags 4 }

diag28Ramused			OBJECT-TYPE
	SYNTAX					INTEGER
	ACCESS					read-only
	STATUS					mandatory
	DESCRIPTION			"Ram used"
	::= { node27Diags 5 }

diag28AckTimeouts	OBJECT-TYPE
	SYNTAX					INTEGER
	ACCESS					read-only
	STATUS					mandatory
	DESCRIPTION			"Node Ack timeouts"
	::= { node27Diags 6 }

diag28PackRecv			OBJECT-TYPE
	SYNTAX					INTEGER
	ACCESS					read-only
	STATUS					mandatory
	DESCRIPTION			"Node packet recvs"
	::= { node27Diags 7 }

diag28PackTrans		OBJECT-TYPE
	SYNTAX					INTEGER
	ACCESS					read-only
	STATUS					mandatory
	DESCRIPTION			"Node packet xmits"
	::= { node27Diags 8 }

diag28PackErrors		OBJECT-TYPE
	SYNTAX					INTEGER
	ACCESS					read-only
	STATUS					mandatory
	DESCRIPTION			"Node packet errors"
	::= { node27Diags 9 }

diag28ErrorMask		OBJECT-TYPE
	SYNTAX					INTEGER
	ACCESS					read-only
	STATUS					mandatory
	DESCRIPTION			"Node error flags"
	::= { node27Diags 10 }

diag28ClockTimeouts	OBJECT-TYPE
	SYNTAX					INTEGER
	ACCESS					read-only
	STATUS					mandatory
	DESCRIPTION			"Node clock timeouts"
	::= { node27Diags 11 }

diag29LinuxVer			OBJECT-TYPE
	SYNTAX					DisplayString
	ACCESS					read-only
	STATUS					mandatory
	DESCRIPTION			"Linux OS version"
	::= { node28Diags 1 }

diag29FirmwareVer	OBJECT-TYPE
	SYNTAX					DisplayString
	ACCESS					read-only
	STATUS					mandatory
	DESCRIPTION			"Firmware version"
	::= { node28Diags 2 }

diag29Diskfree			OBJECT-TYPE
	SYNTAX					INTEGER
	ACCESS					read-only
	STATUS					mandatory
	DESCRIPTION			"Persistant storage free"
	::= { node28Diags 3 }

diag29Uptime				OBJECT-TYPE
	SYNTAX					INTEGER
	ACCESS					read-only
	STATUS					mandatory
	DESCRIPTION			"Time since last boot"
	::= { node28Diags 4 }

diag29Ramused			OBJECT-TYPE
	SYNTAX					INTEGER
	ACCESS					read-only
	STATUS					mandatory
	DESCRIPTION			"Ram used"
	::= { node28Diags 5 }

diag29AckTimeouts	OBJECT-TYPE
	SYNTAX					INTEGER
	ACCESS					read-only
	STATUS					mandatory
	DESCRIPTION			"Node Ack timeouts"
	::= { node28Diags 6 }

diag29PackRecv			OBJECT-TYPE
	SYNTAX					INTEGER
	ACCESS					read-only
	STATUS					mandatory
	DESCRIPTION			"Node packet recvs"
	::= { node28Diags 7 }

diag29PackTrans		OBJECT-TYPE
	SYNTAX					INTEGER
	ACCESS					read-only
	STATUS					mandatory
	DESCRIPTION			"Node packet xmits"
	::= { node28Diags 8 }

diag29PackErrors		OBJECT-TYPE
	SYNTAX					INTEGER
	ACCESS					read-only
	STATUS					mandatory
	DESCRIPTION			"Node packet errors"
	::= { node28Diags 9 }

diag29ErrorMask		OBJECT-TYPE
	SYNTAX					INTEGER
	ACCESS					read-only
	STATUS					mandatory
	DESCRIPTION			"Node error flags"
	::= { node28Diags 10 }

diag29ClockTimeouts	OBJECT-TYPE
	SYNTAX					INTEGER
	ACCESS					read-only
	STATUS					mandatory
	DESCRIPTION			"Node clock timeouts"
	::= { node28Diags 11 }

diag30LinuxVer			OBJECT-TYPE
	SYNTAX					DisplayString
	ACCESS					read-only
	STATUS					mandatory
	DESCRIPTION			"Linux OS version"
	::= { node29Diags 1 }

diag30FirmwareVer	OBJECT-TYPE
	SYNTAX					DisplayString
	ACCESS					read-only
	STATUS					mandatory
	DESCRIPTION			"Firmware version"
	::= { node29Diags 2 }

diag30Diskfree			OBJECT-TYPE
	SYNTAX					INTEGER
	ACCESS					read-only
	STATUS					mandatory
	DESCRIPTION			"Persistant storage free"
	::= { node29Diags 3 }

diag30Uptime				OBJECT-TYPE
	SYNTAX					INTEGER
	ACCESS					read-only
	STATUS					mandatory
	DESCRIPTION			"Time since last boot"
	::= { node29Diags 4 }

diag30Ramused			OBJECT-TYPE
	SYNTAX					INTEGER
	ACCESS					read-only
	STATUS					mandatory
	DESCRIPTION			"Ram used"
	::= { node29Diags 5 }

diag30AckTimeouts	OBJECT-TYPE
	SYNTAX					INTEGER
	ACCESS					read-only
	STATUS					mandatory
	DESCRIPTION			"Node Ack timeouts"
	::= { node29Diags 6 }

diag30PackRecv			OBJECT-TYPE
	SYNTAX					INTEGER
	ACCESS					read-only
	STATUS					mandatory
	DESCRIPTION			"Node packet recvs"
	::= { node29Diags 7 }

diag30PackTrans		OBJECT-TYPE
	SYNTAX					INTEGER
	ACCESS					read-only
	STATUS					mandatory
	DESCRIPTION			"Node packet xmits"
	::= { node29Diags 8 }

diag30PackErrors		OBJECT-TYPE
	SYNTAX					INTEGER
	ACCESS					read-only
	STATUS					mandatory
	DESCRIPTION			"Node packet errors"
	::= { node29Diags 9 }

diag30ErrorMask		OBJECT-TYPE
	SYNTAX					INTEGER
	ACCESS					read-only
	STATUS					mandatory
	DESCRIPTION			"Node error flags"
	::= { node29Diags 10 }

diag30ClockTimeouts	OBJECT-TYPE
	SYNTAX					INTEGER
	ACCESS					read-only
	STATUS					mandatory
	DESCRIPTION			"Node clock timeouts"
	::= { node29Diags 11 }

diag31LinuxVer			OBJECT-TYPE
	SYNTAX					DisplayString
	ACCESS					read-only
	STATUS					mandatory
	DESCRIPTION			"Linux OS version"
	::= { node30Diags 1 }

diag31FirmwareVer	OBJECT-TYPE
	SYNTAX					DisplayString
	ACCESS					read-only
	STATUS					mandatory
	DESCRIPTION			"Firmware version"
	::= { node30Diags 2 }

diag31Diskfree			OBJECT-TYPE
	SYNTAX					INTEGER
	ACCESS					read-only
	STATUS					mandatory
	DESCRIPTION			"Persistant storage free"
	::= { node30Diags 3 }

diag31Uptime				OBJECT-TYPE
	SYNTAX					INTEGER
	ACCESS					read-only
	STATUS					mandatory
	DESCRIPTION			"Time since last boot"
	::= { node30Diags 4 }

diag31Ramused			OBJECT-TYPE
	SYNTAX					INTEGER
	ACCESS					read-only
	STATUS					mandatory
	DESCRIPTION			"Ram used"
	::= { node30Diags 5 }

diag31AckTimeouts	OBJECT-TYPE
	SYNTAX					INTEGER
	ACCESS					read-only
	STATUS					mandatory
	DESCRIPTION			"Node Ack timeouts"
	::= { node30Diags 6 }

diag31PackRecv			OBJECT-TYPE
	SYNTAX					INTEGER
	ACCESS					read-only
	STATUS					mandatory
	DESCRIPTION			"Node packet recvs"
	::= { node30Diags 7 }

diag31PackTrans		OBJECT-TYPE
	SYNTAX					INTEGER
	ACCESS					read-only
	STATUS					mandatory
	DESCRIPTION			"Node packet xmits"
	::= { node30Diags 8 }

diag31PackErrors		OBJECT-TYPE
	SYNTAX					INTEGER
	ACCESS					read-only
	STATUS					mandatory
	DESCRIPTION			"Node packet errors"
	::= { node30Diags 9 }

diag31ErrorMask		OBJECT-TYPE
	SYNTAX					INTEGER
	ACCESS					read-only
	STATUS					mandatory
	DESCRIPTION			"Node error flags"
	::= { node30Diags 10 }

diag31ClockTimeouts	OBJECT-TYPE
	SYNTAX					INTEGER
	ACCESS					read-only
	STATUS					mandatory
	DESCRIPTION			"Node clock timeouts"
	::= { node30Diags 11 }

diag32LinuxVer			OBJECT-TYPE
	SYNTAX					DisplayString
	ACCESS					read-only
	STATUS					mandatory
	DESCRIPTION			"Linux OS version"
	::= { node31Diags 1 }

diag32FirmwareVer	OBJECT-TYPE
	SYNTAX					DisplayString
	ACCESS					read-only
	STATUS					mandatory
	DESCRIPTION			"Firmware version"
	::= { node31Diags 2 }

diag32Diskfree			OBJECT-TYPE
	SYNTAX					INTEGER
	ACCESS					read-only
	STATUS					mandatory
	DESCRIPTION			"Persistant storage free"
	::= { node31Diags 3 }

diag32Uptime				OBJECT-TYPE
	SYNTAX					INTEGER
	ACCESS					read-only
	STATUS					mandatory
	DESCRIPTION			"Time since last boot"
	::= { node31Diags 4 }

diag32Ramused			OBJECT-TYPE
	SYNTAX					INTEGER
	ACCESS					read-only
	STATUS					mandatory
	DESCRIPTION			"Ram used"
	::= { node31Diags 5 }

diag32AckTimeouts	OBJECT-TYPE
	SYNTAX					INTEGER
	ACCESS					read-only
	STATUS					mandatory
	DESCRIPTION			"Node Ack timeouts"
	::= { node31Diags 6 }

diag32PackRecv			OBJECT-TYPE
	SYNTAX					INTEGER
	ACCESS					read-only
	STATUS					mandatory
	DESCRIPTION			"Node packet recvs"
	::= { node31Diags 7 }

diag32PackTrans		OBJECT-TYPE
	SYNTAX					INTEGER
	ACCESS					read-only
	STATUS					mandatory
	DESCRIPTION			"Node packet xmits"
	::= { node31Diags 8 }

diag32PackErrors		OBJECT-TYPE
	SYNTAX					INTEGER
	ACCESS					read-only
	STATUS					mandatory
	DESCRIPTION			"Node packet errors"
	::= { node31Diags 9 }

diag32ErrorMask		OBJECT-TYPE
	SYNTAX					INTEGER
	ACCESS					read-only
	STATUS					mandatory
	DESCRIPTION			"Node error flags"
	::= { node31Diags 10 }

diag32ClockTimeouts	OBJECT-TYPE
	SYNTAX					INTEGER
	ACCESS					read-only
	STATUS					mandatory
	DESCRIPTION			"Node clock timeouts"
	::= { node31Diags 11 }

-- Trap stuff

ims-trap-unit OBJECT-TYPE
	SYNTAX		DisplayString
	ACCESS		read-only
	STATUS		mandatory
	DESCRIPTION "This OID defines the Unit name. A get of this OID will return a NULL string"
	::= { imsTrapArgs 1 }

ims-trap-chan OBJECT-TYPE
	SYNTAX		DisplayString
	ACCESS		read-only
	STATUS		mandatory
	DESCRIPTION "This OID defines the Channel name.  A get of this OID will return a NULL string"
	::= { imsTrapArgs 2 }

ims-trap-env-type OBJECT-TYPE
	SYNTAX		DisplayString
	ACCESS		read-only
	STATUS		mandatory
	DESCRIPTION "This OID defines the type of an env input.  A get of this OID will return a NULL string"
	::= { imsTrapArgs 3 }

ims-trap-value OBJECT-TYPE
	SYNTAX		DisplayString
	ACCESS		read-only
	STATUS		mandatory
	DESCRIPTION "This OID defines the value of an env input.  A get of this OID will return a NULL string"
	::= { imsTrapArgs 4 }

ims-trap-class OBJECT-TYPE
	SYNTAX		DisplayString
	ACCESS		read-only
	STATUS		mandatory
	DESCRIPTION "This OID defines the class of the channel.  A get of this OID will return a NULL string"
	::= { imsTrapArgs 5 }

ims-trap-status OBJECT-TYPE
	SYNTAX		DisplayString
	ACCESS		read-only
	STATUS		mandatory
	DESCRIPTION "This OID defines the Alarm status.  A get of this OID will return a NULL string"
	::= { imsTrapArgs 6 }

ims-trap-time OBJECT-TYPE
	SYNTAX		DisplayString
	ACCESS		read-only
	STATUS		mandatory
	DESCRIPTION "This OID defines the time of the Alarm.  A get of this OID will return a NULL string"
	::= { imsTrapArgs 7 }

ims-trap-pg OBJECT-TYPE
	SYNTAX		DisplayString
	ACCESS		read-only
	STATUS		mandatory
	DESCRIPTION "This OID defines the power gate name.  A get of this OID will return a NULL string"
	::= { imsTrapArgs 8 }


environment-alarm-trap-major TRAP-TYPE
	ENTERPRISE sensaphone
	VARIABLES { ims-trap-time,ims-trap-unit,ims-trap-class,ims-trap-chan,ims-trap-env-type,ims-trap-value,ims-trap-status }
	DESCRIPTION "Description of environmental input alarm"
   --#TYPE "IMS Environmental Alarm"
   --#SUMMARY "An Env input is out of range at $1 in Unit: $2, Class: $3, Channel: $4, Type: $5, Value: $6, Status: $7"
   --#SEVERITY MAJOR
   --#TIMEINDEX 1
   --#HELP ""
   --#HELPTAG 0
   --#STATE OPERATIONAL 
	::= 1

environment-alarm-trap-minor TRAP-TYPE
	ENTERPRISE sensaphone
	VARIABLES { ims-trap-time,ims-trap-unit,ims-trap-class,ims-trap-chan,ims-trap-env-type,ims-trap-value,ims-trap-status }
	DESCRIPTION "Description of environmental input alarm"
   --#TYPE "IMS Environmental Alarm"
   --#SUMMARY "An Env input is out of range at $1 in Unit: $2, Class: $3, Channel: $4, Type: $5, Value: $6, Status: $7"
   --#SEVERITY MINOR
   --#TIMEINDEX 1
   --#HELP ""
   --#HELPTAG 0
   --#STATE OPERATIONAL 
	::= 2

environment-alarm-trap-normal TRAP-TYPE
	ENTERPRISE sensaphone
	VARIABLES { ims-trap-time,ims-trap-unit,ims-trap-class,ims-trap-chan,ims-trap-env-type,ims-trap-value }
	DESCRIPTION "Description of environmental input alarm"
   --#TYPE "IMS Environmental Alarm"
   --#SUMMARY "An Env has returned to normal at $1 in Unit: $2, Class: $3, Channel: $4, Type: $5, Value: $6"
   --#SEVERITY NORMAL
   --#TIMEINDEX 1
   --#HELP ""
   --#HELPTAG 0
   --#STATE OPERATIONAL 
	::= 3

ip-alarm-trap-major TRAP-TYPE
	ENTERPRISE sensaphone
	VARIABLES { ims-trap-time,ims-trap-unit,ims-trap-class,ims-trap-chan,ims-trap-status }
	DESCRIPTION "Description of IP alarm"
   --#TYPE "IMS IP Alarm"
   --#SUMMARY "An IP is not responding at $1 in Unit: $2, Class: $3, Channel: $4, Status: $5"
   --#SEVERITY MAJOR
   --#TIMEINDEX 1
   --#HELP ""
   --#HELPTAG 0
   --#STATE OPERATIONAL 
	::= 4

ip-alarm-trap-minor TRAP-TYPE
	ENTERPRISE sensaphone
	VARIABLES { ims-trap-time,ims-trap-unit,ims-trap-class,ims-trap-chan,ims-trap-status }
	DESCRIPTION "Description of IP alarm"
   --#TYPE "IMS IP Alarm"
   --#SUMMARY "An IP is not responding at $1 in Unit: $2, Class: $3, Channel: $4, Status: $5"
   --#SEVERITY MINOR
   --#TIMEINDEX 1
   --#HELP ""
   --#HELPTAG 0
   --#STATE OPERATIONAL 
	::= 5

ip-alarm-trap-normal TRAP-TYPE
	ENTERPRISE sensaphone
	VARIABLES { ims-trap-time,ims-trap-unit,ims-trap-class,ims-trap-chan }
	DESCRIPTION "Description of IP alarm"
   --#TYPE "IMS IP Alarm"
   --#SUMMARY "An IP has returned to normal at $1 in Unit: $2, Class: $3, Channel: $4"
   --#SEVERITY NORMAL
   --#TIMEINDEX 1
   --#HELP ""
   --#HELPTAG 0
   --#STATE OPERATIONAL 
	::= 6


diagnostic-alarm-trap-sensor TRAP-TYPE
	ENTERPRISE sensaphone
	VARIABLES { ims-trap-time,ims-trap-unit,ims-trap-class,ims-trap-chan }
  DESCRIPTION "Description of diagnostic alarm"
   --#TYPE "IMS Diagnostic Alarm"
   --#SUMMARY "Sensor disruption at $1 in Unit: $2, Class: $3, Channel: $4"
   --#SEVERITY MAJOR
   --#TIMEINDEX 1
   --#HELP ""
   --#HELPTAG 0
   --#STATE OPERATIONAL 
	::= 7

diagnostic-alarm-trap-node TRAP-TYPE
	ENTERPRISE sensaphone
	VARIABLES { ims-trap-time,ims-trap-unit}
  DESCRIPTION "Description of diagnostic alarm"
   --#TYPE "IMS Diagnostic Alarm"
   --#SUMMARY "Node $2 disruption at $1"
   --#SEVERITY MAJOR
   --#TIMEINDEX 1
   --#HELP ""
   --#HELPTAG 0
   --#STATE OPERATIONAL 
	::= 8


diagnostic-alarm-trap-powergate TRAP-TYPE
	ENTERPRISE sensaphone
	VARIABLES { ims-trap-time,ims-trap-unit,ims-trap-pg }
  DESCRIPTION "Description of diagnostic alarm"
   --#TYPE "IMS Diagnostic Alarm"
   --#SUMMARY "Power Gate disruption in Unit: $2 at $1. Powergate: $3"
   --#SEVERITY MAJOR
   --#TIMEINDEX 1
   --#HELP ""
   --#HELPTAG 0
   --#STATE OPERATIONAL 
	::= 9


diagnostic-alarm-trap-nodialtone TRAP-TYPE
	ENTERPRISE sensaphone
	VARIABLES { ims-trap-time,ims-trap-unit }
  DESCRIPTION "Description of diagnostic alarm"
   --#TYPE "IMS Diagnostic Alarm"
   --#SUMMARY "No dialtone at $1 in Unit: $2"
   --#SEVERITY MAJOR
   --#TIMEINDEX 1
   --#HELP ""
   --#HELPTAG 0
   --#STATE OPERATIONAL 
	::= 10

END
