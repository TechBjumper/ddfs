SCHNEIDER-ION7X50-MIB DEFINITIONS ::= BEGIN

          IMPORTS
                  enterprises, private
                      FROM RFC1155-SMI
                  OBJECT-TYPE
                          FROM RFC-1212;

		  -- Schneider's ION products currently use Enterprise number 10439.
		  -- In the future, these objects will become a subset of enterprise
		  -- groupeSchneider's number 3833. 
          schneiderElectric  OBJECT IDENTIFIER ::= { enterprises 10439 }

          -- textual conventions

          DisplayString ::=
              OCTET STRING
          -- This data type is used to model textual information taken
          -- from the NVT ASCII character set.  By convention, objects
          -- with this syntax are declared as having

          --
          --      SIZE (0..255)
          

          smm1_OID1  OBJECT-TYPE
              SYNTAX  DisplayString (SIZE (0..255))
              ACCESS  read-only
              STATUS  mandatory
              DESCRIPTION
                      "SMM1 Input 1"
              ::= { schneiderElectric 1 }

          smm1_OID2  OBJECT-TYPE
              SYNTAX  DisplayString (SIZE (0..255))
              ACCESS  read-only
              STATUS  mandatory
              DESCRIPTION
                      "SMM1 Input 2"
              ::= { schneiderElectric 2 }          

          smm1_OID3  OBJECT-TYPE
              SYNTAX  DisplayString (SIZE (0..255))
              ACCESS  read-only
              STATUS  mandatory
              DESCRIPTION
                      "SMM1 Input 3"
              ::= { schneiderElectric 3 }

          smm1_OID4  OBJECT-TYPE
              SYNTAX  DisplayString (SIZE (0..255))
              ACCESS  read-only
              STATUS  mandatory
              DESCRIPTION
                      "SMM1 Input 4"
              ::= { schneiderElectric 4 }               
 
          smm1_OID5  OBJECT-TYPE
              SYNTAX  DisplayString (SIZE (0..255))
              ACCESS  read-only
              STATUS  mandatory
              DESCRIPTION
                      "SMM1 Input 5"
              ::= { schneiderElectric 5 }


          smm1_OID6  OBJECT-TYPE
              SYNTAX  DisplayString (SIZE (0..255))
              ACCESS  read-only
              STATUS  mandatory
              DESCRIPTION
                      "SMM1 Input 6"
              ::= { schneiderElectric 6 }

          smm1_OID7  OBJECT-TYPE
              SYNTAX  DisplayString (SIZE (0..255))
              ACCESS  read-only
              STATUS  mandatory
              DESCRIPTION
                      "SMM1 Input 7"
              ::= { schneiderElectric 7 }          

          smm1_OID8  OBJECT-TYPE
              SYNTAX  DisplayString (SIZE (0..255))
              ACCESS  read-only
              STATUS  mandatory
              DESCRIPTION
                      "SMM1 Input 8"
              ::= { schneiderElectric 8 }

          smm1_OID9  OBJECT-TYPE
              SYNTAX  DisplayString (SIZE (0..255))
              ACCESS  read-only
              STATUS  mandatory
              DESCRIPTION
                      "SMM1 Input 9"
              ::= { schneiderElectric 9 }               
 
          smm1_OID10  OBJECT-TYPE
              SYNTAX  DisplayString (SIZE (0..255))
              ACCESS  read-only
              STATUS  mandatory
              DESCRIPTION
                      "SMM1 Input 10"
              ::= { schneiderElectric 10 }              
 
          smm2_OID1  OBJECT-TYPE
              SYNTAX  DisplayString (SIZE (0..255))
              ACCESS  read-only
              STATUS  mandatory
              DESCRIPTION
                      "SMM2 Input 1"
              ::= { schneiderElectric 11 }

          smm2_OID2  OBJECT-TYPE
              SYNTAX  DisplayString (SIZE (0..255))
              ACCESS  read-only
              STATUS  mandatory
              DESCRIPTION
                      "SMM2 Input 2"
              ::= { schneiderElectric 12 }          

          smm2_OID3  OBJECT-TYPE
              SYNTAX  DisplayString (SIZE (0..255))
              ACCESS  read-only
              STATUS  mandatory
              DESCRIPTION
                      "SMM2 Input 3"
              ::= { schneiderElectric 13 }

          smm2_OID4  OBJECT-TYPE
              SYNTAX  DisplayString (SIZE (0..255))
              ACCESS  read-only
              STATUS  mandatory
              DESCRIPTION
                      "SMM2 Input 4"
              ::= { schneiderElectric 14 }               
 
          smm2_OID5  OBJECT-TYPE
              SYNTAX  DisplayString (SIZE (0..255))
              ACCESS  read-only
              STATUS  mandatory
              DESCRIPTION
                      "SMM2 Input 5"
              ::= { schneiderElectric 15 }


          smm2_OID6  OBJECT-TYPE
              SYNTAX  DisplayString (SIZE (0..255))
              ACCESS  read-only
              STATUS  mandatory
              DESCRIPTION
                      "SMM2 Input 6"
              ::= { schneiderElectric 16 }

          smm2_OID7  OBJECT-TYPE
              SYNTAX  DisplayString (SIZE (0..255))
              ACCESS  read-only
              STATUS  mandatory
              DESCRIPTION
                      "SMM2 Input 7"
              ::= { schneiderElectric 17 }          

          smm2_OID8  OBJECT-TYPE
              SYNTAX  DisplayString (SIZE (0..255))
              ACCESS  read-only
              STATUS  mandatory
              DESCRIPTION
                      "SMM2 Input 8"
              ::= { schneiderElectric 18 }

          smm2_OID9  OBJECT-TYPE
              SYNTAX  DisplayString (SIZE (0..255))
              ACCESS  read-only
              STATUS  mandatory
              DESCRIPTION
                      "SMM2 Input 9"
              ::= { schneiderElectric 19 }               
 
          smm2_OID10  OBJECT-TYPE
              SYNTAX  DisplayString (SIZE (0..255))
              ACCESS  read-only
              STATUS  mandatory
              DESCRIPTION
                      "SMM2 Input 10"
              ::= { schneiderElectric 20 }                

          smm3_OID1  OBJECT-TYPE
              SYNTAX  DisplayString (SIZE (0..255))
              ACCESS  read-only
              STATUS  mandatory
              DESCRIPTION
                      "SMM3 Input 1"
              ::= { schneiderElectric 21 }

          smm3_OID2  OBJECT-TYPE
              SYNTAX  DisplayString (SIZE (0..255))
              ACCESS  read-only
              STATUS  mandatory
              DESCRIPTION
                      "SMM3 Input 2"
              ::= { schneiderElectric 22 }          

          smm3_OID3  OBJECT-TYPE
              SYNTAX  DisplayString (SIZE (0..255))
              ACCESS  read-only
              STATUS  mandatory
              DESCRIPTION
                      "SMM3 Input 3"
              ::= { schneiderElectric 23 }

          smm3_OID4  OBJECT-TYPE
              SYNTAX  DisplayString (SIZE (0..255))
              ACCESS  read-only
              STATUS  mandatory
              DESCRIPTION
                      "SMM3 Input 4"
              ::= { schneiderElectric 24 }               
 
          smm3_OID5  OBJECT-TYPE
              SYNTAX  DisplayString (SIZE (0..255))
              ACCESS  read-only
              STATUS  mandatory
              DESCRIPTION
                      "SMM3 Input 5"
              ::= { schneiderElectric 25 }


          smm3_OID6  OBJECT-TYPE
              SYNTAX  DisplayString (SIZE (0..255))
              ACCESS  read-only
              STATUS  mandatory
              DESCRIPTION
                      "SMM3 Input 6"
              ::= { schneiderElectric 26 }

          smm3_OID7  OBJECT-TYPE
              SYNTAX  DisplayString (SIZE (0..255))
              ACCESS  read-only
              STATUS  mandatory
              DESCRIPTION
                      "SMM3 Input 7"
              ::= { schneiderElectric 27 }          

          smm3_OID8  OBJECT-TYPE
              SYNTAX  DisplayString (SIZE (0..255))
              ACCESS  read-only
              STATUS  mandatory
              DESCRIPTION
                      "SMM3 Input 8"
              ::= { schneiderElectric 28 }

          smm3_OID9  OBJECT-TYPE
              SYNTAX  DisplayString (SIZE (0..255))
              ACCESS  read-only
              STATUS  mandatory
              DESCRIPTION
                      "SMM3 Input 9"
              ::= { schneiderElectric 29 }               
 
          smm3_OID10  OBJECT-TYPE
              SYNTAX  DisplayString (SIZE (0..255))
              ACCESS  read-only
              STATUS  mandatory
              DESCRIPTION
                      "SMM3 Input 10"
              ::= { schneiderElectric 30 }
                
                END
