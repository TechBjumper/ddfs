--Delta-MIB { iso(1) org(3) dod(6) internet(1) private(4) enterprises(1) delta(2254) ups(2) envirostation(41) }


DeltaEnviro-MIB DEFINITIONS ::= BEGIN


IMPORTS
	enterprises
		FROM RFC1155-SMI
	DisplayString
		FROM RFC1213-MIB
	OBJECT-TYPE
		FROM RFC-1212
	TRAP-TYPE
		FROM RFC-1215;

delta				OBJECT IDENTIFIER ::=  { enterprises 2254 }

ups					OBJECT IDENTIFIER ::=  { delta 2 }

enviro				OBJECT IDENTIFIER ::=  { ups 41 }

denviroIdent		OBJECT IDENTIFIER ::=  { enviro 1 }
denviroStatus		OBJECT IDENTIFIER ::=  { enviro 2 }
denviroDeltaBus		OBJECT IDENTIFIER ::=  { enviro 3 }
denviroRS485		OBJECT IDENTIFIER ::=  { enviro 4 }
denviroControl 		OBJECT IDENTIFIER ::=  { enviro 5 }
denviroPDU			OBJECT IDENTIFIER ::=  { enviro 6 }
denviroReaction		OBJECT IDENTIFIER ::=  { enviro 7 }
denviroTraps		OBJECT IDENTIFIER ::=  { enviro 20 }


--
-- denviro Ident group
--
   denviroIdentManufacturer OBJECT-TYPE
       SYNTAX     DisplayString (SIZE(0..32))
       ACCESS     read-only
       STATUS     mandatory
       DESCRIPTION
               "The EnviroStation Vendor."
       ::= { denviroIdent 1 }

   denviroIdentModel OBJECT-TYPE
       SYNTAX     DisplayString (SIZE(0..32))
       ACCESS     read-only
       STATUS     mandatory
       DESCRIPTION
               "The EnviroStation Model designation."
       ::= { denviroIdent 2 }

   denviroIdentSerialNumber OBJECT-TYPE
       SYNTAX     DisplayString (SIZE(0..16))
       ACCESS     read-only
       STATUS     mandatory
       DESCRIPTION
               "The EnviroStation serial number"
       ::= { denviroIdent 3 }

   denviroIdentAgentFirmwareVersion OBJECT-TYPE
       SYNTAX     DisplayString (SIZE(0..16))
       ACCESS     read-only
       STATUS     mandatory
       DESCRIPTION
               "The EnviroStation sensor firmware version"
       ::= { denviroIdent 4 }

  denviroIdentAgentSoftwareVersion OBJECT-TYPE
       SYNTAX     DisplayString (SIZE(0..16))
       ACCESS     read-only
       STATUS     mandatory
       DESCRIPTION
               "The EnviroStation NMC software version"
       ::= { denviroIdent 5 }

   denviroIdentName OBJECT-TYPE
       SYNTAX     DisplayString (SIZE(0..32))
       ACCESS     read-write
       STATUS     mandatory
       DESCRIPTION
               "A string identifying the EnviroStation.
               This object should be set by the administrator."
       ::= { denviroIdent 6 }

   denviroIdentSensorHub1Title OBJECT-TYPE
       SYNTAX     DisplayString (SIZE(0..32))
       ACCESS     read-write
       STATUS     mandatory
       DESCRIPTION
               "The Sensor Hub1 title."
       ::= { denviroIdent 7 }

   denviroIdentSensorHub2Title OBJECT-TYPE
       SYNTAX     DisplayString (SIZE(0..32))
       ACCESS     read-write
       STATUS     mandatory
       DESCRIPTION
               "The Sensor Hub2 title."
       ::= { denviroIdent 8 }

   denviroIdentSensorHub3Title OBJECT-TYPE
       SYNTAX     DisplayString (SIZE(0..32))
       ACCESS     read-write
       STATUS     mandatory
       DESCRIPTION
               "The Sensor Hub3 title."
       ::= { denviroIdent 9 }

   denviroIdentSensorHub4Title OBJECT-TYPE
       SYNTAX     DisplayString (SIZE(0..32))
       ACCESS     read-write
       STATUS     mandatory
       DESCRIPTION
               "The Sensor Hub4 title."
       ::= { denviroIdent 10 }

   denviroIdentSensorHub5Title OBJECT-TYPE
       SYNTAX     DisplayString (SIZE(0..32))
       ACCESS     read-write
       STATUS     mandatory
       DESCRIPTION
               "The Sensor Hub5 title."
       ::= { denviroIdent 11 }

   denviroIdentSensorHub6Title OBJECT-TYPE
       SYNTAX     DisplayString (SIZE(0..32))
       ACCESS     read-write
       STATUS     mandatory
       DESCRIPTION
               "The Sensor Hub6 title."
       ::= { denviroIdent 12 }

   denviroIdentSensorHub7Title OBJECT-TYPE
       SYNTAX     DisplayString (SIZE(0..32))
       ACCESS     read-write
       STATUS     mandatory
       DESCRIPTION
               "The Sensor Hub7 title."
       ::= { denviroIdent 13 }

   denviroIdentSensorHub8Title OBJECT-TYPE
       SYNTAX     DisplayString (SIZE(0..32))
       ACCESS     read-write
       STATUS     mandatory
       DESCRIPTION
               "The Sensor Hub8 title."
       ::= { denviroIdent 14 }

   denviroIdentAI1Title OBJECT-TYPE
       SYNTAX     DisplayString (SIZE(0..32))
       ACCESS     read-write
       STATUS     mandatory
       DESCRIPTION
               "The AI1 title."
       ::= { denviroIdent 15 }

   denviroIdentAI2Title OBJECT-TYPE
       SYNTAX     DisplayString (SIZE(0..32))
       ACCESS     read-write
       STATUS     mandatory
       DESCRIPTION
               "The AI2 title."
       ::= { denviroIdent 16 }

   denviroIdentAI3Title OBJECT-TYPE
       SYNTAX     DisplayString (SIZE(0..32))
       ACCESS     read-write
       STATUS     mandatory
       DESCRIPTION
               "The AI3 title."
       ::= { denviroIdent 17 }

   denviroIdentAI4Title OBJECT-TYPE
       SYNTAX     DisplayString (SIZE(0..32))
       ACCESS     read-write
       STATUS     mandatory
       DESCRIPTION
               "The AI4 title."
       ::= { denviroIdent 18 }

   denviroIdentDI1Title OBJECT-TYPE
       SYNTAX     DisplayString (SIZE(0..32))
       ACCESS     read-write
       STATUS     mandatory
       DESCRIPTION
               "The DI1 title."
       ::= { denviroIdent 19 }

   denviroIdentDI2Title OBJECT-TYPE
       SYNTAX     DisplayString (SIZE(0..32))
       ACCESS     read-write
       STATUS     mandatory
       DESCRIPTION
               "The DI2 title."
       ::= { denviroIdent 20 }

   denviroIdentDI3Title OBJECT-TYPE
       SYNTAX     DisplayString (SIZE(0..32))
       ACCESS     read-write
       STATUS     mandatory
       DESCRIPTION
               "The DI3 title."
       ::= { denviroIdent 21 }

   denviroIdentDI4Title OBJECT-TYPE
       SYNTAX     DisplayString (SIZE(0..32))
       ACCESS     read-write
       STATUS     mandatory
       DESCRIPTION
               "The DI4 title."
       ::= { denviroIdent 22 }

   denviroIdentDO1Title OBJECT-TYPE
       SYNTAX     DisplayString (SIZE(0..32))
       ACCESS     read-write
       STATUS     mandatory
       DESCRIPTION
               "The DO1 title."
       ::= { denviroIdent 23 }

   denviroIdentDO2Title OBJECT-TYPE
       SYNTAX     DisplayString (SIZE(0..32))
       ACCESS     read-write
       STATUS     mandatory
       DESCRIPTION
               "The DO2 title."
       ::= { denviroIdent 24 }

--
-- denviro Status group
--
    denviroStatusSensorHub1 OBJECT-TYPE
        SYNTAX     INTEGER{
                   alarm(1),
                   normal(2)
        }
	    ACCESS read-only
	    STATUS mandatory
	    DESCRIPTION
            " The detection pin for Sensor Hub 1."
	    ::= { denviroStatus 1 }

    denviroStatusSensorHub2 OBJECT-TYPE
        SYNTAX     INTEGER{
                   alarm(1),
                   normal(2)
        }
	    ACCESS read-only
	    STATUS mandatory
	    DESCRIPTION
		    " The detection pin for Sensor Hub 2."
	    ::= { denviroStatus 2 }

    denviroStatusSensorHub3 OBJECT-TYPE
        SYNTAX     INTEGER{
                   alarm(1),
                   normal(2)
        }
	    ACCESS read-only
	    STATUS mandatory
	    DESCRIPTION
		    " The detection pin for Sensor Hub 3."
	    ::= { denviroStatus 3 }

    denviroStatusSensorHub4 OBJECT-TYPE
        SYNTAX     INTEGER{
                   alarm(1),
                   normal(2)
        }
	    ACCESS read-only
	    STATUS mandatory
	    DESCRIPTION
		    " The detection pin for Sensor Hub 4."
	    ::= { denviroStatus 4 }

    denviroStatusSensorHub5 OBJECT-TYPE
        SYNTAX     INTEGER{
                   alarm(1),
                   normal(2)
        }
	    ACCESS read-only
	    STATUS mandatory
	    DESCRIPTION
		    " The detection pin for Sensor Hub 5."
	    ::= { denviroStatus 5 }

    denviroStatusSensorHub6 OBJECT-TYPE
        SYNTAX     INTEGER{
                   alarm(1),
                   normal(2)
        }
	    ACCESS read-only
	    STATUS mandatory
	    DESCRIPTION
		    " The detection pin for Sensor Hub 6."
	    ::= { denviroStatus 6 }

    denviroStatusSensorHub7 OBJECT-TYPE
        SYNTAX     INTEGER{
                   alarm(1),
                   normal(2)
        }
	    ACCESS read-only
	    STATUS mandatory
	    DESCRIPTION
		    " The detection pin for Sensor Hub 7."
	    ::= { denviroStatus 7 }

    denviroStatusSensorHub8 OBJECT-TYPE
        SYNTAX     INTEGER{
                   alarm(1),
                   normal(2)
        }
	    ACCESS read-only
	    STATUS mandatory
	    DESCRIPTION
		    " The detection pin for Sensor Hub 8."
	    ::= { denviroStatus 8 }

    denviroStatusSensorHubPwr1 OBJECT-TYPE
        SYNTAX     INTEGER{
                   on(1),
                   off(2)
        }
	    ACCESS read-only
	    STATUS mandatory
	    DESCRIPTION
            " The controllable power status of Sensor Hub 1."
	    ::= { denviroStatus 9 }

    denviroStatusSensorHubPwr2 OBJECT-TYPE
        SYNTAX     INTEGER{
                   on(1),
                   off(2)
        }
	    ACCESS read-only
	    STATUS mandatory
	    DESCRIPTION
		    " The controllable power status of Sensor Hub 2."
	    ::= { denviroStatus 10 }

    denviroStatusDI1 OBJECT-TYPE
        SYNTAX     INTEGER{
                   alarm(1),
                   normal(2)
        }
	    ACCESS read-only
	    STATUS mandatory
	    DESCRIPTION
		    " The detection pin for digital input 1."
	    ::= { denviroStatus 11 }

    denviroStatusDI2 OBJECT-TYPE
        SYNTAX     INTEGER{
                   alarm(1),
                   normal(2)
        }
	    ACCESS read-only
	    STATUS mandatory
	    DESCRIPTION
		    " The detection pin for digital input 2."
	    ::= { denviroStatus 12 }

    denviroStatusDI3 OBJECT-TYPE
        SYNTAX     INTEGER{
                   alarm(1),
                   normal(2)
        }
	    ACCESS read-only
	    STATUS mandatory
	    DESCRIPTION
		    " The detection pin for digital input 3."
	    ::= { denviroStatus 13 }

    denviroStatusDI4 OBJECT-TYPE
        SYNTAX     INTEGER{
                   alarm(1),
                   normal(2)
        }
	    ACCESS read-only
	    STATUS mandatory
	    DESCRIPTION
		    " The detection pin for digital input 4."
	    ::= { denviroStatus 14 }

    denviroStatusDO1 OBJECT-TYPE
        SYNTAX     INTEGER{
                   alarm(1),
                   normal(2)
        }
	    ACCESS read-only
	    STATUS mandatory
	    DESCRIPTION
		    " The status for DO 1."
	    ::= { denviroStatus 15 }

    denviroStatusDO2 OBJECT-TYPE
        SYNTAX     INTEGER{
                   alarm(1),
                   normal(2)
        }
	    ACCESS read-only
	    STATUS mandatory
	    DESCRIPTION
		    " The status for DO 2."
	    ::= { denviroStatus 16 }

    denviroMeasureAI1 OBJECT-TYPE
        SYNTAX     INTEGER
        ACCESS     read-only
        STATUS     mandatory
        DESCRIPTION
            " The present analog input 1 measured value."
        ::= { denviroStatus 17 }

    denviroMeasureAI2 OBJECT-TYPE
	    SYNTAX INTEGER
	    ACCESS read-only
	    STATUS mandatory
	    DESCRIPTION
            "The present analog input 2 measured value."
	    ::= { denviroStatus 18 }

    denviroMeasureAI3 OBJECT-TYPE
	    SYNTAX INTEGER
	    ACCESS read-only
	    STATUS mandatory
	    DESCRIPTION
            "The present analog input 3 measured value."
	    ::= { denviroStatus 19 }

    denviroMeasureAI4 OBJECT-TYPE
	    SYNTAX INTEGER
	    ACCESS read-only
	    STATUS mandatory
	    DESCRIPTION
            "The present analog input 4 measured value."
	    ::= { denviroStatus 20 }

    denviroStatusAI1 OBJECT-TYPE
        SYNTAX     INTEGER{
                   warning(1),
                   alarm(2),
                   normal(3)
        }
	    ACCESS read-only
	    STATUS mandatory
	    DESCRIPTION
		    " The status for AI 1."
	    ::= { denviroStatus 21 }

    denviroStatusAI2 OBJECT-TYPE
        SYNTAX     INTEGER{
                   warning(1),
                   alarm(2),
                   normal(3)
        }
	    ACCESS read-only
	    STATUS mandatory
	    DESCRIPTION
		    " The status for AI 2."
	    ::= { denviroStatus 22 }

    denviroStatusAI3 OBJECT-TYPE
        SYNTAX     INTEGER{
                   warning(1),
                   alarm(2),
                   normal(3)
        }
	    ACCESS read-only
	    STATUS mandatory
	    DESCRIPTION
		    " The status for AI 3."
	    ::= { denviroStatus 23 }

    denviroStatusAI4 OBJECT-TYPE
        SYNTAX     INTEGER{
                   warning(1),
                   alarm(2),
                   normal(3)
        }
	    ACCESS read-only
	    STATUS mandatory
	    DESCRIPTION
		    " The status for AI 4."
	    ::= { denviroStatus 24 }

    denviroStatusCommunication OBJECT-TYPE
        SYNTAX     INTEGER{
                   disconnect(1),
                   connect(2)
        }
	    ACCESS read-only
	    STATUS mandatory
	    DESCRIPTION
            " The status of communicate with Sensor board."
	    ::= { denviroStatus 25 }

    denviroStatusShortCircuit OBJECT-TYPE
        SYNTAX     INTEGER{
                   on(1),
                   off(2)
        }
	    ACCESS read-only
	    STATUS mandatory
	    DESCRIPTION
            " Short circuit protection."
	    ::= { denviroStatus 26 }

    denviroStatusOverCurrent OBJECT-TYPE
        SYNTAX     INTEGER{
                   on(1),
                   off(2)
        }
	    ACCESS read-only
	    STATUS mandatory
	    DESCRIPTION
            " Over current protection."
	    ::= { denviroStatus 27 }

    denviroStatusOverVoltage OBJECT-TYPE
        SYNTAX     INTEGER{
                   on(1),
                   off(2)
        }
	    ACCESS read-only
	    STATUS mandatory
	    DESCRIPTION
            " Over voltage protection."
	    ::= { denviroStatus 28 }

--
-- denviro Delta Bus group
--
    denviroDBNum OBJECT-TYPE
        SYNTAX     INTEGER
        ACCESS     read-only
        STATUS     mandatory
        DESCRIPTION
	        "The number of Delta Bus utilized in this device.
	        This variable indicates the number of rows in the
	        Delta Bus table for EMS1000."
        ::= { denviroDeltaBus 1 }

    denviroDBTable OBJECT-TYPE
        SYNTAX     SEQUENCE OF DenviroDBEntry
        ACCESS     not-accessible
        STATUS     mandatory
        DESCRIPTION
	        "A list of Delta Bus table entries for EMS1000.  The number
	        of entries is given by the value of denviroDBNum."
        ::= { denviroDeltaBus 2 }

    denviroDBEntry OBJECT-TYPE
        SYNTAX     DenviroDBEntry
        ACCESS     not-accessible
        STATUS     mandatory
        DESCRIPTION
	        "An entry containing information applicable to a
	        particular Delta Bus."
        INDEX { denviroDBID }
        ::= { denviroDBTable 1 }

    DenviroDBEntry ::= SEQUENCE {
        denviroDBTitle       DisplayString (SIZE (0..32)),
        denviroDBTemperature INTEGER,
        denviroDBHumidity    INTEGER,
        denviroDBInput1      INTEGER (1..3),
        denviroDBInput2      INTEGER (1..3),
        denviroDBInput3      INTEGER (1..3),
        denviroDBInput4      INTEGER (1..3),
        denviroDBIn1Title    DisplayString (SIZE (0..32)),
        denviroDBIn2Title    DisplayString (SIZE (0..32)),
        denviroDBIn3Title    DisplayString (SIZE (0..32)),
        denviroDBIn4Title    DisplayString (SIZE (0..32)),
        denviroDBStatusComm  INTEGER (1..2),
        denviroDBStatusTemperature  INTEGER (1..3),
        denviroDBStatusHumidity  INTEGER (1..3),
        denviroDBID          INTEGER,
		denviroDBTemperatureWarningThreshold             INTEGER,
		denviroDBTemperatureWarningRecoverThreshold      INTEGER,
		denviroDBTemperatureAlarmThreshold               INTEGER,
		denviroDBTemperatureAlarmRecoverThreshold        INTEGER,
		denviroDBHumidityWarningThreshold                INTEGER,
		denviroDBHumidityWarningRecoverThreshold         INTEGER,
		denviroDBHumidityAlarmThreshold                  INTEGER,
		denviroDBHumidityAlarmRecoverThreshold           INTEGER
    }

    denviroDBTitle OBJECT-TYPE
        SYNTAX     DisplayString (SIZE (0..32))
        ACCESS     read-only
        STATUS     mandatory
        DESCRIPTION
	        "The Delta Bus device title."
        ::= { denviroDBEntry 1 }

    denviroDBTemperature OBJECT-TYPE
        SYNTAX     INTEGER
        --         "0.1 degree C"
        ACCESS     read-only
        STATUS     mandatory
        DESCRIPTION
	        "The present temperature."
        ::= { denviroDBEntry 2 }

    denviroDBHumidity OBJECT-TYPE
        SYNTAX     INTEGER
        --         "%"
        ACCESS     read-only
        STATUS     mandatory
        DESCRIPTION
	        "The present humidity."
        ::= { denviroDBEntry 3 }

    denviroDBInput1 OBJECT-TYPE
         SYNTAX     INTEGER{
                    warning(1),
                    alarm(2),
                    normal(3)
        }
        ACCESS     read-only
        STATUS     mandatory
        DESCRIPTION
            "The status of input contact1."
        ::= { denviroDBEntry 4 }

    denviroDBInput2 OBJECT-TYPE
         SYNTAX     INTEGER{
                    warning(1),
                    alarm(2),
                    normal(3)
        }
        ACCESS     read-only
        STATUS     mandatory
        DESCRIPTION
            "The status of input contact2."
        ::= { denviroDBEntry 5 }

    denviroDBInput3 OBJECT-TYPE
         SYNTAX     INTEGER{
                    warning(1),
                    alarm(2),
                    normal(3)
        }
        ACCESS     read-only
        STATUS     mandatory
        DESCRIPTION
            "The status of input contact3."
        ::= { denviroDBEntry 6 }

    denviroDBInput4 OBJECT-TYPE
         SYNTAX     INTEGER{
                    warning(1),
                    alarm(2),
                    normal(3)
        }
        ACCESS     read-only
        STATUS     mandatory
        DESCRIPTION
            "The status of input contact4."
        ::= { denviroDBEntry 7 }

    denviroDBIn1Title OBJECT-TYPE
        SYNTAX     DisplayString (SIZE (0..32))
        ACCESS     read-only
        STATUS     mandatory
        DESCRIPTION
	        "The input contact1 title."
        ::= { denviroDBEntry 8 }

    denviroDBIn2Title OBJECT-TYPE
        SYNTAX     DisplayString (SIZE (0..32))
        ACCESS     read-only
        STATUS     mandatory
        DESCRIPTION
	        "The input contact2 title."
        ::= { denviroDBEntry 9 }

    denviroDBIn3Title OBJECT-TYPE
        SYNTAX     DisplayString (SIZE (0..32))
        ACCESS     read-only
        STATUS     mandatory
        DESCRIPTION
	        "The input contact3 title."
        ::= { denviroDBEntry 10 }

    denviroDBIn4Title OBJECT-TYPE
        SYNTAX     DisplayString (SIZE (0..32))
        ACCESS     read-only
        STATUS     mandatory
        DESCRIPTION
	        "The input contact4 title."
        ::= { denviroDBEntry 11 }

    denviroDBStatusComm OBJECT-TYPE
        SYNTAX     INTEGER{
                   disconnect(1),
                   connect(2)
        }
	    ACCESS read-only
	    STATUS mandatory
	    DESCRIPTION
		    "The communication status of Delta Bus device."
	    ::= { denviroDBEntry 12 }

    denviroDBStatusTemperature OBJECT-TYPE
         SYNTAX     INTEGER{
                    warning(1),
                    alarm(2),
                    normal(3)
        }
	    ACCESS read-only
	    STATUS mandatory
	    DESCRIPTION
		    "The measured temperature status."
	    ::= { denviroDBEntry 13 }

    denviroDBStatusHumidity OBJECT-TYPE
         SYNTAX     INTEGER{
                    warning(1),
                    alarm(2),
                    normal(3)
        }
	    ACCESS read-only
	    STATUS mandatory
	    DESCRIPTION
		    "The measured humidity status."
	    ::= { denviroDBEntry 14 }

    denviroDBID OBJECT-TYPE
        SYNTAX     INTEGER(0..15)
        ACCESS     read-only
        STATUS     mandatory
        DESCRIPTION
	        "The Delta Bus device ID."
        ::= { denviroDBEntry 15 }

    denviroDBTemperatureWarningThreshold OBJECT-TYPE
	    SYNTAX     INTEGER
        ACCESS     read-write
        STATUS     mandatory
        DESCRIPTION
	        "The warning threshold for temperature."
        ::= { denviroDBEntry 16 }

	denviroDBTemperatureWarningRecoverThreshold OBJECT-TYPE
	    SYNTAX     INTEGER
        ACCESS     read-write
        STATUS     mandatory
        DESCRIPTION
	        "The warning recover threshold for temperature."
        ::= { denviroDBEntry 17 }
    
	denviroDBTemperatureAlarmThreshold OBJECT-TYPE
	    SYNTAX     INTEGER
        ACCESS     read-write
        STATUS     mandatory
        DESCRIPTION
	        "The alarm threshold for temperature."
        ::= { denviroDBEntry 18 }

    denviroDBTemperatureAlarmRecoverThreshold OBJECT-TYPE
	    SYNTAX     INTEGER
        ACCESS     read-write
        STATUS     mandatory
        DESCRIPTION
	        "The alarm recover threshold for temperature."
        ::= { denviroDBEntry 19 }

	denviroDBHumidityWarningThreshold OBJECT-TYPE
	    SYNTAX     INTEGER
        ACCESS     read-write
        STATUS     mandatory
        DESCRIPTION
	        "The warning threshold for humidity."
        ::= { denviroDBEntry 20 }

	denviroDBHumidityWarningRecoverThreshold OBJECT-TYPE
	    SYNTAX     INTEGER
        ACCESS     read-write
        STATUS     mandatory
        DESCRIPTION
	        "The warning recover threshold for humidity."
        ::= { denviroDBEntry 21 }
    
	denviroDBHumidityAlarmThreshold OBJECT-TYPE
	    SYNTAX     INTEGER
        ACCESS     read-write
        STATUS     mandatory
        DESCRIPTION
	        "The alarm threshold for humidity."
        ::= { denviroDBEntry 22 }

    denviroDBHumidityAlarmRecoverThreshold OBJECT-TYPE
	    SYNTAX     INTEGER
        ACCESS     read-write
        STATUS     mandatory
        DESCRIPTION
	        "The alarm recover threshold for humidity."
        ::= { denviroDBEntry 23 }
		
	denviroEMS1100DBNum OBJECT-TYPE
        SYNTAX     INTEGER
        ACCESS     read-only
        STATUS     mandatory
        DESCRIPTION
	        "The number of Delta Bus utilized in this device.
	        This variable indicates the number of rows in the
	        Delta Bus table for EMS1100."
        ::= { denviroDeltaBus 3 }

    denviroEMS1100DBTable OBJECT-TYPE
        SYNTAX     SEQUENCE OF DenviroEMS1100DBEntry
        ACCESS     not-accessible
        STATUS     mandatory
        DESCRIPTION
	        "A list of Delta Bus table entries for EMS1100.  The number
	        of entries is given by the value of denviroEMS1100DBNum."
        ::= { denviroDeltaBus 4 }

    denviroEMS1100DBEntry OBJECT-TYPE
        SYNTAX     DenviroEMS1100DBEntry
        ACCESS     not-accessible
        STATUS     mandatory
        DESCRIPTION
	        "An entry containing information applicable to a
	        particular Delta Bus."
        INDEX { denviroEMS1100DBID }
        ::= { denviroEMS1100DBTable 1 }

    DenviroEMS1100DBEntry ::= SEQUENCE {
        denviroEMS1100DBID          INTEGER(0..15),
        denviroEMS1100DBStatusComm  INTEGER (1..2),
        denviroEMS1100DBTitle       DisplayString (SIZE (0..32)),
        denviroEMS1100DBDO1Title    DisplayString (SIZE (0..32)),
        denviroEMS1100DBDO2Title    DisplayString (SIZE (0..32)),
        denviroEMS1100DBDO3Title    DisplayString (SIZE (0..32)),
        denviroEMS1100DBDO4Title    DisplayString (SIZE (0..32)),
        denviroEMS1100DBDO1Status  INTEGER (1..2),
        denviroEMS1100DBDO2Status  INTEGER (1..2),
        denviroEMS1100DBDO3Status  INTEGER (1..2),
        denviroEMS1100DBDO4Status  INTEGER (1..2),
		denviroEMS1100DBDO1Manual  INTEGER (1..2),
		denviroEMS1100DBDO2Manual  INTEGER (1..2),
		denviroEMS1100DBDO3Manual  INTEGER (1..2),
		denviroEMS1100DBDO4Manual  INTEGER (1..2)
    }

    denviroEMS1100DBID OBJECT-TYPE
        SYNTAX     INTEGER(0..15)
        ACCESS     read-only
        STATUS     mandatory
        DESCRIPTION
	        "The Delta Bus device ID."
        ::= { denviroEMS1100DBEntry 1 }

    denviroEMS1100DBStatusComm OBJECT-TYPE
        SYNTAX     INTEGER{
                   disconnect(1),
                   connect(2)
        }
	    ACCESS read-only
	    STATUS mandatory
	    DESCRIPTION
		    "The communication status of Delta Bus device."
	    ::= { denviroEMS1100DBEntry 2 }

    denviroEMS1100DBTitle OBJECT-TYPE
        SYNTAX     DisplayString (SIZE (0..32))
        ACCESS     read-write
        STATUS     mandatory
        DESCRIPTION
	        "The Delta Bus EMS1100 device title."
        ::= { denviroEMS1100DBEntry 3 }

    denviroEMS1100DBDO1Title OBJECT-TYPE
        SYNTAX     DisplayString (SIZE (0..32))
        ACCESS     read-write
        STATUS     mandatory
        DESCRIPTION
	        "The digital output 1 title."
        ::= { denviroEMS1100DBEntry 4 }        

    denviroEMS1100DBDO2Title OBJECT-TYPE
        SYNTAX     DisplayString (SIZE (0..32))
        ACCESS     read-write
        STATUS     mandatory
        DESCRIPTION
	        "The digital output 2 title."
        ::= { denviroEMS1100DBEntry 5 }  		

    denviroEMS1100DBDO3Title OBJECT-TYPE
        SYNTAX     DisplayString (SIZE (0..32))
        ACCESS     read-write
        STATUS     mandatory
        DESCRIPTION
	        "The digital output 3 title."
        ::= { denviroEMS1100DBEntry 6 }

    denviroEMS1100DBDO4Title OBJECT-TYPE
        SYNTAX     DisplayString (SIZE (0..32))
        ACCESS     read-write
        STATUS     mandatory
        DESCRIPTION
	        "The digital output 4 title."
        ::= { denviroEMS1100DBEntry 7 }

    denviroEMS1100DBDO1Status OBJECT-TYPE
         SYNTAX     INTEGER{
                    alarm(1),
                    normal(2)
        }
	    ACCESS read-write
	    STATUS mandatory
	    DESCRIPTION
		    "The digital output 1 status."
	    ::= { denviroEMS1100DBEntry 8 }

    denviroEMS1100DBDO2Status OBJECT-TYPE
         SYNTAX     INTEGER{
                    alarm(1),
                    normal(2)
        }
	    ACCESS read-write
	    STATUS mandatory
	    DESCRIPTION
		    "The digital output 2 status."
	    ::= { denviroEMS1100DBEntry 9 }

    denviroEMS1100DBDO3Status OBJECT-TYPE
         SYNTAX     INTEGER{
                    alarm(1),
                    normal(2)
        }
	    ACCESS read-write
	    STATUS mandatory
	    DESCRIPTION
		    "The digital output 3 status."
	    ::= { denviroEMS1100DBEntry 10 }

    denviroEMS1100DBDO4Status OBJECT-TYPE
         SYNTAX     INTEGER{
                    alarm(1),
                    normal(2)
        }
	    ACCESS read-write
	    STATUS mandatory
	    DESCRIPTION
		    "The digital output 4 status."
	    ::= { denviroEMS1100DBEntry 11 }

    denviroEMS1100DBDO1Manual OBJECT-TYPE
         SYNTAX     INTEGER{
                    automatic(1),
                    manual(2)
        }
	    ACCESS read-write
	    STATUS mandatory
	    DESCRIPTION
		    "Confgure the control of DO 1 to automatically or manually."
	    ::= { denviroEMS1100DBEntry 12 }

    denviroEMS1100DBDO2Manual OBJECT-TYPE
         SYNTAX     INTEGER{
                    automatic(1),
                    manual(2)
        }
	    ACCESS read-write
	    STATUS mandatory
	    DESCRIPTION
		    "Confgure the control of DO 2 to automatically or manually."
	    ::= { denviroEMS1100DBEntry 13 }        
    
	denviroEMS1100DBDO3Manual OBJECT-TYPE
         SYNTAX     INTEGER{
                    automatic(1),
                    manual(2)
        }
	    ACCESS read-write
	    STATUS mandatory
	    DESCRIPTION
		    "Confgure the control of DO 3 to automatically or manually."
	    ::= { denviroEMS1100DBEntry 14 }

	denviroEMS1100DBDO4Manual OBJECT-TYPE
         SYNTAX     INTEGER{
                    automatic(1),
                    manual(2)
        }
	    ACCESS read-write
	    STATUS mandatory
	    DESCRIPTION
		    "Confgure the control of DO 4 to automatically or manually."
	    ::= { denviroEMS1100DBEntry 15 }
		
	denviroEMS1200DBNum OBJECT-TYPE
        SYNTAX     INTEGER
        ACCESS     read-only
        STATUS     mandatory
        DESCRIPTION
	        "The number of Delta Bus utilized in this device.
	        This variable indicates the number of rows in the
	        Delta Bus table for EMS1200."
        ::= { denviroDeltaBus 5 }

	denviroEMS1200DBTable OBJECT-TYPE
        SYNTAX     SEQUENCE OF DenviroEMS1200DBEntry
        ACCESS     not-accessible
        STATUS     mandatory
        DESCRIPTION
	        "A list of Delta Bus table entries for EMS1200.  The number
	        of entries is given by the value of denviroEMS1200DBNum."
        ::= { denviroDeltaBus 6 }

    denviroEMS1200DBEntry OBJECT-TYPE
        SYNTAX     DenviroEMS1200DBEntry
        ACCESS     not-accessible
        STATUS     mandatory
        DESCRIPTION
	        "An entry containing information applicable to a
	        particular Delta Bus."
        INDEX { denviroEMS1200DBID }
        ::= { denviroEMS1200DBTable 1 }

    DenviroEMS1200DBEntry ::= SEQUENCE {
        denviroEMS1200DBID          INTEGER(0..15),
        denviroEMS1200DBStatusComm  INTEGER (1..2),
        denviroEMS1200DBTitle       DisplayString (SIZE (0..32)),
        denviroEMS1200DBAI1Title    DisplayString (SIZE (0..32)),
        denviroEMS1200DBAI2Title    DisplayString (SIZE (0..32)),
        denviroEMS1200DBLeakageTitle    DisplayString (SIZE (0..32)),
        denviroEMS1200DBAOTitle     DisplayString (SIZE (0..32)),
        denviroEMS1200DBAI1Value  INTEGER,
        denviroEMS1200DBAI2Value  INTEGER,
        denviroEMS1200DBAI1Status  INTEGER (1..3),
        denviroEMS1200DBAI2Status  INTEGER (1..3),
        denviroEMS1200DBLeakageLevel  INTEGER (1..3),
        denviroEMS1200DBLeakageBuzzer  INTEGER (1..2),
        denviroEMS1200DBLeakageStatus  INTEGER (1..3),
        denviroEMS1200DBAOControl   INTEGER (1..4095),
        denviroEMS1200DBAOStatus   INTEGER (1..2),
		denviroEMS1200DBAOManual   INTEGER (1..2)
    }

    denviroEMS1200DBID OBJECT-TYPE
        SYNTAX     INTEGER(0..15)
        ACCESS     read-only
        STATUS     mandatory
        DESCRIPTION
	        "The Delta Bus device ID."
        ::= { denviroEMS1200DBEntry 1 }
        
    denviroEMS1200DBStatusComm OBJECT-TYPE
        SYNTAX     INTEGER{
                   disconnect(1),
                   connect(2)
        }
	    ACCESS read-only
	    STATUS mandatory
	    DESCRIPTION
		    "The communication status of Delta Bus device."
	    ::= { denviroEMS1200DBEntry 2 }

    denviroEMS1200DBTitle OBJECT-TYPE
        SYNTAX     DisplayString (SIZE (0..32))
        ACCESS     read-write
        STATUS     mandatory
        DESCRIPTION
	        "The Delta Bus EMS1200 device title."
        ::= { denviroEMS1200DBEntry 3 }

    denviroEMS1200DBAI1Title OBJECT-TYPE
        SYNTAX     DisplayString (SIZE (0..32))
        ACCESS     read-write
        STATUS     mandatory
        DESCRIPTION
	        "The analog input 1 title."
        ::= { denviroEMS1200DBEntry 4 }        

    denviroEMS1200DBAI2Title OBJECT-TYPE
        SYNTAX     DisplayString (SIZE (0..32))
        ACCESS     read-write
        STATUS     mandatory
        DESCRIPTION
	        "The analog input 2 title."
        ::= { denviroEMS1200DBEntry 5 }           

    denviroEMS1200DBLeakageTitle OBJECT-TYPE
        SYNTAX     DisplayString (SIZE (0..32))
        ACCESS     read-write
        STATUS     mandatory
        DESCRIPTION
	        "The leakage title."
        ::= { denviroEMS1200DBEntry 6 }   

    denviroEMS1200DBAOTitle OBJECT-TYPE
        SYNTAX     DisplayString (SIZE (0..32))
        ACCESS     read-write
        STATUS     mandatory
        DESCRIPTION
	        "The analog output title."
        ::= { denviroEMS1200DBEntry 7 }   

    denviroEMS1200DBAI1Value OBJECT-TYPE
        SYNTAX     INTEGER
        ACCESS     read-only
        STATUS     mandatory
        DESCRIPTION
	        "The value of analog iutput 1."
        ::= { denviroEMS1200DBEntry 8 }  

    denviroEMS1200DBAI2Value OBJECT-TYPE
        SYNTAX     INTEGER
        ACCESS     read-only
        STATUS     mandatory
        DESCRIPTION
	        "The value of analog iutput 2."
        ::= { denviroEMS1200DBEntry 9 } 

    denviroEMS1200DBAI1Status OBJECT-TYPE
        SYNTAX     INTEGER{
                    warning(1),
                    alarm(2),
                    normal(3)
        }
	    ACCESS read-only
	    STATUS mandatory
	    DESCRIPTION
		    "The analog input 1 status."
	    ::= { denviroEMS1200DBEntry 10 }
        
    denviroEMS1200DBAI2Status OBJECT-TYPE
        SYNTAX     INTEGER{
                    warning(1),
                    alarm(2),
                    normal(3)
        }
	    ACCESS read-only
	    STATUS mandatory
	    DESCRIPTION
		    "The analog input 2 status."
	    ::= { denviroEMS1200DBEntry 11 }


	denviroEMS1200DBLeakageLevel OBJECT-TYPE
        SYNTAX     INTEGER{
                    low(1),
                    middle(2),
                    high(3)
        }
	    ACCESS read-write
	    STATUS mandatory
	    DESCRIPTION
		    "The sensitivity of leakage."
	    ::= { denviroEMS1200DBEntry 12 }

	denviroEMS1200DBLeakageBuzzer OBJECT-TYPE
        SYNTAX     INTEGER{
                    on(1),
                    off(2)
        }
	    ACCESS read-write
	    STATUS mandatory
	    DESCRIPTION
		    "The buzzer control for leakage."
	    ::= { denviroEMS1200DBEntry 13 }

	denviroEMS1200DBLeakageStatus OBJECT-TYPE
        SYNTAX     INTEGER{
                    warning(1),
                    alarm(2),
                    normal(3)
        }
	    ACCESS read-only
	    STATUS mandatory
	    DESCRIPTION
		    "The leakage status."
	    ::= { denviroEMS1200DBEntry 14 }

	denviroEMS1200DBAOControl OBJECT-TYPE
        SYNTAX INTEGER
	    ACCESS read-write
	    STATUS mandatory
	    DESCRIPTION
		    "The analog output control (0~4095)."
	    ::= { denviroEMS1200DBEntry 15 }

	denviroEMS1200DBAOStatus OBJECT-TYPE
         SYNTAX     INTEGER{
                    alarm(1),
                    normal(2)
        }
	    ACCESS read-only
	    STATUS mandatory
	    DESCRIPTION
		    "The analog output status."
	    ::= { denviroEMS1200DBEntry 16 }
		
	denviroEMS1200DBAOManual OBJECT-TYPE
         SYNTAX     INTEGER{
                    automatic(1),
                    manual(2)
        }
	    ACCESS read-write
	    STATUS mandatory
	    DESCRIPTION
		    "Confgure the control of AO to automatically or manually."
	    ::= { denviroEMS1200DBEntry 17 }
        
--
-- denviro RS485 group
--
    denviroNum485 OBJECT-TYPE
        SYNTAX     INTEGER
        ACCESS     read-only
        STATUS     mandatory
        DESCRIPTION
	        "The device number of RS485-1 and RS485-2 utilized in this device.
	        This variable indicates the number of rows in the RS485 table."
        ::= { denviroRS485 1 }

    denviro485Table OBJECT-TYPE
        SYNTAX     SEQUENCE OF Denviro485Entry
        ACCESS     not-accessible
        STATUS     mandatory
        DESCRIPTION
	        "A list of RS485 table entries.  The number of entries
	        is given by the value of denviroNum485."
        ::= { denviroRS485 2 }

    denviro485Entry OBJECT-TYPE
        SYNTAX     Denviro485Entry
        ACCESS     not-accessible
        STATUS     mandatory
        DESCRIPTION
	        "An entry containing information applicable to a
	        particular RS485 device."
        INDEX { denviro485Port, denviroID485}
        ::= { denviro485Table 1 }

    Denviro485Entry ::= SEQUENCE {
        denviroTitle485       DisplayString (SIZE (0..32)),
        denviroCommLost       INTEGER,
        denviro485Port        INTEGER,
        denviroID485          INTEGER
    }

    denviroTitle485 OBJECT-TYPE
        SYNTAX     DisplayString (SIZE (0..32))
        ACCESS     read-only
        STATUS     mandatory
        DESCRIPTION
	        "The RS485 device title."
        ::= { denviro485Entry 1 }

    denviroCommLost OBJECT-TYPE
        SYNTAX     INTEGER{
                   abnormal(1),
                   normal(2)
        }
	    ACCESS read-only
	    STATUS mandatory
	    DESCRIPTION
		" Indicate the device communication status."
        ::= { denviro485Entry 2 }

    denviro485Port OBJECT-TYPE
        SYNTAX     INTEGER {
                   rs485-1(1),
                   rs485-2(2)
        }
        ACCESS     read-only
        STATUS     mandatory
        DESCRIPTION
	        "Indicate which RS485 port to connect to the device."
        ::= { denviro485Entry 3 }

    denviroID485 OBJECT-TYPE
        SYNTAX     INTEGER (0..255)
        ACCESS     read-only
        STATUS     mandatory
        DESCRIPTION
	        "The ID number for the device."
        ::= { denviro485Entry 4 }

    denviroValueTable OBJECT-TYPE
        SYNTAX     SEQUENCE OF DenviroValueEntry
        ACCESS     not-accessible
        STATUS     mandatory
        DESCRIPTION
	        "A value table of RS485 entries. Each device ID has 32
	        entries, the number of entries is 32 multiply denviroNum485."
        ::= { denviroRS485 3 }

    denviroValueEntry OBJECT-TYPE
        SYNTAX     DenviroValueEntry
        ACCESS     not-accessible
        STATUS     mandatory
        DESCRIPTION
	        "An entry containing information applicable to a
	        particular RS485."
        INDEX { denviroValue485Port, denviroValueID485, denviroValueIndex }
        ::= { denviroValueTable 1 }

    DenviroValueEntry ::= SEQUENCE {
        denviroValueTitle      DisplayString (SIZE (0..32)),
        denviroValueValue      INTEGER,
        denviroValueScaleExp   INTEGER,
        denviroValueUnitString DisplayString (SIZE (0..8)),
        denviroValue485Port    INTEGER,
        denviroValueID485      INTEGER,
        denviroValueIndex      INTEGER (1..32)
    }

    denviroValueTitle OBJECT-TYPE
        SYNTAX     DisplayString (SIZE (0..32))
        ACCESS     read-only
        STATUS     mandatory
        DESCRIPTION
	        "The RS485 device value title."
        ::= { denviroValueEntry 1 }

    denviroValueValue OBJECT-TYPE
        SYNTAX     INTEGER
        ACCESS     read-only
        STATUS     mandatory
        DESCRIPTION
	        "The RS485 device value."
        ::= { denviroValueEntry 2 }

    denviroValueScaleExp OBJECT-TYPE
        SYNTAX     INTEGER
        ACCESS     read-only
        STATUS     mandatory
        DESCRIPTION
	        "The exponent of scale. If the type of value is float, this field is always -2"
        ::= { denviroValueEntry 3 }

    denviroValueUnitString OBJECT-TYPE
        SYNTAX     DisplayString (SIZE (0..8))
        ACCESS     read-only
        STATUS     mandatory
        DESCRIPTION
	        "The RS485 device value unit string."
        ::= { denviroValueEntry 4 }

    denviroValue485Port OBJECT-TYPE
        SYNTAX     INTEGER {
                   rs485-1(1),
                   rs485-2(2)
        }
        ACCESS     read-only
        STATUS     mandatory
        DESCRIPTION
	        "The RS485 port."
        ::= { denviroValueEntry 5 }

    denviroValueID485 OBJECT-TYPE
        SYNTAX     INTEGER (0..255)
        ACCESS     read-only
        STATUS     mandatory
        DESCRIPTION
	        "The RS485 device ID. This value is same as denviroID485."
        ::= { denviroValueEntry 6 }

    denviroValueIndex OBJECT-TYPE
        SYNTAX      INTEGER (1..32)
        ACCESS      not-accessible
        STATUS      mandatory
        DESCRIPTION
	        "The RS485 value index for this device."
        ::= { denviroValueEntry 7 }

    denviroStatusTable OBJECT-TYPE
        SYNTAX     SEQUENCE OF DenviroStatusEntry
        ACCESS     not-accessible
        STATUS     mandatory
        DESCRIPTION
	        "A status table of RS485 entries. Each device ID has 32
	        entries."
        ::= { denviroRS485 4 }

    denviroStatusEntry OBJECT-TYPE
        SYNTAX     DenviroStatusEntry
        ACCESS     not-accessible
        STATUS     mandatory
        DESCRIPTION
	        "An entry containing information applicable to a
	        particular RS485."
        INDEX { denviroStatus485Port, denviroStatusID485, denviroStatusIndex }
        ::= { denviroStatusTable 1 }

    DenviroStatusEntry ::= SEQUENCE {
        denviroStatusTitle    DisplayString (SIZE (0..32)),
        denviroStatusValue    INTEGER (1..3),
        denviroStatus485Port  INTEGER,
        denviroStatusID485    INTEGER,
        denviroStatusIndex    INTEGER (1..32)
    }

    denviroStatusTitle OBJECT-TYPE
        SYNTAX     DisplayString (SIZE (0..32))
        ACCESS     read-only
        STATUS     mandatory
        DESCRIPTION
	        "The RS485 device status title."
        ::= { denviroStatusEntry 1 }

    denviroStatusValue OBJECT-TYPE
         SYNTAX     INTEGER{
                    warning(1),
                    alarm(2),
                    normal(3)
        }
        ACCESS     read-only
        STATUS     mandatory
        DESCRIPTION
	        "The RS485 device status value."
        ::= { denviroStatusEntry 2 }

    denviroStatus485Port OBJECT-TYPE
        SYNTAX     INTEGER {
                   rs485-1(1),
                   rs485-2(2)
        }
        ACCESS     read-only
        STATUS     mandatory
        DESCRIPTION
	        "The RS485 port."
        ::= { denviroStatusEntry 3 }

    denviroStatusID485 OBJECT-TYPE
        SYNTAX     INTEGER (0..255)
        ACCESS     read-only
        STATUS     mandatory
        DESCRIPTION
	        "The RS485 device ID. This value is same as denviroID485"
        ::= { denviroStatusEntry 4 }

    denviroStatusIndex OBJECT-TYPE
        SYNTAX      INTEGER (1..32)
        ACCESS      not-accessible
        STATUS      mandatory
        DESCRIPTION
	        "The RS485 status index for this device."
        ::= { denviroStatusEntry 5 }
		
    denviroWritableValueTable OBJECT-TYPE
        SYNTAX     SEQUENCE OF DenviroWritableValueEntry
        ACCESS     not-accessible
        STATUS     mandatory
        DESCRIPTION
	        "A writable value table of RS485 entries. Each device ID has 16
	        entries."
        ::= { denviroRS485 5 }

	denviroWritableValueEntry OBJECT-TYPE
        SYNTAX     DenviroWritableValueEntry
        ACCESS     not-accessible
        STATUS     mandatory
        DESCRIPTION
	        "An entry containing information applicable to a
	        particular RS485."
        INDEX { denviroWritableValue485Port, denviroWritableValueID485, denviroWritableValueIndex }
        ::= { denviroWritableValueTable 1 }
		
    DenviroWritableValueEntry ::= SEQUENCE {
        denviroWritableValueTitle    DisplayString (SIZE (0..32)),
        denviroWritableValueValue    INTEGER,
        denviroWritableValue485Port  INTEGER,
        denviroWritableValueID485    INTEGER,
        denviroWritableValueIndex    INTEGER (1..16)
    }
	
	denviroWritableValueTitle OBJECT-TYPE
        SYNTAX     DisplayString (SIZE (0..32))
        ACCESS     read-only
        STATUS     mandatory
        DESCRIPTION
	        "The RS485 device writable value title."
        ::= { denviroWritableValueEntry 1 }
		
    denviroWritableValueValue OBJECT-TYPE
        SYNTAX     INTEGER
        ACCESS     read-write
        STATUS     mandatory
        DESCRIPTION
	        "The RS485 device writable value."
        ::= { denviroWritableValueEntry 2 }

    denviroWritableValue485Port OBJECT-TYPE
        SYNTAX     INTEGER {
                   rs485-1(1),
                   rs485-2(2)
        }
        ACCESS     read-only
        STATUS     mandatory
        DESCRIPTION
	        "The RS485 port."
        ::= { denviroWritableValueEntry 3 }

    denviroWritableValueID485 OBJECT-TYPE
        SYNTAX     INTEGER (0..255)
        ACCESS     read-only
        STATUS     mandatory
        DESCRIPTION
	        "The RS485 device ID. This value is same as denviroID485"
        ::= { denviroWritableValueEntry 4 }

    denviroWritableValueIndex OBJECT-TYPE
        SYNTAX      INTEGER (1..16)
        ACCESS      not-accessible
        STATUS      mandatory
        DESCRIPTION
	        "The RS485 status index for this device."
        ::= { denviroWritableValueEntry 5 }

--
-- denviro Control group
--
    denviroCtrlHub1PwrManual OBJECT-TYPE
    SYNTAX     INTEGER{
               automatic(1),
               manual(2)
    }
	ACCESS read-write
	STATUS mandatory
	DESCRIPTION
		" Confgure the power control of Sensor Hub 1 to 
		automatically or manually."
	::= { denviroControl 1 }

    denviroCtrlHub2PwrManual OBJECT-TYPE
    SYNTAX     INTEGER{
               automatic(1),
               manual(2)
    }
	ACCESS read-write
	STATUS mandatory
	DESCRIPTION
		" Confgure the power control of Sensor Hub 2 to 
		automatically or manually."
	::= { denviroControl 2 }

    denviroCtrlHub1Pwr OBJECT-TYPE
    SYNTAX     INTEGER{
               on(1),
               off(2)
    }
	ACCESS read-write
	STATUS mandatory
	DESCRIPTION
		"Switch the power of Sensor Hub 1. You have to 
		configure the value of denviroCtrlHub1PwrManual to
		manual(2) before you control the Hub1."
	::= { denviroControl 3 }

    denviroCtrlHub2Pwr OBJECT-TYPE
    SYNTAX     INTEGER{
               on(1),
               off(2)
    }
	ACCESS read-write
	STATUS mandatory
	DESCRIPTION
		"Switch the power of Sensor Hub 2. You have to 
		configure the value of denviroCtrlHub2PwrManual to
		manual(2) before you control the Hub2."
	::= { denviroControl 4 }

    denviroCtrlDO1Manual OBJECT-TYPE
    SYNTAX     INTEGER{
               automatic(1),
               manual(2)
    }
	ACCESS read-write
	STATUS mandatory
	DESCRIPTION
		" Confgure the control of DO 1 to automatically or manually."
	::= { denviroControl 5 }

    denviroCtrlDO2Manual OBJECT-TYPE
    SYNTAX     INTEGER{
               automatic(1),
               manual(2)
    }
	ACCESS read-write
	STATUS mandatory
	DESCRIPTION
		" Confgure the control of DO 2 to automatically or manually."
	::= { denviroControl 6 }

    denviroCtrlDO1 OBJECT-TYPE
    SYNTAX     INTEGER{
               normal(1),
               alarm(2)
    }
	ACCESS read-write
	STATUS mandatory
	DESCRIPTION
		"Switch the output relay 1. You have to configure
		the value of denviroCtrlDO1Manual to manual(2) 
		before you control the Hub7."
	::= { denviroControl 7 }

    denviroCtrlDO2 OBJECT-TYPE
    SYNTAX     INTEGER{
               normal(1),
               alarm(2)
    }
	ACCESS read-write
	STATUS mandatory
	DESCRIPTION
		"Switch the output relay 2. You have to configure 
		the value of denviroCtrlDO2Manual to manual(2) 
		before you control the Hub7."
	::= { denviroControl 8 }

	
	
--
-- denviro PDU group
--
    denviroPDUEnable OBJECT-TYPE
    SYNTAX     INTEGER{
               on(1),
               off(2)
    }
	ACCESS read-write
	STATUS mandatory
	DESCRIPTION
		" Confgure PDU function enable or disable."
	::= { denviroPDU 1 }


--
-- denviro Reaction group
--	
	denviroReactionTable OBJECT-TYPE
        SYNTAX     SEQUENCE OF DenviroReactionEntry
        ACCESS     not-accessible
        STATUS     mandatory
        DESCRIPTION
	        "A list of reaction rules."
        ::= { denviroReaction 1 }

    denviroReactionEntry OBJECT-TYPE
        SYNTAX     DenviroReactionEntry
        ACCESS     not-accessible
        STATUS     mandatory
        DESCRIPTION
	        "An entry containing information applicable to a
	        particular reaction rule."
        INDEX { denviroReactionRuleName }
        ::= { denviroReactionTable 1 }

    DenviroReactionEntry ::= SEQUENCE {
        denviroReactionRuleName	DisplayString (SIZE (0..32)),
        denviroReactionEnable   INTEGER(1..2)
    }

    denviroReactionRuleName OBJECT-TYPE
        SYNTAX     DisplayString (SIZE (0..32))
        ACCESS     read-only
        STATUS     mandatory
        DESCRIPTION
	        "The name of reaction rule."
        ::= { denviroReactionEntry 1 }
		
	denviroReactionEnable OBJECT-TYPE
		SYNTAX     INTEGER{
					enable(1),
					disable(2)
		}
		ACCESS		read-only
		STATUS 		mandatory
		DESCRIPTION
			"Enable/Disable of reaction rule."
		::= { denviroReactionEntry 2 }

--
-- denviro Trap group
--

   denviroCommunicationLost TRAP-TYPE
       ENTERPRISE denviroTraps
       DESCRIPTION
    "Communication with the enviroStation sensor failed."
       ::= 1

   denviroCommunicationEstablished TRAP-TYPE
       ENTERPRISE denviroTraps
       DESCRIPTION
	"Communication with the enviroStation sensor reestablished."
       ::= 2

   denviroSensorHub1Alarm TRAP-TYPE
       ENTERPRISE denviroTraps
       VARIABLES { denviroIdentSensorHub1Title }
       DESCRIPTION
	"The environment Sensor Hub 1 is not in normal state."
       ::= 3

   denviroSensorHub1Normal TRAP-TYPE
       ENTERPRISE denviroTraps
       VARIABLES { denviroIdentSensorHub1Title }
       DESCRIPTION
	"The environment Sensor Hub 1 is in normal state."
       ::= 4

   denviroSensorHub2Alarm TRAP-TYPE
       ENTERPRISE denviroTraps
       VARIABLES { denviroIdentSensorHub2Title }
       DESCRIPTION
	"The environment Sensor Hub 2 is not in normal state."
       ::= 5

   denviroSensorHub2Normal TRAP-TYPE
       ENTERPRISE denviroTraps
       VARIABLES { denviroIdentSensorHub2Title }
       DESCRIPTION
	"The environment Sensor Hub 2 is in normal state."
       ::= 6

   denviroSensorHub3Alarm TRAP-TYPE
       ENTERPRISE denviroTraps
       VARIABLES { denviroIdentSensorHub3Title }
       DESCRIPTION
	"The environment Sensor Hub 3 is not in normal state."
       ::= 7

   denviroSensorHub3Normal TRAP-TYPE
       ENTERPRISE denviroTraps
       VARIABLES { denviroIdentSensorHub3Title }
       DESCRIPTION
	"The environment Sensor Hub 3 is in normal state."
       ::= 8

   denviroSensorHub4Alarm TRAP-TYPE
       ENTERPRISE denviroTraps
       VARIABLES { denviroIdentSensorHub4Title }
       DESCRIPTION
	"The environment Sensor Hub 4 is not in normal state."
       ::= 9

   denviroSensorHub4Normal TRAP-TYPE
       ENTERPRISE denviroTraps
       VARIABLES { denviroIdentSensorHub4Title }
       DESCRIPTION
	"he environment Sensor Hub 4 is in normal state."
       ::= 10

   denviroSensorHub5Alarm TRAP-TYPE
       ENTERPRISE denviroTraps
       VARIABLES { denviroIdentSensorHub5Title }
       DESCRIPTION
	"The environment Sensor Hub 5 is not in normal state."
       ::= 11

   denviroSensorHub5Normal TRAP-TYPE
       ENTERPRISE denviroTraps
       VARIABLES { denviroIdentSensorHub5Title }
       DESCRIPTION
	"The environment Sensor Hub 5 is in normal state."
       ::= 12

   denviroSensorHub6Alarm TRAP-TYPE
       ENTERPRISE denviroTraps
       VARIABLES { denviroIdentSensorHub6Title }
       DESCRIPTION
	"The environment Sensor Hub 6 is not in normal state."
       ::= 13

   denviroSensorHub6Normal TRAP-TYPE
       ENTERPRISE denviroTraps
       VARIABLES { denviroIdentSensorHub6Title }
       DESCRIPTION
	"The environment Sensor Hub 6 is in normal state."
       ::= 14

   denviroSensorHub7Alarm TRAP-TYPE
       ENTERPRISE denviroTraps
       VARIABLES { denviroIdentSensorHub7Title }
       DESCRIPTION
	"The environment Sensor Hub 7 is not in normal state."
       ::= 15

   denviroSensorHub7Normal TRAP-TYPE
       ENTERPRISE denviroTraps
       VARIABLES { denviroIdentSensorHub7Title }
       DESCRIPTION
	"The environment Sensor Hub 7 is in normal state."
       ::= 16

   denviroSensorHub8Alarm TRAP-TYPE
       ENTERPRISE denviroTraps
       VARIABLES { denviroIdentSensorHub8Title }
       DESCRIPTION
	"The environment Sensor Hub 8 is not in normal state."
       ::= 17

   denviroSensorHub8Normal TRAP-TYPE
       ENTERPRISE denviroTraps
       VARIABLES { denviroIdentSensorHub8Title }
       DESCRIPTION
	"The environment Sensor Hub 8 is in normal state."
       ::= 18

   denviroAI1Alarm TRAP-TYPE
       ENTERPRISE denviroTraps
       VARIABLES { denviroIdentAI1Title }
       DESCRIPTION
	"The environment AI1 is not in normal state."
       ::= 19

   denviroAI1Normal TRAP-TYPE
       ENTERPRISE denviroTraps
       VARIABLES { denviroIdentAI1Title }
       DESCRIPTION
	"The environment AI1 is in normal state."
       ::= 20

   denviroAI2Alarm TRAP-TYPE
       ENTERPRISE denviroTraps
       VARIABLES { denviroIdentAI2Title }
       DESCRIPTION
	"The environment AI2 is not in normal state."
       ::= 21

   denviroAI2Normal TRAP-TYPE
       ENTERPRISE denviroTraps
       VARIABLES { denviroIdentAI2Title }
       DESCRIPTION
	"The environment AI2 is in normal state."
       ::= 22

   denviroAI3Alarm TRAP-TYPE
       ENTERPRISE denviroTraps
       VARIABLES { denviroIdentAI3Title }
       DESCRIPTION
	"The environment AI3 is not in normal state."
       ::= 23

   denviroAI3Normal TRAP-TYPE
       ENTERPRISE denviroTraps
       VARIABLES { denviroIdentAI3Title }
       DESCRIPTION
	"The environment AI3 is in normal state."
       ::= 24

   denviroAI4Alarm TRAP-TYPE
       ENTERPRISE denviroTraps
       VARIABLES { denviroIdentAI4Title }
       DESCRIPTION
	"The environment AI4 is not in normal state."
       ::= 25

   denviroAI4Normal TRAP-TYPE
       ENTERPRISE denviroTraps
       VARIABLES { denviroIdentAI4Title }
       DESCRIPTION
	"The environment AI4 is in normal state."
       ::= 26

   denviroDI1Alarm TRAP-TYPE
       ENTERPRISE denviroTraps
       VARIABLES { denviroIdentDI1Title }
       DESCRIPTION
	"The environment DI1 is not in normal state."
       ::= 27

   denviroDI1Normal TRAP-TYPE
       ENTERPRISE denviroTraps
       VARIABLES { denviroIdentDI1Title }
       DESCRIPTION
	"The environment DI1 is in normal state."
       ::= 28
       
   denviroDI2Alarm TRAP-TYPE
       ENTERPRISE denviroTraps
       VARIABLES { denviroIdentDI2Title }
       DESCRIPTION
	"The environment DI2 is not in normal state."
       ::= 29

   denviroDI2Normal TRAP-TYPE
       ENTERPRISE denviroTraps
       VARIABLES { denviroIdentDI2Title }
       DESCRIPTION
	"The environment DI2 is in normal state."
       ::= 30

   denviroDI3Alarm TRAP-TYPE
       ENTERPRISE denviroTraps
       VARIABLES { denviroIdentDI3Title }
       DESCRIPTION
	"The environment DI3 is not in normal state."
       ::= 31

   denviroDI3Normal TRAP-TYPE
       ENTERPRISE denviroTraps
       VARIABLES { denviroIdentDI3Title }
       DESCRIPTION
	"The environment DI3 is in normal state."
       ::= 32

   denviroDI4Alarm TRAP-TYPE
       ENTERPRISE denviroTraps
       VARIABLES { denviroIdentDI4Title }
       DESCRIPTION
	"The environment DI4 is not in normal state."
       ::= 33

   denviroDI4Normal TRAP-TYPE
       ENTERPRISE denviroTraps
       VARIABLES { denviroIdentDI4Title }
       DESCRIPTION
	"The environment DI4 is in normal state."
       ::= 34

   denviroDBCommunicationLost TRAP-TYPE
       ENTERPRISE denviroTraps
       VARIABLES { denviroDBID, denviroDBTitle }
       DESCRIPTION
	"Communication with the Delta BUS device failed."
       ::= 35

   denviroDBCommunicationEstablished TRAP-TYPE
       ENTERPRISE denviroTraps
       VARIABLES { denviroDBID, denviroDBTitle }
       DESCRIPTION
	"Communication with the Delta Bus device reestablished."
       ::= 36

   denviroDBTempWarn TRAP-TYPE
       ENTERPRISE denviroTraps
       VARIABLES { denviroDBID, denviroDBTitle, denviroDBTemperature }
       DESCRIPTION
	"The temperature of Delta Bus is over warning threshold."
       ::= 37

   denviroDBTempWarnRecover TRAP-TYPE
       ENTERPRISE denviroTraps
       VARIABLES { denviroDBID, denviroDBTitle, denviroDBTemperature }
       DESCRIPTION
	"The temperature of Delta Bus is back to normal."
       ::= 38

   denviroDBTempAlarm TRAP-TYPE
       ENTERPRISE denviroTraps
       VARIABLES { denviroDBID, denviroDBTitle, denviroDBTemperature }
       DESCRIPTION
	"The temperature of Delta Bus is over alarm threshold."
       ::= 39

   denviroDBTempAlarmRecover TRAP-TYPE
       ENTERPRISE denviroTraps
       VARIABLES { denviroDBID, denviroDBTitle, denviroDBTemperature }
       DESCRIPTION
	"The temperature of Delta Bus is back to normal."
       ::= 40

   denviroDBHumidityWarn TRAP-TYPE
       ENTERPRISE denviroTraps
       VARIABLES { denviroDBID, denviroDBTitle, denviroDBHumidity }
       DESCRIPTION
	"The humidity of Delta Bus is over warning threshold."
       ::= 41

   denviroDBHumidityWarnRecover TRAP-TYPE
       ENTERPRISE denviroTraps
       VARIABLES { denviroDBID, denviroDBTitle, denviroDBHumidity }
       DESCRIPTION
	"The humidity of Delta Bus is back to normal."
       ::= 42

   denviroDBHumidityAlarm TRAP-TYPE
       ENTERPRISE denviroTraps
       VARIABLES { denviroDBID, denviroDBTitle, denviroDBHumidity }
       DESCRIPTION
	"The humidity of Delta Bus is over alarm threshold."
       ::= 43

   denviroDBHumidityAlarmRecover TRAP-TYPE
       ENTERPRISE denviroTraps
       VARIABLES { denviroDBID, denviroDBTitle, denviroDBHumidity }
       DESCRIPTION
	"The humidity of Delta Bus is back to normal."
       ::= 44

   denviroDBInput1Alarm TRAP-TYPE
       ENTERPRISE denviroTraps
       VARIABLES { denviroDBID, denviroDBTitle, denviroDBIn1Title }
       DESCRIPTION
	"The input1 of Delta Bus is not in normal state."
       ::= 45

   denviroDBInput1AlarmRecover TRAP-TYPE
       ENTERPRISE denviroTraps
       VARIABLES { denviroDBID, denviroDBTitle, denviroDBIn1Title }
       DESCRIPTION
	"The input1 of Delta Bus is in normal state."
       ::= 46

   denviroDBInput2Alarm TRAP-TYPE
       ENTERPRISE denviroTraps
       VARIABLES { denviroDBID, denviroDBTitle, denviroDBIn2Title }
       DESCRIPTION
	"The input2 of Delta Bus is not in normal state."
       ::= 47

   denviroDBInput2AlarmRecover TRAP-TYPE
       ENTERPRISE denviroTraps
       VARIABLES { denviroDBID, denviroDBTitle, denviroDBIn2Title }
       DESCRIPTION
	"The input2 of Delta Bus is in normal state."
       ::= 48

   denviroDBInput3Alarm TRAP-TYPE
       ENTERPRISE denviroTraps
       VARIABLES { denviroDBID, denviroDBTitle, denviroDBIn3Title }
       DESCRIPTION
	"The input3 of Delta Bus is not in normal state."
       ::= 49

   denviroDBInput3AlarmRecover TRAP-TYPE
       ENTERPRISE denviroTraps
       VARIABLES { denviroDBID, denviroDBTitle, denviroDBIn3Title }
       DESCRIPTION
	"The input3 of Delta Bus is in normal state."
       ::= 50

   denviroDBInput4Alarm TRAP-TYPE
       ENTERPRISE denviroTraps
       VARIABLES { denviroDBID, denviroDBTitle, denviroDBIn4Title }
       DESCRIPTION
	"The input4 of Delta Bus is not in normal state."
       ::= 51

   denviroDBInput4AlarmRecover TRAP-TYPE
       ENTERPRISE denviroTraps
       VARIABLES { denviroDBID, denviroDBTitle, denviroDBIn4Title }
       DESCRIPTION
	"The input4 of Delta Bus is in normal state."
       ::= 52

   denviroRS4851Warn TRAP-TYPE
       ENTERPRISE denviroTraps
       VARIABLES { denviroID485, denviroTitle485, denviroTitle485 }
       DESCRIPTION
	"The device of RS485-1 is in warning state."
       ::= 53

   denviroRS4851WarnRecover TRAP-TYPE
       ENTERPRISE denviroTraps
       VARIABLES { denviroID485, denviroTitle485, denviroTitle485 }
       DESCRIPTION
	"The device of RS485-1 is not in warning state."
       ::= 54
       
   denviroRS4851Alarm TRAP-TYPE
       ENTERPRISE denviroTraps
       VARIABLES { denviroID485, denviroTitle485, denviroTitle485 }
       DESCRIPTION
	"The device of RS485-1 is in alarm state."
       ::= 55

   denviroRS4851AlarmRecover TRAP-TYPE
       ENTERPRISE denviroTraps
       VARIABLES { denviroID485, denviroTitle485, denviroTitle485 }
       DESCRIPTION
	"The device of RS485-1 is not in alarm state."
       ::= 56
       
   denviroRS4852Warn TRAP-TYPE
       ENTERPRISE denviroTraps
       VARIABLES { denviroID485, denviroTitle485, denviroTitle485 }
       DESCRIPTION
	"The device of RS485-2 is in warning state."
       ::= 57

   denviroRS4852WarnRecover TRAP-TYPE
       ENTERPRISE denviroTraps
       VARIABLES { denviroID485, denviroTitle485, denviroTitle485 }
       DESCRIPTION
	"The device of RS485-2 is not in warning state."
       ::= 58

   denviroRS4852Alarm TRAP-TYPE
       ENTERPRISE denviroTraps
       VARIABLES { denviroID485, denviroTitle485, denviroTitle485 }
       DESCRIPTION
	"The device of RS485-2 is in alarm state."
       ::= 59

   denviroRS4852AlarmRecover TRAP-TYPE
       ENTERPRISE denviroTraps
       VARIABLES { denviroID485, denviroTitle485, denviroTitle485 }
       DESCRIPTION
	"The device of RS485-2 is not in alarm state."
       ::= 60
	   
	denviroDBEMS1100RL1 TRAP-TYPE
       ENTERPRISE denviroTraps
       VARIABLES { denviroDBID, denviroDBTitle}
       DESCRIPTION
	"The Relay 1 of EMS1100 on Delta Bus is alarm state."
       ::= 61
	
	denviroDBEMS1100RL1Recover TRAP-TYPE
       ENTERPRISE denviroTraps
       VARIABLES { denviroDBID, denviroDBTitle}
       DESCRIPTION
	"The Relay 1 of EMS1100 on Delta Bus is back to normal state."
       ::= 62
	
	denviroDBEMS1100RL2 TRAP-TYPE
       ENTERPRISE denviroTraps
       VARIABLES { denviroDBID, denviroDBTitle}
       DESCRIPTION
	"The Relay 2 of EMS1100 on Delta Bus is alarm state."
       ::= 63
	
	denviroDBEMS1100RL2Recover TRAP-TYPE
       ENTERPRISE denviroTraps
       VARIABLES { denviroDBID, denviroDBTitle}
       DESCRIPTION
	"The Relay 2 of EMS1100 on Delta Bus is back to normal state."
       ::= 64
	   
	denviroDBEMS1100RL3 TRAP-TYPE
       ENTERPRISE denviroTraps
       VARIABLES { denviroDBID, denviroDBTitle}
       DESCRIPTION
	"The Relay 3 of EMS1100 on Delta Bus is alarm state."
       ::= 65
	
	denviroDBEMS1100RL3Recover TRAP-TYPE
       ENTERPRISE denviroTraps
       VARIABLES { denviroDBID, denviroDBTitle}
       DESCRIPTION
	"The Relay 3 of EMS1100 on Delta Bus is back to normal state."
       ::= 66
	   
	denviroDBEMS1100RL4 TRAP-TYPE
       ENTERPRISE denviroTraps
       VARIABLES { denviroDBID, denviroDBTitle}
       DESCRIPTION
	"The Relay 4 of EMS1100 on Delta Bus is alarm state."
       ::= 67
	
	denviroDBEMS1100RL4Recover TRAP-TYPE
       ENTERPRISE denviroTraps
       VARIABLES { denviroDBID, denviroDBTitle}
       DESCRIPTION
	"The Relay 4 of EMS1100 on Delta Bus is back to normal state."
       ::= 68
	   
	denviroDBEMS1200AI1Warn TRAP-TYPE
       ENTERPRISE denviroTraps
       VARIABLES { denviroDBID, denviroDBTitle}
       DESCRIPTION
	"The AI1 of EMS1200 on Delta Bus is warn state."
       ::= 69

	denviroDBEMS1200AI2Warn TRAP-TYPE
       ENTERPRISE denviroTraps
       VARIABLES { denviroDBID, denviroDBTitle}
       DESCRIPTION
	"The AI2 of EMS1200 on Delta Bus is warn state."
       ::= 70
	   
	denviroDBEMS1200AI1Alarm TRAP-TYPE
       ENTERPRISE denviroTraps
       VARIABLES { denviroDBID, denviroDBTitle}
       DESCRIPTION
	"The AI1 of EMS1200 on Delta Bus is alarm state."
       ::= 71

	denviroDBEMS1200AI2Alarm TRAP-TYPE
       ENTERPRISE denviroTraps
       VARIABLES { denviroDBID, denviroDBTitle}
       DESCRIPTION
	"The AI2 of EMS1200 on Delta Bus is alarm state."
       ::= 72
	   
	denviroDBEMS1200LeakAlarm TRAP-TYPE
       ENTERPRISE denviroTraps
       VARIABLES { denviroDBID, denviroDBTitle}
       DESCRIPTION
	"The Leakage of EMS1200 on Delta Bus is not in normal state."
       ::= 73
	   
	denviroDBEMS1200AI1Recover TRAP-TYPE
       ENTERPRISE denviroTraps
       VARIABLES { denviroDBID, denviroDBTitle}
       DESCRIPTION
	"The AI1 of EMS1200 on Delta Bus is back to normal state."
       ::= 74

	denviroDBEMS1200AI2Recover TRAP-TYPE
       ENTERPRISE denviroTraps
       VARIABLES { denviroDBID, denviroDBTitle}
       DESCRIPTION
	"The AI2 of EMS1200 on Delta Bus is back to normal state."
       ::= 75
	   
	denviroDBEMS1200LeakRecover TRAP-TYPE
       ENTERPRISE denviroTraps
       VARIABLES { denviroDBID, denviroDBTitle}
       DESCRIPTION
	"The Leakage of EMS1200 on Delta Bus is back to normal state."
       ::= 76

	denviroDBEMS1200AOAlarm TRAP-TYPE
       ENTERPRISE denviroTraps
       VARIABLES { denviroDBID, denviroDBTitle}
       DESCRIPTION
	"The AO of EMS1200 on Delta Bus is in alarm state."
       ::= 77

	denviroDBEMS1200AOAlarmRecover TRAP-TYPE
       ENTERPRISE denviroTraps
       VARIABLES { denviroDBID, denviroDBTitle}
       DESCRIPTION
	   "The AO of EMS1200 on Delta Bus is back to noraml state."
       ::= 78
	   
    denviroReactionTriggered TRAP-TYPE
       ENTERPRISE denviroTraps
	   VARIABLES { denviroReactionRuleName }
       DESCRIPTION
	   "The reaction rule is triggered."
       ::= 79
END
