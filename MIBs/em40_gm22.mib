GEISTMFG-EM40GM22-MIB DEFINITIONS ::= BEGIN

IMPORTS
	MODULE-IDENTITY, OBJECT-TYPE, enterprises, Unsigned32 FROM SNMPv2-SMI;

geistmfg MODULE-IDENTITY
	LAST-UPDATED "200612140000Z"
	ORGANIZATION "Geist Manufacturing"
	CONTACT-INFO "support@geistmfg.com/800.432.3219"
	DESCRIPTION "The MIB for EM40/GM22"
	::= { enterprises 21239 }
	

em40gm22 OBJECT IDENTIFIER
	::=  { geistmfg 6 }


productInfo OBJECT IDENTIFIER
	::= { em40gm22 1 }

totalDeciAmps OBJECT IDENTIFIER
	::= { em40gm22 2 }

phaseC OBJECT IDENTIFIER
	::= { em40gm22 3 }

phaseBC OBJECT IDENTIFIER
	::= { em40gm22 4 }

phaseB OBJECT IDENTIFIER
	::= { em40gm22 5 }

phaseAB OBJECT IDENTIFIER
	::= { em40gm22 6 }

phaseA OBJECT IDENTIFIER
	::= { em40gm22 7 }

phaseAC OBJECT IDENTIFIER
	::= { em40gm22 8 }




productTitle    OBJECT-TYPE
   SYNTAX DisplayString
   ACCESS read-only
   STATUS mandatory
   DESCRIPTION
      "Name of product"
   ::= { productInfo 1 }
   
productVersion    OBJECT-TYPE
   SYNTAX DisplayString
   ACCESS read-only
   STATUS mandatory
   DESCRIPTION
      "Firmware version"
   ::= { productInfo 2 }

productName    OBJECT-TYPE
   SYNTAX DisplayString
   ACCESS read-only
   STATUS mandatory
   DESCRIPTION
      "Unit friendly name"
   ::= { productInfo 3 }

productMAC    OBJECT-TYPE
   SYNTAX DisplayString
   ACCESS read-only
   STATUS mandatory
   DESCRIPTION
      "Unit MAC address"
   ::= { productInfo 4 }

productIP    OBJECT-TYPE
   SYNTAX DisplayString
   ACCESS read-only
   STATUS mandatory
   DESCRIPTION
      "IP address of the unit"
   ::= { productInfo 5 }




totalDeciAmpsPhaseA   OBJECT-TYPE
   SYNTAX INTEGER(0..300)
   UNITS "0.1 Amps"
   ACCESS read-only
   STATUS mandatory
   DESCRIPTION
   "Total Amps consumed by PhaseA, in units of 0.1 amps"
   ::= { totalDeciAmps 1 }

totalDeciAmpsPhaseB   OBJECT-TYPE
   SYNTAX INTEGER(0..300)
   UNITS "0.1 Amps"
   ACCESS read-only
   STATUS mandatory
   DESCRIPTION
   "Total Amps consumed by PhaseB, in units of 0.1 amps"
   ::= { totalDeciAmps 2 }

totalDeciAmpsPhaseC   OBJECT-TYPE
   SYNTAX INTEGER(0..300)
   UNITS "0.1 Amps"
   ACCESS read-only
   STATUS mandatory
   DESCRIPTION
   "Total Amps consumed by PhaseC, in units of 0.1 amps"
   ::= { totalDeciAmps 3 }

totalDeciAmpsNeutral   OBJECT-TYPE
   SYNTAX INTEGER(0..300)
   UNITS "0.1 Amps"
   ACCESS read-only
   STATUS mandatory
   DESCRIPTION
   "Total Amps consumed by Neutral, in units of 0.1 amps"
   ::= { totalDeciAmps 4 }





outlet1C1Name OBJECT-TYPE
   SYNTAX DisplayString
   ACCESS read-only
   STATUS mandatory
   DESCRIPTION
   "Friendly name for outlet 1"
   ::= { phaseC 1 }

outlet1C1DeciAmps OBJECT-TYPE
   SYNTAX INTEGER(0..255)
   UNITS "0.1 Amps"
   ACCESS read-only
   STATUS mandatory
   DESCRIPTION
   "Amps used by outlet 1, in units of 0.1 amps"
   ::= { phaseC 2 }

outlet2C2Name OBJECT-TYPE
   SYNTAX DisplayString
   ACCESS read-only
   STATUS mandatory
   DESCRIPTION
   "Friendly name for outlet 2"
   ::= { phaseC 3 }

outlet2C2DeciAmps OBJECT-TYPE
   SYNTAX INTEGER(0..255)
   UNITS "0.1 Amps"
   ACCESS read-only
   STATUS mandatory
   DESCRIPTION
   "Amps used by outlet 2, in units of 0.1 amps"
   ::= { phaseC 4 }



outlet3BC1Name OBJECT-TYPE
   SYNTAX DisplayString
   ACCESS read-only
   STATUS mandatory
   DESCRIPTION
   "Friendly name for outlet 3"
   ::= { phaseBC 1 }

outlet3BC1DeciAmps OBJECT-TYPE
   SYNTAX INTEGER(0..255)
   UNITS "0.1 Amps"
   ACCESS read-only
   STATUS mandatory
   DESCRIPTION
   "Amps used by outlet 3, in units of 0.1 amps"
   ::= { phaseBC 2 }

outlet4BC2Name OBJECT-TYPE
   SYNTAX DisplayString
   ACCESS read-only
   STATUS mandatory
   DESCRIPTION
   "Friendly name for outlet 4"
   ::= { phaseBC 3 }

outlet4BC2DeciAmps OBJECT-TYPE
   SYNTAX INTEGER(0..255)
   UNITS "0.1 Amps"
   ACCESS read-only
   STATUS mandatory
   DESCRIPTION
   "Amps used by outlet 4, in units of 0.1 amps"
   ::= { phaseBC 4 }

outlet5BC3Name OBJECT-TYPE
   SYNTAX DisplayString
   ACCESS read-only
   STATUS mandatory
   DESCRIPTION
   "Friendly name for outlet 5"
   ::= { phaseBC 5 }

outlet5BC3DeciAmps OBJECT-TYPE
   SYNTAX INTEGER(0..255)
   UNITS "0.1 Amps"
   ACCESS read-only
   STATUS mandatory
   DESCRIPTION
   "Amps used by outlet 5, in units of 0.1 amps"
   ::= { phaseBC 6 }

outlet6BC4Name OBJECT-TYPE
   SYNTAX DisplayString
   ACCESS read-only
   STATUS mandatory
   DESCRIPTION
   "Friendly name for outlet 6"
   ::= { phaseBC 7 }

outlet6BC4DeciAmps OBJECT-TYPE
   SYNTAX INTEGER(0..255)
   UNITS "0.1 Amps"
   ACCESS read-only
   STATUS mandatory
   DESCRIPTION
   "Amps used by outlet 6, in units of 0.1 amps"
   ::= { phaseBC 8 }



outlet7B1Name OBJECT-TYPE
   SYNTAX DisplayString
   ACCESS read-only
   STATUS mandatory
   DESCRIPTION
   "Friendly name for outlet 7"
   ::= { phaseB 1 }

outlet7B1DeciAmps OBJECT-TYPE
   SYNTAX INTEGER(0..255)
   UNITS "0.1 Amps"
   ACCESS read-only
   STATUS mandatory
   DESCRIPTION
   "Amps used by outlet 7, in units of 0.1 amps"
   ::= { phaseB 2 }

outlet8B2Name OBJECT-TYPE
   SYNTAX DisplayString
   ACCESS read-only
   STATUS mandatory
   DESCRIPTION
   "Friendly name for outlet 8"
   ::= { phaseB 3 }

outlet8B2DeciAmps OBJECT-TYPE
   SYNTAX INTEGER(0..255)
   UNITS "0.1 Amps"
   ACCESS read-only
   STATUS mandatory
   DESCRIPTION
   "Amps used by outlet 8, in units of 0.1 amps"
   ::= { phaseB 4 }



outlet9AB1Name OBJECT-TYPE
   SYNTAX DisplayString
   ACCESS read-only
   STATUS mandatory
   DESCRIPTION
   "Friendly name for outlet 9"
   ::= { phaseAB 1 }

outlet9AB1DeciAmps OBJECT-TYPE
   SYNTAX INTEGER(0..255)
   UNITS "0.1 Amps"
   ACCESS read-only
   STATUS mandatory
   DESCRIPTION
   "Amps used by outlet 9, in units of 0.1 amps"
   ::= { phaseAB 2 }

outlet10AB2Name OBJECT-TYPE
   SYNTAX DisplayString
   ACCESS read-only
   STATUS mandatory
   DESCRIPTION
   "Friendly name for outlet 10"
   ::= { phaseAB 3 }

outlet10AB2DeciAmps OBJECT-TYPE
   SYNTAX INTEGER(0..255)
   UNITS "0.1 Amps"
   ACCESS read-only
   STATUS mandatory
   DESCRIPTION
   "Amps used by outlet 10, in units of 0.1 amps"
   ::= { phaseAB 4 }

outlet11AB3Name OBJECT-TYPE
   SYNTAX DisplayString
   ACCESS read-only
   STATUS mandatory
   DESCRIPTION
   "Friendly name for outlet 11"
   ::= { phaseAB 5 }

outlet11AB3DeciAmps OBJECT-TYPE
   SYNTAX INTEGER(0..255)
   UNITS "0.1 Amps"
   ACCESS read-only
   STATUS mandatory
   DESCRIPTION
   "Amps used by outlet 11, in units of 0.1 amps"
   ::= { phaseAB 6 }

outlet12AB4Name OBJECT-TYPE
   SYNTAX DisplayString
   ACCESS read-only
   STATUS mandatory
   DESCRIPTION
   "Friendly name for outlet 12"
   ::= { phaseAB 7 }

outlet12AB4DeciAmps OBJECT-TYPE
   SYNTAX INTEGER(0..255)
   UNITS "0.1 Amps"
   ACCESS read-only
   STATUS mandatory
   DESCRIPTION
   "Amps used by outlet 12, in units of 0.1 amps"
   ::= { phaseAB 8 }



outlet13A1Name OBJECT-TYPE
   SYNTAX DisplayString
   ACCESS read-only
   STATUS mandatory
   DESCRIPTION
   "Friendly name for outlet 13"
   ::= { phaseA 1 }

outlet13A1DeciAmps OBJECT-TYPE
   SYNTAX INTEGER(0..255)
   UNITS "0.1 Amps"
   ACCESS read-only
   STATUS mandatory
   DESCRIPTION
   "Amps used by outlet 13, in units of 0.1 amps"
   ::= { phaseA 2 }

outlet14A2Name OBJECT-TYPE
   SYNTAX DisplayString
   ACCESS read-only
   STATUS mandatory
   DESCRIPTION
   "Friendly name for outlet 14"
   ::= { phaseA 3 }

outlet14A2DeciAmps OBJECT-TYPE
   SYNTAX INTEGER(0..255)
   UNITS "0.1 Amps"
   ACCESS read-only
   STATUS mandatory
   DESCRIPTION
   "Amps used by outlet 14, in units of 0.1 amps"
   ::= { phaseA 4 }



outlet15AC1Name OBJECT-TYPE
   SYNTAX DisplayString
   ACCESS read-only
   STATUS mandatory
   DESCRIPTION
   "Friendly name for outlet 15"
   ::= { phaseAC 1 }

outlet15AC1DeciAmps OBJECT-TYPE
   SYNTAX INTEGER(0..255)
   UNITS "0.1 Amps"
   ACCESS read-only
   STATUS mandatory
   DESCRIPTION
   "Amps used by outlet 15, in units of 0.1 amps"
   ::= { phaseAC 2 }

outlet16AC2Name OBJECT-TYPE
   SYNTAX DisplayString
   ACCESS read-only
   STATUS mandatory
   DESCRIPTION
   "Friendly name for outlet 16"
   ::= { phaseAC 3 }

outlet16AC2DeciAmps OBJECT-TYPE
   SYNTAX INTEGER(0..255)
   UNITS "0.1 Amps"
   ACCESS read-only
   STATUS mandatory
   DESCRIPTION
   "Amps used by outlet 16, in units of 0.1 amps"
   ::= { phaseAC 4 }

outlet17AC3Name OBJECT-TYPE
   SYNTAX DisplayString
   ACCESS read-only
   STATUS mandatory
   DESCRIPTION
   "Friendly name for outlet 17"
   ::= { phaseAC 5 }

outlet17AC3DeciAmps OBJECT-TYPE
   SYNTAX INTEGER(0..255)
   UNITS "0.1 Amps"
   ACCESS read-only
   STATUS mandatory
   DESCRIPTION
   "Amps used by outlet 17, in units of 0.1 amps"
   ::= { phaseAC 6 }

outlet18AC4Name OBJECT-TYPE
   SYNTAX DisplayString
   ACCESS read-only
   STATUS mandatory
   DESCRIPTION
   "Friendly name for outlet 18"
   ::= { phaseAC 7 }

outlet18AC4DeciAmps OBJECT-TYPE
   SYNTAX INTEGER(0..255)
   UNITS "0.1 Amps"
   ACCESS read-only
   STATUS mandatory
   DESCRIPTION
   "Amps used by outlet 18, in units of 0.1 amps"
   ::= { phaseAC 8 }





totalDeciAmpsPhaseATRAP TRAP-TYPE
ENTERPRISE geistmfg
VARIABLES { totalDeciAmpsPhaseA }
DESCRIPTION "Amps PhaseA Trap"
::= 1

totalDeciAmpsPhaseBTRAP TRAP-TYPE
ENTERPRISE geistmfg
VARIABLES { totalDeciAmpsPhaseB }
DESCRIPTION "Amps PhaseB Trap"
::= 2

totalDeciAmpsPhaseCTRAP TRAP-TYPE
ENTERPRISE geistmfg
VARIABLES { totalDeciAmpsPhaseC }
DESCRIPTION "Amps PhaseC Trap"
::= 3

totalDeciAmpsNeutralTRAP TRAP-TYPE
ENTERPRISE geistmfg
VARIABLES { totalDeciAmpsNeutral }
DESCRIPTION "Amps Neutral Trap"
::= 4





outlet1C1DeciAmpsTRAP TRAP-TYPE
ENTERPRISE geistmfg
VARIABLES { outlet1C1DeciAmps }
DESCRIPTION "Amps outlet1C1DeciAmps Trap"
::= 5

outlet2C2DeciAmpsTRAP TRAP-TYPE
ENTERPRISE geistmfg
VARIABLES { outlet2C2DeciAmps }
DESCRIPTION "Amps outlet2C2DeciAmps Trap"
::= 6



outlet3BC1DeciAmpsTRAP TRAP-TYPE
ENTERPRISE geistmfg
VARIABLES { outlet3BC1DeciAmps }
DESCRIPTION "Amps outlet3BC1DeciAmps Trap"
::= 7

outlet4BC2DeciAmpsTRAP TRAP-TYPE
ENTERPRISE geistmfg
VARIABLES { outlet4BC2DeciAmps }
DESCRIPTION "Amps outlet4BC2DeciAmps Trap"
::= 8

outlet5BC3DeciAmpsTRAP TRAP-TYPE
ENTERPRISE geistmfg
VARIABLES { outlet5BC3DeciAmps }
DESCRIPTION "Amps outlet5BC3DeciAmps Trap"
::= 9

outlet6BC4DeciAmpsTRAP TRAP-TYPE
ENTERPRISE geistmfg
VARIABLES { outlet6BC4DeciAmps }
DESCRIPTION "Amps outlet6BC4DeciAmps Trap"
::= 10



outlet7B1DeciAmpsTRAP TRAP-TYPE
ENTERPRISE geistmfg
VARIABLES { outlet7B1DeciAmps }
DESCRIPTION "Amps outlet7B1DeciAmps Trap"
::= 11

outlet8B2DeciAmpsTRAP TRAP-TYPE
ENTERPRISE geistmfg
VARIABLES { outlet8B2DeciAmps }
DESCRIPTION "Amps outlet8B2DeciAmps Trap"
::= 12



outlet9AB1DeciAmpsTRAP TRAP-TYPE
ENTERPRISE geistmfg
VARIABLES { outlet9AB1DeciAmps }
DESCRIPTION "Amps outlet9AB1DeciAmps Trap"
::= 13

outlet10AB2DeciAmpsTRAP TRAP-TYPE
ENTERPRISE geistmfg
VARIABLES { outlet10AB2DeciAmps }
DESCRIPTION "Amps outlet10AB2DeciAmps Trap"
::= 14

outlet11AB3DeciAmpsTRAP TRAP-TYPE
ENTERPRISE geistmfg
VARIABLES { outlet11AB3DeciAmps }
DESCRIPTION "Amps outlet11AB3DeciAmps Trap"
::= 15

outlet12AB4DeciAmpsTRAP TRAP-TYPE
ENTERPRISE geistmfg
VARIABLES { outlet12AB4DeciAmps }
DESCRIPTION "Amps outlet12AB4DeciAmps Trap"
::= 16



outlet13A1DeciAmpsTRAP TRAP-TYPE
ENTERPRISE geistmfg
VARIABLES { outlet13A1DeciAmps }
DESCRIPTION "Amps outlet13A1DeciAmps Trap"
::= 17

outlet14A2DeciAmpsTRAP TRAP-TYPE
ENTERPRISE geistmfg
VARIABLES { outlet14A2DeciAmps }
DESCRIPTION "Amps outlet14A2DeciAmps Trap"
::= 18



outlet15AC1DeciAmpsTRAP TRAP-TYPE
ENTERPRISE geistmfg
VARIABLES { outlet15AC1DeciAmps }
DESCRIPTION "Amps outlet15AC1DeciAmps Trap"
::= 19

outlet16AC2DeciAmpsTRAP TRAP-TYPE
ENTERPRISE geistmfg
VARIABLES { outlet16AC2DeciAmps }
DESCRIPTION "Amps outlet16AC2DeciAmps Trap"
::= 20

outlet17AC3DeciAmpsTRAP TRAP-TYPE
ENTERPRISE geistmfg
VARIABLES { outlet17AC3DeciAmps }
DESCRIPTION "Amps outlet17AC3DeciAmps Trap"
::= 21

outlet18AC4DeciAmpsTRAP TRAP-TYPE
ENTERPRISE geistmfg
VARIABLES { outlet18AC4DeciAmps }
DESCRIPTION "Amps outlet18AC4DeciAmps Trap"
::= 22



END
