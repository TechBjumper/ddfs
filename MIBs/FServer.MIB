FIELDSERVER-MIB DEFINITIONS ::= BEGIN

IMPORTS
enterprises, OBJECT-TYPE, MODULE-IDENTITY
FROM SNMPv2-SMI
TRAP-TYPE
FROM RFC-1215;

fieldserver_technologies MODULE-IDENTITY
LAST-UPDATED "200308121338Z"
ORGANIZATION
"FieldServer Technologies"
CONTACT-INFO
"info@fieldserver.com"
DESCRIPTION
"FieldServer Technologies"
::= { enterprises 6347 }

s08090201_trane_st_jude_v1_00b OBJECT IDENTIFIER ::= { fieldserver_technologies  1 }

dataArray1 OBJECT IDENTIFIER ::= { s08090201_trane_st_jude_v1_00b 1 }

dataValue1_0 OBJECT-TYPE
SYNTAX INTEGER
MAX-ACCESS read-write
STATUS current
DESCRIPTION
"Data value."
::= { dataArray1 0 }

dataValue1_1 OBJECT-TYPE
SYNTAX INTEGER
MAX-ACCESS read-write
STATUS current
DESCRIPTION
"Data value."
::= { dataArray1 1 }

dataValue1_2 OBJECT-TYPE
SYNTAX INTEGER
MAX-ACCESS read-write
STATUS current
DESCRIPTION
"Data value."
::= { dataArray1 2 }

dataValue1_3 OBJECT-TYPE
SYNTAX INTEGER
MAX-ACCESS read-write
STATUS current
DESCRIPTION
"Data value."
::= { dataArray1 3 }

dataValue1_4 OBJECT-TYPE
SYNTAX INTEGER
MAX-ACCESS read-write
STATUS current
DESCRIPTION
"Data value."
::= { dataArray1 4 }

dataValue1_5 OBJECT-TYPE
SYNTAX INTEGER
MAX-ACCESS read-write
STATUS current
DESCRIPTION
"Data value."
::= { dataArray1 5 }

dataValue1_6 OBJECT-TYPE
SYNTAX INTEGER
MAX-ACCESS read-write
STATUS current
DESCRIPTION
"Data value."
::= { dataArray1 6 }

dataValue1_7 OBJECT-TYPE
SYNTAX INTEGER
MAX-ACCESS read-write
STATUS current
DESCRIPTION
"Data value."
::= { dataArray1 7 }

dataValue1_8 OBJECT-TYPE
SYNTAX INTEGER
MAX-ACCESS read-write
STATUS current
DESCRIPTION
"Data value."
::= { dataArray1 8 }

dataValue1_9 OBJECT-TYPE
SYNTAX INTEGER
MAX-ACCESS read-write
STATUS current
DESCRIPTION
"Data value."
::= { dataArray1 9 }

dataValue1_10 OBJECT-TYPE
SYNTAX INTEGER
MAX-ACCESS read-write
STATUS current
DESCRIPTION
"Data value."
::= { dataArray1 10 }

dataValue1_11 OBJECT-TYPE
SYNTAX INTEGER
MAX-ACCESS read-write
STATUS current
DESCRIPTION
"Data value."
::= { dataArray1 11 }

dataValue1_12 OBJECT-TYPE
SYNTAX INTEGER
MAX-ACCESS read-write
STATUS current
DESCRIPTION
"Data value."
::= { dataArray1 12 }

dataValue1_13 OBJECT-TYPE
SYNTAX INTEGER
MAX-ACCESS read-write
STATUS current
DESCRIPTION
"Data value."
::= { dataArray1 13 }

dataValue1_14 OBJECT-TYPE
SYNTAX INTEGER
MAX-ACCESS read-write
STATUS current
DESCRIPTION
"Data value."
::= { dataArray1 14 }

dataValue1_15 OBJECT-TYPE
SYNTAX INTEGER
MAX-ACCESS read-write
STATUS current
DESCRIPTION
"Data value."
::= { dataArray1 15 }

dataValue1_16 OBJECT-TYPE
SYNTAX INTEGER
MAX-ACCESS read-write
STATUS current
DESCRIPTION
"Data value."
::= { dataArray1 16 }

dataValue1_17 OBJECT-TYPE
SYNTAX INTEGER
MAX-ACCESS read-write
STATUS current
DESCRIPTION
"Data value."
::= { dataArray1 17 }

dataValue1_18 OBJECT-TYPE
SYNTAX INTEGER
MAX-ACCESS read-write
STATUS current
DESCRIPTION
"Data value."
::= { dataArray1 18 }

dataValue1_19 OBJECT-TYPE
SYNTAX INTEGER
MAX-ACCESS read-write
STATUS current
DESCRIPTION
"Data value."
::= { dataArray1 19 }

dataValue1_20 OBJECT-TYPE
SYNTAX INTEGER
MAX-ACCESS read-write
STATUS current
DESCRIPTION
"Data value."
::= { dataArray1 20 }

dataValue1_21 OBJECT-TYPE
SYNTAX INTEGER
MAX-ACCESS read-write
STATUS current
DESCRIPTION
"Data value."
::= { dataArray1 21 }

dataValue1_22 OBJECT-TYPE
SYNTAX INTEGER
MAX-ACCESS read-write
STATUS current
DESCRIPTION
"Data value."
::= { dataArray1 22 }

dataValue1_23 OBJECT-TYPE
SYNTAX INTEGER
MAX-ACCESS read-write
STATUS current
DESCRIPTION
"Data value."
::= { dataArray1 23 }

dataValue1_24 OBJECT-TYPE
SYNTAX INTEGER
MAX-ACCESS read-write
STATUS current
DESCRIPTION
"Data value."
::= { dataArray1 24 }

dataValue1_25 OBJECT-TYPE
SYNTAX INTEGER
MAX-ACCESS read-write
STATUS current
DESCRIPTION
"Data value."
::= { dataArray1 25 }

dataValue1_26 OBJECT-TYPE
SYNTAX INTEGER
MAX-ACCESS read-write
STATUS current
DESCRIPTION
"Data value."
::= { dataArray1 26 }

dataValue1_27 OBJECT-TYPE
SYNTAX INTEGER
MAX-ACCESS read-write
STATUS current
DESCRIPTION
"Data value."
::= { dataArray1 27 }

dataValue1_28 OBJECT-TYPE
SYNTAX INTEGER
MAX-ACCESS read-write
STATUS current
DESCRIPTION
"Data value."
::= { dataArray1 28 }

dataValue1_29 OBJECT-TYPE
SYNTAX INTEGER
MAX-ACCESS read-write
STATUS current
DESCRIPTION
"Data value."
::= { dataArray1 29 }

dataValue1_30 OBJECT-TYPE
SYNTAX INTEGER
MAX-ACCESS read-write
STATUS current
DESCRIPTION
"Data value."
::= { dataArray1 30 }

dataValue1_31 OBJECT-TYPE
SYNTAX INTEGER
MAX-ACCESS read-write
STATUS current
DESCRIPTION
"Data value."
::= { dataArray1 31 }

dataValue1_32 OBJECT-TYPE
SYNTAX INTEGER
MAX-ACCESS read-write
STATUS current
DESCRIPTION
"Data value."
::= { dataArray1 32 }

dataValue1_33 OBJECT-TYPE
SYNTAX INTEGER
MAX-ACCESS read-write
STATUS current
DESCRIPTION
"Data value."
::= { dataArray1 33 }

dataValue1_34 OBJECT-TYPE
SYNTAX INTEGER
MAX-ACCESS read-write
STATUS current
DESCRIPTION
"Data value."
::= { dataArray1 34 }

dataValue1_35 OBJECT-TYPE
SYNTAX INTEGER
MAX-ACCESS read-write
STATUS current
DESCRIPTION
"Data value."
::= { dataArray1 35 }

dataValue1_36 OBJECT-TYPE
SYNTAX INTEGER
MAX-ACCESS read-write
STATUS current
DESCRIPTION
"Data value."
::= { dataArray1 36 }

dataValue1_37 OBJECT-TYPE
SYNTAX INTEGER
MAX-ACCESS read-write
STATUS current
DESCRIPTION
"Data value."
::= { dataArray1 37 }

dataValue1_38 OBJECT-TYPE
SYNTAX INTEGER
MAX-ACCESS read-write
STATUS current
DESCRIPTION
"Data value."
::= { dataArray1 38 }

dataValue1_39 OBJECT-TYPE
SYNTAX INTEGER
MAX-ACCESS read-write
STATUS current
DESCRIPTION
"Data value."
::= { dataArray1 39 }

dataValue1_40 OBJECT-TYPE
SYNTAX INTEGER
MAX-ACCESS read-write
STATUS current
DESCRIPTION
"Data value."
::= { dataArray1 40 }

dataValue1_41 OBJECT-TYPE
SYNTAX INTEGER
MAX-ACCESS read-write
STATUS current
DESCRIPTION
"Data value."
::= { dataArray1 41 }

dataValue1_42 OBJECT-TYPE
SYNTAX INTEGER
MAX-ACCESS read-write
STATUS current
DESCRIPTION
"Data value."
::= { dataArray1 42 }

dataValue1_43 OBJECT-TYPE
SYNTAX INTEGER
MAX-ACCESS read-write
STATUS current
DESCRIPTION
"Data value."
::= { dataArray1 43 }

dataValue1_44 OBJECT-TYPE
SYNTAX INTEGER
MAX-ACCESS read-write
STATUS current
DESCRIPTION
"Data value."
::= { dataArray1 44 }

dataValue1_45 OBJECT-TYPE
SYNTAX INTEGER
MAX-ACCESS read-write
STATUS current
DESCRIPTION
"Data value."
::= { dataArray1 45 }

dataValue1_46 OBJECT-TYPE
SYNTAX INTEGER
MAX-ACCESS read-write
STATUS current
DESCRIPTION
"Data value."
::= { dataArray1 46 }

dataValue1_47 OBJECT-TYPE
SYNTAX INTEGER
MAX-ACCESS read-write
STATUS current
DESCRIPTION
"Data value."
::= { dataArray1 47 }

dataValue1_48 OBJECT-TYPE
SYNTAX INTEGER
MAX-ACCESS read-write
STATUS current
DESCRIPTION
"Data value."
::= { dataArray1 48 }

dataValue1_49 OBJECT-TYPE
SYNTAX INTEGER
MAX-ACCESS read-write
STATUS current
DESCRIPTION
"Data value."
::= { dataArray1 49 }

dataValue1_50 OBJECT-TYPE
SYNTAX INTEGER
MAX-ACCESS read-write
STATUS current
DESCRIPTION
"Data value."
::= { dataArray1 50 }

dataValue1_51 OBJECT-TYPE
SYNTAX INTEGER
MAX-ACCESS read-write
STATUS current
DESCRIPTION
"Data value."
::= { dataArray1 51 }

dataValue1_52 OBJECT-TYPE
SYNTAX INTEGER
MAX-ACCESS read-write
STATUS current
DESCRIPTION
"Data value."
::= { dataArray1 52 }

dataValue1_53 OBJECT-TYPE
SYNTAX INTEGER
MAX-ACCESS read-write
STATUS current
DESCRIPTION
"Data value."
::= { dataArray1 53 }

dataValue1_54 OBJECT-TYPE
SYNTAX INTEGER
MAX-ACCESS read-write
STATUS current
DESCRIPTION
"Data value."
::= { dataArray1 54 }

dataValue1_55 OBJECT-TYPE
SYNTAX INTEGER
MAX-ACCESS read-write
STATUS current
DESCRIPTION
"Data value."
::= { dataArray1 55 }

dataValue1_56 OBJECT-TYPE
SYNTAX INTEGER
MAX-ACCESS read-write
STATUS current
DESCRIPTION
"Data value."
::= { dataArray1 56 }

dataValue1_57 OBJECT-TYPE
SYNTAX INTEGER
MAX-ACCESS read-write
STATUS current
DESCRIPTION
"Data value."
::= { dataArray1 57 }

dataValue1_58 OBJECT-TYPE
SYNTAX INTEGER
MAX-ACCESS read-write
STATUS current
DESCRIPTION
"Data value."
::= { dataArray1 58 }

dataValue1_59 OBJECT-TYPE
SYNTAX INTEGER
MAX-ACCESS read-write
STATUS current
DESCRIPTION
"Data value."
::= { dataArray1 59 }

dataValue1_60 OBJECT-TYPE
SYNTAX INTEGER
MAX-ACCESS read-write
STATUS current
DESCRIPTION
"Data value."
::= { dataArray1 60 }

dataValue1_61 OBJECT-TYPE
SYNTAX INTEGER
MAX-ACCESS read-write
STATUS current
DESCRIPTION
"Data value."
::= { dataArray1 61 }

dataValue1_62 OBJECT-TYPE
SYNTAX INTEGER
MAX-ACCESS read-write
STATUS current
DESCRIPTION
"Data value."
::= { dataArray1 62 }

dataValue1_63 OBJECT-TYPE
SYNTAX INTEGER
MAX-ACCESS read-write
STATUS current
DESCRIPTION
"Data value."
::= { dataArray1 63 }

dataValue1_64 OBJECT-TYPE
SYNTAX INTEGER
MAX-ACCESS read-write
STATUS current
DESCRIPTION
"Data value."
::= { dataArray1 64 }

dataValue1_65 OBJECT-TYPE
SYNTAX INTEGER
MAX-ACCESS read-write
STATUS current
DESCRIPTION
"Data value."
::= { dataArray1 65 }

dataValue1_66 OBJECT-TYPE
SYNTAX INTEGER
MAX-ACCESS read-write
STATUS current
DESCRIPTION
"Data value."
::= { dataArray1 66 }

dataValue1_67 OBJECT-TYPE
SYNTAX INTEGER
MAX-ACCESS read-write
STATUS current
DESCRIPTION
"Data value."
::= { dataArray1 67 }

dataValue1_68 OBJECT-TYPE
SYNTAX INTEGER
MAX-ACCESS read-write
STATUS current
DESCRIPTION
"Data value."
::= { dataArray1 68 }

dataValue1_69 OBJECT-TYPE
SYNTAX INTEGER
MAX-ACCESS read-write
STATUS current
DESCRIPTION
"Data value."
::= { dataArray1 69 }

dataValue1_70 OBJECT-TYPE
SYNTAX INTEGER
MAX-ACCESS read-write
STATUS current
DESCRIPTION
"Data value."
::= { dataArray1 70 }

dataValue1_71 OBJECT-TYPE
SYNTAX INTEGER
MAX-ACCESS read-write
STATUS current
DESCRIPTION
"Data value."
::= { dataArray1 71 }

dataValue1_72 OBJECT-TYPE
SYNTAX INTEGER
MAX-ACCESS read-write
STATUS current
DESCRIPTION
"Data value."
::= { dataArray1 72 }

dataValue1_73 OBJECT-TYPE
SYNTAX INTEGER
MAX-ACCESS read-write
STATUS current
DESCRIPTION
"Data value."
::= { dataArray1 73 }

dataValue1_74 OBJECT-TYPE
SYNTAX INTEGER
MAX-ACCESS read-write
STATUS current
DESCRIPTION
"Data value."
::= { dataArray1 74 }

dataValue1_75 OBJECT-TYPE
SYNTAX INTEGER
MAX-ACCESS read-write
STATUS current
DESCRIPTION
"Data value."
::= { dataArray1 75 }

dataValue1_76 OBJECT-TYPE
SYNTAX INTEGER
MAX-ACCESS read-write
STATUS current
DESCRIPTION
"Data value."
::= { dataArray1 76 }

dataValue1_77 OBJECT-TYPE
SYNTAX INTEGER
MAX-ACCESS read-write
STATUS current
DESCRIPTION
"Data value."
::= { dataArray1 77 }

dataValue1_78 OBJECT-TYPE
SYNTAX INTEGER
MAX-ACCESS read-write
STATUS current
DESCRIPTION
"Data value."
::= { dataArray1 78 }

dataValue1_79 OBJECT-TYPE
SYNTAX INTEGER
MAX-ACCESS read-write
STATUS current
DESCRIPTION
"Data value."
::= { dataArray1 79 }

dataValue1_80 OBJECT-TYPE
SYNTAX INTEGER
MAX-ACCESS read-write
STATUS current
DESCRIPTION
"Data value."
::= { dataArray1 80 }

dataValue1_81 OBJECT-TYPE
SYNTAX INTEGER
MAX-ACCESS read-write
STATUS current
DESCRIPTION
"Data value."
::= { dataArray1 81 }

dataValue1_82 OBJECT-TYPE
SYNTAX INTEGER
MAX-ACCESS read-write
STATUS current
DESCRIPTION
"Data value."
::= { dataArray1 82 }

dataValue1_83 OBJECT-TYPE
SYNTAX INTEGER
MAX-ACCESS read-write
STATUS current
DESCRIPTION
"Data value."
::= { dataArray1 83 }

dataValue1_84 OBJECT-TYPE
SYNTAX INTEGER
MAX-ACCESS read-write
STATUS current
DESCRIPTION
"Data value."
::= { dataArray1 84 }

dataValue1_85 OBJECT-TYPE
SYNTAX INTEGER
MAX-ACCESS read-write
STATUS current
DESCRIPTION
"Data value."
::= { dataArray1 85 }

dataValue1_86 OBJECT-TYPE
SYNTAX INTEGER
MAX-ACCESS read-write
STATUS current
DESCRIPTION
"Data value."
::= { dataArray1 86 }

dataValue1_87 OBJECT-TYPE
SYNTAX INTEGER
MAX-ACCESS read-write
STATUS current
DESCRIPTION
"Data value."
::= { dataArray1 87 }

dataValue1_88 OBJECT-TYPE
SYNTAX INTEGER
MAX-ACCESS read-write
STATUS current
DESCRIPTION
"Data value."
::= { dataArray1 88 }

dataValue1_89 OBJECT-TYPE
SYNTAX INTEGER
MAX-ACCESS read-write
STATUS current
DESCRIPTION
"Data value."
::= { dataArray1 89 }

dataValue1_90 OBJECT-TYPE
SYNTAX INTEGER
MAX-ACCESS read-write
STATUS current
DESCRIPTION
"Data value."
::= { dataArray1 90 }

dataValue1_91 OBJECT-TYPE
SYNTAX INTEGER
MAX-ACCESS read-write
STATUS current
DESCRIPTION
"Data value."
::= { dataArray1 91 }

dataValue1_92 OBJECT-TYPE
SYNTAX INTEGER
MAX-ACCESS read-write
STATUS current
DESCRIPTION
"Data value."
::= { dataArray1 92 }

dataValue1_93 OBJECT-TYPE
SYNTAX INTEGER
MAX-ACCESS read-write
STATUS current
DESCRIPTION
"Data value."
::= { dataArray1 93 }

dataValue1_94 OBJECT-TYPE
SYNTAX INTEGER
MAX-ACCESS read-write
STATUS current
DESCRIPTION
"Data value."
::= { dataArray1 94 }

dataValue1_95 OBJECT-TYPE
SYNTAX INTEGER
MAX-ACCESS read-write
STATUS current
DESCRIPTION
"Data value."
::= { dataArray1 95 }

dataValue1_96 OBJECT-TYPE
SYNTAX INTEGER
MAX-ACCESS read-write
STATUS current
DESCRIPTION
"Data value."
::= { dataArray1 96 }

dataValue1_97 OBJECT-TYPE
SYNTAX INTEGER
MAX-ACCESS read-write
STATUS current
DESCRIPTION
"Data value."
::= { dataArray1 97 }

dataValue1_98 OBJECT-TYPE
SYNTAX INTEGER
MAX-ACCESS read-write
STATUS current
DESCRIPTION
"Data value."
::= { dataArray1 98 }

dataValue1_99 OBJECT-TYPE
SYNTAX INTEGER
MAX-ACCESS read-write
STATUS current
DESCRIPTION
"Data value."
::= { dataArray1 99 }

dataArray2 OBJECT IDENTIFIER ::= { s08090201_trane_st_jude_v1_00b 2 }

dataValue2_0 OBJECT-TYPE
SYNTAX INTEGER
MAX-ACCESS read-write
STATUS current
DESCRIPTION
"Data value."
::= { dataArray2 0 }

dataValue2_1 OBJECT-TYPE
SYNTAX INTEGER
MAX-ACCESS read-write
STATUS current
DESCRIPTION
"Data value."
::= { dataArray2 1 }

dataValue2_2 OBJECT-TYPE
SYNTAX INTEGER
MAX-ACCESS read-write
STATUS current
DESCRIPTION
"Data value."
::= { dataArray2 2 }

dataValue2_3 OBJECT-TYPE
SYNTAX INTEGER
MAX-ACCESS read-write
STATUS current
DESCRIPTION
"Data value."
::= { dataArray2 3 }

dataValue2_4 OBJECT-TYPE
SYNTAX INTEGER
MAX-ACCESS read-write
STATUS current
DESCRIPTION
"Data value."
::= { dataArray2 4 }

dataValue2_5 OBJECT-TYPE
SYNTAX INTEGER
MAX-ACCESS read-write
STATUS current
DESCRIPTION
"Data value."
::= { dataArray2 5 }

dataValue2_6 OBJECT-TYPE
SYNTAX INTEGER
MAX-ACCESS read-write
STATUS current
DESCRIPTION
"Data value."
::= { dataArray2 6 }

dataValue2_7 OBJECT-TYPE
SYNTAX INTEGER
MAX-ACCESS read-write
STATUS current
DESCRIPTION
"Data value."
::= { dataArray2 7 }

dataValue2_8 OBJECT-TYPE
SYNTAX INTEGER
MAX-ACCESS read-write
STATUS current
DESCRIPTION
"Data value."
::= { dataArray2 8 }

dataValue2_9 OBJECT-TYPE
SYNTAX INTEGER
MAX-ACCESS read-write
STATUS current
DESCRIPTION
"Data value."
::= { dataArray2 9 }

dataValue2_10 OBJECT-TYPE
SYNTAX INTEGER
MAX-ACCESS read-write
STATUS current
DESCRIPTION
"Data value."
::= { dataArray2 10 }

dataValue2_11 OBJECT-TYPE
SYNTAX INTEGER
MAX-ACCESS read-write
STATUS current
DESCRIPTION
"Data value."
::= { dataArray2 11 }

dataValue2_12 OBJECT-TYPE
SYNTAX INTEGER
MAX-ACCESS read-write
STATUS current
DESCRIPTION
"Data value."
::= { dataArray2 12 }

dataValue2_13 OBJECT-TYPE
SYNTAX INTEGER
MAX-ACCESS read-write
STATUS current
DESCRIPTION
"Data value."
::= { dataArray2 13 }

dataValue2_14 OBJECT-TYPE
SYNTAX INTEGER
MAX-ACCESS read-write
STATUS current
DESCRIPTION
"Data value."
::= { dataArray2 14 }

dataValue2_15 OBJECT-TYPE
SYNTAX INTEGER
MAX-ACCESS read-write
STATUS current
DESCRIPTION
"Data value."
::= { dataArray2 15 }

dataValue2_16 OBJECT-TYPE
SYNTAX INTEGER
MAX-ACCESS read-write
STATUS current
DESCRIPTION
"Data value."
::= { dataArray2 16 }

dataValue2_17 OBJECT-TYPE
SYNTAX INTEGER
MAX-ACCESS read-write
STATUS current
DESCRIPTION
"Data value."
::= { dataArray2 17 }

dataValue2_18 OBJECT-TYPE
SYNTAX INTEGER
MAX-ACCESS read-write
STATUS current
DESCRIPTION
"Data value."
::= { dataArray2 18 }

dataValue2_19 OBJECT-TYPE
SYNTAX INTEGER
MAX-ACCESS read-write
STATUS current
DESCRIPTION
"Data value."
::= { dataArray2 19 }

dataValue2_20 OBJECT-TYPE
SYNTAX INTEGER
MAX-ACCESS read-write
STATUS current
DESCRIPTION
"Data value."
::= { dataArray2 20 }

dataValue2_21 OBJECT-TYPE
SYNTAX INTEGER
MAX-ACCESS read-write
STATUS current
DESCRIPTION
"Data value."
::= { dataArray2 21 }

dataValue2_22 OBJECT-TYPE
SYNTAX INTEGER
MAX-ACCESS read-write
STATUS current
DESCRIPTION
"Data value."
::= { dataArray2 22 }

dataValue2_23 OBJECT-TYPE
SYNTAX INTEGER
MAX-ACCESS read-write
STATUS current
DESCRIPTION
"Data value."
::= { dataArray2 23 }

dataValue2_24 OBJECT-TYPE
SYNTAX INTEGER
MAX-ACCESS read-write
STATUS current
DESCRIPTION
"Data value."
::= { dataArray2 24 }

dataValue2_25 OBJECT-TYPE
SYNTAX INTEGER
MAX-ACCESS read-write
STATUS current
DESCRIPTION
"Data value."
::= { dataArray2 25 }

dataValue2_26 OBJECT-TYPE
SYNTAX INTEGER
MAX-ACCESS read-write
STATUS current
DESCRIPTION
"Data value."
::= { dataArray2 26 }

dataValue2_27 OBJECT-TYPE
SYNTAX INTEGER
MAX-ACCESS read-write
STATUS current
DESCRIPTION
"Data value."
::= { dataArray2 27 }

dataValue2_28 OBJECT-TYPE
SYNTAX INTEGER
MAX-ACCESS read-write
STATUS current
DESCRIPTION
"Data value."
::= { dataArray2 28 }

dataValue2_29 OBJECT-TYPE
SYNTAX INTEGER
MAX-ACCESS read-write
STATUS current
DESCRIPTION
"Data value."
::= { dataArray2 29 }

dataValue2_30 OBJECT-TYPE
SYNTAX INTEGER
MAX-ACCESS read-write
STATUS current
DESCRIPTION
"Data value."
::= { dataArray2 30 }

dataValue2_31 OBJECT-TYPE
SYNTAX INTEGER
MAX-ACCESS read-write
STATUS current
DESCRIPTION
"Data value."
::= { dataArray2 31 }

dataValue2_32 OBJECT-TYPE
SYNTAX INTEGER
MAX-ACCESS read-write
STATUS current
DESCRIPTION
"Data value."
::= { dataArray2 32 }

dataValue2_33 OBJECT-TYPE
SYNTAX INTEGER
MAX-ACCESS read-write
STATUS current
DESCRIPTION
"Data value."
::= { dataArray2 33 }

dataValue2_34 OBJECT-TYPE
SYNTAX INTEGER
MAX-ACCESS read-write
STATUS current
DESCRIPTION
"Data value."
::= { dataArray2 34 }

dataValue2_35 OBJECT-TYPE
SYNTAX INTEGER
MAX-ACCESS read-write
STATUS current
DESCRIPTION
"Data value."
::= { dataArray2 35 }

dataValue2_36 OBJECT-TYPE
SYNTAX INTEGER
MAX-ACCESS read-write
STATUS current
DESCRIPTION
"Data value."
::= { dataArray2 36 }

dataValue2_37 OBJECT-TYPE
SYNTAX INTEGER
MAX-ACCESS read-write
STATUS current
DESCRIPTION
"Data value."
::= { dataArray2 37 }

dataValue2_38 OBJECT-TYPE
SYNTAX INTEGER
MAX-ACCESS read-write
STATUS current
DESCRIPTION
"Data value."
::= { dataArray2 38 }

dataValue2_39 OBJECT-TYPE
SYNTAX INTEGER
MAX-ACCESS read-write
STATUS current
DESCRIPTION
"Data value."
::= { dataArray2 39 }

dataValue2_40 OBJECT-TYPE
SYNTAX INTEGER
MAX-ACCESS read-write
STATUS current
DESCRIPTION
"Data value."
::= { dataArray2 40 }

dataValue2_41 OBJECT-TYPE
SYNTAX INTEGER
MAX-ACCESS read-write
STATUS current
DESCRIPTION
"Data value."
::= { dataArray2 41 }

dataValue2_42 OBJECT-TYPE
SYNTAX INTEGER
MAX-ACCESS read-write
STATUS current
DESCRIPTION
"Data value."
::= { dataArray2 42 }

dataValue2_43 OBJECT-TYPE
SYNTAX INTEGER
MAX-ACCESS read-write
STATUS current
DESCRIPTION
"Data value."
::= { dataArray2 43 }

dataValue2_44 OBJECT-TYPE
SYNTAX INTEGER
MAX-ACCESS read-write
STATUS current
DESCRIPTION
"Data value."
::= { dataArray2 44 }

dataValue2_45 OBJECT-TYPE
SYNTAX INTEGER
MAX-ACCESS read-write
STATUS current
DESCRIPTION
"Data value."
::= { dataArray2 45 }

dataValue2_46 OBJECT-TYPE
SYNTAX INTEGER
MAX-ACCESS read-write
STATUS current
DESCRIPTION
"Data value."
::= { dataArray2 46 }

dataValue2_47 OBJECT-TYPE
SYNTAX INTEGER
MAX-ACCESS read-write
STATUS current
DESCRIPTION
"Data value."
::= { dataArray2 47 }

dataValue2_48 OBJECT-TYPE
SYNTAX INTEGER
MAX-ACCESS read-write
STATUS current
DESCRIPTION
"Data value."
::= { dataArray2 48 }

dataValue2_49 OBJECT-TYPE
SYNTAX INTEGER
MAX-ACCESS read-write
STATUS current
DESCRIPTION
"Data value."
::= { dataArray2 49 }

dataValue2_50 OBJECT-TYPE
SYNTAX INTEGER
MAX-ACCESS read-write
STATUS current
DESCRIPTION
"Data value."
::= { dataArray2 50 }

dataValue2_51 OBJECT-TYPE
SYNTAX INTEGER
MAX-ACCESS read-write
STATUS current
DESCRIPTION
"Data value."
::= { dataArray2 51 }

dataValue2_52 OBJECT-TYPE
SYNTAX INTEGER
MAX-ACCESS read-write
STATUS current
DESCRIPTION
"Data value."
::= { dataArray2 52 }

dataValue2_53 OBJECT-TYPE
SYNTAX INTEGER
MAX-ACCESS read-write
STATUS current
DESCRIPTION
"Data value."
::= { dataArray2 53 }

dataValue2_54 OBJECT-TYPE
SYNTAX INTEGER
MAX-ACCESS read-write
STATUS current
DESCRIPTION
"Data value."
::= { dataArray2 54 }

dataValue2_55 OBJECT-TYPE
SYNTAX INTEGER
MAX-ACCESS read-write
STATUS current
DESCRIPTION
"Data value."
::= { dataArray2 55 }

dataValue2_56 OBJECT-TYPE
SYNTAX INTEGER
MAX-ACCESS read-write
STATUS current
DESCRIPTION
"Data value."
::= { dataArray2 56 }

dataValue2_57 OBJECT-TYPE
SYNTAX INTEGER
MAX-ACCESS read-write
STATUS current
DESCRIPTION
"Data value."
::= { dataArray2 57 }

dataValue2_58 OBJECT-TYPE
SYNTAX INTEGER
MAX-ACCESS read-write
STATUS current
DESCRIPTION
"Data value."
::= { dataArray2 58 }

dataValue2_59 OBJECT-TYPE
SYNTAX INTEGER
MAX-ACCESS read-write
STATUS current
DESCRIPTION
"Data value."
::= { dataArray2 59 }

dataValue2_60 OBJECT-TYPE
SYNTAX INTEGER
MAX-ACCESS read-write
STATUS current
DESCRIPTION
"Data value."
::= { dataArray2 60 }

dataValue2_61 OBJECT-TYPE
SYNTAX INTEGER
MAX-ACCESS read-write
STATUS current
DESCRIPTION
"Data value."
::= { dataArray2 61 }

dataValue2_62 OBJECT-TYPE
SYNTAX INTEGER
MAX-ACCESS read-write
STATUS current
DESCRIPTION
"Data value."
::= { dataArray2 62 }

dataValue2_63 OBJECT-TYPE
SYNTAX INTEGER
MAX-ACCESS read-write
STATUS current
DESCRIPTION
"Data value."
::= { dataArray2 63 }

dataValue2_64 OBJECT-TYPE
SYNTAX INTEGER
MAX-ACCESS read-write
STATUS current
DESCRIPTION
"Data value."
::= { dataArray2 64 }

dataValue2_65 OBJECT-TYPE
SYNTAX INTEGER
MAX-ACCESS read-write
STATUS current
DESCRIPTION
"Data value."
::= { dataArray2 65 }

dataValue2_66 OBJECT-TYPE
SYNTAX INTEGER
MAX-ACCESS read-write
STATUS current
DESCRIPTION
"Data value."
::= { dataArray2 66 }

dataValue2_67 OBJECT-TYPE
SYNTAX INTEGER
MAX-ACCESS read-write
STATUS current
DESCRIPTION
"Data value."
::= { dataArray2 67 }

dataValue2_68 OBJECT-TYPE
SYNTAX INTEGER
MAX-ACCESS read-write
STATUS current
DESCRIPTION
"Data value."
::= { dataArray2 68 }

dataValue2_69 OBJECT-TYPE
SYNTAX INTEGER
MAX-ACCESS read-write
STATUS current
DESCRIPTION
"Data value."
::= { dataArray2 69 }

dataValue2_70 OBJECT-TYPE
SYNTAX INTEGER
MAX-ACCESS read-write
STATUS current
DESCRIPTION
"Data value."
::= { dataArray2 70 }

dataValue2_71 OBJECT-TYPE
SYNTAX INTEGER
MAX-ACCESS read-write
STATUS current
DESCRIPTION
"Data value."
::= { dataArray2 71 }

dataValue2_72 OBJECT-TYPE
SYNTAX INTEGER
MAX-ACCESS read-write
STATUS current
DESCRIPTION
"Data value."
::= { dataArray2 72 }

dataValue2_73 OBJECT-TYPE
SYNTAX INTEGER
MAX-ACCESS read-write
STATUS current
DESCRIPTION
"Data value."
::= { dataArray2 73 }

dataValue2_74 OBJECT-TYPE
SYNTAX INTEGER
MAX-ACCESS read-write
STATUS current
DESCRIPTION
"Data value."
::= { dataArray2 74 }

dataValue2_75 OBJECT-TYPE
SYNTAX INTEGER
MAX-ACCESS read-write
STATUS current
DESCRIPTION
"Data value."
::= { dataArray2 75 }

dataValue2_76 OBJECT-TYPE
SYNTAX INTEGER
MAX-ACCESS read-write
STATUS current
DESCRIPTION
"Data value."
::= { dataArray2 76 }

dataValue2_77 OBJECT-TYPE
SYNTAX INTEGER
MAX-ACCESS read-write
STATUS current
DESCRIPTION
"Data value."
::= { dataArray2 77 }

dataValue2_78 OBJECT-TYPE
SYNTAX INTEGER
MAX-ACCESS read-write
STATUS current
DESCRIPTION
"Data value."
::= { dataArray2 78 }

dataValue2_79 OBJECT-TYPE
SYNTAX INTEGER
MAX-ACCESS read-write
STATUS current
DESCRIPTION
"Data value."
::= { dataArray2 79 }

dataValue2_80 OBJECT-TYPE
SYNTAX INTEGER
MAX-ACCESS read-write
STATUS current
DESCRIPTION
"Data value."
::= { dataArray2 80 }

dataValue2_81 OBJECT-TYPE
SYNTAX INTEGER
MAX-ACCESS read-write
STATUS current
DESCRIPTION
"Data value."
::= { dataArray2 81 }

dataValue2_82 OBJECT-TYPE
SYNTAX INTEGER
MAX-ACCESS read-write
STATUS current
DESCRIPTION
"Data value."
::= { dataArray2 82 }

dataValue2_83 OBJECT-TYPE
SYNTAX INTEGER
MAX-ACCESS read-write
STATUS current
DESCRIPTION
"Data value."
::= { dataArray2 83 }

dataValue2_84 OBJECT-TYPE
SYNTAX INTEGER
MAX-ACCESS read-write
STATUS current
DESCRIPTION
"Data value."
::= { dataArray2 84 }

dataValue2_85 OBJECT-TYPE
SYNTAX INTEGER
MAX-ACCESS read-write
STATUS current
DESCRIPTION
"Data value."
::= { dataArray2 85 }

dataValue2_86 OBJECT-TYPE
SYNTAX INTEGER
MAX-ACCESS read-write
STATUS current
DESCRIPTION
"Data value."
::= { dataArray2 86 }

dataValue2_87 OBJECT-TYPE
SYNTAX INTEGER
MAX-ACCESS read-write
STATUS current
DESCRIPTION
"Data value."
::= { dataArray2 87 }

dataValue2_88 OBJECT-TYPE
SYNTAX INTEGER
MAX-ACCESS read-write
STATUS current
DESCRIPTION
"Data value."
::= { dataArray2 88 }

dataValue2_89 OBJECT-TYPE
SYNTAX INTEGER
MAX-ACCESS read-write
STATUS current
DESCRIPTION
"Data value."
::= { dataArray2 89 }

dataValue2_90 OBJECT-TYPE
SYNTAX INTEGER
MAX-ACCESS read-write
STATUS current
DESCRIPTION
"Data value."
::= { dataArray2 90 }

dataValue2_91 OBJECT-TYPE
SYNTAX INTEGER
MAX-ACCESS read-write
STATUS current
DESCRIPTION
"Data value."
::= { dataArray2 91 }

dataValue2_92 OBJECT-TYPE
SYNTAX INTEGER
MAX-ACCESS read-write
STATUS current
DESCRIPTION
"Data value."
::= { dataArray2 92 }

dataValue2_93 OBJECT-TYPE
SYNTAX INTEGER
MAX-ACCESS read-write
STATUS current
DESCRIPTION
"Data value."
::= { dataArray2 93 }

dataValue2_94 OBJECT-TYPE
SYNTAX INTEGER
MAX-ACCESS read-write
STATUS current
DESCRIPTION
"Data value."
::= { dataArray2 94 }

dataValue2_95 OBJECT-TYPE
SYNTAX INTEGER
MAX-ACCESS read-write
STATUS current
DESCRIPTION
"Data value."
::= { dataArray2 95 }

dataValue2_96 OBJECT-TYPE
SYNTAX INTEGER
MAX-ACCESS read-write
STATUS current
DESCRIPTION
"Data value."
::= { dataArray2 96 }

dataValue2_97 OBJECT-TYPE
SYNTAX INTEGER
MAX-ACCESS read-write
STATUS current
DESCRIPTION
"Data value."
::= { dataArray2 97 }

dataValue2_98 OBJECT-TYPE
SYNTAX INTEGER
MAX-ACCESS read-write
STATUS current
DESCRIPTION
"Data value."
::= { dataArray2 98 }

dataValue2_99 OBJECT-TYPE
SYNTAX INTEGER
MAX-ACCESS read-write
STATUS current
DESCRIPTION
"Data value."
::= { dataArray2 99 }

dataArray3 OBJECT IDENTIFIER ::= { s08090201_trane_st_jude_v1_00b 3 }

dataValue3_0 OBJECT-TYPE
SYNTAX INTEGER
MAX-ACCESS read-write
STATUS current
DESCRIPTION
"Data value."
::= { dataArray3 0 }

dataValue3_1 OBJECT-TYPE
SYNTAX INTEGER
MAX-ACCESS read-write
STATUS current
DESCRIPTION
"Data value."
::= { dataArray3 1 }

dataValue3_2 OBJECT-TYPE
SYNTAX INTEGER
MAX-ACCESS read-write
STATUS current
DESCRIPTION
"Data value."
::= { dataArray3 2 }

dataValue3_3 OBJECT-TYPE
SYNTAX INTEGER
MAX-ACCESS read-write
STATUS current
DESCRIPTION
"Data value."
::= { dataArray3 3 }

dataValue3_4 OBJECT-TYPE
SYNTAX INTEGER
MAX-ACCESS read-write
STATUS current
DESCRIPTION
"Data value."
::= { dataArray3 4 }

dataValue3_5 OBJECT-TYPE
SYNTAX INTEGER
MAX-ACCESS read-write
STATUS current
DESCRIPTION
"Data value."
::= { dataArray3 5 }

dataValue3_6 OBJECT-TYPE
SYNTAX INTEGER
MAX-ACCESS read-write
STATUS current
DESCRIPTION
"Data value."
::= { dataArray3 6 }

dataValue3_7 OBJECT-TYPE
SYNTAX INTEGER
MAX-ACCESS read-write
STATUS current
DESCRIPTION
"Data value."
::= { dataArray3 7 }

dataValue3_8 OBJECT-TYPE
SYNTAX INTEGER
MAX-ACCESS read-write
STATUS current
DESCRIPTION
"Data value."
::= { dataArray3 8 }

dataValue3_9 OBJECT-TYPE
SYNTAX INTEGER
MAX-ACCESS read-write
STATUS current
DESCRIPTION
"Data value."
::= { dataArray3 9 }

dataValue3_10 OBJECT-TYPE
SYNTAX INTEGER
MAX-ACCESS read-write
STATUS current
DESCRIPTION
"Data value."
::= { dataArray3 10 }

dataValue3_11 OBJECT-TYPE
SYNTAX INTEGER
MAX-ACCESS read-write
STATUS current
DESCRIPTION
"Data value."
::= { dataArray3 11 }

dataValue3_12 OBJECT-TYPE
SYNTAX INTEGER
MAX-ACCESS read-write
STATUS current
DESCRIPTION
"Data value."
::= { dataArray3 12 }

dataValue3_13 OBJECT-TYPE
SYNTAX INTEGER
MAX-ACCESS read-write
STATUS current
DESCRIPTION
"Data value."
::= { dataArray3 13 }

dataValue3_14 OBJECT-TYPE
SYNTAX INTEGER
MAX-ACCESS read-write
STATUS current
DESCRIPTION
"Data value."
::= { dataArray3 14 }

dataValue3_15 OBJECT-TYPE
SYNTAX INTEGER
MAX-ACCESS read-write
STATUS current
DESCRIPTION
"Data value."
::= { dataArray3 15 }

dataValue3_16 OBJECT-TYPE
SYNTAX INTEGER
MAX-ACCESS read-write
STATUS current
DESCRIPTION
"Data value."
::= { dataArray3 16 }

dataValue3_17 OBJECT-TYPE
SYNTAX INTEGER
MAX-ACCESS read-write
STATUS current
DESCRIPTION
"Data value."
::= { dataArray3 17 }

dataValue3_18 OBJECT-TYPE
SYNTAX INTEGER
MAX-ACCESS read-write
STATUS current
DESCRIPTION
"Data value."
::= { dataArray3 18 }

dataValue3_19 OBJECT-TYPE
SYNTAX INTEGER
MAX-ACCESS read-write
STATUS current
DESCRIPTION
"Data value."
::= { dataArray3 19 }

dataValue3_20 OBJECT-TYPE
SYNTAX INTEGER
MAX-ACCESS read-write
STATUS current
DESCRIPTION
"Data value."
::= { dataArray3 20 }

dataValue3_21 OBJECT-TYPE
SYNTAX INTEGER
MAX-ACCESS read-write
STATUS current
DESCRIPTION
"Data value."
::= { dataArray3 21 }

dataValue3_22 OBJECT-TYPE
SYNTAX INTEGER
MAX-ACCESS read-write
STATUS current
DESCRIPTION
"Data value."
::= { dataArray3 22 }

dataValue3_23 OBJECT-TYPE
SYNTAX INTEGER
MAX-ACCESS read-write
STATUS current
DESCRIPTION
"Data value."
::= { dataArray3 23 }

dataValue3_24 OBJECT-TYPE
SYNTAX INTEGER
MAX-ACCESS read-write
STATUS current
DESCRIPTION
"Data value."
::= { dataArray3 24 }

dataValue3_25 OBJECT-TYPE
SYNTAX INTEGER
MAX-ACCESS read-write
STATUS current
DESCRIPTION
"Data value."
::= { dataArray3 25 }

dataValue3_26 OBJECT-TYPE
SYNTAX INTEGER
MAX-ACCESS read-write
STATUS current
DESCRIPTION
"Data value."
::= { dataArray3 26 }

dataValue3_27 OBJECT-TYPE
SYNTAX INTEGER
MAX-ACCESS read-write
STATUS current
DESCRIPTION
"Data value."
::= { dataArray3 27 }

dataValue3_28 OBJECT-TYPE
SYNTAX INTEGER
MAX-ACCESS read-write
STATUS current
DESCRIPTION
"Data value."
::= { dataArray3 28 }

dataValue3_29 OBJECT-TYPE
SYNTAX INTEGER
MAX-ACCESS read-write
STATUS current
DESCRIPTION
"Data value."
::= { dataArray3 29 }

dataValue3_30 OBJECT-TYPE
SYNTAX INTEGER
MAX-ACCESS read-write
STATUS current
DESCRIPTION
"Data value."
::= { dataArray3 30 }

dataValue3_31 OBJECT-TYPE
SYNTAX INTEGER
MAX-ACCESS read-write
STATUS current
DESCRIPTION
"Data value."
::= { dataArray3 31 }

dataValue3_32 OBJECT-TYPE
SYNTAX INTEGER
MAX-ACCESS read-write
STATUS current
DESCRIPTION
"Data value."
::= { dataArray3 32 }

dataValue3_33 OBJECT-TYPE
SYNTAX INTEGER
MAX-ACCESS read-write
STATUS current
DESCRIPTION
"Data value."
::= { dataArray3 33 }

dataValue3_34 OBJECT-TYPE
SYNTAX INTEGER
MAX-ACCESS read-write
STATUS current
DESCRIPTION
"Data value."
::= { dataArray3 34 }

dataValue3_35 OBJECT-TYPE
SYNTAX INTEGER
MAX-ACCESS read-write
STATUS current
DESCRIPTION
"Data value."
::= { dataArray3 35 }

dataValue3_36 OBJECT-TYPE
SYNTAX INTEGER
MAX-ACCESS read-write
STATUS current
DESCRIPTION
"Data value."
::= { dataArray3 36 }

dataValue3_37 OBJECT-TYPE
SYNTAX INTEGER
MAX-ACCESS read-write
STATUS current
DESCRIPTION
"Data value."
::= { dataArray3 37 }

dataValue3_38 OBJECT-TYPE
SYNTAX INTEGER
MAX-ACCESS read-write
STATUS current
DESCRIPTION
"Data value."
::= { dataArray3 38 }

dataValue3_39 OBJECT-TYPE
SYNTAX INTEGER
MAX-ACCESS read-write
STATUS current
DESCRIPTION
"Data value."
::= { dataArray3 39 }

dataValue3_40 OBJECT-TYPE
SYNTAX INTEGER
MAX-ACCESS read-write
STATUS current
DESCRIPTION
"Data value."
::= { dataArray3 40 }

dataValue3_41 OBJECT-TYPE
SYNTAX INTEGER
MAX-ACCESS read-write
STATUS current
DESCRIPTION
"Data value."
::= { dataArray3 41 }

dataValue3_42 OBJECT-TYPE
SYNTAX INTEGER
MAX-ACCESS read-write
STATUS current
DESCRIPTION
"Data value."
::= { dataArray3 42 }

dataValue3_43 OBJECT-TYPE
SYNTAX INTEGER
MAX-ACCESS read-write
STATUS current
DESCRIPTION
"Data value."
::= { dataArray3 43 }

dataValue3_44 OBJECT-TYPE
SYNTAX INTEGER
MAX-ACCESS read-write
STATUS current
DESCRIPTION
"Data value."
::= { dataArray3 44 }

dataValue3_45 OBJECT-TYPE
SYNTAX INTEGER
MAX-ACCESS read-write
STATUS current
DESCRIPTION
"Data value."
::= { dataArray3 45 }

dataValue3_46 OBJECT-TYPE
SYNTAX INTEGER
MAX-ACCESS read-write
STATUS current
DESCRIPTION
"Data value."
::= { dataArray3 46 }

dataValue3_47 OBJECT-TYPE
SYNTAX INTEGER
MAX-ACCESS read-write
STATUS current
DESCRIPTION
"Data value."
::= { dataArray3 47 }

dataValue3_48 OBJECT-TYPE
SYNTAX INTEGER
MAX-ACCESS read-write
STATUS current
DESCRIPTION
"Data value."
::= { dataArray3 48 }

dataValue3_49 OBJECT-TYPE
SYNTAX INTEGER
MAX-ACCESS read-write
STATUS current
DESCRIPTION
"Data value."
::= { dataArray3 49 }

dataValue3_50 OBJECT-TYPE
SYNTAX INTEGER
MAX-ACCESS read-write
STATUS current
DESCRIPTION
"Data value."
::= { dataArray3 50 }

dataValue3_51 OBJECT-TYPE
SYNTAX INTEGER
MAX-ACCESS read-write
STATUS current
DESCRIPTION
"Data value."
::= { dataArray3 51 }

dataValue3_52 OBJECT-TYPE
SYNTAX INTEGER
MAX-ACCESS read-write
STATUS current
DESCRIPTION
"Data value."
::= { dataArray3 52 }

dataValue3_53 OBJECT-TYPE
SYNTAX INTEGER
MAX-ACCESS read-write
STATUS current
DESCRIPTION
"Data value."
::= { dataArray3 53 }

dataValue3_54 OBJECT-TYPE
SYNTAX INTEGER
MAX-ACCESS read-write
STATUS current
DESCRIPTION
"Data value."
::= { dataArray3 54 }

dataValue3_55 OBJECT-TYPE
SYNTAX INTEGER
MAX-ACCESS read-write
STATUS current
DESCRIPTION
"Data value."
::= { dataArray3 55 }

dataValue3_56 OBJECT-TYPE
SYNTAX INTEGER
MAX-ACCESS read-write
STATUS current
DESCRIPTION
"Data value."
::= { dataArray3 56 }

dataValue3_57 OBJECT-TYPE
SYNTAX INTEGER
MAX-ACCESS read-write
STATUS current
DESCRIPTION
"Data value."
::= { dataArray3 57 }

dataValue3_58 OBJECT-TYPE
SYNTAX INTEGER
MAX-ACCESS read-write
STATUS current
DESCRIPTION
"Data value."
::= { dataArray3 58 }

dataValue3_59 OBJECT-TYPE
SYNTAX INTEGER
MAX-ACCESS read-write
STATUS current
DESCRIPTION
"Data value."
::= { dataArray3 59 }

dataValue3_60 OBJECT-TYPE
SYNTAX INTEGER
MAX-ACCESS read-write
STATUS current
DESCRIPTION
"Data value."
::= { dataArray3 60 }

dataValue3_61 OBJECT-TYPE
SYNTAX INTEGER
MAX-ACCESS read-write
STATUS current
DESCRIPTION
"Data value."
::= { dataArray3 61 }

dataValue3_62 OBJECT-TYPE
SYNTAX INTEGER
MAX-ACCESS read-write
STATUS current
DESCRIPTION
"Data value."
::= { dataArray3 62 }

dataValue3_63 OBJECT-TYPE
SYNTAX INTEGER
MAX-ACCESS read-write
STATUS current
DESCRIPTION
"Data value."
::= { dataArray3 63 }

dataValue3_64 OBJECT-TYPE
SYNTAX INTEGER
MAX-ACCESS read-write
STATUS current
DESCRIPTION
"Data value."
::= { dataArray3 64 }

dataValue3_65 OBJECT-TYPE
SYNTAX INTEGER
MAX-ACCESS read-write
STATUS current
DESCRIPTION
"Data value."
::= { dataArray3 65 }

dataValue3_66 OBJECT-TYPE
SYNTAX INTEGER
MAX-ACCESS read-write
STATUS current
DESCRIPTION
"Data value."
::= { dataArray3 66 }

dataValue3_67 OBJECT-TYPE
SYNTAX INTEGER
MAX-ACCESS read-write
STATUS current
DESCRIPTION
"Data value."
::= { dataArray3 67 }

dataValue3_68 OBJECT-TYPE
SYNTAX INTEGER
MAX-ACCESS read-write
STATUS current
DESCRIPTION
"Data value."
::= { dataArray3 68 }

dataValue3_69 OBJECT-TYPE
SYNTAX INTEGER
MAX-ACCESS read-write
STATUS current
DESCRIPTION
"Data value."
::= { dataArray3 69 }

dataValue3_70 OBJECT-TYPE
SYNTAX INTEGER
MAX-ACCESS read-write
STATUS current
DESCRIPTION
"Data value."
::= { dataArray3 70 }

dataValue3_71 OBJECT-TYPE
SYNTAX INTEGER
MAX-ACCESS read-write
STATUS current
DESCRIPTION
"Data value."
::= { dataArray3 71 }

dataValue3_72 OBJECT-TYPE
SYNTAX INTEGER
MAX-ACCESS read-write
STATUS current
DESCRIPTION
"Data value."
::= { dataArray3 72 }

dataValue3_73 OBJECT-TYPE
SYNTAX INTEGER
MAX-ACCESS read-write
STATUS current
DESCRIPTION
"Data value."
::= { dataArray3 73 }

dataValue3_74 OBJECT-TYPE
SYNTAX INTEGER
MAX-ACCESS read-write
STATUS current
DESCRIPTION
"Data value."
::= { dataArray3 74 }

dataValue3_75 OBJECT-TYPE
SYNTAX INTEGER
MAX-ACCESS read-write
STATUS current
DESCRIPTION
"Data value."
::= { dataArray3 75 }

dataValue3_76 OBJECT-TYPE
SYNTAX INTEGER
MAX-ACCESS read-write
STATUS current
DESCRIPTION
"Data value."
::= { dataArray3 76 }

dataValue3_77 OBJECT-TYPE
SYNTAX INTEGER
MAX-ACCESS read-write
STATUS current
DESCRIPTION
"Data value."
::= { dataArray3 77 }

dataValue3_78 OBJECT-TYPE
SYNTAX INTEGER
MAX-ACCESS read-write
STATUS current
DESCRIPTION
"Data value."
::= { dataArray3 78 }

dataValue3_79 OBJECT-TYPE
SYNTAX INTEGER
MAX-ACCESS read-write
STATUS current
DESCRIPTION
"Data value."
::= { dataArray3 79 }

dataValue3_80 OBJECT-TYPE
SYNTAX INTEGER
MAX-ACCESS read-write
STATUS current
DESCRIPTION
"Data value."
::= { dataArray3 80 }

dataValue3_81 OBJECT-TYPE
SYNTAX INTEGER
MAX-ACCESS read-write
STATUS current
DESCRIPTION
"Data value."
::= { dataArray3 81 }

dataValue3_82 OBJECT-TYPE
SYNTAX INTEGER
MAX-ACCESS read-write
STATUS current
DESCRIPTION
"Data value."
::= { dataArray3 82 }

dataValue3_83 OBJECT-TYPE
SYNTAX INTEGER
MAX-ACCESS read-write
STATUS current
DESCRIPTION
"Data value."
::= { dataArray3 83 }

dataValue3_84 OBJECT-TYPE
SYNTAX INTEGER
MAX-ACCESS read-write
STATUS current
DESCRIPTION
"Data value."
::= { dataArray3 84 }

dataValue3_85 OBJECT-TYPE
SYNTAX INTEGER
MAX-ACCESS read-write
STATUS current
DESCRIPTION
"Data value."
::= { dataArray3 85 }

dataValue3_86 OBJECT-TYPE
SYNTAX INTEGER
MAX-ACCESS read-write
STATUS current
DESCRIPTION
"Data value."
::= { dataArray3 86 }

dataValue3_87 OBJECT-TYPE
SYNTAX INTEGER
MAX-ACCESS read-write
STATUS current
DESCRIPTION
"Data value."
::= { dataArray3 87 }

dataValue3_88 OBJECT-TYPE
SYNTAX INTEGER
MAX-ACCESS read-write
STATUS current
DESCRIPTION
"Data value."
::= { dataArray3 88 }

dataValue3_89 OBJECT-TYPE
SYNTAX INTEGER
MAX-ACCESS read-write
STATUS current
DESCRIPTION
"Data value."
::= { dataArray3 89 }

dataValue3_90 OBJECT-TYPE
SYNTAX INTEGER
MAX-ACCESS read-write
STATUS current
DESCRIPTION
"Data value."
::= { dataArray3 90 }

dataValue3_91 OBJECT-TYPE
SYNTAX INTEGER
MAX-ACCESS read-write
STATUS current
DESCRIPTION
"Data value."
::= { dataArray3 91 }

dataValue3_92 OBJECT-TYPE
SYNTAX INTEGER
MAX-ACCESS read-write
STATUS current
DESCRIPTION
"Data value."
::= { dataArray3 92 }

dataValue3_93 OBJECT-TYPE
SYNTAX INTEGER
MAX-ACCESS read-write
STATUS current
DESCRIPTION
"Data value."
::= { dataArray3 93 }

dataValue3_94 OBJECT-TYPE
SYNTAX INTEGER
MAX-ACCESS read-write
STATUS current
DESCRIPTION
"Data value."
::= { dataArray3 94 }

dataValue3_95 OBJECT-TYPE
SYNTAX INTEGER
MAX-ACCESS read-write
STATUS current
DESCRIPTION
"Data value."
::= { dataArray3 95 }

dataValue3_96 OBJECT-TYPE
SYNTAX INTEGER
MAX-ACCESS read-write
STATUS current
DESCRIPTION
"Data value."
::= { dataArray3 96 }

dataValue3_97 OBJECT-TYPE
SYNTAX INTEGER
MAX-ACCESS read-write
STATUS current
DESCRIPTION
"Data value."
::= { dataArray3 97 }

dataValue3_98 OBJECT-TYPE
SYNTAX INTEGER
MAX-ACCESS read-write
STATUS current
DESCRIPTION
"Data value."
::= { dataArray3 98 }

dataValue3_99 OBJECT-TYPE
SYNTAX INTEGER
MAX-ACCESS read-write
STATUS current
DESCRIPTION
"Data value."
::= { dataArray3 99 }

dataArray4 OBJECT IDENTIFIER ::= { s08090201_trane_st_jude_v1_00b 4 }

dataValue4_0 OBJECT-TYPE
SYNTAX INTEGER
MAX-ACCESS read-write
STATUS current
DESCRIPTION
"Data value."
::= { dataArray4 0 }

dataValue4_1 OBJECT-TYPE
SYNTAX INTEGER
MAX-ACCESS read-write
STATUS current
DESCRIPTION
"Data value."
::= { dataArray4 1 }

dataValue4_2 OBJECT-TYPE
SYNTAX INTEGER
MAX-ACCESS read-write
STATUS current
DESCRIPTION
"Data value."
::= { dataArray4 2 }

dataValue4_3 OBJECT-TYPE
SYNTAX INTEGER
MAX-ACCESS read-write
STATUS current
DESCRIPTION
"Data value."
::= { dataArray4 3 }

dataValue4_4 OBJECT-TYPE
SYNTAX INTEGER
MAX-ACCESS read-write
STATUS current
DESCRIPTION
"Data value."
::= { dataArray4 4 }

dataValue4_5 OBJECT-TYPE
SYNTAX INTEGER
MAX-ACCESS read-write
STATUS current
DESCRIPTION
"Data value."
::= { dataArray4 5 }

dataValue4_6 OBJECT-TYPE
SYNTAX INTEGER
MAX-ACCESS read-write
STATUS current
DESCRIPTION
"Data value."
::= { dataArray4 6 }

dataValue4_7 OBJECT-TYPE
SYNTAX INTEGER
MAX-ACCESS read-write
STATUS current
DESCRIPTION
"Data value."
::= { dataArray4 7 }

dataValue4_8 OBJECT-TYPE
SYNTAX INTEGER
MAX-ACCESS read-write
STATUS current
DESCRIPTION
"Data value."
::= { dataArray4 8 }

dataValue4_9 OBJECT-TYPE
SYNTAX INTEGER
MAX-ACCESS read-write
STATUS current
DESCRIPTION
"Data value."
::= { dataArray4 9 }

dataValue4_10 OBJECT-TYPE
SYNTAX INTEGER
MAX-ACCESS read-write
STATUS current
DESCRIPTION
"Data value."
::= { dataArray4 10 }

dataValue4_11 OBJECT-TYPE
SYNTAX INTEGER
MAX-ACCESS read-write
STATUS current
DESCRIPTION
"Data value."
::= { dataArray4 11 }

dataValue4_12 OBJECT-TYPE
SYNTAX INTEGER
MAX-ACCESS read-write
STATUS current
DESCRIPTION
"Data value."
::= { dataArray4 12 }

dataValue4_13 OBJECT-TYPE
SYNTAX INTEGER
MAX-ACCESS read-write
STATUS current
DESCRIPTION
"Data value."
::= { dataArray4 13 }

dataValue4_14 OBJECT-TYPE
SYNTAX INTEGER
MAX-ACCESS read-write
STATUS current
DESCRIPTION
"Data value."
::= { dataArray4 14 }

dataValue4_15 OBJECT-TYPE
SYNTAX INTEGER
MAX-ACCESS read-write
STATUS current
DESCRIPTION
"Data value."
::= { dataArray4 15 }

dataValue4_16 OBJECT-TYPE
SYNTAX INTEGER
MAX-ACCESS read-write
STATUS current
DESCRIPTION
"Data value."
::= { dataArray4 16 }

dataValue4_17 OBJECT-TYPE
SYNTAX INTEGER
MAX-ACCESS read-write
STATUS current
DESCRIPTION
"Data value."
::= { dataArray4 17 }

dataValue4_18 OBJECT-TYPE
SYNTAX INTEGER
MAX-ACCESS read-write
STATUS current
DESCRIPTION
"Data value."
::= { dataArray4 18 }

dataValue4_19 OBJECT-TYPE
SYNTAX INTEGER
MAX-ACCESS read-write
STATUS current
DESCRIPTION
"Data value."
::= { dataArray4 19 }

dataValue4_20 OBJECT-TYPE
SYNTAX INTEGER
MAX-ACCESS read-write
STATUS current
DESCRIPTION
"Data value."
::= { dataArray4 20 }

dataValue4_21 OBJECT-TYPE
SYNTAX INTEGER
MAX-ACCESS read-write
STATUS current
DESCRIPTION
"Data value."
::= { dataArray4 21 }

dataValue4_22 OBJECT-TYPE
SYNTAX INTEGER
MAX-ACCESS read-write
STATUS current
DESCRIPTION
"Data value."
::= { dataArray4 22 }

dataValue4_23 OBJECT-TYPE
SYNTAX INTEGER
MAX-ACCESS read-write
STATUS current
DESCRIPTION
"Data value."
::= { dataArray4 23 }

dataValue4_24 OBJECT-TYPE
SYNTAX INTEGER
MAX-ACCESS read-write
STATUS current
DESCRIPTION
"Data value."
::= { dataArray4 24 }

dataValue4_25 OBJECT-TYPE
SYNTAX INTEGER
MAX-ACCESS read-write
STATUS current
DESCRIPTION
"Data value."
::= { dataArray4 25 }

dataValue4_26 OBJECT-TYPE
SYNTAX INTEGER
MAX-ACCESS read-write
STATUS current
DESCRIPTION
"Data value."
::= { dataArray4 26 }

dataValue4_27 OBJECT-TYPE
SYNTAX INTEGER
MAX-ACCESS read-write
STATUS current
DESCRIPTION
"Data value."
::= { dataArray4 27 }

dataValue4_28 OBJECT-TYPE
SYNTAX INTEGER
MAX-ACCESS read-write
STATUS current
DESCRIPTION
"Data value."
::= { dataArray4 28 }

dataValue4_29 OBJECT-TYPE
SYNTAX INTEGER
MAX-ACCESS read-write
STATUS current
DESCRIPTION
"Data value."
::= { dataArray4 29 }

dataValue4_30 OBJECT-TYPE
SYNTAX INTEGER
MAX-ACCESS read-write
STATUS current
DESCRIPTION
"Data value."
::= { dataArray4 30 }

dataValue4_31 OBJECT-TYPE
SYNTAX INTEGER
MAX-ACCESS read-write
STATUS current
DESCRIPTION
"Data value."
::= { dataArray4 31 }

dataValue4_32 OBJECT-TYPE
SYNTAX INTEGER
MAX-ACCESS read-write
STATUS current
DESCRIPTION
"Data value."
::= { dataArray4 32 }

dataValue4_33 OBJECT-TYPE
SYNTAX INTEGER
MAX-ACCESS read-write
STATUS current
DESCRIPTION
"Data value."
::= { dataArray4 33 }

dataValue4_34 OBJECT-TYPE
SYNTAX INTEGER
MAX-ACCESS read-write
STATUS current
DESCRIPTION
"Data value."
::= { dataArray4 34 }

dataValue4_35 OBJECT-TYPE
SYNTAX INTEGER
MAX-ACCESS read-write
STATUS current
DESCRIPTION
"Data value."
::= { dataArray4 35 }

dataValue4_36 OBJECT-TYPE
SYNTAX INTEGER
MAX-ACCESS read-write
STATUS current
DESCRIPTION
"Data value."
::= { dataArray4 36 }

dataValue4_37 OBJECT-TYPE
SYNTAX INTEGER
MAX-ACCESS read-write
STATUS current
DESCRIPTION
"Data value."
::= { dataArray4 37 }

dataValue4_38 OBJECT-TYPE
SYNTAX INTEGER
MAX-ACCESS read-write
STATUS current
DESCRIPTION
"Data value."
::= { dataArray4 38 }

dataValue4_39 OBJECT-TYPE
SYNTAX INTEGER
MAX-ACCESS read-write
STATUS current
DESCRIPTION
"Data value."
::= { dataArray4 39 }

dataValue4_40 OBJECT-TYPE
SYNTAX INTEGER
MAX-ACCESS read-write
STATUS current
DESCRIPTION
"Data value."
::= { dataArray4 40 }

dataValue4_41 OBJECT-TYPE
SYNTAX INTEGER
MAX-ACCESS read-write
STATUS current
DESCRIPTION
"Data value."
::= { dataArray4 41 }

dataValue4_42 OBJECT-TYPE
SYNTAX INTEGER
MAX-ACCESS read-write
STATUS current
DESCRIPTION
"Data value."
::= { dataArray4 42 }

dataValue4_43 OBJECT-TYPE
SYNTAX INTEGER
MAX-ACCESS read-write
STATUS current
DESCRIPTION
"Data value."
::= { dataArray4 43 }

dataValue4_44 OBJECT-TYPE
SYNTAX INTEGER
MAX-ACCESS read-write
STATUS current
DESCRIPTION
"Data value."
::= { dataArray4 44 }

dataValue4_45 OBJECT-TYPE
SYNTAX INTEGER
MAX-ACCESS read-write
STATUS current
DESCRIPTION
"Data value."
::= { dataArray4 45 }

dataValue4_46 OBJECT-TYPE
SYNTAX INTEGER
MAX-ACCESS read-write
STATUS current
DESCRIPTION
"Data value."
::= { dataArray4 46 }

dataValue4_47 OBJECT-TYPE
SYNTAX INTEGER
MAX-ACCESS read-write
STATUS current
DESCRIPTION
"Data value."
::= { dataArray4 47 }

dataValue4_48 OBJECT-TYPE
SYNTAX INTEGER
MAX-ACCESS read-write
STATUS current
DESCRIPTION
"Data value."
::= { dataArray4 48 }

dataValue4_49 OBJECT-TYPE
SYNTAX INTEGER
MAX-ACCESS read-write
STATUS current
DESCRIPTION
"Data value."
::= { dataArray4 49 }

dataValue4_50 OBJECT-TYPE
SYNTAX INTEGER
MAX-ACCESS read-write
STATUS current
DESCRIPTION
"Data value."
::= { dataArray4 50 }

dataValue4_51 OBJECT-TYPE
SYNTAX INTEGER
MAX-ACCESS read-write
STATUS current
DESCRIPTION
"Data value."
::= { dataArray4 51 }

dataValue4_52 OBJECT-TYPE
SYNTAX INTEGER
MAX-ACCESS read-write
STATUS current
DESCRIPTION
"Data value."
::= { dataArray4 52 }

dataValue4_53 OBJECT-TYPE
SYNTAX INTEGER
MAX-ACCESS read-write
STATUS current
DESCRIPTION
"Data value."
::= { dataArray4 53 }

dataValue4_54 OBJECT-TYPE
SYNTAX INTEGER
MAX-ACCESS read-write
STATUS current
DESCRIPTION
"Data value."
::= { dataArray4 54 }

dataValue4_55 OBJECT-TYPE
SYNTAX INTEGER
MAX-ACCESS read-write
STATUS current
DESCRIPTION
"Data value."
::= { dataArray4 55 }

dataValue4_56 OBJECT-TYPE
SYNTAX INTEGER
MAX-ACCESS read-write
STATUS current
DESCRIPTION
"Data value."
::= { dataArray4 56 }

dataValue4_57 OBJECT-TYPE
SYNTAX INTEGER
MAX-ACCESS read-write
STATUS current
DESCRIPTION
"Data value."
::= { dataArray4 57 }

dataValue4_58 OBJECT-TYPE
SYNTAX INTEGER
MAX-ACCESS read-write
STATUS current
DESCRIPTION
"Data value."
::= { dataArray4 58 }

dataValue4_59 OBJECT-TYPE
SYNTAX INTEGER
MAX-ACCESS read-write
STATUS current
DESCRIPTION
"Data value."
::= { dataArray4 59 }

dataValue4_60 OBJECT-TYPE
SYNTAX INTEGER
MAX-ACCESS read-write
STATUS current
DESCRIPTION
"Data value."
::= { dataArray4 60 }

dataValue4_61 OBJECT-TYPE
SYNTAX INTEGER
MAX-ACCESS read-write
STATUS current
DESCRIPTION
"Data value."
::= { dataArray4 61 }

dataValue4_62 OBJECT-TYPE
SYNTAX INTEGER
MAX-ACCESS read-write
STATUS current
DESCRIPTION
"Data value."
::= { dataArray4 62 }

dataValue4_63 OBJECT-TYPE
SYNTAX INTEGER
MAX-ACCESS read-write
STATUS current
DESCRIPTION
"Data value."
::= { dataArray4 63 }

dataValue4_64 OBJECT-TYPE
SYNTAX INTEGER
MAX-ACCESS read-write
STATUS current
DESCRIPTION
"Data value."
::= { dataArray4 64 }

dataValue4_65 OBJECT-TYPE
SYNTAX INTEGER
MAX-ACCESS read-write
STATUS current
DESCRIPTION
"Data value."
::= { dataArray4 65 }

dataValue4_66 OBJECT-TYPE
SYNTAX INTEGER
MAX-ACCESS read-write
STATUS current
DESCRIPTION
"Data value."
::= { dataArray4 66 }

dataValue4_67 OBJECT-TYPE
SYNTAX INTEGER
MAX-ACCESS read-write
STATUS current
DESCRIPTION
"Data value."
::= { dataArray4 67 }

dataValue4_68 OBJECT-TYPE
SYNTAX INTEGER
MAX-ACCESS read-write
STATUS current
DESCRIPTION
"Data value."
::= { dataArray4 68 }

dataValue4_69 OBJECT-TYPE
SYNTAX INTEGER
MAX-ACCESS read-write
STATUS current
DESCRIPTION
"Data value."
::= { dataArray4 69 }

dataValue4_70 OBJECT-TYPE
SYNTAX INTEGER
MAX-ACCESS read-write
STATUS current
DESCRIPTION
"Data value."
::= { dataArray4 70 }

dataValue4_71 OBJECT-TYPE
SYNTAX INTEGER
MAX-ACCESS read-write
STATUS current
DESCRIPTION
"Data value."
::= { dataArray4 71 }

dataValue4_72 OBJECT-TYPE
SYNTAX INTEGER
MAX-ACCESS read-write
STATUS current
DESCRIPTION
"Data value."
::= { dataArray4 72 }

dataValue4_73 OBJECT-TYPE
SYNTAX INTEGER
MAX-ACCESS read-write
STATUS current
DESCRIPTION
"Data value."
::= { dataArray4 73 }

dataValue4_74 OBJECT-TYPE
SYNTAX INTEGER
MAX-ACCESS read-write
STATUS current
DESCRIPTION
"Data value."
::= { dataArray4 74 }

dataValue4_75 OBJECT-TYPE
SYNTAX INTEGER
MAX-ACCESS read-write
STATUS current
DESCRIPTION
"Data value."
::= { dataArray4 75 }

dataValue4_76 OBJECT-TYPE
SYNTAX INTEGER
MAX-ACCESS read-write
STATUS current
DESCRIPTION
"Data value."
::= { dataArray4 76 }

dataValue4_77 OBJECT-TYPE
SYNTAX INTEGER
MAX-ACCESS read-write
STATUS current
DESCRIPTION
"Data value."
::= { dataArray4 77 }

dataValue4_78 OBJECT-TYPE
SYNTAX INTEGER
MAX-ACCESS read-write
STATUS current
DESCRIPTION
"Data value."
::= { dataArray4 78 }

dataValue4_79 OBJECT-TYPE
SYNTAX INTEGER
MAX-ACCESS read-write
STATUS current
DESCRIPTION
"Data value."
::= { dataArray4 79 }

dataValue4_80 OBJECT-TYPE
SYNTAX INTEGER
MAX-ACCESS read-write
STATUS current
DESCRIPTION
"Data value."
::= { dataArray4 80 }

dataValue4_81 OBJECT-TYPE
SYNTAX INTEGER
MAX-ACCESS read-write
STATUS current
DESCRIPTION
"Data value."
::= { dataArray4 81 }

dataValue4_82 OBJECT-TYPE
SYNTAX INTEGER
MAX-ACCESS read-write
STATUS current
DESCRIPTION
"Data value."
::= { dataArray4 82 }

dataValue4_83 OBJECT-TYPE
SYNTAX INTEGER
MAX-ACCESS read-write
STATUS current
DESCRIPTION
"Data value."
::= { dataArray4 83 }

dataValue4_84 OBJECT-TYPE
SYNTAX INTEGER
MAX-ACCESS read-write
STATUS current
DESCRIPTION
"Data value."
::= { dataArray4 84 }

dataValue4_85 OBJECT-TYPE
SYNTAX INTEGER
MAX-ACCESS read-write
STATUS current
DESCRIPTION
"Data value."
::= { dataArray4 85 }

dataValue4_86 OBJECT-TYPE
SYNTAX INTEGER
MAX-ACCESS read-write
STATUS current
DESCRIPTION
"Data value."
::= { dataArray4 86 }

dataValue4_87 OBJECT-TYPE
SYNTAX INTEGER
MAX-ACCESS read-write
STATUS current
DESCRIPTION
"Data value."
::= { dataArray4 87 }

dataValue4_88 OBJECT-TYPE
SYNTAX INTEGER
MAX-ACCESS read-write
STATUS current
DESCRIPTION
"Data value."
::= { dataArray4 88 }

dataValue4_89 OBJECT-TYPE
SYNTAX INTEGER
MAX-ACCESS read-write
STATUS current
DESCRIPTION
"Data value."
::= { dataArray4 89 }

dataValue4_90 OBJECT-TYPE
SYNTAX INTEGER
MAX-ACCESS read-write
STATUS current
DESCRIPTION
"Data value."
::= { dataArray4 90 }

dataValue4_91 OBJECT-TYPE
SYNTAX INTEGER
MAX-ACCESS read-write
STATUS current
DESCRIPTION
"Data value."
::= { dataArray4 91 }

dataValue4_92 OBJECT-TYPE
SYNTAX INTEGER
MAX-ACCESS read-write
STATUS current
DESCRIPTION
"Data value."
::= { dataArray4 92 }

dataValue4_93 OBJECT-TYPE
SYNTAX INTEGER
MAX-ACCESS read-write
STATUS current
DESCRIPTION
"Data value."
::= { dataArray4 93 }

dataValue4_94 OBJECT-TYPE
SYNTAX INTEGER
MAX-ACCESS read-write
STATUS current
DESCRIPTION
"Data value."
::= { dataArray4 94 }

dataValue4_95 OBJECT-TYPE
SYNTAX INTEGER
MAX-ACCESS read-write
STATUS current
DESCRIPTION
"Data value."
::= { dataArray4 95 }

dataValue4_96 OBJECT-TYPE
SYNTAX INTEGER
MAX-ACCESS read-write
STATUS current
DESCRIPTION
"Data value."
::= { dataArray4 96 }

dataValue4_97 OBJECT-TYPE
SYNTAX INTEGER
MAX-ACCESS read-write
STATUS current
DESCRIPTION
"Data value."
::= { dataArray4 97 }

dataValue4_98 OBJECT-TYPE
SYNTAX INTEGER
MAX-ACCESS read-write
STATUS current
DESCRIPTION
"Data value."
::= { dataArray4 98 }

dataValue4_99 OBJECT-TYPE
SYNTAX INTEGER
MAX-ACCESS read-write
STATUS current
DESCRIPTION
"Data value."
::= { dataArray4 99 }

dataArray5 OBJECT IDENTIFIER ::= { s08090201_trane_st_jude_v1_00b 5 }

dataValue5_0 OBJECT-TYPE
SYNTAX INTEGER
MAX-ACCESS read-write
STATUS current
DESCRIPTION
"Data value."
::= { dataArray5 0 }

dataValue5_1 OBJECT-TYPE
SYNTAX INTEGER
MAX-ACCESS read-write
STATUS current
DESCRIPTION
"Data value."
::= { dataArray5 1 }

dataValue5_2 OBJECT-TYPE
SYNTAX INTEGER
MAX-ACCESS read-write
STATUS current
DESCRIPTION
"Data value."
::= { dataArray5 2 }

dataValue5_3 OBJECT-TYPE
SYNTAX INTEGER
MAX-ACCESS read-write
STATUS current
DESCRIPTION
"Data value."
::= { dataArray5 3 }

dataValue5_4 OBJECT-TYPE
SYNTAX INTEGER
MAX-ACCESS read-write
STATUS current
DESCRIPTION
"Data value."
::= { dataArray5 4 }

dataValue5_5 OBJECT-TYPE
SYNTAX INTEGER
MAX-ACCESS read-write
STATUS current
DESCRIPTION
"Data value."
::= { dataArray5 5 }

dataValue5_6 OBJECT-TYPE
SYNTAX INTEGER
MAX-ACCESS read-write
STATUS current
DESCRIPTION
"Data value."
::= { dataArray5 6 }

dataValue5_7 OBJECT-TYPE
SYNTAX INTEGER
MAX-ACCESS read-write
STATUS current
DESCRIPTION
"Data value."
::= { dataArray5 7 }

dataValue5_8 OBJECT-TYPE
SYNTAX INTEGER
MAX-ACCESS read-write
STATUS current
DESCRIPTION
"Data value."
::= { dataArray5 8 }

dataValue5_9 OBJECT-TYPE
SYNTAX INTEGER
MAX-ACCESS read-write
STATUS current
DESCRIPTION
"Data value."
::= { dataArray5 9 }

dataValue5_10 OBJECT-TYPE
SYNTAX INTEGER
MAX-ACCESS read-write
STATUS current
DESCRIPTION
"Data value."
::= { dataArray5 10 }

dataValue5_11 OBJECT-TYPE
SYNTAX INTEGER
MAX-ACCESS read-write
STATUS current
DESCRIPTION
"Data value."
::= { dataArray5 11 }

dataValue5_12 OBJECT-TYPE
SYNTAX INTEGER
MAX-ACCESS read-write
STATUS current
DESCRIPTION
"Data value."
::= { dataArray5 12 }

dataValue5_13 OBJECT-TYPE
SYNTAX INTEGER
MAX-ACCESS read-write
STATUS current
DESCRIPTION
"Data value."
::= { dataArray5 13 }

dataValue5_14 OBJECT-TYPE
SYNTAX INTEGER
MAX-ACCESS read-write
STATUS current
DESCRIPTION
"Data value."
::= { dataArray5 14 }

dataValue5_15 OBJECT-TYPE
SYNTAX INTEGER
MAX-ACCESS read-write
STATUS current
DESCRIPTION
"Data value."
::= { dataArray5 15 }

dataValue5_16 OBJECT-TYPE
SYNTAX INTEGER
MAX-ACCESS read-write
STATUS current
DESCRIPTION
"Data value."
::= { dataArray5 16 }

dataValue5_17 OBJECT-TYPE
SYNTAX INTEGER
MAX-ACCESS read-write
STATUS current
DESCRIPTION
"Data value."
::= { dataArray5 17 }

dataValue5_18 OBJECT-TYPE
SYNTAX INTEGER
MAX-ACCESS read-write
STATUS current
DESCRIPTION
"Data value."
::= { dataArray5 18 }

dataValue5_19 OBJECT-TYPE
SYNTAX INTEGER
MAX-ACCESS read-write
STATUS current
DESCRIPTION
"Data value."
::= { dataArray5 19 }

dataValue5_20 OBJECT-TYPE
SYNTAX INTEGER
MAX-ACCESS read-write
STATUS current
DESCRIPTION
"Data value."
::= { dataArray5 20 }

dataValue5_21 OBJECT-TYPE
SYNTAX INTEGER
MAX-ACCESS read-write
STATUS current
DESCRIPTION
"Data value."
::= { dataArray5 21 }

dataValue5_22 OBJECT-TYPE
SYNTAX INTEGER
MAX-ACCESS read-write
STATUS current
DESCRIPTION
"Data value."
::= { dataArray5 22 }

dataValue5_23 OBJECT-TYPE
SYNTAX INTEGER
MAX-ACCESS read-write
STATUS current
DESCRIPTION
"Data value."
::= { dataArray5 23 }

dataValue5_24 OBJECT-TYPE
SYNTAX INTEGER
MAX-ACCESS read-write
STATUS current
DESCRIPTION
"Data value."
::= { dataArray5 24 }

dataValue5_25 OBJECT-TYPE
SYNTAX INTEGER
MAX-ACCESS read-write
STATUS current
DESCRIPTION
"Data value."
::= { dataArray5 25 }

dataValue5_26 OBJECT-TYPE
SYNTAX INTEGER
MAX-ACCESS read-write
STATUS current
DESCRIPTION
"Data value."
::= { dataArray5 26 }

dataValue5_27 OBJECT-TYPE
SYNTAX INTEGER
MAX-ACCESS read-write
STATUS current
DESCRIPTION
"Data value."
::= { dataArray5 27 }

dataValue5_28 OBJECT-TYPE
SYNTAX INTEGER
MAX-ACCESS read-write
STATUS current
DESCRIPTION
"Data value."
::= { dataArray5 28 }

dataValue5_29 OBJECT-TYPE
SYNTAX INTEGER
MAX-ACCESS read-write
STATUS current
DESCRIPTION
"Data value."
::= { dataArray5 29 }

dataValue5_30 OBJECT-TYPE
SYNTAX INTEGER
MAX-ACCESS read-write
STATUS current
DESCRIPTION
"Data value."
::= { dataArray5 30 }

dataValue5_31 OBJECT-TYPE
SYNTAX INTEGER
MAX-ACCESS read-write
STATUS current
DESCRIPTION
"Data value."
::= { dataArray5 31 }

dataValue5_32 OBJECT-TYPE
SYNTAX INTEGER
MAX-ACCESS read-write
STATUS current
DESCRIPTION
"Data value."
::= { dataArray5 32 }

dataValue5_33 OBJECT-TYPE
SYNTAX INTEGER
MAX-ACCESS read-write
STATUS current
DESCRIPTION
"Data value."
::= { dataArray5 33 }

dataValue5_34 OBJECT-TYPE
SYNTAX INTEGER
MAX-ACCESS read-write
STATUS current
DESCRIPTION
"Data value."
::= { dataArray5 34 }

dataValue5_35 OBJECT-TYPE
SYNTAX INTEGER
MAX-ACCESS read-write
STATUS current
DESCRIPTION
"Data value."
::= { dataArray5 35 }

dataValue5_36 OBJECT-TYPE
SYNTAX INTEGER
MAX-ACCESS read-write
STATUS current
DESCRIPTION
"Data value."
::= { dataArray5 36 }

dataValue5_37 OBJECT-TYPE
SYNTAX INTEGER
MAX-ACCESS read-write
STATUS current
DESCRIPTION
"Data value."
::= { dataArray5 37 }

dataValue5_38 OBJECT-TYPE
SYNTAX INTEGER
MAX-ACCESS read-write
STATUS current
DESCRIPTION
"Data value."
::= { dataArray5 38 }

dataValue5_39 OBJECT-TYPE
SYNTAX INTEGER
MAX-ACCESS read-write
STATUS current
DESCRIPTION
"Data value."
::= { dataArray5 39 }

dataValue5_40 OBJECT-TYPE
SYNTAX INTEGER
MAX-ACCESS read-write
STATUS current
DESCRIPTION
"Data value."
::= { dataArray5 40 }

dataValue5_41 OBJECT-TYPE
SYNTAX INTEGER
MAX-ACCESS read-write
STATUS current
DESCRIPTION
"Data value."
::= { dataArray5 41 }

dataValue5_42 OBJECT-TYPE
SYNTAX INTEGER
MAX-ACCESS read-write
STATUS current
DESCRIPTION
"Data value."
::= { dataArray5 42 }

dataValue5_43 OBJECT-TYPE
SYNTAX INTEGER
MAX-ACCESS read-write
STATUS current
DESCRIPTION
"Data value."
::= { dataArray5 43 }

dataValue5_44 OBJECT-TYPE
SYNTAX INTEGER
MAX-ACCESS read-write
STATUS current
DESCRIPTION
"Data value."
::= { dataArray5 44 }

dataValue5_45 OBJECT-TYPE
SYNTAX INTEGER
MAX-ACCESS read-write
STATUS current
DESCRIPTION
"Data value."
::= { dataArray5 45 }

dataValue5_46 OBJECT-TYPE
SYNTAX INTEGER
MAX-ACCESS read-write
STATUS current
DESCRIPTION
"Data value."
::= { dataArray5 46 }

dataValue5_47 OBJECT-TYPE
SYNTAX INTEGER
MAX-ACCESS read-write
STATUS current
DESCRIPTION
"Data value."
::= { dataArray5 47 }

dataValue5_48 OBJECT-TYPE
SYNTAX INTEGER
MAX-ACCESS read-write
STATUS current
DESCRIPTION
"Data value."
::= { dataArray5 48 }

dataValue5_49 OBJECT-TYPE
SYNTAX INTEGER
MAX-ACCESS read-write
STATUS current
DESCRIPTION
"Data value."
::= { dataArray5 49 }

dataValue5_50 OBJECT-TYPE
SYNTAX INTEGER
MAX-ACCESS read-write
STATUS current
DESCRIPTION
"Data value."
::= { dataArray5 50 }

dataValue5_51 OBJECT-TYPE
SYNTAX INTEGER
MAX-ACCESS read-write
STATUS current
DESCRIPTION
"Data value."
::= { dataArray5 51 }

dataValue5_52 OBJECT-TYPE
SYNTAX INTEGER
MAX-ACCESS read-write
STATUS current
DESCRIPTION
"Data value."
::= { dataArray5 52 }

dataValue5_53 OBJECT-TYPE
SYNTAX INTEGER
MAX-ACCESS read-write
STATUS current
DESCRIPTION
"Data value."
::= { dataArray5 53 }

dataValue5_54 OBJECT-TYPE
SYNTAX INTEGER
MAX-ACCESS read-write
STATUS current
DESCRIPTION
"Data value."
::= { dataArray5 54 }

dataValue5_55 OBJECT-TYPE
SYNTAX INTEGER
MAX-ACCESS read-write
STATUS current
DESCRIPTION
"Data value."
::= { dataArray5 55 }

dataValue5_56 OBJECT-TYPE
SYNTAX INTEGER
MAX-ACCESS read-write
STATUS current
DESCRIPTION
"Data value."
::= { dataArray5 56 }

dataValue5_57 OBJECT-TYPE
SYNTAX INTEGER
MAX-ACCESS read-write
STATUS current
DESCRIPTION
"Data value."
::= { dataArray5 57 }

dataValue5_58 OBJECT-TYPE
SYNTAX INTEGER
MAX-ACCESS read-write
STATUS current
DESCRIPTION
"Data value."
::= { dataArray5 58 }

dataValue5_59 OBJECT-TYPE
SYNTAX INTEGER
MAX-ACCESS read-write
STATUS current
DESCRIPTION
"Data value."
::= { dataArray5 59 }

dataValue5_60 OBJECT-TYPE
SYNTAX INTEGER
MAX-ACCESS read-write
STATUS current
DESCRIPTION
"Data value."
::= { dataArray5 60 }

dataValue5_61 OBJECT-TYPE
SYNTAX INTEGER
MAX-ACCESS read-write
STATUS current
DESCRIPTION
"Data value."
::= { dataArray5 61 }

dataValue5_62 OBJECT-TYPE
SYNTAX INTEGER
MAX-ACCESS read-write
STATUS current
DESCRIPTION
"Data value."
::= { dataArray5 62 }

dataValue5_63 OBJECT-TYPE
SYNTAX INTEGER
MAX-ACCESS read-write
STATUS current
DESCRIPTION
"Data value."
::= { dataArray5 63 }

dataValue5_64 OBJECT-TYPE
SYNTAX INTEGER
MAX-ACCESS read-write
STATUS current
DESCRIPTION
"Data value."
::= { dataArray5 64 }

dataValue5_65 OBJECT-TYPE
SYNTAX INTEGER
MAX-ACCESS read-write
STATUS current
DESCRIPTION
"Data value."
::= { dataArray5 65 }

dataValue5_66 OBJECT-TYPE
SYNTAX INTEGER
MAX-ACCESS read-write
STATUS current
DESCRIPTION
"Data value."
::= { dataArray5 66 }

dataValue5_67 OBJECT-TYPE
SYNTAX INTEGER
MAX-ACCESS read-write
STATUS current
DESCRIPTION
"Data value."
::= { dataArray5 67 }

dataValue5_68 OBJECT-TYPE
SYNTAX INTEGER
MAX-ACCESS read-write
STATUS current
DESCRIPTION
"Data value."
::= { dataArray5 68 }

dataValue5_69 OBJECT-TYPE
SYNTAX INTEGER
MAX-ACCESS read-write
STATUS current
DESCRIPTION
"Data value."
::= { dataArray5 69 }

dataValue5_70 OBJECT-TYPE
SYNTAX INTEGER
MAX-ACCESS read-write
STATUS current
DESCRIPTION
"Data value."
::= { dataArray5 70 }

dataValue5_71 OBJECT-TYPE
SYNTAX INTEGER
MAX-ACCESS read-write
STATUS current
DESCRIPTION
"Data value."
::= { dataArray5 71 }

dataValue5_72 OBJECT-TYPE
SYNTAX INTEGER
MAX-ACCESS read-write
STATUS current
DESCRIPTION
"Data value."
::= { dataArray5 72 }

dataValue5_73 OBJECT-TYPE
SYNTAX INTEGER
MAX-ACCESS read-write
STATUS current
DESCRIPTION
"Data value."
::= { dataArray5 73 }

dataValue5_74 OBJECT-TYPE
SYNTAX INTEGER
MAX-ACCESS read-write
STATUS current
DESCRIPTION
"Data value."
::= { dataArray5 74 }

dataValue5_75 OBJECT-TYPE
SYNTAX INTEGER
MAX-ACCESS read-write
STATUS current
DESCRIPTION
"Data value."
::= { dataArray5 75 }

dataValue5_76 OBJECT-TYPE
SYNTAX INTEGER
MAX-ACCESS read-write
STATUS current
DESCRIPTION
"Data value."
::= { dataArray5 76 }

dataValue5_77 OBJECT-TYPE
SYNTAX INTEGER
MAX-ACCESS read-write
STATUS current
DESCRIPTION
"Data value."
::= { dataArray5 77 }

dataValue5_78 OBJECT-TYPE
SYNTAX INTEGER
MAX-ACCESS read-write
STATUS current
DESCRIPTION
"Data value."
::= { dataArray5 78 }

dataValue5_79 OBJECT-TYPE
SYNTAX INTEGER
MAX-ACCESS read-write
STATUS current
DESCRIPTION
"Data value."
::= { dataArray5 79 }

dataValue5_80 OBJECT-TYPE
SYNTAX INTEGER
MAX-ACCESS read-write
STATUS current
DESCRIPTION
"Data value."
::= { dataArray5 80 }

dataValue5_81 OBJECT-TYPE
SYNTAX INTEGER
MAX-ACCESS read-write
STATUS current
DESCRIPTION
"Data value."
::= { dataArray5 81 }

dataValue5_82 OBJECT-TYPE
SYNTAX INTEGER
MAX-ACCESS read-write
STATUS current
DESCRIPTION
"Data value."
::= { dataArray5 82 }

dataValue5_83 OBJECT-TYPE
SYNTAX INTEGER
MAX-ACCESS read-write
STATUS current
DESCRIPTION
"Data value."
::= { dataArray5 83 }

dataValue5_84 OBJECT-TYPE
SYNTAX INTEGER
MAX-ACCESS read-write
STATUS current
DESCRIPTION
"Data value."
::= { dataArray5 84 }

dataValue5_85 OBJECT-TYPE
SYNTAX INTEGER
MAX-ACCESS read-write
STATUS current
DESCRIPTION
"Data value."
::= { dataArray5 85 }

dataValue5_86 OBJECT-TYPE
SYNTAX INTEGER
MAX-ACCESS read-write
STATUS current
DESCRIPTION
"Data value."
::= { dataArray5 86 }

dataValue5_87 OBJECT-TYPE
SYNTAX INTEGER
MAX-ACCESS read-write
STATUS current
DESCRIPTION
"Data value."
::= { dataArray5 87 }

dataValue5_88 OBJECT-TYPE
SYNTAX INTEGER
MAX-ACCESS read-write
STATUS current
DESCRIPTION
"Data value."
::= { dataArray5 88 }

dataValue5_89 OBJECT-TYPE
SYNTAX INTEGER
MAX-ACCESS read-write
STATUS current
DESCRIPTION
"Data value."
::= { dataArray5 89 }

dataValue5_90 OBJECT-TYPE
SYNTAX INTEGER
MAX-ACCESS read-write
STATUS current
DESCRIPTION
"Data value."
::= { dataArray5 90 }

dataValue5_91 OBJECT-TYPE
SYNTAX INTEGER
MAX-ACCESS read-write
STATUS current
DESCRIPTION
"Data value."
::= { dataArray5 91 }

dataValue5_92 OBJECT-TYPE
SYNTAX INTEGER
MAX-ACCESS read-write
STATUS current
DESCRIPTION
"Data value."
::= { dataArray5 92 }

dataValue5_93 OBJECT-TYPE
SYNTAX INTEGER
MAX-ACCESS read-write
STATUS current
DESCRIPTION
"Data value."
::= { dataArray5 93 }

dataValue5_94 OBJECT-TYPE
SYNTAX INTEGER
MAX-ACCESS read-write
STATUS current
DESCRIPTION
"Data value."
::= { dataArray5 94 }

dataValue5_95 OBJECT-TYPE
SYNTAX INTEGER
MAX-ACCESS read-write
STATUS current
DESCRIPTION
"Data value."
::= { dataArray5 95 }

dataValue5_96 OBJECT-TYPE
SYNTAX INTEGER
MAX-ACCESS read-write
STATUS current
DESCRIPTION
"Data value."
::= { dataArray5 96 }

dataValue5_97 OBJECT-TYPE
SYNTAX INTEGER
MAX-ACCESS read-write
STATUS current
DESCRIPTION
"Data value."
::= { dataArray5 97 }

dataValue5_98 OBJECT-TYPE
SYNTAX INTEGER
MAX-ACCESS read-write
STATUS current
DESCRIPTION
"Data value."
::= { dataArray5 98 }

dataValue5_99 OBJECT-TYPE
SYNTAX INTEGER
MAX-ACCESS read-write
STATUS current
DESCRIPTION
"Data value."
::= { dataArray5 99 }

dataArray6 OBJECT IDENTIFIER ::= { s08090201_trane_st_jude_v1_00b 6 }

dataValue6_0 OBJECT-TYPE
SYNTAX INTEGER
MAX-ACCESS read-write
STATUS current
DESCRIPTION
"Data value."
::= { dataArray6 0 }

dataValue6_1 OBJECT-TYPE
SYNTAX INTEGER
MAX-ACCESS read-write
STATUS current
DESCRIPTION
"Data value."
::= { dataArray6 1 }

dataValue6_2 OBJECT-TYPE
SYNTAX INTEGER
MAX-ACCESS read-write
STATUS current
DESCRIPTION
"Data value."
::= { dataArray6 2 }

dataValue6_3 OBJECT-TYPE
SYNTAX INTEGER
MAX-ACCESS read-write
STATUS current
DESCRIPTION
"Data value."
::= { dataArray6 3 }

dataValue6_4 OBJECT-TYPE
SYNTAX INTEGER
MAX-ACCESS read-write
STATUS current
DESCRIPTION
"Data value."
::= { dataArray6 4 }

dataValue6_5 OBJECT-TYPE
SYNTAX INTEGER
MAX-ACCESS read-write
STATUS current
DESCRIPTION
"Data value."
::= { dataArray6 5 }

dataValue6_6 OBJECT-TYPE
SYNTAX INTEGER
MAX-ACCESS read-write
STATUS current
DESCRIPTION
"Data value."
::= { dataArray6 6 }

dataValue6_7 OBJECT-TYPE
SYNTAX INTEGER
MAX-ACCESS read-write
STATUS current
DESCRIPTION
"Data value."
::= { dataArray6 7 }

dataValue6_8 OBJECT-TYPE
SYNTAX INTEGER
MAX-ACCESS read-write
STATUS current
DESCRIPTION
"Data value."
::= { dataArray6 8 }

dataValue6_9 OBJECT-TYPE
SYNTAX INTEGER
MAX-ACCESS read-write
STATUS current
DESCRIPTION
"Data value."
::= { dataArray6 9 }

dataValue6_10 OBJECT-TYPE
SYNTAX INTEGER
MAX-ACCESS read-write
STATUS current
DESCRIPTION
"Data value."
::= { dataArray6 10 }

dataValue6_11 OBJECT-TYPE
SYNTAX INTEGER
MAX-ACCESS read-write
STATUS current
DESCRIPTION
"Data value."
::= { dataArray6 11 }

dataValue6_12 OBJECT-TYPE
SYNTAX INTEGER
MAX-ACCESS read-write
STATUS current
DESCRIPTION
"Data value."
::= { dataArray6 12 }

dataValue6_13 OBJECT-TYPE
SYNTAX INTEGER
MAX-ACCESS read-write
STATUS current
DESCRIPTION
"Data value."
::= { dataArray6 13 }

dataValue6_14 OBJECT-TYPE
SYNTAX INTEGER
MAX-ACCESS read-write
STATUS current
DESCRIPTION
"Data value."
::= { dataArray6 14 }

dataValue6_15 OBJECT-TYPE
SYNTAX INTEGER
MAX-ACCESS read-write
STATUS current
DESCRIPTION
"Data value."
::= { dataArray6 15 }

dataValue6_16 OBJECT-TYPE
SYNTAX INTEGER
MAX-ACCESS read-write
STATUS current
DESCRIPTION
"Data value."
::= { dataArray6 16 }

dataValue6_17 OBJECT-TYPE
SYNTAX INTEGER
MAX-ACCESS read-write
STATUS current
DESCRIPTION
"Data value."
::= { dataArray6 17 }

dataValue6_18 OBJECT-TYPE
SYNTAX INTEGER
MAX-ACCESS read-write
STATUS current
DESCRIPTION
"Data value."
::= { dataArray6 18 }

dataValue6_19 OBJECT-TYPE
SYNTAX INTEGER
MAX-ACCESS read-write
STATUS current
DESCRIPTION
"Data value."
::= { dataArray6 19 }

dataValue6_20 OBJECT-TYPE
SYNTAX INTEGER
MAX-ACCESS read-write
STATUS current
DESCRIPTION
"Data value."
::= { dataArray6 20 }

dataValue6_21 OBJECT-TYPE
SYNTAX INTEGER
MAX-ACCESS read-write
STATUS current
DESCRIPTION
"Data value."
::= { dataArray6 21 }

dataValue6_22 OBJECT-TYPE
SYNTAX INTEGER
MAX-ACCESS read-write
STATUS current
DESCRIPTION
"Data value."
::= { dataArray6 22 }

dataValue6_23 OBJECT-TYPE
SYNTAX INTEGER
MAX-ACCESS read-write
STATUS current
DESCRIPTION
"Data value."
::= { dataArray6 23 }

dataValue6_24 OBJECT-TYPE
SYNTAX INTEGER
MAX-ACCESS read-write
STATUS current
DESCRIPTION
"Data value."
::= { dataArray6 24 }

dataValue6_25 OBJECT-TYPE
SYNTAX INTEGER
MAX-ACCESS read-write
STATUS current
DESCRIPTION
"Data value."
::= { dataArray6 25 }

dataValue6_26 OBJECT-TYPE
SYNTAX INTEGER
MAX-ACCESS read-write
STATUS current
DESCRIPTION
"Data value."
::= { dataArray6 26 }

dataValue6_27 OBJECT-TYPE
SYNTAX INTEGER
MAX-ACCESS read-write
STATUS current
DESCRIPTION
"Data value."
::= { dataArray6 27 }

dataValue6_28 OBJECT-TYPE
SYNTAX INTEGER
MAX-ACCESS read-write
STATUS current
DESCRIPTION
"Data value."
::= { dataArray6 28 }

dataValue6_29 OBJECT-TYPE
SYNTAX INTEGER
MAX-ACCESS read-write
STATUS current
DESCRIPTION
"Data value."
::= { dataArray6 29 }

dataValue6_30 OBJECT-TYPE
SYNTAX INTEGER
MAX-ACCESS read-write
STATUS current
DESCRIPTION
"Data value."
::= { dataArray6 30 }

dataValue6_31 OBJECT-TYPE
SYNTAX INTEGER
MAX-ACCESS read-write
STATUS current
DESCRIPTION
"Data value."
::= { dataArray6 31 }

dataValue6_32 OBJECT-TYPE
SYNTAX INTEGER
MAX-ACCESS read-write
STATUS current
DESCRIPTION
"Data value."
::= { dataArray6 32 }

dataValue6_33 OBJECT-TYPE
SYNTAX INTEGER
MAX-ACCESS read-write
STATUS current
DESCRIPTION
"Data value."
::= { dataArray6 33 }

dataValue6_34 OBJECT-TYPE
SYNTAX INTEGER
MAX-ACCESS read-write
STATUS current
DESCRIPTION
"Data value."
::= { dataArray6 34 }

dataValue6_35 OBJECT-TYPE
SYNTAX INTEGER
MAX-ACCESS read-write
STATUS current
DESCRIPTION
"Data value."
::= { dataArray6 35 }

dataValue6_36 OBJECT-TYPE
SYNTAX INTEGER
MAX-ACCESS read-write
STATUS current
DESCRIPTION
"Data value."
::= { dataArray6 36 }

dataValue6_37 OBJECT-TYPE
SYNTAX INTEGER
MAX-ACCESS read-write
STATUS current
DESCRIPTION
"Data value."
::= { dataArray6 37 }

dataValue6_38 OBJECT-TYPE
SYNTAX INTEGER
MAX-ACCESS read-write
STATUS current
DESCRIPTION
"Data value."
::= { dataArray6 38 }

dataValue6_39 OBJECT-TYPE
SYNTAX INTEGER
MAX-ACCESS read-write
STATUS current
DESCRIPTION
"Data value."
::= { dataArray6 39 }

dataValue6_40 OBJECT-TYPE
SYNTAX INTEGER
MAX-ACCESS read-write
STATUS current
DESCRIPTION
"Data value."
::= { dataArray6 40 }

dataValue6_41 OBJECT-TYPE
SYNTAX INTEGER
MAX-ACCESS read-write
STATUS current
DESCRIPTION
"Data value."
::= { dataArray6 41 }

dataValue6_42 OBJECT-TYPE
SYNTAX INTEGER
MAX-ACCESS read-write
STATUS current
DESCRIPTION
"Data value."
::= { dataArray6 42 }

dataValue6_43 OBJECT-TYPE
SYNTAX INTEGER
MAX-ACCESS read-write
STATUS current
DESCRIPTION
"Data value."
::= { dataArray6 43 }

dataValue6_44 OBJECT-TYPE
SYNTAX INTEGER
MAX-ACCESS read-write
STATUS current
DESCRIPTION
"Data value."
::= { dataArray6 44 }

dataValue6_45 OBJECT-TYPE
SYNTAX INTEGER
MAX-ACCESS read-write
STATUS current
DESCRIPTION
"Data value."
::= { dataArray6 45 }

dataValue6_46 OBJECT-TYPE
SYNTAX INTEGER
MAX-ACCESS read-write
STATUS current
DESCRIPTION
"Data value."
::= { dataArray6 46 }

dataValue6_47 OBJECT-TYPE
SYNTAX INTEGER
MAX-ACCESS read-write
STATUS current
DESCRIPTION
"Data value."
::= { dataArray6 47 }

dataValue6_48 OBJECT-TYPE
SYNTAX INTEGER
MAX-ACCESS read-write
STATUS current
DESCRIPTION
"Data value."
::= { dataArray6 48 }

dataValue6_49 OBJECT-TYPE
SYNTAX INTEGER
MAX-ACCESS read-write
STATUS current
DESCRIPTION
"Data value."
::= { dataArray6 49 }

dataValue6_50 OBJECT-TYPE
SYNTAX INTEGER
MAX-ACCESS read-write
STATUS current
DESCRIPTION
"Data value."
::= { dataArray6 50 }

dataValue6_51 OBJECT-TYPE
SYNTAX INTEGER
MAX-ACCESS read-write
STATUS current
DESCRIPTION
"Data value."
::= { dataArray6 51 }

dataValue6_52 OBJECT-TYPE
SYNTAX INTEGER
MAX-ACCESS read-write
STATUS current
DESCRIPTION
"Data value."
::= { dataArray6 52 }

dataValue6_53 OBJECT-TYPE
SYNTAX INTEGER
MAX-ACCESS read-write
STATUS current
DESCRIPTION
"Data value."
::= { dataArray6 53 }

dataValue6_54 OBJECT-TYPE
SYNTAX INTEGER
MAX-ACCESS read-write
STATUS current
DESCRIPTION
"Data value."
::= { dataArray6 54 }

dataValue6_55 OBJECT-TYPE
SYNTAX INTEGER
MAX-ACCESS read-write
STATUS current
DESCRIPTION
"Data value."
::= { dataArray6 55 }

dataValue6_56 OBJECT-TYPE
SYNTAX INTEGER
MAX-ACCESS read-write
STATUS current
DESCRIPTION
"Data value."
::= { dataArray6 56 }

dataValue6_57 OBJECT-TYPE
SYNTAX INTEGER
MAX-ACCESS read-write
STATUS current
DESCRIPTION
"Data value."
::= { dataArray6 57 }

dataValue6_58 OBJECT-TYPE
SYNTAX INTEGER
MAX-ACCESS read-write
STATUS current
DESCRIPTION
"Data value."
::= { dataArray6 58 }

dataValue6_59 OBJECT-TYPE
SYNTAX INTEGER
MAX-ACCESS read-write
STATUS current
DESCRIPTION
"Data value."
::= { dataArray6 59 }

dataValue6_60 OBJECT-TYPE
SYNTAX INTEGER
MAX-ACCESS read-write
STATUS current
DESCRIPTION
"Data value."
::= { dataArray6 60 }

dataValue6_61 OBJECT-TYPE
SYNTAX INTEGER
MAX-ACCESS read-write
STATUS current
DESCRIPTION
"Data value."
::= { dataArray6 61 }

dataValue6_62 OBJECT-TYPE
SYNTAX INTEGER
MAX-ACCESS read-write
STATUS current
DESCRIPTION
"Data value."
::= { dataArray6 62 }

dataValue6_63 OBJECT-TYPE
SYNTAX INTEGER
MAX-ACCESS read-write
STATUS current
DESCRIPTION
"Data value."
::= { dataArray6 63 }

dataValue6_64 OBJECT-TYPE
SYNTAX INTEGER
MAX-ACCESS read-write
STATUS current
DESCRIPTION
"Data value."
::= { dataArray6 64 }

dataValue6_65 OBJECT-TYPE
SYNTAX INTEGER
MAX-ACCESS read-write
STATUS current
DESCRIPTION
"Data value."
::= { dataArray6 65 }

dataValue6_66 OBJECT-TYPE
SYNTAX INTEGER
MAX-ACCESS read-write
STATUS current
DESCRIPTION
"Data value."
::= { dataArray6 66 }

dataValue6_67 OBJECT-TYPE
SYNTAX INTEGER
MAX-ACCESS read-write
STATUS current
DESCRIPTION
"Data value."
::= { dataArray6 67 }

dataValue6_68 OBJECT-TYPE
SYNTAX INTEGER
MAX-ACCESS read-write
STATUS current
DESCRIPTION
"Data value."
::= { dataArray6 68 }

dataValue6_69 OBJECT-TYPE
SYNTAX INTEGER
MAX-ACCESS read-write
STATUS current
DESCRIPTION
"Data value."
::= { dataArray6 69 }

dataValue6_70 OBJECT-TYPE
SYNTAX INTEGER
MAX-ACCESS read-write
STATUS current
DESCRIPTION
"Data value."
::= { dataArray6 70 }

dataValue6_71 OBJECT-TYPE
SYNTAX INTEGER
MAX-ACCESS read-write
STATUS current
DESCRIPTION
"Data value."
::= { dataArray6 71 }

dataValue6_72 OBJECT-TYPE
SYNTAX INTEGER
MAX-ACCESS read-write
STATUS current
DESCRIPTION
"Data value."
::= { dataArray6 72 }

dataValue6_73 OBJECT-TYPE
SYNTAX INTEGER
MAX-ACCESS read-write
STATUS current
DESCRIPTION
"Data value."
::= { dataArray6 73 }

dataValue6_74 OBJECT-TYPE
SYNTAX INTEGER
MAX-ACCESS read-write
STATUS current
DESCRIPTION
"Data value."
::= { dataArray6 74 }

dataValue6_75 OBJECT-TYPE
SYNTAX INTEGER
MAX-ACCESS read-write
STATUS current
DESCRIPTION
"Data value."
::= { dataArray6 75 }

dataValue6_76 OBJECT-TYPE
SYNTAX INTEGER
MAX-ACCESS read-write
STATUS current
DESCRIPTION
"Data value."
::= { dataArray6 76 }

dataValue6_77 OBJECT-TYPE
SYNTAX INTEGER
MAX-ACCESS read-write
STATUS current
DESCRIPTION
"Data value."
::= { dataArray6 77 }

dataValue6_78 OBJECT-TYPE
SYNTAX INTEGER
MAX-ACCESS read-write
STATUS current
DESCRIPTION
"Data value."
::= { dataArray6 78 }

dataValue6_79 OBJECT-TYPE
SYNTAX INTEGER
MAX-ACCESS read-write
STATUS current
DESCRIPTION
"Data value."
::= { dataArray6 79 }

dataValue6_80 OBJECT-TYPE
SYNTAX INTEGER
MAX-ACCESS read-write
STATUS current
DESCRIPTION
"Data value."
::= { dataArray6 80 }

dataValue6_81 OBJECT-TYPE
SYNTAX INTEGER
MAX-ACCESS read-write
STATUS current
DESCRIPTION
"Data value."
::= { dataArray6 81 }

dataValue6_82 OBJECT-TYPE
SYNTAX INTEGER
MAX-ACCESS read-write
STATUS current
DESCRIPTION
"Data value."
::= { dataArray6 82 }

dataValue6_83 OBJECT-TYPE
SYNTAX INTEGER
MAX-ACCESS read-write
STATUS current
DESCRIPTION
"Data value."
::= { dataArray6 83 }

dataValue6_84 OBJECT-TYPE
SYNTAX INTEGER
MAX-ACCESS read-write
STATUS current
DESCRIPTION
"Data value."
::= { dataArray6 84 }

dataValue6_85 OBJECT-TYPE
SYNTAX INTEGER
MAX-ACCESS read-write
STATUS current
DESCRIPTION
"Data value."
::= { dataArray6 85 }

dataValue6_86 OBJECT-TYPE
SYNTAX INTEGER
MAX-ACCESS read-write
STATUS current
DESCRIPTION
"Data value."
::= { dataArray6 86 }

dataValue6_87 OBJECT-TYPE
SYNTAX INTEGER
MAX-ACCESS read-write
STATUS current
DESCRIPTION
"Data value."
::= { dataArray6 87 }

dataValue6_88 OBJECT-TYPE
SYNTAX INTEGER
MAX-ACCESS read-write
STATUS current
DESCRIPTION
"Data value."
::= { dataArray6 88 }

dataValue6_89 OBJECT-TYPE
SYNTAX INTEGER
MAX-ACCESS read-write
STATUS current
DESCRIPTION
"Data value."
::= { dataArray6 89 }

dataValue6_90 OBJECT-TYPE
SYNTAX INTEGER
MAX-ACCESS read-write
STATUS current
DESCRIPTION
"Data value."
::= { dataArray6 90 }

dataValue6_91 OBJECT-TYPE
SYNTAX INTEGER
MAX-ACCESS read-write
STATUS current
DESCRIPTION
"Data value."
::= { dataArray6 91 }

dataValue6_92 OBJECT-TYPE
SYNTAX INTEGER
MAX-ACCESS read-write
STATUS current
DESCRIPTION
"Data value."
::= { dataArray6 92 }

dataValue6_93 OBJECT-TYPE
SYNTAX INTEGER
MAX-ACCESS read-write
STATUS current
DESCRIPTION
"Data value."
::= { dataArray6 93 }

dataValue6_94 OBJECT-TYPE
SYNTAX INTEGER
MAX-ACCESS read-write
STATUS current
DESCRIPTION
"Data value."
::= { dataArray6 94 }

dataValue6_95 OBJECT-TYPE
SYNTAX INTEGER
MAX-ACCESS read-write
STATUS current
DESCRIPTION
"Data value."
::= { dataArray6 95 }

dataValue6_96 OBJECT-TYPE
SYNTAX INTEGER
MAX-ACCESS read-write
STATUS current
DESCRIPTION
"Data value."
::= { dataArray6 96 }

dataValue6_97 OBJECT-TYPE
SYNTAX INTEGER
MAX-ACCESS read-write
STATUS current
DESCRIPTION
"Data value."
::= { dataArray6 97 }

dataValue6_98 OBJECT-TYPE
SYNTAX INTEGER
MAX-ACCESS read-write
STATUS current
DESCRIPTION
"Data value."
::= { dataArray6 98 }

dataValue6_99 OBJECT-TYPE
SYNTAX INTEGER
MAX-ACCESS read-write
STATUS current
DESCRIPTION
"Data value."
::= { dataArray6 99 }

dataArray7 OBJECT IDENTIFIER ::= { s08090201_trane_st_jude_v1_00b 7 }

dataValue7_0 OBJECT-TYPE
SYNTAX INTEGER
MAX-ACCESS read-write
STATUS current
DESCRIPTION
"Data value."
::= { dataArray7 0 }

dataValue7_1 OBJECT-TYPE
SYNTAX INTEGER
MAX-ACCESS read-write
STATUS current
DESCRIPTION
"Data value."
::= { dataArray7 1 }

dataValue7_2 OBJECT-TYPE
SYNTAX INTEGER
MAX-ACCESS read-write
STATUS current
DESCRIPTION
"Data value."
::= { dataArray7 2 }

dataValue7_3 OBJECT-TYPE
SYNTAX INTEGER
MAX-ACCESS read-write
STATUS current
DESCRIPTION
"Data value."
::= { dataArray7 3 }

dataValue7_4 OBJECT-TYPE
SYNTAX INTEGER
MAX-ACCESS read-write
STATUS current
DESCRIPTION
"Data value."
::= { dataArray7 4 }

dataValue7_5 OBJECT-TYPE
SYNTAX INTEGER
MAX-ACCESS read-write
STATUS current
DESCRIPTION
"Data value."
::= { dataArray7 5 }

dataValue7_6 OBJECT-TYPE
SYNTAX INTEGER
MAX-ACCESS read-write
STATUS current
DESCRIPTION
"Data value."
::= { dataArray7 6 }

dataValue7_7 OBJECT-TYPE
SYNTAX INTEGER
MAX-ACCESS read-write
STATUS current
DESCRIPTION
"Data value."
::= { dataArray7 7 }

dataValue7_8 OBJECT-TYPE
SYNTAX INTEGER
MAX-ACCESS read-write
STATUS current
DESCRIPTION
"Data value."
::= { dataArray7 8 }

dataValue7_9 OBJECT-TYPE
SYNTAX INTEGER
MAX-ACCESS read-write
STATUS current
DESCRIPTION
"Data value."
::= { dataArray7 9 }

dataValue7_10 OBJECT-TYPE
SYNTAX INTEGER
MAX-ACCESS read-write
STATUS current
DESCRIPTION
"Data value."
::= { dataArray7 10 }

dataValue7_11 OBJECT-TYPE
SYNTAX INTEGER
MAX-ACCESS read-write
STATUS current
DESCRIPTION
"Data value."
::= { dataArray7 11 }

dataValue7_12 OBJECT-TYPE
SYNTAX INTEGER
MAX-ACCESS read-write
STATUS current
DESCRIPTION
"Data value."
::= { dataArray7 12 }

dataValue7_13 OBJECT-TYPE
SYNTAX INTEGER
MAX-ACCESS read-write
STATUS current
DESCRIPTION
"Data value."
::= { dataArray7 13 }

dataValue7_14 OBJECT-TYPE
SYNTAX INTEGER
MAX-ACCESS read-write
STATUS current
DESCRIPTION
"Data value."
::= { dataArray7 14 }

dataValue7_15 OBJECT-TYPE
SYNTAX INTEGER
MAX-ACCESS read-write
STATUS current
DESCRIPTION
"Data value."
::= { dataArray7 15 }

dataValue7_16 OBJECT-TYPE
SYNTAX INTEGER
MAX-ACCESS read-write
STATUS current
DESCRIPTION
"Data value."
::= { dataArray7 16 }

dataValue7_17 OBJECT-TYPE
SYNTAX INTEGER
MAX-ACCESS read-write
STATUS current
DESCRIPTION
"Data value."
::= { dataArray7 17 }

dataValue7_18 OBJECT-TYPE
SYNTAX INTEGER
MAX-ACCESS read-write
STATUS current
DESCRIPTION
"Data value."
::= { dataArray7 18 }

dataValue7_19 OBJECT-TYPE
SYNTAX INTEGER
MAX-ACCESS read-write
STATUS current
DESCRIPTION
"Data value."
::= { dataArray7 19 }

dataValue7_20 OBJECT-TYPE
SYNTAX INTEGER
MAX-ACCESS read-write
STATUS current
DESCRIPTION
"Data value."
::= { dataArray7 20 }

dataValue7_21 OBJECT-TYPE
SYNTAX INTEGER
MAX-ACCESS read-write
STATUS current
DESCRIPTION
"Data value."
::= { dataArray7 21 }

dataValue7_22 OBJECT-TYPE
SYNTAX INTEGER
MAX-ACCESS read-write
STATUS current
DESCRIPTION
"Data value."
::= { dataArray7 22 }

dataValue7_23 OBJECT-TYPE
SYNTAX INTEGER
MAX-ACCESS read-write
STATUS current
DESCRIPTION
"Data value."
::= { dataArray7 23 }

dataValue7_24 OBJECT-TYPE
SYNTAX INTEGER
MAX-ACCESS read-write
STATUS current
DESCRIPTION
"Data value."
::= { dataArray7 24 }

dataValue7_25 OBJECT-TYPE
SYNTAX INTEGER
MAX-ACCESS read-write
STATUS current
DESCRIPTION
"Data value."
::= { dataArray7 25 }

dataValue7_26 OBJECT-TYPE
SYNTAX INTEGER
MAX-ACCESS read-write
STATUS current
DESCRIPTION
"Data value."
::= { dataArray7 26 }

dataValue7_27 OBJECT-TYPE
SYNTAX INTEGER
MAX-ACCESS read-write
STATUS current
DESCRIPTION
"Data value."
::= { dataArray7 27 }

dataValue7_28 OBJECT-TYPE
SYNTAX INTEGER
MAX-ACCESS read-write
STATUS current
DESCRIPTION
"Data value."
::= { dataArray7 28 }

dataValue7_29 OBJECT-TYPE
SYNTAX INTEGER
MAX-ACCESS read-write
STATUS current
DESCRIPTION
"Data value."
::= { dataArray7 29 }

dataValue7_30 OBJECT-TYPE
SYNTAX INTEGER
MAX-ACCESS read-write
STATUS current
DESCRIPTION
"Data value."
::= { dataArray7 30 }

dataValue7_31 OBJECT-TYPE
SYNTAX INTEGER
MAX-ACCESS read-write
STATUS current
DESCRIPTION
"Data value."
::= { dataArray7 31 }

dataValue7_32 OBJECT-TYPE
SYNTAX INTEGER
MAX-ACCESS read-write
STATUS current
DESCRIPTION
"Data value."
::= { dataArray7 32 }

dataValue7_33 OBJECT-TYPE
SYNTAX INTEGER
MAX-ACCESS read-write
STATUS current
DESCRIPTION
"Data value."
::= { dataArray7 33 }

dataValue7_34 OBJECT-TYPE
SYNTAX INTEGER
MAX-ACCESS read-write
STATUS current
DESCRIPTION
"Data value."
::= { dataArray7 34 }

dataValue7_35 OBJECT-TYPE
SYNTAX INTEGER
MAX-ACCESS read-write
STATUS current
DESCRIPTION
"Data value."
::= { dataArray7 35 }

dataValue7_36 OBJECT-TYPE
SYNTAX INTEGER
MAX-ACCESS read-write
STATUS current
DESCRIPTION
"Data value."
::= { dataArray7 36 }

dataValue7_37 OBJECT-TYPE
SYNTAX INTEGER
MAX-ACCESS read-write
STATUS current
DESCRIPTION
"Data value."
::= { dataArray7 37 }

dataValue7_38 OBJECT-TYPE
SYNTAX INTEGER
MAX-ACCESS read-write
STATUS current
DESCRIPTION
"Data value."
::= { dataArray7 38 }

dataValue7_39 OBJECT-TYPE
SYNTAX INTEGER
MAX-ACCESS read-write
STATUS current
DESCRIPTION
"Data value."
::= { dataArray7 39 }

dataValue7_40 OBJECT-TYPE
SYNTAX INTEGER
MAX-ACCESS read-write
STATUS current
DESCRIPTION
"Data value."
::= { dataArray7 40 }

dataValue7_41 OBJECT-TYPE
SYNTAX INTEGER
MAX-ACCESS read-write
STATUS current
DESCRIPTION
"Data value."
::= { dataArray7 41 }

dataValue7_42 OBJECT-TYPE
SYNTAX INTEGER
MAX-ACCESS read-write
STATUS current
DESCRIPTION
"Data value."
::= { dataArray7 42 }

dataValue7_43 OBJECT-TYPE
SYNTAX INTEGER
MAX-ACCESS read-write
STATUS current
DESCRIPTION
"Data value."
::= { dataArray7 43 }

dataValue7_44 OBJECT-TYPE
SYNTAX INTEGER
MAX-ACCESS read-write
STATUS current
DESCRIPTION
"Data value."
::= { dataArray7 44 }

dataValue7_45 OBJECT-TYPE
SYNTAX INTEGER
MAX-ACCESS read-write
STATUS current
DESCRIPTION
"Data value."
::= { dataArray7 45 }

dataValue7_46 OBJECT-TYPE
SYNTAX INTEGER
MAX-ACCESS read-write
STATUS current
DESCRIPTION
"Data value."
::= { dataArray7 46 }

dataValue7_47 OBJECT-TYPE
SYNTAX INTEGER
MAX-ACCESS read-write
STATUS current
DESCRIPTION
"Data value."
::= { dataArray7 47 }

dataValue7_48 OBJECT-TYPE
SYNTAX INTEGER
MAX-ACCESS read-write
STATUS current
DESCRIPTION
"Data value."
::= { dataArray7 48 }

dataValue7_49 OBJECT-TYPE
SYNTAX INTEGER
MAX-ACCESS read-write
STATUS current
DESCRIPTION
"Data value."
::= { dataArray7 49 }

dataValue7_50 OBJECT-TYPE
SYNTAX INTEGER
MAX-ACCESS read-write
STATUS current
DESCRIPTION
"Data value."
::= { dataArray7 50 }

dataValue7_51 OBJECT-TYPE
SYNTAX INTEGER
MAX-ACCESS read-write
STATUS current
DESCRIPTION
"Data value."
::= { dataArray7 51 }

dataValue7_52 OBJECT-TYPE
SYNTAX INTEGER
MAX-ACCESS read-write
STATUS current
DESCRIPTION
"Data value."
::= { dataArray7 52 }

dataValue7_53 OBJECT-TYPE
SYNTAX INTEGER
MAX-ACCESS read-write
STATUS current
DESCRIPTION
"Data value."
::= { dataArray7 53 }

dataValue7_54 OBJECT-TYPE
SYNTAX INTEGER
MAX-ACCESS read-write
STATUS current
DESCRIPTION
"Data value."
::= { dataArray7 54 }

dataValue7_55 OBJECT-TYPE
SYNTAX INTEGER
MAX-ACCESS read-write
STATUS current
DESCRIPTION
"Data value."
::= { dataArray7 55 }

dataValue7_56 OBJECT-TYPE
SYNTAX INTEGER
MAX-ACCESS read-write
STATUS current
DESCRIPTION
"Data value."
::= { dataArray7 56 }

dataValue7_57 OBJECT-TYPE
SYNTAX INTEGER
MAX-ACCESS read-write
STATUS current
DESCRIPTION
"Data value."
::= { dataArray7 57 }

dataValue7_58 OBJECT-TYPE
SYNTAX INTEGER
MAX-ACCESS read-write
STATUS current
DESCRIPTION
"Data value."
::= { dataArray7 58 }

dataValue7_59 OBJECT-TYPE
SYNTAX INTEGER
MAX-ACCESS read-write
STATUS current
DESCRIPTION
"Data value."
::= { dataArray7 59 }

dataValue7_60 OBJECT-TYPE
SYNTAX INTEGER
MAX-ACCESS read-write
STATUS current
DESCRIPTION
"Data value."
::= { dataArray7 60 }

dataValue7_61 OBJECT-TYPE
SYNTAX INTEGER
MAX-ACCESS read-write
STATUS current
DESCRIPTION
"Data value."
::= { dataArray7 61 }

dataValue7_62 OBJECT-TYPE
SYNTAX INTEGER
MAX-ACCESS read-write
STATUS current
DESCRIPTION
"Data value."
::= { dataArray7 62 }

dataValue7_63 OBJECT-TYPE
SYNTAX INTEGER
MAX-ACCESS read-write
STATUS current
DESCRIPTION
"Data value."
::= { dataArray7 63 }

dataValue7_64 OBJECT-TYPE
SYNTAX INTEGER
MAX-ACCESS read-write
STATUS current
DESCRIPTION
"Data value."
::= { dataArray7 64 }

dataValue7_65 OBJECT-TYPE
SYNTAX INTEGER
MAX-ACCESS read-write
STATUS current
DESCRIPTION
"Data value."
::= { dataArray7 65 }

dataValue7_66 OBJECT-TYPE
SYNTAX INTEGER
MAX-ACCESS read-write
STATUS current
DESCRIPTION
"Data value."
::= { dataArray7 66 }

dataValue7_67 OBJECT-TYPE
SYNTAX INTEGER
MAX-ACCESS read-write
STATUS current
DESCRIPTION
"Data value."
::= { dataArray7 67 }

dataValue7_68 OBJECT-TYPE
SYNTAX INTEGER
MAX-ACCESS read-write
STATUS current
DESCRIPTION
"Data value."
::= { dataArray7 68 }

dataValue7_69 OBJECT-TYPE
SYNTAX INTEGER
MAX-ACCESS read-write
STATUS current
DESCRIPTION
"Data value."
::= { dataArray7 69 }

dataValue7_70 OBJECT-TYPE
SYNTAX INTEGER
MAX-ACCESS read-write
STATUS current
DESCRIPTION
"Data value."
::= { dataArray7 70 }

dataValue7_71 OBJECT-TYPE
SYNTAX INTEGER
MAX-ACCESS read-write
STATUS current
DESCRIPTION
"Data value."
::= { dataArray7 71 }

dataValue7_72 OBJECT-TYPE
SYNTAX INTEGER
MAX-ACCESS read-write
STATUS current
DESCRIPTION
"Data value."
::= { dataArray7 72 }

dataValue7_73 OBJECT-TYPE
SYNTAX INTEGER
MAX-ACCESS read-write
STATUS current
DESCRIPTION
"Data value."
::= { dataArray7 73 }

dataValue7_74 OBJECT-TYPE
SYNTAX INTEGER
MAX-ACCESS read-write
STATUS current
DESCRIPTION
"Data value."
::= { dataArray7 74 }

dataValue7_75 OBJECT-TYPE
SYNTAX INTEGER
MAX-ACCESS read-write
STATUS current
DESCRIPTION
"Data value."
::= { dataArray7 75 }

dataValue7_76 OBJECT-TYPE
SYNTAX INTEGER
MAX-ACCESS read-write
STATUS current
DESCRIPTION
"Data value."
::= { dataArray7 76 }

dataValue7_77 OBJECT-TYPE
SYNTAX INTEGER
MAX-ACCESS read-write
STATUS current
DESCRIPTION
"Data value."
::= { dataArray7 77 }

dataValue7_78 OBJECT-TYPE
SYNTAX INTEGER
MAX-ACCESS read-write
STATUS current
DESCRIPTION
"Data value."
::= { dataArray7 78 }

dataValue7_79 OBJECT-TYPE
SYNTAX INTEGER
MAX-ACCESS read-write
STATUS current
DESCRIPTION
"Data value."
::= { dataArray7 79 }

dataValue7_80 OBJECT-TYPE
SYNTAX INTEGER
MAX-ACCESS read-write
STATUS current
DESCRIPTION
"Data value."
::= { dataArray7 80 }

dataValue7_81 OBJECT-TYPE
SYNTAX INTEGER
MAX-ACCESS read-write
STATUS current
DESCRIPTION
"Data value."
::= { dataArray7 81 }

dataValue7_82 OBJECT-TYPE
SYNTAX INTEGER
MAX-ACCESS read-write
STATUS current
DESCRIPTION
"Data value."
::= { dataArray7 82 }

dataValue7_83 OBJECT-TYPE
SYNTAX INTEGER
MAX-ACCESS read-write
STATUS current
DESCRIPTION
"Data value."
::= { dataArray7 83 }

dataValue7_84 OBJECT-TYPE
SYNTAX INTEGER
MAX-ACCESS read-write
STATUS current
DESCRIPTION
"Data value."
::= { dataArray7 84 }

dataValue7_85 OBJECT-TYPE
SYNTAX INTEGER
MAX-ACCESS read-write
STATUS current
DESCRIPTION
"Data value."
::= { dataArray7 85 }

dataValue7_86 OBJECT-TYPE
SYNTAX INTEGER
MAX-ACCESS read-write
STATUS current
DESCRIPTION
"Data value."
::= { dataArray7 86 }

dataValue7_87 OBJECT-TYPE
SYNTAX INTEGER
MAX-ACCESS read-write
STATUS current
DESCRIPTION
"Data value."
::= { dataArray7 87 }

dataValue7_88 OBJECT-TYPE
SYNTAX INTEGER
MAX-ACCESS read-write
STATUS current
DESCRIPTION
"Data value."
::= { dataArray7 88 }

dataValue7_89 OBJECT-TYPE
SYNTAX INTEGER
MAX-ACCESS read-write
STATUS current
DESCRIPTION
"Data value."
::= { dataArray7 89 }

dataValue7_90 OBJECT-TYPE
SYNTAX INTEGER
MAX-ACCESS read-write
STATUS current
DESCRIPTION
"Data value."
::= { dataArray7 90 }

dataValue7_91 OBJECT-TYPE
SYNTAX INTEGER
MAX-ACCESS read-write
STATUS current
DESCRIPTION
"Data value."
::= { dataArray7 91 }

dataValue7_92 OBJECT-TYPE
SYNTAX INTEGER
MAX-ACCESS read-write
STATUS current
DESCRIPTION
"Data value."
::= { dataArray7 92 }

dataValue7_93 OBJECT-TYPE
SYNTAX INTEGER
MAX-ACCESS read-write
STATUS current
DESCRIPTION
"Data value."
::= { dataArray7 93 }

dataValue7_94 OBJECT-TYPE
SYNTAX INTEGER
MAX-ACCESS read-write
STATUS current
DESCRIPTION
"Data value."
::= { dataArray7 94 }

dataValue7_95 OBJECT-TYPE
SYNTAX INTEGER
MAX-ACCESS read-write
STATUS current
DESCRIPTION
"Data value."
::= { dataArray7 95 }

dataValue7_96 OBJECT-TYPE
SYNTAX INTEGER
MAX-ACCESS read-write
STATUS current
DESCRIPTION
"Data value."
::= { dataArray7 96 }

dataValue7_97 OBJECT-TYPE
SYNTAX INTEGER
MAX-ACCESS read-write
STATUS current
DESCRIPTION
"Data value."
::= { dataArray7 97 }

dataValue7_98 OBJECT-TYPE
SYNTAX INTEGER
MAX-ACCESS read-write
STATUS current
DESCRIPTION
"Data value."
::= { dataArray7 98 }

dataValue7_99 OBJECT-TYPE
SYNTAX INTEGER
MAX-ACCESS read-write
STATUS current
DESCRIPTION
"Data value."
::= { dataArray7 99 }

dataArray8 OBJECT IDENTIFIER ::= { s08090201_trane_st_jude_v1_00b 8 }

dataValue8_0 OBJECT-TYPE
SYNTAX INTEGER
MAX-ACCESS read-write
STATUS current
DESCRIPTION
"Data value."
::= { dataArray8 0 }

dataValue8_1 OBJECT-TYPE
SYNTAX INTEGER
MAX-ACCESS read-write
STATUS current
DESCRIPTION
"Data value."
::= { dataArray8 1 }

dataValue8_2 OBJECT-TYPE
SYNTAX INTEGER
MAX-ACCESS read-write
STATUS current
DESCRIPTION
"Data value."
::= { dataArray8 2 }

dataValue8_3 OBJECT-TYPE
SYNTAX INTEGER
MAX-ACCESS read-write
STATUS current
DESCRIPTION
"Data value."
::= { dataArray8 3 }

dataValue8_4 OBJECT-TYPE
SYNTAX INTEGER
MAX-ACCESS read-write
STATUS current
DESCRIPTION
"Data value."
::= { dataArray8 4 }

dataValue8_5 OBJECT-TYPE
SYNTAX INTEGER
MAX-ACCESS read-write
STATUS current
DESCRIPTION
"Data value."
::= { dataArray8 5 }

dataValue8_6 OBJECT-TYPE
SYNTAX INTEGER
MAX-ACCESS read-write
STATUS current
DESCRIPTION
"Data value."
::= { dataArray8 6 }

dataValue8_7 OBJECT-TYPE
SYNTAX INTEGER
MAX-ACCESS read-write
STATUS current
DESCRIPTION
"Data value."
::= { dataArray8 7 }

dataValue8_8 OBJECT-TYPE
SYNTAX INTEGER
MAX-ACCESS read-write
STATUS current
DESCRIPTION
"Data value."
::= { dataArray8 8 }

dataValue8_9 OBJECT-TYPE
SYNTAX INTEGER
MAX-ACCESS read-write
STATUS current
DESCRIPTION
"Data value."
::= { dataArray8 9 }

dataValue8_10 OBJECT-TYPE
SYNTAX INTEGER
MAX-ACCESS read-write
STATUS current
DESCRIPTION
"Data value."
::= { dataArray8 10 }

dataValue8_11 OBJECT-TYPE
SYNTAX INTEGER
MAX-ACCESS read-write
STATUS current
DESCRIPTION
"Data value."
::= { dataArray8 11 }

dataValue8_12 OBJECT-TYPE
SYNTAX INTEGER
MAX-ACCESS read-write
STATUS current
DESCRIPTION
"Data value."
::= { dataArray8 12 }

dataValue8_13 OBJECT-TYPE
SYNTAX INTEGER
MAX-ACCESS read-write
STATUS current
DESCRIPTION
"Data value."
::= { dataArray8 13 }

dataValue8_14 OBJECT-TYPE
SYNTAX INTEGER
MAX-ACCESS read-write
STATUS current
DESCRIPTION
"Data value."
::= { dataArray8 14 }

dataValue8_15 OBJECT-TYPE
SYNTAX INTEGER
MAX-ACCESS read-write
STATUS current
DESCRIPTION
"Data value."
::= { dataArray8 15 }

dataValue8_16 OBJECT-TYPE
SYNTAX INTEGER
MAX-ACCESS read-write
STATUS current
DESCRIPTION
"Data value."
::= { dataArray8 16 }

dataValue8_17 OBJECT-TYPE
SYNTAX INTEGER
MAX-ACCESS read-write
STATUS current
DESCRIPTION
"Data value."
::= { dataArray8 17 }

dataValue8_18 OBJECT-TYPE
SYNTAX INTEGER
MAX-ACCESS read-write
STATUS current
DESCRIPTION
"Data value."
::= { dataArray8 18 }

dataValue8_19 OBJECT-TYPE
SYNTAX INTEGER
MAX-ACCESS read-write
STATUS current
DESCRIPTION
"Data value."
::= { dataArray8 19 }

dataValue8_20 OBJECT-TYPE
SYNTAX INTEGER
MAX-ACCESS read-write
STATUS current
DESCRIPTION
"Data value."
::= { dataArray8 20 }

dataValue8_21 OBJECT-TYPE
SYNTAX INTEGER
MAX-ACCESS read-write
STATUS current
DESCRIPTION
"Data value."
::= { dataArray8 21 }

dataValue8_22 OBJECT-TYPE
SYNTAX INTEGER
MAX-ACCESS read-write
STATUS current
DESCRIPTION
"Data value."
::= { dataArray8 22 }

dataValue8_23 OBJECT-TYPE
SYNTAX INTEGER
MAX-ACCESS read-write
STATUS current
DESCRIPTION
"Data value."
::= { dataArray8 23 }

dataValue8_24 OBJECT-TYPE
SYNTAX INTEGER
MAX-ACCESS read-write
STATUS current
DESCRIPTION
"Data value."
::= { dataArray8 24 }

dataValue8_25 OBJECT-TYPE
SYNTAX INTEGER
MAX-ACCESS read-write
STATUS current
DESCRIPTION
"Data value."
::= { dataArray8 25 }

dataValue8_26 OBJECT-TYPE
SYNTAX INTEGER
MAX-ACCESS read-write
STATUS current
DESCRIPTION
"Data value."
::= { dataArray8 26 }

dataValue8_27 OBJECT-TYPE
SYNTAX INTEGER
MAX-ACCESS read-write
STATUS current
DESCRIPTION
"Data value."
::= { dataArray8 27 }

dataValue8_28 OBJECT-TYPE
SYNTAX INTEGER
MAX-ACCESS read-write
STATUS current
DESCRIPTION
"Data value."
::= { dataArray8 28 }

dataValue8_29 OBJECT-TYPE
SYNTAX INTEGER
MAX-ACCESS read-write
STATUS current
DESCRIPTION
"Data value."
::= { dataArray8 29 }

dataValue8_30 OBJECT-TYPE
SYNTAX INTEGER
MAX-ACCESS read-write
STATUS current
DESCRIPTION
"Data value."
::= { dataArray8 30 }

dataValue8_31 OBJECT-TYPE
SYNTAX INTEGER
MAX-ACCESS read-write
STATUS current
DESCRIPTION
"Data value."
::= { dataArray8 31 }

dataValue8_32 OBJECT-TYPE
SYNTAX INTEGER
MAX-ACCESS read-write
STATUS current
DESCRIPTION
"Data value."
::= { dataArray8 32 }

dataValue8_33 OBJECT-TYPE
SYNTAX INTEGER
MAX-ACCESS read-write
STATUS current
DESCRIPTION
"Data value."
::= { dataArray8 33 }

dataValue8_34 OBJECT-TYPE
SYNTAX INTEGER
MAX-ACCESS read-write
STATUS current
DESCRIPTION
"Data value."
::= { dataArray8 34 }

dataValue8_35 OBJECT-TYPE
SYNTAX INTEGER
MAX-ACCESS read-write
STATUS current
DESCRIPTION
"Data value."
::= { dataArray8 35 }

dataValue8_36 OBJECT-TYPE
SYNTAX INTEGER
MAX-ACCESS read-write
STATUS current
DESCRIPTION
"Data value."
::= { dataArray8 36 }

dataValue8_37 OBJECT-TYPE
SYNTAX INTEGER
MAX-ACCESS read-write
STATUS current
DESCRIPTION
"Data value."
::= { dataArray8 37 }

dataValue8_38 OBJECT-TYPE
SYNTAX INTEGER
MAX-ACCESS read-write
STATUS current
DESCRIPTION
"Data value."
::= { dataArray8 38 }

dataValue8_39 OBJECT-TYPE
SYNTAX INTEGER
MAX-ACCESS read-write
STATUS current
DESCRIPTION
"Data value."
::= { dataArray8 39 }

dataValue8_40 OBJECT-TYPE
SYNTAX INTEGER
MAX-ACCESS read-write
STATUS current
DESCRIPTION
"Data value."
::= { dataArray8 40 }

dataValue8_41 OBJECT-TYPE
SYNTAX INTEGER
MAX-ACCESS read-write
STATUS current
DESCRIPTION
"Data value."
::= { dataArray8 41 }

dataValue8_42 OBJECT-TYPE
SYNTAX INTEGER
MAX-ACCESS read-write
STATUS current
DESCRIPTION
"Data value."
::= { dataArray8 42 }

dataValue8_43 OBJECT-TYPE
SYNTAX INTEGER
MAX-ACCESS read-write
STATUS current
DESCRIPTION
"Data value."
::= { dataArray8 43 }

dataValue8_44 OBJECT-TYPE
SYNTAX INTEGER
MAX-ACCESS read-write
STATUS current
DESCRIPTION
"Data value."
::= { dataArray8 44 }

dataValue8_45 OBJECT-TYPE
SYNTAX INTEGER
MAX-ACCESS read-write
STATUS current
DESCRIPTION
"Data value."
::= { dataArray8 45 }

dataValue8_46 OBJECT-TYPE
SYNTAX INTEGER
MAX-ACCESS read-write
STATUS current
DESCRIPTION
"Data value."
::= { dataArray8 46 }

dataValue8_47 OBJECT-TYPE
SYNTAX INTEGER
MAX-ACCESS read-write
STATUS current
DESCRIPTION
"Data value."
::= { dataArray8 47 }

dataValue8_48 OBJECT-TYPE
SYNTAX INTEGER
MAX-ACCESS read-write
STATUS current
DESCRIPTION
"Data value."
::= { dataArray8 48 }

dataValue8_49 OBJECT-TYPE
SYNTAX INTEGER
MAX-ACCESS read-write
STATUS current
DESCRIPTION
"Data value."
::= { dataArray8 49 }

dataValue8_50 OBJECT-TYPE
SYNTAX INTEGER
MAX-ACCESS read-write
STATUS current
DESCRIPTION
"Data value."
::= { dataArray8 50 }

dataValue8_51 OBJECT-TYPE
SYNTAX INTEGER
MAX-ACCESS read-write
STATUS current
DESCRIPTION
"Data value."
::= { dataArray8 51 }

dataValue8_52 OBJECT-TYPE
SYNTAX INTEGER
MAX-ACCESS read-write
STATUS current
DESCRIPTION
"Data value."
::= { dataArray8 52 }

dataValue8_53 OBJECT-TYPE
SYNTAX INTEGER
MAX-ACCESS read-write
STATUS current
DESCRIPTION
"Data value."
::= { dataArray8 53 }

dataValue8_54 OBJECT-TYPE
SYNTAX INTEGER
MAX-ACCESS read-write
STATUS current
DESCRIPTION
"Data value."
::= { dataArray8 54 }

dataValue8_55 OBJECT-TYPE
SYNTAX INTEGER
MAX-ACCESS read-write
STATUS current
DESCRIPTION
"Data value."
::= { dataArray8 55 }

dataValue8_56 OBJECT-TYPE
SYNTAX INTEGER
MAX-ACCESS read-write
STATUS current
DESCRIPTION
"Data value."
::= { dataArray8 56 }

dataValue8_57 OBJECT-TYPE
SYNTAX INTEGER
MAX-ACCESS read-write
STATUS current
DESCRIPTION
"Data value."
::= { dataArray8 57 }

dataValue8_58 OBJECT-TYPE
SYNTAX INTEGER
MAX-ACCESS read-write
STATUS current
DESCRIPTION
"Data value."
::= { dataArray8 58 }

dataValue8_59 OBJECT-TYPE
SYNTAX INTEGER
MAX-ACCESS read-write
STATUS current
DESCRIPTION
"Data value."
::= { dataArray8 59 }

dataValue8_60 OBJECT-TYPE
SYNTAX INTEGER
MAX-ACCESS read-write
STATUS current
DESCRIPTION
"Data value."
::= { dataArray8 60 }

dataValue8_61 OBJECT-TYPE
SYNTAX INTEGER
MAX-ACCESS read-write
STATUS current
DESCRIPTION
"Data value."
::= { dataArray8 61 }

dataValue8_62 OBJECT-TYPE
SYNTAX INTEGER
MAX-ACCESS read-write
STATUS current
DESCRIPTION
"Data value."
::= { dataArray8 62 }

dataValue8_63 OBJECT-TYPE
SYNTAX INTEGER
MAX-ACCESS read-write
STATUS current
DESCRIPTION
"Data value."
::= { dataArray8 63 }

dataValue8_64 OBJECT-TYPE
SYNTAX INTEGER
MAX-ACCESS read-write
STATUS current
DESCRIPTION
"Data value."
::= { dataArray8 64 }

dataValue8_65 OBJECT-TYPE
SYNTAX INTEGER
MAX-ACCESS read-write
STATUS current
DESCRIPTION
"Data value."
::= { dataArray8 65 }

dataValue8_66 OBJECT-TYPE
SYNTAX INTEGER
MAX-ACCESS read-write
STATUS current
DESCRIPTION
"Data value."
::= { dataArray8 66 }

dataValue8_67 OBJECT-TYPE
SYNTAX INTEGER
MAX-ACCESS read-write
STATUS current
DESCRIPTION
"Data value."
::= { dataArray8 67 }

dataValue8_68 OBJECT-TYPE
SYNTAX INTEGER
MAX-ACCESS read-write
STATUS current
DESCRIPTION
"Data value."
::= { dataArray8 68 }

dataValue8_69 OBJECT-TYPE
SYNTAX INTEGER
MAX-ACCESS read-write
STATUS current
DESCRIPTION
"Data value."
::= { dataArray8 69 }

dataValue8_70 OBJECT-TYPE
SYNTAX INTEGER
MAX-ACCESS read-write
STATUS current
DESCRIPTION
"Data value."
::= { dataArray8 70 }

dataValue8_71 OBJECT-TYPE
SYNTAX INTEGER
MAX-ACCESS read-write
STATUS current
DESCRIPTION
"Data value."
::= { dataArray8 71 }

dataValue8_72 OBJECT-TYPE
SYNTAX INTEGER
MAX-ACCESS read-write
STATUS current
DESCRIPTION
"Data value."
::= { dataArray8 72 }

dataValue8_73 OBJECT-TYPE
SYNTAX INTEGER
MAX-ACCESS read-write
STATUS current
DESCRIPTION
"Data value."
::= { dataArray8 73 }

dataValue8_74 OBJECT-TYPE
SYNTAX INTEGER
MAX-ACCESS read-write
STATUS current
DESCRIPTION
"Data value."
::= { dataArray8 74 }

dataValue8_75 OBJECT-TYPE
SYNTAX INTEGER
MAX-ACCESS read-write
STATUS current
DESCRIPTION
"Data value."
::= { dataArray8 75 }

dataValue8_76 OBJECT-TYPE
SYNTAX INTEGER
MAX-ACCESS read-write
STATUS current
DESCRIPTION
"Data value."
::= { dataArray8 76 }

dataValue8_77 OBJECT-TYPE
SYNTAX INTEGER
MAX-ACCESS read-write
STATUS current
DESCRIPTION
"Data value."
::= { dataArray8 77 }

dataValue8_78 OBJECT-TYPE
SYNTAX INTEGER
MAX-ACCESS read-write
STATUS current
DESCRIPTION
"Data value."
::= { dataArray8 78 }

dataValue8_79 OBJECT-TYPE
SYNTAX INTEGER
MAX-ACCESS read-write
STATUS current
DESCRIPTION
"Data value."
::= { dataArray8 79 }

dataValue8_80 OBJECT-TYPE
SYNTAX INTEGER
MAX-ACCESS read-write
STATUS current
DESCRIPTION
"Data value."
::= { dataArray8 80 }

dataValue8_81 OBJECT-TYPE
SYNTAX INTEGER
MAX-ACCESS read-write
STATUS current
DESCRIPTION
"Data value."
::= { dataArray8 81 }

dataValue8_82 OBJECT-TYPE
SYNTAX INTEGER
MAX-ACCESS read-write
STATUS current
DESCRIPTION
"Data value."
::= { dataArray8 82 }

dataValue8_83 OBJECT-TYPE
SYNTAX INTEGER
MAX-ACCESS read-write
STATUS current
DESCRIPTION
"Data value."
::= { dataArray8 83 }

dataValue8_84 OBJECT-TYPE
SYNTAX INTEGER
MAX-ACCESS read-write
STATUS current
DESCRIPTION
"Data value."
::= { dataArray8 84 }

dataValue8_85 OBJECT-TYPE
SYNTAX INTEGER
MAX-ACCESS read-write
STATUS current
DESCRIPTION
"Data value."
::= { dataArray8 85 }

dataValue8_86 OBJECT-TYPE
SYNTAX INTEGER
MAX-ACCESS read-write
STATUS current
DESCRIPTION
"Data value."
::= { dataArray8 86 }

dataValue8_87 OBJECT-TYPE
SYNTAX INTEGER
MAX-ACCESS read-write
STATUS current
DESCRIPTION
"Data value."
::= { dataArray8 87 }

dataValue8_88 OBJECT-TYPE
SYNTAX INTEGER
MAX-ACCESS read-write
STATUS current
DESCRIPTION
"Data value."
::= { dataArray8 88 }

dataValue8_89 OBJECT-TYPE
SYNTAX INTEGER
MAX-ACCESS read-write
STATUS current
DESCRIPTION
"Data value."
::= { dataArray8 89 }

dataValue8_90 OBJECT-TYPE
SYNTAX INTEGER
MAX-ACCESS read-write
STATUS current
DESCRIPTION
"Data value."
::= { dataArray8 90 }

dataValue8_91 OBJECT-TYPE
SYNTAX INTEGER
MAX-ACCESS read-write
STATUS current
DESCRIPTION
"Data value."
::= { dataArray8 91 }

dataValue8_92 OBJECT-TYPE
SYNTAX INTEGER
MAX-ACCESS read-write
STATUS current
DESCRIPTION
"Data value."
::= { dataArray8 92 }

dataValue8_93 OBJECT-TYPE
SYNTAX INTEGER
MAX-ACCESS read-write
STATUS current
DESCRIPTION
"Data value."
::= { dataArray8 93 }

dataValue8_94 OBJECT-TYPE
SYNTAX INTEGER
MAX-ACCESS read-write
STATUS current
DESCRIPTION
"Data value."
::= { dataArray8 94 }

dataValue8_95 OBJECT-TYPE
SYNTAX INTEGER
MAX-ACCESS read-write
STATUS current
DESCRIPTION
"Data value."
::= { dataArray8 95 }

dataValue8_96 OBJECT-TYPE
SYNTAX INTEGER
MAX-ACCESS read-write
STATUS current
DESCRIPTION
"Data value."
::= { dataArray8 96 }

dataValue8_97 OBJECT-TYPE
SYNTAX INTEGER
MAX-ACCESS read-write
STATUS current
DESCRIPTION
"Data value."
::= { dataArray8 97 }

dataValue8_98 OBJECT-TYPE
SYNTAX INTEGER
MAX-ACCESS read-write
STATUS current
DESCRIPTION
"Data value."
::= { dataArray8 98 }

dataValue8_99 OBJECT-TYPE
SYNTAX INTEGER
MAX-ACCESS read-write
STATUS current
DESCRIPTION
"Data value."
::= { dataArray8 99 }

dataArray9 OBJECT IDENTIFIER ::= { s08090201_trane_st_jude_v1_00b 9 }

dataValue9_0 OBJECT-TYPE
SYNTAX INTEGER
MAX-ACCESS read-write
STATUS current
DESCRIPTION
"Data value."
::= { dataArray9 0 }

dataValue9_1 OBJECT-TYPE
SYNTAX INTEGER
MAX-ACCESS read-write
STATUS current
DESCRIPTION
"Data value."
::= { dataArray9 1 }

dataValue9_2 OBJECT-TYPE
SYNTAX INTEGER
MAX-ACCESS read-write
STATUS current
DESCRIPTION
"Data value."
::= { dataArray9 2 }

dataValue9_3 OBJECT-TYPE
SYNTAX INTEGER
MAX-ACCESS read-write
STATUS current
DESCRIPTION
"Data value."
::= { dataArray9 3 }

dataValue9_4 OBJECT-TYPE
SYNTAX INTEGER
MAX-ACCESS read-write
STATUS current
DESCRIPTION
"Data value."
::= { dataArray9 4 }

dataValue9_5 OBJECT-TYPE
SYNTAX INTEGER
MAX-ACCESS read-write
STATUS current
DESCRIPTION
"Data value."
::= { dataArray9 5 }

dataValue9_6 OBJECT-TYPE
SYNTAX INTEGER
MAX-ACCESS read-write
STATUS current
DESCRIPTION
"Data value."
::= { dataArray9 6 }

dataValue9_7 OBJECT-TYPE
SYNTAX INTEGER
MAX-ACCESS read-write
STATUS current
DESCRIPTION
"Data value."
::= { dataArray9 7 }

dataValue9_8 OBJECT-TYPE
SYNTAX INTEGER
MAX-ACCESS read-write
STATUS current
DESCRIPTION
"Data value."
::= { dataArray9 8 }

dataValue9_9 OBJECT-TYPE
SYNTAX INTEGER
MAX-ACCESS read-write
STATUS current
DESCRIPTION
"Data value."
::= { dataArray9 9 }

dataValue9_10 OBJECT-TYPE
SYNTAX INTEGER
MAX-ACCESS read-write
STATUS current
DESCRIPTION
"Data value."
::= { dataArray9 10 }

dataValue9_11 OBJECT-TYPE
SYNTAX INTEGER
MAX-ACCESS read-write
STATUS current
DESCRIPTION
"Data value."
::= { dataArray9 11 }

dataValue9_12 OBJECT-TYPE
SYNTAX INTEGER
MAX-ACCESS read-write
STATUS current
DESCRIPTION
"Data value."
::= { dataArray9 12 }

dataValue9_13 OBJECT-TYPE
SYNTAX INTEGER
MAX-ACCESS read-write
STATUS current
DESCRIPTION
"Data value."
::= { dataArray9 13 }

dataValue9_14 OBJECT-TYPE
SYNTAX INTEGER
MAX-ACCESS read-write
STATUS current
DESCRIPTION
"Data value."
::= { dataArray9 14 }

dataValue9_15 OBJECT-TYPE
SYNTAX INTEGER
MAX-ACCESS read-write
STATUS current
DESCRIPTION
"Data value."
::= { dataArray9 15 }

dataValue9_16 OBJECT-TYPE
SYNTAX INTEGER
MAX-ACCESS read-write
STATUS current
DESCRIPTION
"Data value."
::= { dataArray9 16 }

dataValue9_17 OBJECT-TYPE
SYNTAX INTEGER
MAX-ACCESS read-write
STATUS current
DESCRIPTION
"Data value."
::= { dataArray9 17 }

dataValue9_18 OBJECT-TYPE
SYNTAX INTEGER
MAX-ACCESS read-write
STATUS current
DESCRIPTION
"Data value."
::= { dataArray9 18 }

dataValue9_19 OBJECT-TYPE
SYNTAX INTEGER
MAX-ACCESS read-write
STATUS current
DESCRIPTION
"Data value."
::= { dataArray9 19 }

dataValue9_20 OBJECT-TYPE
SYNTAX INTEGER
MAX-ACCESS read-write
STATUS current
DESCRIPTION
"Data value."
::= { dataArray9 20 }

dataValue9_21 OBJECT-TYPE
SYNTAX INTEGER
MAX-ACCESS read-write
STATUS current
DESCRIPTION
"Data value."
::= { dataArray9 21 }

dataValue9_22 OBJECT-TYPE
SYNTAX INTEGER
MAX-ACCESS read-write
STATUS current
DESCRIPTION
"Data value."
::= { dataArray9 22 }

dataValue9_23 OBJECT-TYPE
SYNTAX INTEGER
MAX-ACCESS read-write
STATUS current
DESCRIPTION
"Data value."
::= { dataArray9 23 }

dataValue9_24 OBJECT-TYPE
SYNTAX INTEGER
MAX-ACCESS read-write
STATUS current
DESCRIPTION
"Data value."
::= { dataArray9 24 }

dataValue9_25 OBJECT-TYPE
SYNTAX INTEGER
MAX-ACCESS read-write
STATUS current
DESCRIPTION
"Data value."
::= { dataArray9 25 }

dataValue9_26 OBJECT-TYPE
SYNTAX INTEGER
MAX-ACCESS read-write
STATUS current
DESCRIPTION
"Data value."
::= { dataArray9 26 }

dataValue9_27 OBJECT-TYPE
SYNTAX INTEGER
MAX-ACCESS read-write
STATUS current
DESCRIPTION
"Data value."
::= { dataArray9 27 }

dataValue9_28 OBJECT-TYPE
SYNTAX INTEGER
MAX-ACCESS read-write
STATUS current
DESCRIPTION
"Data value."
::= { dataArray9 28 }

dataValue9_29 OBJECT-TYPE
SYNTAX INTEGER
MAX-ACCESS read-write
STATUS current
DESCRIPTION
"Data value."
::= { dataArray9 29 }

dataValue9_30 OBJECT-TYPE
SYNTAX INTEGER
MAX-ACCESS read-write
STATUS current
DESCRIPTION
"Data value."
::= { dataArray9 30 }

dataValue9_31 OBJECT-TYPE
SYNTAX INTEGER
MAX-ACCESS read-write
STATUS current
DESCRIPTION
"Data value."
::= { dataArray9 31 }

dataValue9_32 OBJECT-TYPE
SYNTAX INTEGER
MAX-ACCESS read-write
STATUS current
DESCRIPTION
"Data value."
::= { dataArray9 32 }

dataValue9_33 OBJECT-TYPE
SYNTAX INTEGER
MAX-ACCESS read-write
STATUS current
DESCRIPTION
"Data value."
::= { dataArray9 33 }

dataValue9_34 OBJECT-TYPE
SYNTAX INTEGER
MAX-ACCESS read-write
STATUS current
DESCRIPTION
"Data value."
::= { dataArray9 34 }

dataValue9_35 OBJECT-TYPE
SYNTAX INTEGER
MAX-ACCESS read-write
STATUS current
DESCRIPTION
"Data value."
::= { dataArray9 35 }

dataValue9_36 OBJECT-TYPE
SYNTAX INTEGER
MAX-ACCESS read-write
STATUS current
DESCRIPTION
"Data value."
::= { dataArray9 36 }

dataValue9_37 OBJECT-TYPE
SYNTAX INTEGER
MAX-ACCESS read-write
STATUS current
DESCRIPTION
"Data value."
::= { dataArray9 37 }

dataValue9_38 OBJECT-TYPE
SYNTAX INTEGER
MAX-ACCESS read-write
STATUS current
DESCRIPTION
"Data value."
::= { dataArray9 38 }

dataValue9_39 OBJECT-TYPE
SYNTAX INTEGER
MAX-ACCESS read-write
STATUS current
DESCRIPTION
"Data value."
::= { dataArray9 39 }

dataValue9_40 OBJECT-TYPE
SYNTAX INTEGER
MAX-ACCESS read-write
STATUS current
DESCRIPTION
"Data value."
::= { dataArray9 40 }

dataValue9_41 OBJECT-TYPE
SYNTAX INTEGER
MAX-ACCESS read-write
STATUS current
DESCRIPTION
"Data value."
::= { dataArray9 41 }

dataValue9_42 OBJECT-TYPE
SYNTAX INTEGER
MAX-ACCESS read-write
STATUS current
DESCRIPTION
"Data value."
::= { dataArray9 42 }

dataValue9_43 OBJECT-TYPE
SYNTAX INTEGER
MAX-ACCESS read-write
STATUS current
DESCRIPTION
"Data value."
::= { dataArray9 43 }

dataValue9_44 OBJECT-TYPE
SYNTAX INTEGER
MAX-ACCESS read-write
STATUS current
DESCRIPTION
"Data value."
::= { dataArray9 44 }

dataValue9_45 OBJECT-TYPE
SYNTAX INTEGER
MAX-ACCESS read-write
STATUS current
DESCRIPTION
"Data value."
::= { dataArray9 45 }

dataValue9_46 OBJECT-TYPE
SYNTAX INTEGER
MAX-ACCESS read-write
STATUS current
DESCRIPTION
"Data value."
::= { dataArray9 46 }

dataValue9_47 OBJECT-TYPE
SYNTAX INTEGER
MAX-ACCESS read-write
STATUS current
DESCRIPTION
"Data value."
::= { dataArray9 47 }

dataValue9_48 OBJECT-TYPE
SYNTAX INTEGER
MAX-ACCESS read-write
STATUS current
DESCRIPTION
"Data value."
::= { dataArray9 48 }

dataValue9_49 OBJECT-TYPE
SYNTAX INTEGER
MAX-ACCESS read-write
STATUS current
DESCRIPTION
"Data value."
::= { dataArray9 49 }

dataValue9_50 OBJECT-TYPE
SYNTAX INTEGER
MAX-ACCESS read-write
STATUS current
DESCRIPTION
"Data value."
::= { dataArray9 50 }

dataValue9_51 OBJECT-TYPE
SYNTAX INTEGER
MAX-ACCESS read-write
STATUS current
DESCRIPTION
"Data value."
::= { dataArray9 51 }

dataValue9_52 OBJECT-TYPE
SYNTAX INTEGER
MAX-ACCESS read-write
STATUS current
DESCRIPTION
"Data value."
::= { dataArray9 52 }

dataValue9_53 OBJECT-TYPE
SYNTAX INTEGER
MAX-ACCESS read-write
STATUS current
DESCRIPTION
"Data value."
::= { dataArray9 53 }

dataValue9_54 OBJECT-TYPE
SYNTAX INTEGER
MAX-ACCESS read-write
STATUS current
DESCRIPTION
"Data value."
::= { dataArray9 54 }

dataValue9_55 OBJECT-TYPE
SYNTAX INTEGER
MAX-ACCESS read-write
STATUS current
DESCRIPTION
"Data value."
::= { dataArray9 55 }

dataValue9_56 OBJECT-TYPE
SYNTAX INTEGER
MAX-ACCESS read-write
STATUS current
DESCRIPTION
"Data value."
::= { dataArray9 56 }

dataValue9_57 OBJECT-TYPE
SYNTAX INTEGER
MAX-ACCESS read-write
STATUS current
DESCRIPTION
"Data value."
::= { dataArray9 57 }

dataValue9_58 OBJECT-TYPE
SYNTAX INTEGER
MAX-ACCESS read-write
STATUS current
DESCRIPTION
"Data value."
::= { dataArray9 58 }

dataValue9_59 OBJECT-TYPE
SYNTAX INTEGER
MAX-ACCESS read-write
STATUS current
DESCRIPTION
"Data value."
::= { dataArray9 59 }

dataValue9_60 OBJECT-TYPE
SYNTAX INTEGER
MAX-ACCESS read-write
STATUS current
DESCRIPTION
"Data value."
::= { dataArray9 60 }

dataValue9_61 OBJECT-TYPE
SYNTAX INTEGER
MAX-ACCESS read-write
STATUS current
DESCRIPTION
"Data value."
::= { dataArray9 61 }

dataValue9_62 OBJECT-TYPE
SYNTAX INTEGER
MAX-ACCESS read-write
STATUS current
DESCRIPTION
"Data value."
::= { dataArray9 62 }

dataValue9_63 OBJECT-TYPE
SYNTAX INTEGER
MAX-ACCESS read-write
STATUS current
DESCRIPTION
"Data value."
::= { dataArray9 63 }

dataValue9_64 OBJECT-TYPE
SYNTAX INTEGER
MAX-ACCESS read-write
STATUS current
DESCRIPTION
"Data value."
::= { dataArray9 64 }

dataValue9_65 OBJECT-TYPE
SYNTAX INTEGER
MAX-ACCESS read-write
STATUS current
DESCRIPTION
"Data value."
::= { dataArray9 65 }

dataValue9_66 OBJECT-TYPE
SYNTAX INTEGER
MAX-ACCESS read-write
STATUS current
DESCRIPTION
"Data value."
::= { dataArray9 66 }

dataValue9_67 OBJECT-TYPE
SYNTAX INTEGER
MAX-ACCESS read-write
STATUS current
DESCRIPTION
"Data value."
::= { dataArray9 67 }

dataValue9_68 OBJECT-TYPE
SYNTAX INTEGER
MAX-ACCESS read-write
STATUS current
DESCRIPTION
"Data value."
::= { dataArray9 68 }

dataValue9_69 OBJECT-TYPE
SYNTAX INTEGER
MAX-ACCESS read-write
STATUS current
DESCRIPTION
"Data value."
::= { dataArray9 69 }

dataValue9_70 OBJECT-TYPE
SYNTAX INTEGER
MAX-ACCESS read-write
STATUS current
DESCRIPTION
"Data value."
::= { dataArray9 70 }

dataValue9_71 OBJECT-TYPE
SYNTAX INTEGER
MAX-ACCESS read-write
STATUS current
DESCRIPTION
"Data value."
::= { dataArray9 71 }

dataValue9_72 OBJECT-TYPE
SYNTAX INTEGER
MAX-ACCESS read-write
STATUS current
DESCRIPTION
"Data value."
::= { dataArray9 72 }

dataValue9_73 OBJECT-TYPE
SYNTAX INTEGER
MAX-ACCESS read-write
STATUS current
DESCRIPTION
"Data value."
::= { dataArray9 73 }

dataValue9_74 OBJECT-TYPE
SYNTAX INTEGER
MAX-ACCESS read-write
STATUS current
DESCRIPTION
"Data value."
::= { dataArray9 74 }

dataValue9_75 OBJECT-TYPE
SYNTAX INTEGER
MAX-ACCESS read-write
STATUS current
DESCRIPTION
"Data value."
::= { dataArray9 75 }

dataValue9_76 OBJECT-TYPE
SYNTAX INTEGER
MAX-ACCESS read-write
STATUS current
DESCRIPTION
"Data value."
::= { dataArray9 76 }

dataValue9_77 OBJECT-TYPE
SYNTAX INTEGER
MAX-ACCESS read-write
STATUS current
DESCRIPTION
"Data value."
::= { dataArray9 77 }

dataValue9_78 OBJECT-TYPE
SYNTAX INTEGER
MAX-ACCESS read-write
STATUS current
DESCRIPTION
"Data value."
::= { dataArray9 78 }

dataValue9_79 OBJECT-TYPE
SYNTAX INTEGER
MAX-ACCESS read-write
STATUS current
DESCRIPTION
"Data value."
::= { dataArray9 79 }

dataValue9_80 OBJECT-TYPE
SYNTAX INTEGER
MAX-ACCESS read-write
STATUS current
DESCRIPTION
"Data value."
::= { dataArray9 80 }

dataValue9_81 OBJECT-TYPE
SYNTAX INTEGER
MAX-ACCESS read-write
STATUS current
DESCRIPTION
"Data value."
::= { dataArray9 81 }

dataValue9_82 OBJECT-TYPE
SYNTAX INTEGER
MAX-ACCESS read-write
STATUS current
DESCRIPTION
"Data value."
::= { dataArray9 82 }

dataValue9_83 OBJECT-TYPE
SYNTAX INTEGER
MAX-ACCESS read-write
STATUS current
DESCRIPTION
"Data value."
::= { dataArray9 83 }

dataValue9_84 OBJECT-TYPE
SYNTAX INTEGER
MAX-ACCESS read-write
STATUS current
DESCRIPTION
"Data value."
::= { dataArray9 84 }

dataValue9_85 OBJECT-TYPE
SYNTAX INTEGER
MAX-ACCESS read-write
STATUS current
DESCRIPTION
"Data value."
::= { dataArray9 85 }

dataValue9_86 OBJECT-TYPE
SYNTAX INTEGER
MAX-ACCESS read-write
STATUS current
DESCRIPTION
"Data value."
::= { dataArray9 86 }

dataValue9_87 OBJECT-TYPE
SYNTAX INTEGER
MAX-ACCESS read-write
STATUS current
DESCRIPTION
"Data value."
::= { dataArray9 87 }

dataValue9_88 OBJECT-TYPE
SYNTAX INTEGER
MAX-ACCESS read-write
STATUS current
DESCRIPTION
"Data value."
::= { dataArray9 88 }

dataValue9_89 OBJECT-TYPE
SYNTAX INTEGER
MAX-ACCESS read-write
STATUS current
DESCRIPTION
"Data value."
::= { dataArray9 89 }

dataValue9_90 OBJECT-TYPE
SYNTAX INTEGER
MAX-ACCESS read-write
STATUS current
DESCRIPTION
"Data value."
::= { dataArray9 90 }

dataValue9_91 OBJECT-TYPE
SYNTAX INTEGER
MAX-ACCESS read-write
STATUS current
DESCRIPTION
"Data value."
::= { dataArray9 91 }

dataValue9_92 OBJECT-TYPE
SYNTAX INTEGER
MAX-ACCESS read-write
STATUS current
DESCRIPTION
"Data value."
::= { dataArray9 92 }

dataValue9_93 OBJECT-TYPE
SYNTAX INTEGER
MAX-ACCESS read-write
STATUS current
DESCRIPTION
"Data value."
::= { dataArray9 93 }

dataValue9_94 OBJECT-TYPE
SYNTAX INTEGER
MAX-ACCESS read-write
STATUS current
DESCRIPTION
"Data value."
::= { dataArray9 94 }

dataValue9_95 OBJECT-TYPE
SYNTAX INTEGER
MAX-ACCESS read-write
STATUS current
DESCRIPTION
"Data value."
::= { dataArray9 95 }

dataValue9_96 OBJECT-TYPE
SYNTAX INTEGER
MAX-ACCESS read-write
STATUS current
DESCRIPTION
"Data value."
::= { dataArray9 96 }

dataValue9_97 OBJECT-TYPE
SYNTAX INTEGER
MAX-ACCESS read-write
STATUS current
DESCRIPTION
"Data value."
::= { dataArray9 97 }

dataValue9_98 OBJECT-TYPE
SYNTAX INTEGER
MAX-ACCESS read-write
STATUS current
DESCRIPTION
"Data value."
::= { dataArray9 98 }

dataValue9_99 OBJECT-TYPE
SYNTAX INTEGER
MAX-ACCESS read-write
STATUS current
DESCRIPTION
"Data value."
::= { dataArray9 99 }

dataArray10 OBJECT IDENTIFIER ::= { s08090201_trane_st_jude_v1_00b 10 }

dataValue10_0 OBJECT-TYPE
SYNTAX INTEGER
MAX-ACCESS read-write
STATUS current
DESCRIPTION
"Data value."
::= { dataArray10 0 }

dataValue10_1 OBJECT-TYPE
SYNTAX INTEGER
MAX-ACCESS read-write
STATUS current
DESCRIPTION
"Data value."
::= { dataArray10 1 }

dataValue10_2 OBJECT-TYPE
SYNTAX INTEGER
MAX-ACCESS read-write
STATUS current
DESCRIPTION
"Data value."
::= { dataArray10 2 }

dataValue10_3 OBJECT-TYPE
SYNTAX INTEGER
MAX-ACCESS read-write
STATUS current
DESCRIPTION
"Data value."
::= { dataArray10 3 }

dataValue10_4 OBJECT-TYPE
SYNTAX INTEGER
MAX-ACCESS read-write
STATUS current
DESCRIPTION
"Data value."
::= { dataArray10 4 }

dataValue10_5 OBJECT-TYPE
SYNTAX INTEGER
MAX-ACCESS read-write
STATUS current
DESCRIPTION
"Data value."
::= { dataArray10 5 }

dataValue10_6 OBJECT-TYPE
SYNTAX INTEGER
MAX-ACCESS read-write
STATUS current
DESCRIPTION
"Data value."
::= { dataArray10 6 }

dataValue10_7 OBJECT-TYPE
SYNTAX INTEGER
MAX-ACCESS read-write
STATUS current
DESCRIPTION
"Data value."
::= { dataArray10 7 }

dataValue10_8 OBJECT-TYPE
SYNTAX INTEGER
MAX-ACCESS read-write
STATUS current
DESCRIPTION
"Data value."
::= { dataArray10 8 }

dataValue10_9 OBJECT-TYPE
SYNTAX INTEGER
MAX-ACCESS read-write
STATUS current
DESCRIPTION
"Data value."
::= { dataArray10 9 }

dataValue10_10 OBJECT-TYPE
SYNTAX INTEGER
MAX-ACCESS read-write
STATUS current
DESCRIPTION
"Data value."
::= { dataArray10 10 }

dataValue10_11 OBJECT-TYPE
SYNTAX INTEGER
MAX-ACCESS read-write
STATUS current
DESCRIPTION
"Data value."
::= { dataArray10 11 }

dataValue10_12 OBJECT-TYPE
SYNTAX INTEGER
MAX-ACCESS read-write
STATUS current
DESCRIPTION
"Data value."
::= { dataArray10 12 }

dataValue10_13 OBJECT-TYPE
SYNTAX INTEGER
MAX-ACCESS read-write
STATUS current
DESCRIPTION
"Data value."
::= { dataArray10 13 }

dataValue10_14 OBJECT-TYPE
SYNTAX INTEGER
MAX-ACCESS read-write
STATUS current
DESCRIPTION
"Data value."
::= { dataArray10 14 }

dataValue10_15 OBJECT-TYPE
SYNTAX INTEGER
MAX-ACCESS read-write
STATUS current
DESCRIPTION
"Data value."
::= { dataArray10 15 }

dataValue10_16 OBJECT-TYPE
SYNTAX INTEGER
MAX-ACCESS read-write
STATUS current
DESCRIPTION
"Data value."
::= { dataArray10 16 }

dataValue10_17 OBJECT-TYPE
SYNTAX INTEGER
MAX-ACCESS read-write
STATUS current
DESCRIPTION
"Data value."
::= { dataArray10 17 }

dataValue10_18 OBJECT-TYPE
SYNTAX INTEGER
MAX-ACCESS read-write
STATUS current
DESCRIPTION
"Data value."
::= { dataArray10 18 }

dataValue10_19 OBJECT-TYPE
SYNTAX INTEGER
MAX-ACCESS read-write
STATUS current
DESCRIPTION
"Data value."
::= { dataArray10 19 }

dataValue10_20 OBJECT-TYPE
SYNTAX INTEGER
MAX-ACCESS read-write
STATUS current
DESCRIPTION
"Data value."
::= { dataArray10 20 }

dataValue10_21 OBJECT-TYPE
SYNTAX INTEGER
MAX-ACCESS read-write
STATUS current
DESCRIPTION
"Data value."
::= { dataArray10 21 }

dataValue10_22 OBJECT-TYPE
SYNTAX INTEGER
MAX-ACCESS read-write
STATUS current
DESCRIPTION
"Data value."
::= { dataArray10 22 }

dataValue10_23 OBJECT-TYPE
SYNTAX INTEGER
MAX-ACCESS read-write
STATUS current
DESCRIPTION
"Data value."
::= { dataArray10 23 }

dataValue10_24 OBJECT-TYPE
SYNTAX INTEGER
MAX-ACCESS read-write
STATUS current
DESCRIPTION
"Data value."
::= { dataArray10 24 }

dataValue10_25 OBJECT-TYPE
SYNTAX INTEGER
MAX-ACCESS read-write
STATUS current
DESCRIPTION
"Data value."
::= { dataArray10 25 }

dataValue10_26 OBJECT-TYPE
SYNTAX INTEGER
MAX-ACCESS read-write
STATUS current
DESCRIPTION
"Data value."
::= { dataArray10 26 }

dataValue10_27 OBJECT-TYPE
SYNTAX INTEGER
MAX-ACCESS read-write
STATUS current
DESCRIPTION
"Data value."
::= { dataArray10 27 }

dataValue10_28 OBJECT-TYPE
SYNTAX INTEGER
MAX-ACCESS read-write
STATUS current
DESCRIPTION
"Data value."
::= { dataArray10 28 }

dataValue10_29 OBJECT-TYPE
SYNTAX INTEGER
MAX-ACCESS read-write
STATUS current
DESCRIPTION
"Data value."
::= { dataArray10 29 }

dataValue10_30 OBJECT-TYPE
SYNTAX INTEGER
MAX-ACCESS read-write
STATUS current
DESCRIPTION
"Data value."
::= { dataArray10 30 }

dataValue10_31 OBJECT-TYPE
SYNTAX INTEGER
MAX-ACCESS read-write
STATUS current
DESCRIPTION
"Data value."
::= { dataArray10 31 }

dataValue10_32 OBJECT-TYPE
SYNTAX INTEGER
MAX-ACCESS read-write
STATUS current
DESCRIPTION
"Data value."
::= { dataArray10 32 }

dataValue10_33 OBJECT-TYPE
SYNTAX INTEGER
MAX-ACCESS read-write
STATUS current
DESCRIPTION
"Data value."
::= { dataArray10 33 }

dataValue10_34 OBJECT-TYPE
SYNTAX INTEGER
MAX-ACCESS read-write
STATUS current
DESCRIPTION
"Data value."
::= { dataArray10 34 }

dataValue10_35 OBJECT-TYPE
SYNTAX INTEGER
MAX-ACCESS read-write
STATUS current
DESCRIPTION
"Data value."
::= { dataArray10 35 }

dataValue10_36 OBJECT-TYPE
SYNTAX INTEGER
MAX-ACCESS read-write
STATUS current
DESCRIPTION
"Data value."
::= { dataArray10 36 }

dataValue10_37 OBJECT-TYPE
SYNTAX INTEGER
MAX-ACCESS read-write
STATUS current
DESCRIPTION
"Data value."
::= { dataArray10 37 }

dataValue10_38 OBJECT-TYPE
SYNTAX INTEGER
MAX-ACCESS read-write
STATUS current
DESCRIPTION
"Data value."
::= { dataArray10 38 }

dataValue10_39 OBJECT-TYPE
SYNTAX INTEGER
MAX-ACCESS read-write
STATUS current
DESCRIPTION
"Data value."
::= { dataArray10 39 }

dataValue10_40 OBJECT-TYPE
SYNTAX INTEGER
MAX-ACCESS read-write
STATUS current
DESCRIPTION
"Data value."
::= { dataArray10 40 }

dataValue10_41 OBJECT-TYPE
SYNTAX INTEGER
MAX-ACCESS read-write
STATUS current
DESCRIPTION
"Data value."
::= { dataArray10 41 }

dataValue10_42 OBJECT-TYPE
SYNTAX INTEGER
MAX-ACCESS read-write
STATUS current
DESCRIPTION
"Data value."
::= { dataArray10 42 }

dataValue10_43 OBJECT-TYPE
SYNTAX INTEGER
MAX-ACCESS read-write
STATUS current
DESCRIPTION
"Data value."
::= { dataArray10 43 }

dataValue10_44 OBJECT-TYPE
SYNTAX INTEGER
MAX-ACCESS read-write
STATUS current
DESCRIPTION
"Data value."
::= { dataArray10 44 }

dataValue10_45 OBJECT-TYPE
SYNTAX INTEGER
MAX-ACCESS read-write
STATUS current
DESCRIPTION
"Data value."
::= { dataArray10 45 }

dataValue10_46 OBJECT-TYPE
SYNTAX INTEGER
MAX-ACCESS read-write
STATUS current
DESCRIPTION
"Data value."
::= { dataArray10 46 }

dataValue10_47 OBJECT-TYPE
SYNTAX INTEGER
MAX-ACCESS read-write
STATUS current
DESCRIPTION
"Data value."
::= { dataArray10 47 }

dataValue10_48 OBJECT-TYPE
SYNTAX INTEGER
MAX-ACCESS read-write
STATUS current
DESCRIPTION
"Data value."
::= { dataArray10 48 }

dataValue10_49 OBJECT-TYPE
SYNTAX INTEGER
MAX-ACCESS read-write
STATUS current
DESCRIPTION
"Data value."
::= { dataArray10 49 }

dataValue10_50 OBJECT-TYPE
SYNTAX INTEGER
MAX-ACCESS read-write
STATUS current
DESCRIPTION
"Data value."
::= { dataArray10 50 }

dataValue10_51 OBJECT-TYPE
SYNTAX INTEGER
MAX-ACCESS read-write
STATUS current
DESCRIPTION
"Data value."
::= { dataArray10 51 }

dataValue10_52 OBJECT-TYPE
SYNTAX INTEGER
MAX-ACCESS read-write
STATUS current
DESCRIPTION
"Data value."
::= { dataArray10 52 }

dataValue10_53 OBJECT-TYPE
SYNTAX INTEGER
MAX-ACCESS read-write
STATUS current
DESCRIPTION
"Data value."
::= { dataArray10 53 }

dataValue10_54 OBJECT-TYPE
SYNTAX INTEGER
MAX-ACCESS read-write
STATUS current
DESCRIPTION
"Data value."
::= { dataArray10 54 }

dataValue10_55 OBJECT-TYPE
SYNTAX INTEGER
MAX-ACCESS read-write
STATUS current
DESCRIPTION
"Data value."
::= { dataArray10 55 }

dataValue10_56 OBJECT-TYPE
SYNTAX INTEGER
MAX-ACCESS read-write
STATUS current
DESCRIPTION
"Data value."
::= { dataArray10 56 }

dataValue10_57 OBJECT-TYPE
SYNTAX INTEGER
MAX-ACCESS read-write
STATUS current
DESCRIPTION
"Data value."
::= { dataArray10 57 }

dataValue10_58 OBJECT-TYPE
SYNTAX INTEGER
MAX-ACCESS read-write
STATUS current
DESCRIPTION
"Data value."
::= { dataArray10 58 }

dataValue10_59 OBJECT-TYPE
SYNTAX INTEGER
MAX-ACCESS read-write
STATUS current
DESCRIPTION
"Data value."
::= { dataArray10 59 }

dataValue10_60 OBJECT-TYPE
SYNTAX INTEGER
MAX-ACCESS read-write
STATUS current
DESCRIPTION
"Data value."
::= { dataArray10 60 }

dataValue10_61 OBJECT-TYPE
SYNTAX INTEGER
MAX-ACCESS read-write
STATUS current
DESCRIPTION
"Data value."
::= { dataArray10 61 }

dataValue10_62 OBJECT-TYPE
SYNTAX INTEGER
MAX-ACCESS read-write
STATUS current
DESCRIPTION
"Data value."
::= { dataArray10 62 }

dataValue10_63 OBJECT-TYPE
SYNTAX INTEGER
MAX-ACCESS read-write
STATUS current
DESCRIPTION
"Data value."
::= { dataArray10 63 }

dataValue10_64 OBJECT-TYPE
SYNTAX INTEGER
MAX-ACCESS read-write
STATUS current
DESCRIPTION
"Data value."
::= { dataArray10 64 }

dataValue10_65 OBJECT-TYPE
SYNTAX INTEGER
MAX-ACCESS read-write
STATUS current
DESCRIPTION
"Data value."
::= { dataArray10 65 }

dataValue10_66 OBJECT-TYPE
SYNTAX INTEGER
MAX-ACCESS read-write
STATUS current
DESCRIPTION
"Data value."
::= { dataArray10 66 }

dataValue10_67 OBJECT-TYPE
SYNTAX INTEGER
MAX-ACCESS read-write
STATUS current
DESCRIPTION
"Data value."
::= { dataArray10 67 }

dataValue10_68 OBJECT-TYPE
SYNTAX INTEGER
MAX-ACCESS read-write
STATUS current
DESCRIPTION
"Data value."
::= { dataArray10 68 }

dataValue10_69 OBJECT-TYPE
SYNTAX INTEGER
MAX-ACCESS read-write
STATUS current
DESCRIPTION
"Data value."
::= { dataArray10 69 }

dataValue10_70 OBJECT-TYPE
SYNTAX INTEGER
MAX-ACCESS read-write
STATUS current
DESCRIPTION
"Data value."
::= { dataArray10 70 }

dataValue10_71 OBJECT-TYPE
SYNTAX INTEGER
MAX-ACCESS read-write
STATUS current
DESCRIPTION
"Data value."
::= { dataArray10 71 }

dataValue10_72 OBJECT-TYPE
SYNTAX INTEGER
MAX-ACCESS read-write
STATUS current
DESCRIPTION
"Data value."
::= { dataArray10 72 }

dataValue10_73 OBJECT-TYPE
SYNTAX INTEGER
MAX-ACCESS read-write
STATUS current
DESCRIPTION
"Data value."
::= { dataArray10 73 }

dataValue10_74 OBJECT-TYPE
SYNTAX INTEGER
MAX-ACCESS read-write
STATUS current
DESCRIPTION
"Data value."
::= { dataArray10 74 }

dataValue10_75 OBJECT-TYPE
SYNTAX INTEGER
MAX-ACCESS read-write
STATUS current
DESCRIPTION
"Data value."
::= { dataArray10 75 }

dataValue10_76 OBJECT-TYPE
SYNTAX INTEGER
MAX-ACCESS read-write
STATUS current
DESCRIPTION
"Data value."
::= { dataArray10 76 }

dataValue10_77 OBJECT-TYPE
SYNTAX INTEGER
MAX-ACCESS read-write
STATUS current
DESCRIPTION
"Data value."
::= { dataArray10 77 }

dataValue10_78 OBJECT-TYPE
SYNTAX INTEGER
MAX-ACCESS read-write
STATUS current
DESCRIPTION
"Data value."
::= { dataArray10 78 }

dataValue10_79 OBJECT-TYPE
SYNTAX INTEGER
MAX-ACCESS read-write
STATUS current
DESCRIPTION
"Data value."
::= { dataArray10 79 }

dataValue10_80 OBJECT-TYPE
SYNTAX INTEGER
MAX-ACCESS read-write
STATUS current
DESCRIPTION
"Data value."
::= { dataArray10 80 }

dataValue10_81 OBJECT-TYPE
SYNTAX INTEGER
MAX-ACCESS read-write
STATUS current
DESCRIPTION
"Data value."
::= { dataArray10 81 }

dataValue10_82 OBJECT-TYPE
SYNTAX INTEGER
MAX-ACCESS read-write
STATUS current
DESCRIPTION
"Data value."
::= { dataArray10 82 }

dataValue10_83 OBJECT-TYPE
SYNTAX INTEGER
MAX-ACCESS read-write
STATUS current
DESCRIPTION
"Data value."
::= { dataArray10 83 }

dataValue10_84 OBJECT-TYPE
SYNTAX INTEGER
MAX-ACCESS read-write
STATUS current
DESCRIPTION
"Data value."
::= { dataArray10 84 }

dataValue10_85 OBJECT-TYPE
SYNTAX INTEGER
MAX-ACCESS read-write
STATUS current
DESCRIPTION
"Data value."
::= { dataArray10 85 }

dataValue10_86 OBJECT-TYPE
SYNTAX INTEGER
MAX-ACCESS read-write
STATUS current
DESCRIPTION
"Data value."
::= { dataArray10 86 }

dataValue10_87 OBJECT-TYPE
SYNTAX INTEGER
MAX-ACCESS read-write
STATUS current
DESCRIPTION
"Data value."
::= { dataArray10 87 }

dataValue10_88 OBJECT-TYPE
SYNTAX INTEGER
MAX-ACCESS read-write
STATUS current
DESCRIPTION
"Data value."
::= { dataArray10 88 }

dataValue10_89 OBJECT-TYPE
SYNTAX INTEGER
MAX-ACCESS read-write
STATUS current
DESCRIPTION
"Data value."
::= { dataArray10 89 }

dataValue10_90 OBJECT-TYPE
SYNTAX INTEGER
MAX-ACCESS read-write
STATUS current
DESCRIPTION
"Data value."
::= { dataArray10 90 }

dataValue10_91 OBJECT-TYPE
SYNTAX INTEGER
MAX-ACCESS read-write
STATUS current
DESCRIPTION
"Data value."
::= { dataArray10 91 }

dataValue10_92 OBJECT-TYPE
SYNTAX INTEGER
MAX-ACCESS read-write
STATUS current
DESCRIPTION
"Data value."
::= { dataArray10 92 }

dataValue10_93 OBJECT-TYPE
SYNTAX INTEGER
MAX-ACCESS read-write
STATUS current
DESCRIPTION
"Data value."
::= { dataArray10 93 }

dataValue10_94 OBJECT-TYPE
SYNTAX INTEGER
MAX-ACCESS read-write
STATUS current
DESCRIPTION
"Data value."
::= { dataArray10 94 }

dataValue10_95 OBJECT-TYPE
SYNTAX INTEGER
MAX-ACCESS read-write
STATUS current
DESCRIPTION
"Data value."
::= { dataArray10 95 }

dataValue10_96 OBJECT-TYPE
SYNTAX INTEGER
MAX-ACCESS read-write
STATUS current
DESCRIPTION
"Data value."
::= { dataArray10 96 }

dataValue10_97 OBJECT-TYPE
SYNTAX INTEGER
MAX-ACCESS read-write
STATUS current
DESCRIPTION
"Data value."
::= { dataArray10 97 }

dataValue10_98 OBJECT-TYPE
SYNTAX INTEGER
MAX-ACCESS read-write
STATUS current
DESCRIPTION
"Data value."
::= { dataArray10 98 }

dataValue10_99 OBJECT-TYPE
SYNTAX INTEGER
MAX-ACCESS read-write
STATUS current
DESCRIPTION
"Data value."
::= { dataArray10 99 }

dataArray11 OBJECT IDENTIFIER ::= { s08090201_trane_st_jude_v1_00b 11 }

dataValue11_0 OBJECT-TYPE
SYNTAX INTEGER
MAX-ACCESS read-write
STATUS current
DESCRIPTION
"Data value."
::= { dataArray11 0 }

dataValue11_1 OBJECT-TYPE
SYNTAX INTEGER
MAX-ACCESS read-write
STATUS current
DESCRIPTION
"Data value."
::= { dataArray11 1 }

dataValue11_2 OBJECT-TYPE
SYNTAX INTEGER
MAX-ACCESS read-write
STATUS current
DESCRIPTION
"Data value."
::= { dataArray11 2 }

dataValue11_3 OBJECT-TYPE
SYNTAX INTEGER
MAX-ACCESS read-write
STATUS current
DESCRIPTION
"Data value."
::= { dataArray11 3 }

dataValue11_4 OBJECT-TYPE
SYNTAX INTEGER
MAX-ACCESS read-write
STATUS current
DESCRIPTION
"Data value."
::= { dataArray11 4 }

dataValue11_5 OBJECT-TYPE
SYNTAX INTEGER
MAX-ACCESS read-write
STATUS current
DESCRIPTION
"Data value."
::= { dataArray11 5 }

dataValue11_6 OBJECT-TYPE
SYNTAX INTEGER
MAX-ACCESS read-write
STATUS current
DESCRIPTION
"Data value."
::= { dataArray11 6 }

dataValue11_7 OBJECT-TYPE
SYNTAX INTEGER
MAX-ACCESS read-write
STATUS current
DESCRIPTION
"Data value."
::= { dataArray11 7 }

dataValue11_8 OBJECT-TYPE
SYNTAX INTEGER
MAX-ACCESS read-write
STATUS current
DESCRIPTION
"Data value."
::= { dataArray11 8 }

dataValue11_9 OBJECT-TYPE
SYNTAX INTEGER
MAX-ACCESS read-write
STATUS current
DESCRIPTION
"Data value."
::= { dataArray11 9 }

dataValue11_10 OBJECT-TYPE
SYNTAX INTEGER
MAX-ACCESS read-write
STATUS current
DESCRIPTION
"Data value."
::= { dataArray11 10 }

dataValue11_11 OBJECT-TYPE
SYNTAX INTEGER
MAX-ACCESS read-write
STATUS current
DESCRIPTION
"Data value."
::= { dataArray11 11 }

dataValue11_12 OBJECT-TYPE
SYNTAX INTEGER
MAX-ACCESS read-write
STATUS current
DESCRIPTION
"Data value."
::= { dataArray11 12 }

dataValue11_13 OBJECT-TYPE
SYNTAX INTEGER
MAX-ACCESS read-write
STATUS current
DESCRIPTION
"Data value."
::= { dataArray11 13 }

dataValue11_14 OBJECT-TYPE
SYNTAX INTEGER
MAX-ACCESS read-write
STATUS current
DESCRIPTION
"Data value."
::= { dataArray11 14 }

dataValue11_15 OBJECT-TYPE
SYNTAX INTEGER
MAX-ACCESS read-write
STATUS current
DESCRIPTION
"Data value."
::= { dataArray11 15 }

dataValue11_16 OBJECT-TYPE
SYNTAX INTEGER
MAX-ACCESS read-write
STATUS current
DESCRIPTION
"Data value."
::= { dataArray11 16 }

dataValue11_17 OBJECT-TYPE
SYNTAX INTEGER
MAX-ACCESS read-write
STATUS current
DESCRIPTION
"Data value."
::= { dataArray11 17 }

dataValue11_18 OBJECT-TYPE
SYNTAX INTEGER
MAX-ACCESS read-write
STATUS current
DESCRIPTION
"Data value."
::= { dataArray11 18 }

dataValue11_19 OBJECT-TYPE
SYNTAX INTEGER
MAX-ACCESS read-write
STATUS current
DESCRIPTION
"Data value."
::= { dataArray11 19 }

dataValue11_20 OBJECT-TYPE
SYNTAX INTEGER
MAX-ACCESS read-write
STATUS current
DESCRIPTION
"Data value."
::= { dataArray11 20 }

dataValue11_21 OBJECT-TYPE
SYNTAX INTEGER
MAX-ACCESS read-write
STATUS current
DESCRIPTION
"Data value."
::= { dataArray11 21 }

dataValue11_22 OBJECT-TYPE
SYNTAX INTEGER
MAX-ACCESS read-write
STATUS current
DESCRIPTION
"Data value."
::= { dataArray11 22 }

dataValue11_23 OBJECT-TYPE
SYNTAX INTEGER
MAX-ACCESS read-write
STATUS current
DESCRIPTION
"Data value."
::= { dataArray11 23 }

dataValue11_24 OBJECT-TYPE
SYNTAX INTEGER
MAX-ACCESS read-write
STATUS current
DESCRIPTION
"Data value."
::= { dataArray11 24 }

dataValue11_25 OBJECT-TYPE
SYNTAX INTEGER
MAX-ACCESS read-write
STATUS current
DESCRIPTION
"Data value."
::= { dataArray11 25 }

dataValue11_26 OBJECT-TYPE
SYNTAX INTEGER
MAX-ACCESS read-write
STATUS current
DESCRIPTION
"Data value."
::= { dataArray11 26 }

dataValue11_27 OBJECT-TYPE
SYNTAX INTEGER
MAX-ACCESS read-write
STATUS current
DESCRIPTION
"Data value."
::= { dataArray11 27 }

dataValue11_28 OBJECT-TYPE
SYNTAX INTEGER
MAX-ACCESS read-write
STATUS current
DESCRIPTION
"Data value."
::= { dataArray11 28 }

dataValue11_29 OBJECT-TYPE
SYNTAX INTEGER
MAX-ACCESS read-write
STATUS current
DESCRIPTION
"Data value."
::= { dataArray11 29 }

dataValue11_30 OBJECT-TYPE
SYNTAX INTEGER
MAX-ACCESS read-write
STATUS current
DESCRIPTION
"Data value."
::= { dataArray11 30 }

dataValue11_31 OBJECT-TYPE
SYNTAX INTEGER
MAX-ACCESS read-write
STATUS current
DESCRIPTION
"Data value."
::= { dataArray11 31 }

dataValue11_32 OBJECT-TYPE
SYNTAX INTEGER
MAX-ACCESS read-write
STATUS current
DESCRIPTION
"Data value."
::= { dataArray11 32 }

dataValue11_33 OBJECT-TYPE
SYNTAX INTEGER
MAX-ACCESS read-write
STATUS current
DESCRIPTION
"Data value."
::= { dataArray11 33 }

dataValue11_34 OBJECT-TYPE
SYNTAX INTEGER
MAX-ACCESS read-write
STATUS current
DESCRIPTION
"Data value."
::= { dataArray11 34 }

dataValue11_35 OBJECT-TYPE
SYNTAX INTEGER
MAX-ACCESS read-write
STATUS current
DESCRIPTION
"Data value."
::= { dataArray11 35 }

dataValue11_36 OBJECT-TYPE
SYNTAX INTEGER
MAX-ACCESS read-write
STATUS current
DESCRIPTION
"Data value."
::= { dataArray11 36 }

dataValue11_37 OBJECT-TYPE
SYNTAX INTEGER
MAX-ACCESS read-write
STATUS current
DESCRIPTION
"Data value."
::= { dataArray11 37 }

dataValue11_38 OBJECT-TYPE
SYNTAX INTEGER
MAX-ACCESS read-write
STATUS current
DESCRIPTION
"Data value."
::= { dataArray11 38 }

dataValue11_39 OBJECT-TYPE
SYNTAX INTEGER
MAX-ACCESS read-write
STATUS current
DESCRIPTION
"Data value."
::= { dataArray11 39 }

dataValue11_40 OBJECT-TYPE
SYNTAX INTEGER
MAX-ACCESS read-write
STATUS current
DESCRIPTION
"Data value."
::= { dataArray11 40 }

dataValue11_41 OBJECT-TYPE
SYNTAX INTEGER
MAX-ACCESS read-write
STATUS current
DESCRIPTION
"Data value."
::= { dataArray11 41 }

dataValue11_42 OBJECT-TYPE
SYNTAX INTEGER
MAX-ACCESS read-write
STATUS current
DESCRIPTION
"Data value."
::= { dataArray11 42 }

dataValue11_43 OBJECT-TYPE
SYNTAX INTEGER
MAX-ACCESS read-write
STATUS current
DESCRIPTION
"Data value."
::= { dataArray11 43 }

dataValue11_44 OBJECT-TYPE
SYNTAX INTEGER
MAX-ACCESS read-write
STATUS current
DESCRIPTION
"Data value."
::= { dataArray11 44 }

dataValue11_45 OBJECT-TYPE
SYNTAX INTEGER
MAX-ACCESS read-write
STATUS current
DESCRIPTION
"Data value."
::= { dataArray11 45 }

dataValue11_46 OBJECT-TYPE
SYNTAX INTEGER
MAX-ACCESS read-write
STATUS current
DESCRIPTION
"Data value."
::= { dataArray11 46 }

dataValue11_47 OBJECT-TYPE
SYNTAX INTEGER
MAX-ACCESS read-write
STATUS current
DESCRIPTION
"Data value."
::= { dataArray11 47 }

dataValue11_48 OBJECT-TYPE
SYNTAX INTEGER
MAX-ACCESS read-write
STATUS current
DESCRIPTION
"Data value."
::= { dataArray11 48 }

dataValue11_49 OBJECT-TYPE
SYNTAX INTEGER
MAX-ACCESS read-write
STATUS current
DESCRIPTION
"Data value."
::= { dataArray11 49 }

dataValue11_50 OBJECT-TYPE
SYNTAX INTEGER
MAX-ACCESS read-write
STATUS current
DESCRIPTION
"Data value."
::= { dataArray11 50 }

dataValue11_51 OBJECT-TYPE
SYNTAX INTEGER
MAX-ACCESS read-write
STATUS current
DESCRIPTION
"Data value."
::= { dataArray11 51 }

dataValue11_52 OBJECT-TYPE
SYNTAX INTEGER
MAX-ACCESS read-write
STATUS current
DESCRIPTION
"Data value."
::= { dataArray11 52 }

dataValue11_53 OBJECT-TYPE
SYNTAX INTEGER
MAX-ACCESS read-write
STATUS current
DESCRIPTION
"Data value."
::= { dataArray11 53 }

dataValue11_54 OBJECT-TYPE
SYNTAX INTEGER
MAX-ACCESS read-write
STATUS current
DESCRIPTION
"Data value."
::= { dataArray11 54 }

dataValue11_55 OBJECT-TYPE
SYNTAX INTEGER
MAX-ACCESS read-write
STATUS current
DESCRIPTION
"Data value."
::= { dataArray11 55 }

dataValue11_56 OBJECT-TYPE
SYNTAX INTEGER
MAX-ACCESS read-write
STATUS current
DESCRIPTION
"Data value."
::= { dataArray11 56 }

dataValue11_57 OBJECT-TYPE
SYNTAX INTEGER
MAX-ACCESS read-write
STATUS current
DESCRIPTION
"Data value."
::= { dataArray11 57 }

dataValue11_58 OBJECT-TYPE
SYNTAX INTEGER
MAX-ACCESS read-write
STATUS current
DESCRIPTION
"Data value."
::= { dataArray11 58 }

dataValue11_59 OBJECT-TYPE
SYNTAX INTEGER
MAX-ACCESS read-write
STATUS current
DESCRIPTION
"Data value."
::= { dataArray11 59 }

dataValue11_60 OBJECT-TYPE
SYNTAX INTEGER
MAX-ACCESS read-write
STATUS current
DESCRIPTION
"Data value."
::= { dataArray11 60 }

dataValue11_61 OBJECT-TYPE
SYNTAX INTEGER
MAX-ACCESS read-write
STATUS current
DESCRIPTION
"Data value."
::= { dataArray11 61 }

dataValue11_62 OBJECT-TYPE
SYNTAX INTEGER
MAX-ACCESS read-write
STATUS current
DESCRIPTION
"Data value."
::= { dataArray11 62 }

dataValue11_63 OBJECT-TYPE
SYNTAX INTEGER
MAX-ACCESS read-write
STATUS current
DESCRIPTION
"Data value."
::= { dataArray11 63 }

dataValue11_64 OBJECT-TYPE
SYNTAX INTEGER
MAX-ACCESS read-write
STATUS current
DESCRIPTION
"Data value."
::= { dataArray11 64 }

dataValue11_65 OBJECT-TYPE
SYNTAX INTEGER
MAX-ACCESS read-write
STATUS current
DESCRIPTION
"Data value."
::= { dataArray11 65 }

dataValue11_66 OBJECT-TYPE
SYNTAX INTEGER
MAX-ACCESS read-write
STATUS current
DESCRIPTION
"Data value."
::= { dataArray11 66 }

dataValue11_67 OBJECT-TYPE
SYNTAX INTEGER
MAX-ACCESS read-write
STATUS current
DESCRIPTION
"Data value."
::= { dataArray11 67 }

dataValue11_68 OBJECT-TYPE
SYNTAX INTEGER
MAX-ACCESS read-write
STATUS current
DESCRIPTION
"Data value."
::= { dataArray11 68 }

dataValue11_69 OBJECT-TYPE
SYNTAX INTEGER
MAX-ACCESS read-write
STATUS current
DESCRIPTION
"Data value."
::= { dataArray11 69 }

dataValue11_70 OBJECT-TYPE
SYNTAX INTEGER
MAX-ACCESS read-write
STATUS current
DESCRIPTION
"Data value."
::= { dataArray11 70 }

dataValue11_71 OBJECT-TYPE
SYNTAX INTEGER
MAX-ACCESS read-write
STATUS current
DESCRIPTION
"Data value."
::= { dataArray11 71 }

dataValue11_72 OBJECT-TYPE
SYNTAX INTEGER
MAX-ACCESS read-write
STATUS current
DESCRIPTION
"Data value."
::= { dataArray11 72 }

dataValue11_73 OBJECT-TYPE
SYNTAX INTEGER
MAX-ACCESS read-write
STATUS current
DESCRIPTION
"Data value."
::= { dataArray11 73 }

dataValue11_74 OBJECT-TYPE
SYNTAX INTEGER
MAX-ACCESS read-write
STATUS current
DESCRIPTION
"Data value."
::= { dataArray11 74 }

dataValue11_75 OBJECT-TYPE
SYNTAX INTEGER
MAX-ACCESS read-write
STATUS current
DESCRIPTION
"Data value."
::= { dataArray11 75 }

dataValue11_76 OBJECT-TYPE
SYNTAX INTEGER
MAX-ACCESS read-write
STATUS current
DESCRIPTION
"Data value."
::= { dataArray11 76 }

dataValue11_77 OBJECT-TYPE
SYNTAX INTEGER
MAX-ACCESS read-write
STATUS current
DESCRIPTION
"Data value."
::= { dataArray11 77 }

dataValue11_78 OBJECT-TYPE
SYNTAX INTEGER
MAX-ACCESS read-write
STATUS current
DESCRIPTION
"Data value."
::= { dataArray11 78 }

dataValue11_79 OBJECT-TYPE
SYNTAX INTEGER
MAX-ACCESS read-write
STATUS current
DESCRIPTION
"Data value."
::= { dataArray11 79 }

dataValue11_80 OBJECT-TYPE
SYNTAX INTEGER
MAX-ACCESS read-write
STATUS current
DESCRIPTION
"Data value."
::= { dataArray11 80 }

dataValue11_81 OBJECT-TYPE
SYNTAX INTEGER
MAX-ACCESS read-write
STATUS current
DESCRIPTION
"Data value."
::= { dataArray11 81 }

dataValue11_82 OBJECT-TYPE
SYNTAX INTEGER
MAX-ACCESS read-write
STATUS current
DESCRIPTION
"Data value."
::= { dataArray11 82 }

dataValue11_83 OBJECT-TYPE
SYNTAX INTEGER
MAX-ACCESS read-write
STATUS current
DESCRIPTION
"Data value."
::= { dataArray11 83 }

dataValue11_84 OBJECT-TYPE
SYNTAX INTEGER
MAX-ACCESS read-write
STATUS current
DESCRIPTION
"Data value."
::= { dataArray11 84 }

dataValue11_85 OBJECT-TYPE
SYNTAX INTEGER
MAX-ACCESS read-write
STATUS current
DESCRIPTION
"Data value."
::= { dataArray11 85 }

dataValue11_86 OBJECT-TYPE
SYNTAX INTEGER
MAX-ACCESS read-write
STATUS current
DESCRIPTION
"Data value."
::= { dataArray11 86 }

dataValue11_87 OBJECT-TYPE
SYNTAX INTEGER
MAX-ACCESS read-write
STATUS current
DESCRIPTION
"Data value."
::= { dataArray11 87 }

dataValue11_88 OBJECT-TYPE
SYNTAX INTEGER
MAX-ACCESS read-write
STATUS current
DESCRIPTION
"Data value."
::= { dataArray11 88 }

dataValue11_89 OBJECT-TYPE
SYNTAX INTEGER
MAX-ACCESS read-write
STATUS current
DESCRIPTION
"Data value."
::= { dataArray11 89 }

dataValue11_90 OBJECT-TYPE
SYNTAX INTEGER
MAX-ACCESS read-write
STATUS current
DESCRIPTION
"Data value."
::= { dataArray11 90 }

dataValue11_91 OBJECT-TYPE
SYNTAX INTEGER
MAX-ACCESS read-write
STATUS current
DESCRIPTION
"Data value."
::= { dataArray11 91 }

dataValue11_92 OBJECT-TYPE
SYNTAX INTEGER
MAX-ACCESS read-write
STATUS current
DESCRIPTION
"Data value."
::= { dataArray11 92 }

dataValue11_93 OBJECT-TYPE
SYNTAX INTEGER
MAX-ACCESS read-write
STATUS current
DESCRIPTION
"Data value."
::= { dataArray11 93 }

dataValue11_94 OBJECT-TYPE
SYNTAX INTEGER
MAX-ACCESS read-write
STATUS current
DESCRIPTION
"Data value."
::= { dataArray11 94 }

dataValue11_95 OBJECT-TYPE
SYNTAX INTEGER
MAX-ACCESS read-write
STATUS current
DESCRIPTION
"Data value."
::= { dataArray11 95 }

dataValue11_96 OBJECT-TYPE
SYNTAX INTEGER
MAX-ACCESS read-write
STATUS current
DESCRIPTION
"Data value."
::= { dataArray11 96 }

dataValue11_97 OBJECT-TYPE
SYNTAX INTEGER
MAX-ACCESS read-write
STATUS current
DESCRIPTION
"Data value."
::= { dataArray11 97 }

dataValue11_98 OBJECT-TYPE
SYNTAX INTEGER
MAX-ACCESS read-write
STATUS current
DESCRIPTION
"Data value."
::= { dataArray11 98 }

dataValue11_99 OBJECT-TYPE
SYNTAX INTEGER
MAX-ACCESS read-write
STATUS current
DESCRIPTION
"Data value."
::= { dataArray11 99 }

dataArray12 OBJECT IDENTIFIER ::= { s08090201_trane_st_jude_v1_00b 12 }

dataValue12_0 OBJECT-TYPE
SYNTAX INTEGER
MAX-ACCESS read-write
STATUS current
DESCRIPTION
"Data value."
::= { dataArray12 0 }

dataValue12_1 OBJECT-TYPE
SYNTAX INTEGER
MAX-ACCESS read-write
STATUS current
DESCRIPTION
"Data value."
::= { dataArray12 1 }

dataValue12_2 OBJECT-TYPE
SYNTAX INTEGER
MAX-ACCESS read-write
STATUS current
DESCRIPTION
"Data value."
::= { dataArray12 2 }

dataValue12_3 OBJECT-TYPE
SYNTAX INTEGER
MAX-ACCESS read-write
STATUS current
DESCRIPTION
"Data value."
::= { dataArray12 3 }

dataValue12_4 OBJECT-TYPE
SYNTAX INTEGER
MAX-ACCESS read-write
STATUS current
DESCRIPTION
"Data value."
::= { dataArray12 4 }

dataValue12_5 OBJECT-TYPE
SYNTAX INTEGER
MAX-ACCESS read-write
STATUS current
DESCRIPTION
"Data value."
::= { dataArray12 5 }

dataValue12_6 OBJECT-TYPE
SYNTAX INTEGER
MAX-ACCESS read-write
STATUS current
DESCRIPTION
"Data value."
::= { dataArray12 6 }

dataValue12_7 OBJECT-TYPE
SYNTAX INTEGER
MAX-ACCESS read-write
STATUS current
DESCRIPTION
"Data value."
::= { dataArray12 7 }

dataValue12_8 OBJECT-TYPE
SYNTAX INTEGER
MAX-ACCESS read-write
STATUS current
DESCRIPTION
"Data value."
::= { dataArray12 8 }

dataValue12_9 OBJECT-TYPE
SYNTAX INTEGER
MAX-ACCESS read-write
STATUS current
DESCRIPTION
"Data value."
::= { dataArray12 9 }

dataValue12_10 OBJECT-TYPE
SYNTAX INTEGER
MAX-ACCESS read-write
STATUS current
DESCRIPTION
"Data value."
::= { dataArray12 10 }

dataValue12_11 OBJECT-TYPE
SYNTAX INTEGER
MAX-ACCESS read-write
STATUS current
DESCRIPTION
"Data value."
::= { dataArray12 11 }

dataValue12_12 OBJECT-TYPE
SYNTAX INTEGER
MAX-ACCESS read-write
STATUS current
DESCRIPTION
"Data value."
::= { dataArray12 12 }

dataValue12_13 OBJECT-TYPE
SYNTAX INTEGER
MAX-ACCESS read-write
STATUS current
DESCRIPTION
"Data value."
::= { dataArray12 13 }

dataValue12_14 OBJECT-TYPE
SYNTAX INTEGER
MAX-ACCESS read-write
STATUS current
DESCRIPTION
"Data value."
::= { dataArray12 14 }

dataValue12_15 OBJECT-TYPE
SYNTAX INTEGER
MAX-ACCESS read-write
STATUS current
DESCRIPTION
"Data value."
::= { dataArray12 15 }

dataValue12_16 OBJECT-TYPE
SYNTAX INTEGER
MAX-ACCESS read-write
STATUS current
DESCRIPTION
"Data value."
::= { dataArray12 16 }

dataValue12_17 OBJECT-TYPE
SYNTAX INTEGER
MAX-ACCESS read-write
STATUS current
DESCRIPTION
"Data value."
::= { dataArray12 17 }

dataValue12_18 OBJECT-TYPE
SYNTAX INTEGER
MAX-ACCESS read-write
STATUS current
DESCRIPTION
"Data value."
::= { dataArray12 18 }

dataValue12_19 OBJECT-TYPE
SYNTAX INTEGER
MAX-ACCESS read-write
STATUS current
DESCRIPTION
"Data value."
::= { dataArray12 19 }

dataValue12_20 OBJECT-TYPE
SYNTAX INTEGER
MAX-ACCESS read-write
STATUS current
DESCRIPTION
"Data value."
::= { dataArray12 20 }

dataValue12_21 OBJECT-TYPE
SYNTAX INTEGER
MAX-ACCESS read-write
STATUS current
DESCRIPTION
"Data value."
::= { dataArray12 21 }

dataValue12_22 OBJECT-TYPE
SYNTAX INTEGER
MAX-ACCESS read-write
STATUS current
DESCRIPTION
"Data value."
::= { dataArray12 22 }

dataValue12_23 OBJECT-TYPE
SYNTAX INTEGER
MAX-ACCESS read-write
STATUS current
DESCRIPTION
"Data value."
::= { dataArray12 23 }

dataValue12_24 OBJECT-TYPE
SYNTAX INTEGER
MAX-ACCESS read-write
STATUS current
DESCRIPTION
"Data value."
::= { dataArray12 24 }

dataValue12_25 OBJECT-TYPE
SYNTAX INTEGER
MAX-ACCESS read-write
STATUS current
DESCRIPTION
"Data value."
::= { dataArray12 25 }

dataValue12_26 OBJECT-TYPE
SYNTAX INTEGER
MAX-ACCESS read-write
STATUS current
DESCRIPTION
"Data value."
::= { dataArray12 26 }

dataValue12_27 OBJECT-TYPE
SYNTAX INTEGER
MAX-ACCESS read-write
STATUS current
DESCRIPTION
"Data value."
::= { dataArray12 27 }

dataValue12_28 OBJECT-TYPE
SYNTAX INTEGER
MAX-ACCESS read-write
STATUS current
DESCRIPTION
"Data value."
::= { dataArray12 28 }

dataValue12_29 OBJECT-TYPE
SYNTAX INTEGER
MAX-ACCESS read-write
STATUS current
DESCRIPTION
"Data value."
::= { dataArray12 29 }

dataValue12_30 OBJECT-TYPE
SYNTAX INTEGER
MAX-ACCESS read-write
STATUS current
DESCRIPTION
"Data value."
::= { dataArray12 30 }

dataValue12_31 OBJECT-TYPE
SYNTAX INTEGER
MAX-ACCESS read-write
STATUS current
DESCRIPTION
"Data value."
::= { dataArray12 31 }

dataValue12_32 OBJECT-TYPE
SYNTAX INTEGER
MAX-ACCESS read-write
STATUS current
DESCRIPTION
"Data value."
::= { dataArray12 32 }

dataValue12_33 OBJECT-TYPE
SYNTAX INTEGER
MAX-ACCESS read-write
STATUS current
DESCRIPTION
"Data value."
::= { dataArray12 33 }

dataValue12_34 OBJECT-TYPE
SYNTAX INTEGER
MAX-ACCESS read-write
STATUS current
DESCRIPTION
"Data value."
::= { dataArray12 34 }

dataValue12_35 OBJECT-TYPE
SYNTAX INTEGER
MAX-ACCESS read-write
STATUS current
DESCRIPTION
"Data value."
::= { dataArray12 35 }

dataValue12_36 OBJECT-TYPE
SYNTAX INTEGER
MAX-ACCESS read-write
STATUS current
DESCRIPTION
"Data value."
::= { dataArray12 36 }

dataValue12_37 OBJECT-TYPE
SYNTAX INTEGER
MAX-ACCESS read-write
STATUS current
DESCRIPTION
"Data value."
::= { dataArray12 37 }

dataValue12_38 OBJECT-TYPE
SYNTAX INTEGER
MAX-ACCESS read-write
STATUS current
DESCRIPTION
"Data value."
::= { dataArray12 38 }

dataValue12_39 OBJECT-TYPE
SYNTAX INTEGER
MAX-ACCESS read-write
STATUS current
DESCRIPTION
"Data value."
::= { dataArray12 39 }

dataValue12_40 OBJECT-TYPE
SYNTAX INTEGER
MAX-ACCESS read-write
STATUS current
DESCRIPTION
"Data value."
::= { dataArray12 40 }

dataValue12_41 OBJECT-TYPE
SYNTAX INTEGER
MAX-ACCESS read-write
STATUS current
DESCRIPTION
"Data value."
::= { dataArray12 41 }

dataValue12_42 OBJECT-TYPE
SYNTAX INTEGER
MAX-ACCESS read-write
STATUS current
DESCRIPTION
"Data value."
::= { dataArray12 42 }

dataValue12_43 OBJECT-TYPE
SYNTAX INTEGER
MAX-ACCESS read-write
STATUS current
DESCRIPTION
"Data value."
::= { dataArray12 43 }

dataValue12_44 OBJECT-TYPE
SYNTAX INTEGER
MAX-ACCESS read-write
STATUS current
DESCRIPTION
"Data value."
::= { dataArray12 44 }

dataValue12_45 OBJECT-TYPE
SYNTAX INTEGER
MAX-ACCESS read-write
STATUS current
DESCRIPTION
"Data value."
::= { dataArray12 45 }

dataValue12_46 OBJECT-TYPE
SYNTAX INTEGER
MAX-ACCESS read-write
STATUS current
DESCRIPTION
"Data value."
::= { dataArray12 46 }

dataValue12_47 OBJECT-TYPE
SYNTAX INTEGER
MAX-ACCESS read-write
STATUS current
DESCRIPTION
"Data value."
::= { dataArray12 47 }

dataValue12_48 OBJECT-TYPE
SYNTAX INTEGER
MAX-ACCESS read-write
STATUS current
DESCRIPTION
"Data value."
::= { dataArray12 48 }

dataValue12_49 OBJECT-TYPE
SYNTAX INTEGER
MAX-ACCESS read-write
STATUS current
DESCRIPTION
"Data value."
::= { dataArray12 49 }

dataValue12_50 OBJECT-TYPE
SYNTAX INTEGER
MAX-ACCESS read-write
STATUS current
DESCRIPTION
"Data value."
::= { dataArray12 50 }

dataValue12_51 OBJECT-TYPE
SYNTAX INTEGER
MAX-ACCESS read-write
STATUS current
DESCRIPTION
"Data value."
::= { dataArray12 51 }

dataValue12_52 OBJECT-TYPE
SYNTAX INTEGER
MAX-ACCESS read-write
STATUS current
DESCRIPTION
"Data value."
::= { dataArray12 52 }

dataValue12_53 OBJECT-TYPE
SYNTAX INTEGER
MAX-ACCESS read-write
STATUS current
DESCRIPTION
"Data value."
::= { dataArray12 53 }

dataValue12_54 OBJECT-TYPE
SYNTAX INTEGER
MAX-ACCESS read-write
STATUS current
DESCRIPTION
"Data value."
::= { dataArray12 54 }

dataValue12_55 OBJECT-TYPE
SYNTAX INTEGER
MAX-ACCESS read-write
STATUS current
DESCRIPTION
"Data value."
::= { dataArray12 55 }

dataValue12_56 OBJECT-TYPE
SYNTAX INTEGER
MAX-ACCESS read-write
STATUS current
DESCRIPTION
"Data value."
::= { dataArray12 56 }

dataValue12_57 OBJECT-TYPE
SYNTAX INTEGER
MAX-ACCESS read-write
STATUS current
DESCRIPTION
"Data value."
::= { dataArray12 57 }

dataValue12_58 OBJECT-TYPE
SYNTAX INTEGER
MAX-ACCESS read-write
STATUS current
DESCRIPTION
"Data value."
::= { dataArray12 58 }

dataValue12_59 OBJECT-TYPE
SYNTAX INTEGER
MAX-ACCESS read-write
STATUS current
DESCRIPTION
"Data value."
::= { dataArray12 59 }

dataValue12_60 OBJECT-TYPE
SYNTAX INTEGER
MAX-ACCESS read-write
STATUS current
DESCRIPTION
"Data value."
::= { dataArray12 60 }

dataValue12_61 OBJECT-TYPE
SYNTAX INTEGER
MAX-ACCESS read-write
STATUS current
DESCRIPTION
"Data value."
::= { dataArray12 61 }

dataValue12_62 OBJECT-TYPE
SYNTAX INTEGER
MAX-ACCESS read-write
STATUS current
DESCRIPTION
"Data value."
::= { dataArray12 62 }

dataValue12_63 OBJECT-TYPE
SYNTAX INTEGER
MAX-ACCESS read-write
STATUS current
DESCRIPTION
"Data value."
::= { dataArray12 63 }

dataValue12_64 OBJECT-TYPE
SYNTAX INTEGER
MAX-ACCESS read-write
STATUS current
DESCRIPTION
"Data value."
::= { dataArray12 64 }

dataValue12_65 OBJECT-TYPE
SYNTAX INTEGER
MAX-ACCESS read-write
STATUS current
DESCRIPTION
"Data value."
::= { dataArray12 65 }

dataValue12_66 OBJECT-TYPE
SYNTAX INTEGER
MAX-ACCESS read-write
STATUS current
DESCRIPTION
"Data value."
::= { dataArray12 66 }

dataValue12_67 OBJECT-TYPE
SYNTAX INTEGER
MAX-ACCESS read-write
STATUS current
DESCRIPTION
"Data value."
::= { dataArray12 67 }

dataValue12_68 OBJECT-TYPE
SYNTAX INTEGER
MAX-ACCESS read-write
STATUS current
DESCRIPTION
"Data value."
::= { dataArray12 68 }

dataValue12_69 OBJECT-TYPE
SYNTAX INTEGER
MAX-ACCESS read-write
STATUS current
DESCRIPTION
"Data value."
::= { dataArray12 69 }

dataValue12_70 OBJECT-TYPE
SYNTAX INTEGER
MAX-ACCESS read-write
STATUS current
DESCRIPTION
"Data value."
::= { dataArray12 70 }

dataValue12_71 OBJECT-TYPE
SYNTAX INTEGER
MAX-ACCESS read-write
STATUS current
DESCRIPTION
"Data value."
::= { dataArray12 71 }

dataValue12_72 OBJECT-TYPE
SYNTAX INTEGER
MAX-ACCESS read-write
STATUS current
DESCRIPTION
"Data value."
::= { dataArray12 72 }

dataValue12_73 OBJECT-TYPE
SYNTAX INTEGER
MAX-ACCESS read-write
STATUS current
DESCRIPTION
"Data value."
::= { dataArray12 73 }

dataValue12_74 OBJECT-TYPE
SYNTAX INTEGER
MAX-ACCESS read-write
STATUS current
DESCRIPTION
"Data value."
::= { dataArray12 74 }

dataValue12_75 OBJECT-TYPE
SYNTAX INTEGER
MAX-ACCESS read-write
STATUS current
DESCRIPTION
"Data value."
::= { dataArray12 75 }

dataValue12_76 OBJECT-TYPE
SYNTAX INTEGER
MAX-ACCESS read-write
STATUS current
DESCRIPTION
"Data value."
::= { dataArray12 76 }

dataValue12_77 OBJECT-TYPE
SYNTAX INTEGER
MAX-ACCESS read-write
STATUS current
DESCRIPTION
"Data value."
::= { dataArray12 77 }

dataValue12_78 OBJECT-TYPE
SYNTAX INTEGER
MAX-ACCESS read-write
STATUS current
DESCRIPTION
"Data value."
::= { dataArray12 78 }

dataValue12_79 OBJECT-TYPE
SYNTAX INTEGER
MAX-ACCESS read-write
STATUS current
DESCRIPTION
"Data value."
::= { dataArray12 79 }

dataValue12_80 OBJECT-TYPE
SYNTAX INTEGER
MAX-ACCESS read-write
STATUS current
DESCRIPTION
"Data value."
::= { dataArray12 80 }

dataValue12_81 OBJECT-TYPE
SYNTAX INTEGER
MAX-ACCESS read-write
STATUS current
DESCRIPTION
"Data value."
::= { dataArray12 81 }

dataValue12_82 OBJECT-TYPE
SYNTAX INTEGER
MAX-ACCESS read-write
STATUS current
DESCRIPTION
"Data value."
::= { dataArray12 82 }

dataValue12_83 OBJECT-TYPE
SYNTAX INTEGER
MAX-ACCESS read-write
STATUS current
DESCRIPTION
"Data value."
::= { dataArray12 83 }

dataValue12_84 OBJECT-TYPE
SYNTAX INTEGER
MAX-ACCESS read-write
STATUS current
DESCRIPTION
"Data value."
::= { dataArray12 84 }

dataValue12_85 OBJECT-TYPE
SYNTAX INTEGER
MAX-ACCESS read-write
STATUS current
DESCRIPTION
"Data value."
::= { dataArray12 85 }

dataValue12_86 OBJECT-TYPE
SYNTAX INTEGER
MAX-ACCESS read-write
STATUS current
DESCRIPTION
"Data value."
::= { dataArray12 86 }

dataValue12_87 OBJECT-TYPE
SYNTAX INTEGER
MAX-ACCESS read-write
STATUS current
DESCRIPTION
"Data value."
::= { dataArray12 87 }

dataValue12_88 OBJECT-TYPE
SYNTAX INTEGER
MAX-ACCESS read-write
STATUS current
DESCRIPTION
"Data value."
::= { dataArray12 88 }

dataValue12_89 OBJECT-TYPE
SYNTAX INTEGER
MAX-ACCESS read-write
STATUS current
DESCRIPTION
"Data value."
::= { dataArray12 89 }

dataValue12_90 OBJECT-TYPE
SYNTAX INTEGER
MAX-ACCESS read-write
STATUS current
DESCRIPTION
"Data value."
::= { dataArray12 90 }

dataValue12_91 OBJECT-TYPE
SYNTAX INTEGER
MAX-ACCESS read-write
STATUS current
DESCRIPTION
"Data value."
::= { dataArray12 91 }

dataValue12_92 OBJECT-TYPE
SYNTAX INTEGER
MAX-ACCESS read-write
STATUS current
DESCRIPTION
"Data value."
::= { dataArray12 92 }

dataValue12_93 OBJECT-TYPE
SYNTAX INTEGER
MAX-ACCESS read-write
STATUS current
DESCRIPTION
"Data value."
::= { dataArray12 93 }

dataValue12_94 OBJECT-TYPE
SYNTAX INTEGER
MAX-ACCESS read-write
STATUS current
DESCRIPTION
"Data value."
::= { dataArray12 94 }

dataValue12_95 OBJECT-TYPE
SYNTAX INTEGER
MAX-ACCESS read-write
STATUS current
DESCRIPTION
"Data value."
::= { dataArray12 95 }

dataValue12_96 OBJECT-TYPE
SYNTAX INTEGER
MAX-ACCESS read-write
STATUS current
DESCRIPTION
"Data value."
::= { dataArray12 96 }

dataValue12_97 OBJECT-TYPE
SYNTAX INTEGER
MAX-ACCESS read-write
STATUS current
DESCRIPTION
"Data value."
::= { dataArray12 97 }

dataValue12_98 OBJECT-TYPE
SYNTAX INTEGER
MAX-ACCESS read-write
STATUS current
DESCRIPTION
"Data value."
::= { dataArray12 98 }

dataValue12_99 OBJECT-TYPE
SYNTAX INTEGER
MAX-ACCESS read-write
STATUS current
DESCRIPTION
"Data value."
::= { dataArray12 99 }

dataArray13 OBJECT IDENTIFIER ::= { s08090201_trane_st_jude_v1_00b 13 }

dataValue13_0 OBJECT-TYPE
SYNTAX INTEGER
MAX-ACCESS read-write
STATUS current
DESCRIPTION
"Data value."
::= { dataArray13 0 }

dataValue13_1 OBJECT-TYPE
SYNTAX INTEGER
MAX-ACCESS read-write
STATUS current
DESCRIPTION
"Data value."
::= { dataArray13 1 }

dataValue13_2 OBJECT-TYPE
SYNTAX INTEGER
MAX-ACCESS read-write
STATUS current
DESCRIPTION
"Data value."
::= { dataArray13 2 }

dataValue13_3 OBJECT-TYPE
SYNTAX INTEGER
MAX-ACCESS read-write
STATUS current
DESCRIPTION
"Data value."
::= { dataArray13 3 }

dataValue13_4 OBJECT-TYPE
SYNTAX INTEGER
MAX-ACCESS read-write
STATUS current
DESCRIPTION
"Data value."
::= { dataArray13 4 }

dataValue13_5 OBJECT-TYPE
SYNTAX INTEGER
MAX-ACCESS read-write
STATUS current
DESCRIPTION
"Data value."
::= { dataArray13 5 }

dataValue13_6 OBJECT-TYPE
SYNTAX INTEGER
MAX-ACCESS read-write
STATUS current
DESCRIPTION
"Data value."
::= { dataArray13 6 }

dataValue13_7 OBJECT-TYPE
SYNTAX INTEGER
MAX-ACCESS read-write
STATUS current
DESCRIPTION
"Data value."
::= { dataArray13 7 }

dataValue13_8 OBJECT-TYPE
SYNTAX INTEGER
MAX-ACCESS read-write
STATUS current
DESCRIPTION
"Data value."
::= { dataArray13 8 }

dataValue13_9 OBJECT-TYPE
SYNTAX INTEGER
MAX-ACCESS read-write
STATUS current
DESCRIPTION
"Data value."
::= { dataArray13 9 }

dataValue13_10 OBJECT-TYPE
SYNTAX INTEGER
MAX-ACCESS read-write
STATUS current
DESCRIPTION
"Data value."
::= { dataArray13 10 }

dataValue13_11 OBJECT-TYPE
SYNTAX INTEGER
MAX-ACCESS read-write
STATUS current
DESCRIPTION
"Data value."
::= { dataArray13 11 }

dataValue13_12 OBJECT-TYPE
SYNTAX INTEGER
MAX-ACCESS read-write
STATUS current
DESCRIPTION
"Data value."
::= { dataArray13 12 }

dataValue13_13 OBJECT-TYPE
SYNTAX INTEGER
MAX-ACCESS read-write
STATUS current
DESCRIPTION
"Data value."
::= { dataArray13 13 }

dataValue13_14 OBJECT-TYPE
SYNTAX INTEGER
MAX-ACCESS read-write
STATUS current
DESCRIPTION
"Data value."
::= { dataArray13 14 }

dataValue13_15 OBJECT-TYPE
SYNTAX INTEGER
MAX-ACCESS read-write
STATUS current
DESCRIPTION
"Data value."
::= { dataArray13 15 }

dataValue13_16 OBJECT-TYPE
SYNTAX INTEGER
MAX-ACCESS read-write
STATUS current
DESCRIPTION
"Data value."
::= { dataArray13 16 }

dataValue13_17 OBJECT-TYPE
SYNTAX INTEGER
MAX-ACCESS read-write
STATUS current
DESCRIPTION
"Data value."
::= { dataArray13 17 }

dataValue13_18 OBJECT-TYPE
SYNTAX INTEGER
MAX-ACCESS read-write
STATUS current
DESCRIPTION
"Data value."
::= { dataArray13 18 }

dataValue13_19 OBJECT-TYPE
SYNTAX INTEGER
MAX-ACCESS read-write
STATUS current
DESCRIPTION
"Data value."
::= { dataArray13 19 }

dataValue13_20 OBJECT-TYPE
SYNTAX INTEGER
MAX-ACCESS read-write
STATUS current
DESCRIPTION
"Data value."
::= { dataArray13 20 }

dataValue13_21 OBJECT-TYPE
SYNTAX INTEGER
MAX-ACCESS read-write
STATUS current
DESCRIPTION
"Data value."
::= { dataArray13 21 }

dataValue13_22 OBJECT-TYPE
SYNTAX INTEGER
MAX-ACCESS read-write
STATUS current
DESCRIPTION
"Data value."
::= { dataArray13 22 }

dataValue13_23 OBJECT-TYPE
SYNTAX INTEGER
MAX-ACCESS read-write
STATUS current
DESCRIPTION
"Data value."
::= { dataArray13 23 }

dataValue13_24 OBJECT-TYPE
SYNTAX INTEGER
MAX-ACCESS read-write
STATUS current
DESCRIPTION
"Data value."
::= { dataArray13 24 }

dataValue13_25 OBJECT-TYPE
SYNTAX INTEGER
MAX-ACCESS read-write
STATUS current
DESCRIPTION
"Data value."
::= { dataArray13 25 }

dataValue13_26 OBJECT-TYPE
SYNTAX INTEGER
MAX-ACCESS read-write
STATUS current
DESCRIPTION
"Data value."
::= { dataArray13 26 }

dataValue13_27 OBJECT-TYPE
SYNTAX INTEGER
MAX-ACCESS read-write
STATUS current
DESCRIPTION
"Data value."
::= { dataArray13 27 }

dataValue13_28 OBJECT-TYPE
SYNTAX INTEGER
MAX-ACCESS read-write
STATUS current
DESCRIPTION
"Data value."
::= { dataArray13 28 }

dataValue13_29 OBJECT-TYPE
SYNTAX INTEGER
MAX-ACCESS read-write
STATUS current
DESCRIPTION
"Data value."
::= { dataArray13 29 }

dataValue13_30 OBJECT-TYPE
SYNTAX INTEGER
MAX-ACCESS read-write
STATUS current
DESCRIPTION
"Data value."
::= { dataArray13 30 }

dataValue13_31 OBJECT-TYPE
SYNTAX INTEGER
MAX-ACCESS read-write
STATUS current
DESCRIPTION
"Data value."
::= { dataArray13 31 }

dataValue13_32 OBJECT-TYPE
SYNTAX INTEGER
MAX-ACCESS read-write
STATUS current
DESCRIPTION
"Data value."
::= { dataArray13 32 }

dataValue13_33 OBJECT-TYPE
SYNTAX INTEGER
MAX-ACCESS read-write
STATUS current
DESCRIPTION
"Data value."
::= { dataArray13 33 }

dataValue13_34 OBJECT-TYPE
SYNTAX INTEGER
MAX-ACCESS read-write
STATUS current
DESCRIPTION
"Data value."
::= { dataArray13 34 }

dataValue13_35 OBJECT-TYPE
SYNTAX INTEGER
MAX-ACCESS read-write
STATUS current
DESCRIPTION
"Data value."
::= { dataArray13 35 }

dataValue13_36 OBJECT-TYPE
SYNTAX INTEGER
MAX-ACCESS read-write
STATUS current
DESCRIPTION
"Data value."
::= { dataArray13 36 }

dataValue13_37 OBJECT-TYPE
SYNTAX INTEGER
MAX-ACCESS read-write
STATUS current
DESCRIPTION
"Data value."
::= { dataArray13 37 }

dataValue13_38 OBJECT-TYPE
SYNTAX INTEGER
MAX-ACCESS read-write
STATUS current
DESCRIPTION
"Data value."
::= { dataArray13 38 }

dataValue13_39 OBJECT-TYPE
SYNTAX INTEGER
MAX-ACCESS read-write
STATUS current
DESCRIPTION
"Data value."
::= { dataArray13 39 }

dataValue13_40 OBJECT-TYPE
SYNTAX INTEGER
MAX-ACCESS read-write
STATUS current
DESCRIPTION
"Data value."
::= { dataArray13 40 }

dataValue13_41 OBJECT-TYPE
SYNTAX INTEGER
MAX-ACCESS read-write
STATUS current
DESCRIPTION
"Data value."
::= { dataArray13 41 }

dataValue13_42 OBJECT-TYPE
SYNTAX INTEGER
MAX-ACCESS read-write
STATUS current
DESCRIPTION
"Data value."
::= { dataArray13 42 }

dataValue13_43 OBJECT-TYPE
SYNTAX INTEGER
MAX-ACCESS read-write
STATUS current
DESCRIPTION
"Data value."
::= { dataArray13 43 }

dataValue13_44 OBJECT-TYPE
SYNTAX INTEGER
MAX-ACCESS read-write
STATUS current
DESCRIPTION
"Data value."
::= { dataArray13 44 }

dataValue13_45 OBJECT-TYPE
SYNTAX INTEGER
MAX-ACCESS read-write
STATUS current
DESCRIPTION
"Data value."
::= { dataArray13 45 }

dataValue13_46 OBJECT-TYPE
SYNTAX INTEGER
MAX-ACCESS read-write
STATUS current
DESCRIPTION
"Data value."
::= { dataArray13 46 }

dataValue13_47 OBJECT-TYPE
SYNTAX INTEGER
MAX-ACCESS read-write
STATUS current
DESCRIPTION
"Data value."
::= { dataArray13 47 }

dataValue13_48 OBJECT-TYPE
SYNTAX INTEGER
MAX-ACCESS read-write
STATUS current
DESCRIPTION
"Data value."
::= { dataArray13 48 }

dataValue13_49 OBJECT-TYPE
SYNTAX INTEGER
MAX-ACCESS read-write
STATUS current
DESCRIPTION
"Data value."
::= { dataArray13 49 }

dataValue13_50 OBJECT-TYPE
SYNTAX INTEGER
MAX-ACCESS read-write
STATUS current
DESCRIPTION
"Data value."
::= { dataArray13 50 }

dataValue13_51 OBJECT-TYPE
SYNTAX INTEGER
MAX-ACCESS read-write
STATUS current
DESCRIPTION
"Data value."
::= { dataArray13 51 }

dataValue13_52 OBJECT-TYPE
SYNTAX INTEGER
MAX-ACCESS read-write
STATUS current
DESCRIPTION
"Data value."
::= { dataArray13 52 }

dataValue13_53 OBJECT-TYPE
SYNTAX INTEGER
MAX-ACCESS read-write
STATUS current
DESCRIPTION
"Data value."
::= { dataArray13 53 }

dataValue13_54 OBJECT-TYPE
SYNTAX INTEGER
MAX-ACCESS read-write
STATUS current
DESCRIPTION
"Data value."
::= { dataArray13 54 }

dataValue13_55 OBJECT-TYPE
SYNTAX INTEGER
MAX-ACCESS read-write
STATUS current
DESCRIPTION
"Data value."
::= { dataArray13 55 }

dataValue13_56 OBJECT-TYPE
SYNTAX INTEGER
MAX-ACCESS read-write
STATUS current
DESCRIPTION
"Data value."
::= { dataArray13 56 }

dataValue13_57 OBJECT-TYPE
SYNTAX INTEGER
MAX-ACCESS read-write
STATUS current
DESCRIPTION
"Data value."
::= { dataArray13 57 }

dataValue13_58 OBJECT-TYPE
SYNTAX INTEGER
MAX-ACCESS read-write
STATUS current
DESCRIPTION
"Data value."
::= { dataArray13 58 }

dataValue13_59 OBJECT-TYPE
SYNTAX INTEGER
MAX-ACCESS read-write
STATUS current
DESCRIPTION
"Data value."
::= { dataArray13 59 }

dataValue13_60 OBJECT-TYPE
SYNTAX INTEGER
MAX-ACCESS read-write
STATUS current
DESCRIPTION
"Data value."
::= { dataArray13 60 }

dataValue13_61 OBJECT-TYPE
SYNTAX INTEGER
MAX-ACCESS read-write
STATUS current
DESCRIPTION
"Data value."
::= { dataArray13 61 }

dataValue13_62 OBJECT-TYPE
SYNTAX INTEGER
MAX-ACCESS read-write
STATUS current
DESCRIPTION
"Data value."
::= { dataArray13 62 }

dataValue13_63 OBJECT-TYPE
SYNTAX INTEGER
MAX-ACCESS read-write
STATUS current
DESCRIPTION
"Data value."
::= { dataArray13 63 }

dataValue13_64 OBJECT-TYPE
SYNTAX INTEGER
MAX-ACCESS read-write
STATUS current
DESCRIPTION
"Data value."
::= { dataArray13 64 }

dataValue13_65 OBJECT-TYPE
SYNTAX INTEGER
MAX-ACCESS read-write
STATUS current
DESCRIPTION
"Data value."
::= { dataArray13 65 }

dataValue13_66 OBJECT-TYPE
SYNTAX INTEGER
MAX-ACCESS read-write
STATUS current
DESCRIPTION
"Data value."
::= { dataArray13 66 }

dataValue13_67 OBJECT-TYPE
SYNTAX INTEGER
MAX-ACCESS read-write
STATUS current
DESCRIPTION
"Data value."
::= { dataArray13 67 }

dataValue13_68 OBJECT-TYPE
SYNTAX INTEGER
MAX-ACCESS read-write
STATUS current
DESCRIPTION
"Data value."
::= { dataArray13 68 }

dataValue13_69 OBJECT-TYPE
SYNTAX INTEGER
MAX-ACCESS read-write
STATUS current
DESCRIPTION
"Data value."
::= { dataArray13 69 }

dataValue13_70 OBJECT-TYPE
SYNTAX INTEGER
MAX-ACCESS read-write
STATUS current
DESCRIPTION
"Data value."
::= { dataArray13 70 }

dataValue13_71 OBJECT-TYPE
SYNTAX INTEGER
MAX-ACCESS read-write
STATUS current
DESCRIPTION
"Data value."
::= { dataArray13 71 }

dataValue13_72 OBJECT-TYPE
SYNTAX INTEGER
MAX-ACCESS read-write
STATUS current
DESCRIPTION
"Data value."
::= { dataArray13 72 }

dataValue13_73 OBJECT-TYPE
SYNTAX INTEGER
MAX-ACCESS read-write
STATUS current
DESCRIPTION
"Data value."
::= { dataArray13 73 }

dataValue13_74 OBJECT-TYPE
SYNTAX INTEGER
MAX-ACCESS read-write
STATUS current
DESCRIPTION
"Data value."
::= { dataArray13 74 }

dataValue13_75 OBJECT-TYPE
SYNTAX INTEGER
MAX-ACCESS read-write
STATUS current
DESCRIPTION
"Data value."
::= { dataArray13 75 }

dataValue13_76 OBJECT-TYPE
SYNTAX INTEGER
MAX-ACCESS read-write
STATUS current
DESCRIPTION
"Data value."
::= { dataArray13 76 }

dataValue13_77 OBJECT-TYPE
SYNTAX INTEGER
MAX-ACCESS read-write
STATUS current
DESCRIPTION
"Data value."
::= { dataArray13 77 }

dataValue13_78 OBJECT-TYPE
SYNTAX INTEGER
MAX-ACCESS read-write
STATUS current
DESCRIPTION
"Data value."
::= { dataArray13 78 }

dataValue13_79 OBJECT-TYPE
SYNTAX INTEGER
MAX-ACCESS read-write
STATUS current
DESCRIPTION
"Data value."
::= { dataArray13 79 }

dataValue13_80 OBJECT-TYPE
SYNTAX INTEGER
MAX-ACCESS read-write
STATUS current
DESCRIPTION
"Data value."
::= { dataArray13 80 }

dataValue13_81 OBJECT-TYPE
SYNTAX INTEGER
MAX-ACCESS read-write
STATUS current
DESCRIPTION
"Data value."
::= { dataArray13 81 }

dataValue13_82 OBJECT-TYPE
SYNTAX INTEGER
MAX-ACCESS read-write
STATUS current
DESCRIPTION
"Data value."
::= { dataArray13 82 }

dataValue13_83 OBJECT-TYPE
SYNTAX INTEGER
MAX-ACCESS read-write
STATUS current
DESCRIPTION
"Data value."
::= { dataArray13 83 }

dataValue13_84 OBJECT-TYPE
SYNTAX INTEGER
MAX-ACCESS read-write
STATUS current
DESCRIPTION
"Data value."
::= { dataArray13 84 }

dataValue13_85 OBJECT-TYPE
SYNTAX INTEGER
MAX-ACCESS read-write
STATUS current
DESCRIPTION
"Data value."
::= { dataArray13 85 }

dataValue13_86 OBJECT-TYPE
SYNTAX INTEGER
MAX-ACCESS read-write
STATUS current
DESCRIPTION
"Data value."
::= { dataArray13 86 }

dataValue13_87 OBJECT-TYPE
SYNTAX INTEGER
MAX-ACCESS read-write
STATUS current
DESCRIPTION
"Data value."
::= { dataArray13 87 }

dataValue13_88 OBJECT-TYPE
SYNTAX INTEGER
MAX-ACCESS read-write
STATUS current
DESCRIPTION
"Data value."
::= { dataArray13 88 }

dataValue13_89 OBJECT-TYPE
SYNTAX INTEGER
MAX-ACCESS read-write
STATUS current
DESCRIPTION
"Data value."
::= { dataArray13 89 }

dataValue13_90 OBJECT-TYPE
SYNTAX INTEGER
MAX-ACCESS read-write
STATUS current
DESCRIPTION
"Data value."
::= { dataArray13 90 }

dataValue13_91 OBJECT-TYPE
SYNTAX INTEGER
MAX-ACCESS read-write
STATUS current
DESCRIPTION
"Data value."
::= { dataArray13 91 }

dataValue13_92 OBJECT-TYPE
SYNTAX INTEGER
MAX-ACCESS read-write
STATUS current
DESCRIPTION
"Data value."
::= { dataArray13 92 }

dataValue13_93 OBJECT-TYPE
SYNTAX INTEGER
MAX-ACCESS read-write
STATUS current
DESCRIPTION
"Data value."
::= { dataArray13 93 }

dataValue13_94 OBJECT-TYPE
SYNTAX INTEGER
MAX-ACCESS read-write
STATUS current
DESCRIPTION
"Data value."
::= { dataArray13 94 }

dataValue13_95 OBJECT-TYPE
SYNTAX INTEGER
MAX-ACCESS read-write
STATUS current
DESCRIPTION
"Data value."
::= { dataArray13 95 }

dataValue13_96 OBJECT-TYPE
SYNTAX INTEGER
MAX-ACCESS read-write
STATUS current
DESCRIPTION
"Data value."
::= { dataArray13 96 }

dataValue13_97 OBJECT-TYPE
SYNTAX INTEGER
MAX-ACCESS read-write
STATUS current
DESCRIPTION
"Data value."
::= { dataArray13 97 }

dataValue13_98 OBJECT-TYPE
SYNTAX INTEGER
MAX-ACCESS read-write
STATUS current
DESCRIPTION
"Data value."
::= { dataArray13 98 }

dataValue13_99 OBJECT-TYPE
SYNTAX INTEGER
MAX-ACCESS read-write
STATUS current
DESCRIPTION
"Data value."
::= { dataArray13 99 }

dataArray14 OBJECT IDENTIFIER ::= { s08090201_trane_st_jude_v1_00b 14 }

dataValue14_0 OBJECT-TYPE
SYNTAX INTEGER
MAX-ACCESS read-write
STATUS current
DESCRIPTION
"Data value."
::= { dataArray14 0 }

dataValue14_1 OBJECT-TYPE
SYNTAX INTEGER
MAX-ACCESS read-write
STATUS current
DESCRIPTION
"Data value."
::= { dataArray14 1 }

dataValue14_2 OBJECT-TYPE
SYNTAX INTEGER
MAX-ACCESS read-write
STATUS current
DESCRIPTION
"Data value."
::= { dataArray14 2 }

dataValue14_3 OBJECT-TYPE
SYNTAX INTEGER
MAX-ACCESS read-write
STATUS current
DESCRIPTION
"Data value."
::= { dataArray14 3 }

dataValue14_4 OBJECT-TYPE
SYNTAX INTEGER
MAX-ACCESS read-write
STATUS current
DESCRIPTION
"Data value."
::= { dataArray14 4 }

dataValue14_5 OBJECT-TYPE
SYNTAX INTEGER
MAX-ACCESS read-write
STATUS current
DESCRIPTION
"Data value."
::= { dataArray14 5 }

dataValue14_6 OBJECT-TYPE
SYNTAX INTEGER
MAX-ACCESS read-write
STATUS current
DESCRIPTION
"Data value."
::= { dataArray14 6 }

dataValue14_7 OBJECT-TYPE
SYNTAX INTEGER
MAX-ACCESS read-write
STATUS current
DESCRIPTION
"Data value."
::= { dataArray14 7 }

dataValue14_8 OBJECT-TYPE
SYNTAX INTEGER
MAX-ACCESS read-write
STATUS current
DESCRIPTION
"Data value."
::= { dataArray14 8 }

dataValue14_9 OBJECT-TYPE
SYNTAX INTEGER
MAX-ACCESS read-write
STATUS current
DESCRIPTION
"Data value."
::= { dataArray14 9 }

dataValue14_10 OBJECT-TYPE
SYNTAX INTEGER
MAX-ACCESS read-write
STATUS current
DESCRIPTION
"Data value."
::= { dataArray14 10 }

dataValue14_11 OBJECT-TYPE
SYNTAX INTEGER
MAX-ACCESS read-write
STATUS current
DESCRIPTION
"Data value."
::= { dataArray14 11 }

dataValue14_12 OBJECT-TYPE
SYNTAX INTEGER
MAX-ACCESS read-write
STATUS current
DESCRIPTION
"Data value."
::= { dataArray14 12 }

dataValue14_13 OBJECT-TYPE
SYNTAX INTEGER
MAX-ACCESS read-write
STATUS current
DESCRIPTION
"Data value."
::= { dataArray14 13 }

dataValue14_14 OBJECT-TYPE
SYNTAX INTEGER
MAX-ACCESS read-write
STATUS current
DESCRIPTION
"Data value."
::= { dataArray14 14 }

dataValue14_15 OBJECT-TYPE
SYNTAX INTEGER
MAX-ACCESS read-write
STATUS current
DESCRIPTION
"Data value."
::= { dataArray14 15 }

dataValue14_16 OBJECT-TYPE
SYNTAX INTEGER
MAX-ACCESS read-write
STATUS current
DESCRIPTION
"Data value."
::= { dataArray14 16 }

dataValue14_17 OBJECT-TYPE
SYNTAX INTEGER
MAX-ACCESS read-write
STATUS current
DESCRIPTION
"Data value."
::= { dataArray14 17 }

dataValue14_18 OBJECT-TYPE
SYNTAX INTEGER
MAX-ACCESS read-write
STATUS current
DESCRIPTION
"Data value."
::= { dataArray14 18 }

dataValue14_19 OBJECT-TYPE
SYNTAX INTEGER
MAX-ACCESS read-write
STATUS current
DESCRIPTION
"Data value."
::= { dataArray14 19 }

dataValue14_20 OBJECT-TYPE
SYNTAX INTEGER
MAX-ACCESS read-write
STATUS current
DESCRIPTION
"Data value."
::= { dataArray14 20 }

dataValue14_21 OBJECT-TYPE
SYNTAX INTEGER
MAX-ACCESS read-write
STATUS current
DESCRIPTION
"Data value."
::= { dataArray14 21 }

dataValue14_22 OBJECT-TYPE
SYNTAX INTEGER
MAX-ACCESS read-write
STATUS current
DESCRIPTION
"Data value."
::= { dataArray14 22 }

dataValue14_23 OBJECT-TYPE
SYNTAX INTEGER
MAX-ACCESS read-write
STATUS current
DESCRIPTION
"Data value."
::= { dataArray14 23 }

dataValue14_24 OBJECT-TYPE
SYNTAX INTEGER
MAX-ACCESS read-write
STATUS current
DESCRIPTION
"Data value."
::= { dataArray14 24 }

dataValue14_25 OBJECT-TYPE
SYNTAX INTEGER
MAX-ACCESS read-write
STATUS current
DESCRIPTION
"Data value."
::= { dataArray14 25 }

dataValue14_26 OBJECT-TYPE
SYNTAX INTEGER
MAX-ACCESS read-write
STATUS current
DESCRIPTION
"Data value."
::= { dataArray14 26 }

dataValue14_27 OBJECT-TYPE
SYNTAX INTEGER
MAX-ACCESS read-write
STATUS current
DESCRIPTION
"Data value."
::= { dataArray14 27 }

dataValue14_28 OBJECT-TYPE
SYNTAX INTEGER
MAX-ACCESS read-write
STATUS current
DESCRIPTION
"Data value."
::= { dataArray14 28 }

dataValue14_29 OBJECT-TYPE
SYNTAX INTEGER
MAX-ACCESS read-write
STATUS current
DESCRIPTION
"Data value."
::= { dataArray14 29 }

dataValue14_30 OBJECT-TYPE
SYNTAX INTEGER
MAX-ACCESS read-write
STATUS current
DESCRIPTION
"Data value."
::= { dataArray14 30 }

dataValue14_31 OBJECT-TYPE
SYNTAX INTEGER
MAX-ACCESS read-write
STATUS current
DESCRIPTION
"Data value."
::= { dataArray14 31 }

dataValue14_32 OBJECT-TYPE
SYNTAX INTEGER
MAX-ACCESS read-write
STATUS current
DESCRIPTION
"Data value."
::= { dataArray14 32 }

dataValue14_33 OBJECT-TYPE
SYNTAX INTEGER
MAX-ACCESS read-write
STATUS current
DESCRIPTION
"Data value."
::= { dataArray14 33 }

dataValue14_34 OBJECT-TYPE
SYNTAX INTEGER
MAX-ACCESS read-write
STATUS current
DESCRIPTION
"Data value."
::= { dataArray14 34 }

dataValue14_35 OBJECT-TYPE
SYNTAX INTEGER
MAX-ACCESS read-write
STATUS current
DESCRIPTION
"Data value."
::= { dataArray14 35 }

dataValue14_36 OBJECT-TYPE
SYNTAX INTEGER
MAX-ACCESS read-write
STATUS current
DESCRIPTION
"Data value."
::= { dataArray14 36 }

dataValue14_37 OBJECT-TYPE
SYNTAX INTEGER
MAX-ACCESS read-write
STATUS current
DESCRIPTION
"Data value."
::= { dataArray14 37 }

dataValue14_38 OBJECT-TYPE
SYNTAX INTEGER
MAX-ACCESS read-write
STATUS current
DESCRIPTION
"Data value."
::= { dataArray14 38 }

dataValue14_39 OBJECT-TYPE
SYNTAX INTEGER
MAX-ACCESS read-write
STATUS current
DESCRIPTION
"Data value."
::= { dataArray14 39 }

dataValue14_40 OBJECT-TYPE
SYNTAX INTEGER
MAX-ACCESS read-write
STATUS current
DESCRIPTION
"Data value."
::= { dataArray14 40 }

dataValue14_41 OBJECT-TYPE
SYNTAX INTEGER
MAX-ACCESS read-write
STATUS current
DESCRIPTION
"Data value."
::= { dataArray14 41 }

dataValue14_42 OBJECT-TYPE
SYNTAX INTEGER
MAX-ACCESS read-write
STATUS current
DESCRIPTION
"Data value."
::= { dataArray14 42 }

dataValue14_43 OBJECT-TYPE
SYNTAX INTEGER
MAX-ACCESS read-write
STATUS current
DESCRIPTION
"Data value."
::= { dataArray14 43 }

dataValue14_44 OBJECT-TYPE
SYNTAX INTEGER
MAX-ACCESS read-write
STATUS current
DESCRIPTION
"Data value."
::= { dataArray14 44 }

dataValue14_45 OBJECT-TYPE
SYNTAX INTEGER
MAX-ACCESS read-write
STATUS current
DESCRIPTION
"Data value."
::= { dataArray14 45 }

dataValue14_46 OBJECT-TYPE
SYNTAX INTEGER
MAX-ACCESS read-write
STATUS current
DESCRIPTION
"Data value."
::= { dataArray14 46 }

dataValue14_47 OBJECT-TYPE
SYNTAX INTEGER
MAX-ACCESS read-write
STATUS current
DESCRIPTION
"Data value."
::= { dataArray14 47 }

dataValue14_48 OBJECT-TYPE
SYNTAX INTEGER
MAX-ACCESS read-write
STATUS current
DESCRIPTION
"Data value."
::= { dataArray14 48 }

dataValue14_49 OBJECT-TYPE
SYNTAX INTEGER
MAX-ACCESS read-write
STATUS current
DESCRIPTION
"Data value."
::= { dataArray14 49 }

dataValue14_50 OBJECT-TYPE
SYNTAX INTEGER
MAX-ACCESS read-write
STATUS current
DESCRIPTION
"Data value."
::= { dataArray14 50 }

dataValue14_51 OBJECT-TYPE
SYNTAX INTEGER
MAX-ACCESS read-write
STATUS current
DESCRIPTION
"Data value."
::= { dataArray14 51 }

dataValue14_52 OBJECT-TYPE
SYNTAX INTEGER
MAX-ACCESS read-write
STATUS current
DESCRIPTION
"Data value."
::= { dataArray14 52 }

dataValue14_53 OBJECT-TYPE
SYNTAX INTEGER
MAX-ACCESS read-write
STATUS current
DESCRIPTION
"Data value."
::= { dataArray14 53 }

dataValue14_54 OBJECT-TYPE
SYNTAX INTEGER
MAX-ACCESS read-write
STATUS current
DESCRIPTION
"Data value."
::= { dataArray14 54 }

dataValue14_55 OBJECT-TYPE
SYNTAX INTEGER
MAX-ACCESS read-write
STATUS current
DESCRIPTION
"Data value."
::= { dataArray14 55 }

dataValue14_56 OBJECT-TYPE
SYNTAX INTEGER
MAX-ACCESS read-write
STATUS current
DESCRIPTION
"Data value."
::= { dataArray14 56 }

dataValue14_57 OBJECT-TYPE
SYNTAX INTEGER
MAX-ACCESS read-write
STATUS current
DESCRIPTION
"Data value."
::= { dataArray14 57 }

dataValue14_58 OBJECT-TYPE
SYNTAX INTEGER
MAX-ACCESS read-write
STATUS current
DESCRIPTION
"Data value."
::= { dataArray14 58 }

dataValue14_59 OBJECT-TYPE
SYNTAX INTEGER
MAX-ACCESS read-write
STATUS current
DESCRIPTION
"Data value."
::= { dataArray14 59 }

dataValue14_60 OBJECT-TYPE
SYNTAX INTEGER
MAX-ACCESS read-write
STATUS current
DESCRIPTION
"Data value."
::= { dataArray14 60 }

dataValue14_61 OBJECT-TYPE
SYNTAX INTEGER
MAX-ACCESS read-write
STATUS current
DESCRIPTION
"Data value."
::= { dataArray14 61 }

dataValue14_62 OBJECT-TYPE
SYNTAX INTEGER
MAX-ACCESS read-write
STATUS current
DESCRIPTION
"Data value."
::= { dataArray14 62 }

dataValue14_63 OBJECT-TYPE
SYNTAX INTEGER
MAX-ACCESS read-write
STATUS current
DESCRIPTION
"Data value."
::= { dataArray14 63 }

dataValue14_64 OBJECT-TYPE
SYNTAX INTEGER
MAX-ACCESS read-write
STATUS current
DESCRIPTION
"Data value."
::= { dataArray14 64 }

dataValue14_65 OBJECT-TYPE
SYNTAX INTEGER
MAX-ACCESS read-write
STATUS current
DESCRIPTION
"Data value."
::= { dataArray14 65 }

dataValue14_66 OBJECT-TYPE
SYNTAX INTEGER
MAX-ACCESS read-write
STATUS current
DESCRIPTION
"Data value."
::= { dataArray14 66 }

dataValue14_67 OBJECT-TYPE
SYNTAX INTEGER
MAX-ACCESS read-write
STATUS current
DESCRIPTION
"Data value."
::= { dataArray14 67 }

dataValue14_68 OBJECT-TYPE
SYNTAX INTEGER
MAX-ACCESS read-write
STATUS current
DESCRIPTION
"Data value."
::= { dataArray14 68 }

dataValue14_69 OBJECT-TYPE
SYNTAX INTEGER
MAX-ACCESS read-write
STATUS current
DESCRIPTION
"Data value."
::= { dataArray14 69 }

dataValue14_70 OBJECT-TYPE
SYNTAX INTEGER
MAX-ACCESS read-write
STATUS current
DESCRIPTION
"Data value."
::= { dataArray14 70 }

dataValue14_71 OBJECT-TYPE
SYNTAX INTEGER
MAX-ACCESS read-write
STATUS current
DESCRIPTION
"Data value."
::= { dataArray14 71 }

dataValue14_72 OBJECT-TYPE
SYNTAX INTEGER
MAX-ACCESS read-write
STATUS current
DESCRIPTION
"Data value."
::= { dataArray14 72 }

dataValue14_73 OBJECT-TYPE
SYNTAX INTEGER
MAX-ACCESS read-write
STATUS current
DESCRIPTION
"Data value."
::= { dataArray14 73 }

dataValue14_74 OBJECT-TYPE
SYNTAX INTEGER
MAX-ACCESS read-write
STATUS current
DESCRIPTION
"Data value."
::= { dataArray14 74 }

dataValue14_75 OBJECT-TYPE
SYNTAX INTEGER
MAX-ACCESS read-write
STATUS current
DESCRIPTION
"Data value."
::= { dataArray14 75 }

dataValue14_76 OBJECT-TYPE
SYNTAX INTEGER
MAX-ACCESS read-write
STATUS current
DESCRIPTION
"Data value."
::= { dataArray14 76 }

dataValue14_77 OBJECT-TYPE
SYNTAX INTEGER
MAX-ACCESS read-write
STATUS current
DESCRIPTION
"Data value."
::= { dataArray14 77 }

dataValue14_78 OBJECT-TYPE
SYNTAX INTEGER
MAX-ACCESS read-write
STATUS current
DESCRIPTION
"Data value."
::= { dataArray14 78 }

dataValue14_79 OBJECT-TYPE
SYNTAX INTEGER
MAX-ACCESS read-write
STATUS current
DESCRIPTION
"Data value."
::= { dataArray14 79 }

dataValue14_80 OBJECT-TYPE
SYNTAX INTEGER
MAX-ACCESS read-write
STATUS current
DESCRIPTION
"Data value."
::= { dataArray14 80 }

dataValue14_81 OBJECT-TYPE
SYNTAX INTEGER
MAX-ACCESS read-write
STATUS current
DESCRIPTION
"Data value."
::= { dataArray14 81 }

dataValue14_82 OBJECT-TYPE
SYNTAX INTEGER
MAX-ACCESS read-write
STATUS current
DESCRIPTION
"Data value."
::= { dataArray14 82 }

dataValue14_83 OBJECT-TYPE
SYNTAX INTEGER
MAX-ACCESS read-write
STATUS current
DESCRIPTION
"Data value."
::= { dataArray14 83 }

dataValue14_84 OBJECT-TYPE
SYNTAX INTEGER
MAX-ACCESS read-write
STATUS current
DESCRIPTION
"Data value."
::= { dataArray14 84 }

dataValue14_85 OBJECT-TYPE
SYNTAX INTEGER
MAX-ACCESS read-write
STATUS current
DESCRIPTION
"Data value."
::= { dataArray14 85 }

dataValue14_86 OBJECT-TYPE
SYNTAX INTEGER
MAX-ACCESS read-write
STATUS current
DESCRIPTION
"Data value."
::= { dataArray14 86 }

dataValue14_87 OBJECT-TYPE
SYNTAX INTEGER
MAX-ACCESS read-write
STATUS current
DESCRIPTION
"Data value."
::= { dataArray14 87 }

dataValue14_88 OBJECT-TYPE
SYNTAX INTEGER
MAX-ACCESS read-write
STATUS current
DESCRIPTION
"Data value."
::= { dataArray14 88 }

dataValue14_89 OBJECT-TYPE
SYNTAX INTEGER
MAX-ACCESS read-write
STATUS current
DESCRIPTION
"Data value."
::= { dataArray14 89 }

dataValue14_90 OBJECT-TYPE
SYNTAX INTEGER
MAX-ACCESS read-write
STATUS current
DESCRIPTION
"Data value."
::= { dataArray14 90 }

dataValue14_91 OBJECT-TYPE
SYNTAX INTEGER
MAX-ACCESS read-write
STATUS current
DESCRIPTION
"Data value."
::= { dataArray14 91 }

dataValue14_92 OBJECT-TYPE
SYNTAX INTEGER
MAX-ACCESS read-write
STATUS current
DESCRIPTION
"Data value."
::= { dataArray14 92 }

dataValue14_93 OBJECT-TYPE
SYNTAX INTEGER
MAX-ACCESS read-write
STATUS current
DESCRIPTION
"Data value."
::= { dataArray14 93 }

dataValue14_94 OBJECT-TYPE
SYNTAX INTEGER
MAX-ACCESS read-write
STATUS current
DESCRIPTION
"Data value."
::= { dataArray14 94 }

dataValue14_95 OBJECT-TYPE
SYNTAX INTEGER
MAX-ACCESS read-write
STATUS current
DESCRIPTION
"Data value."
::= { dataArray14 95 }

dataValue14_96 OBJECT-TYPE
SYNTAX INTEGER
MAX-ACCESS read-write
STATUS current
DESCRIPTION
"Data value."
::= { dataArray14 96 }

dataValue14_97 OBJECT-TYPE
SYNTAX INTEGER
MAX-ACCESS read-write
STATUS current
DESCRIPTION
"Data value."
::= { dataArray14 97 }

dataValue14_98 OBJECT-TYPE
SYNTAX INTEGER
MAX-ACCESS read-write
STATUS current
DESCRIPTION
"Data value."
::= { dataArray14 98 }

dataValue14_99 OBJECT-TYPE
SYNTAX INTEGER
MAX-ACCESS read-write
STATUS current
DESCRIPTION
"Data value."
::= { dataArray14 99 }

dataArray15 OBJECT IDENTIFIER ::= { s08090201_trane_st_jude_v1_00b 15 }

dataValue15_0 OBJECT-TYPE
SYNTAX INTEGER
MAX-ACCESS read-write
STATUS current
DESCRIPTION
"Data value."
::= { dataArray15 0 }

dataValue15_1 OBJECT-TYPE
SYNTAX INTEGER
MAX-ACCESS read-write
STATUS current
DESCRIPTION
"Data value."
::= { dataArray15 1 }

dataValue15_2 OBJECT-TYPE
SYNTAX INTEGER
MAX-ACCESS read-write
STATUS current
DESCRIPTION
"Data value."
::= { dataArray15 2 }

dataValue15_3 OBJECT-TYPE
SYNTAX INTEGER
MAX-ACCESS read-write
STATUS current
DESCRIPTION
"Data value."
::= { dataArray15 3 }

dataValue15_4 OBJECT-TYPE
SYNTAX INTEGER
MAX-ACCESS read-write
STATUS current
DESCRIPTION
"Data value."
::= { dataArray15 4 }

dataValue15_5 OBJECT-TYPE
SYNTAX INTEGER
MAX-ACCESS read-write
STATUS current
DESCRIPTION
"Data value."
::= { dataArray15 5 }

dataValue15_6 OBJECT-TYPE
SYNTAX INTEGER
MAX-ACCESS read-write
STATUS current
DESCRIPTION
"Data value."
::= { dataArray15 6 }

dataValue15_7 OBJECT-TYPE
SYNTAX INTEGER
MAX-ACCESS read-write
STATUS current
DESCRIPTION
"Data value."
::= { dataArray15 7 }

dataValue15_8 OBJECT-TYPE
SYNTAX INTEGER
MAX-ACCESS read-write
STATUS current
DESCRIPTION
"Data value."
::= { dataArray15 8 }

dataValue15_9 OBJECT-TYPE
SYNTAX INTEGER
MAX-ACCESS read-write
STATUS current
DESCRIPTION
"Data value."
::= { dataArray15 9 }

dataValue15_10 OBJECT-TYPE
SYNTAX INTEGER
MAX-ACCESS read-write
STATUS current
DESCRIPTION
"Data value."
::= { dataArray15 10 }

dataValue15_11 OBJECT-TYPE
SYNTAX INTEGER
MAX-ACCESS read-write
STATUS current
DESCRIPTION
"Data value."
::= { dataArray15 11 }

dataValue15_12 OBJECT-TYPE
SYNTAX INTEGER
MAX-ACCESS read-write
STATUS current
DESCRIPTION
"Data value."
::= { dataArray15 12 }

dataValue15_13 OBJECT-TYPE
SYNTAX INTEGER
MAX-ACCESS read-write
STATUS current
DESCRIPTION
"Data value."
::= { dataArray15 13 }

dataValue15_14 OBJECT-TYPE
SYNTAX INTEGER
MAX-ACCESS read-write
STATUS current
DESCRIPTION
"Data value."
::= { dataArray15 14 }

dataValue15_15 OBJECT-TYPE
SYNTAX INTEGER
MAX-ACCESS read-write
STATUS current
DESCRIPTION
"Data value."
::= { dataArray15 15 }

dataValue15_16 OBJECT-TYPE
SYNTAX INTEGER
MAX-ACCESS read-write
STATUS current
DESCRIPTION
"Data value."
::= { dataArray15 16 }

dataValue15_17 OBJECT-TYPE
SYNTAX INTEGER
MAX-ACCESS read-write
STATUS current
DESCRIPTION
"Data value."
::= { dataArray15 17 }

dataValue15_18 OBJECT-TYPE
SYNTAX INTEGER
MAX-ACCESS read-write
STATUS current
DESCRIPTION
"Data value."
::= { dataArray15 18 }

dataValue15_19 OBJECT-TYPE
SYNTAX INTEGER
MAX-ACCESS read-write
STATUS current
DESCRIPTION
"Data value."
::= { dataArray15 19 }

dataValue15_20 OBJECT-TYPE
SYNTAX INTEGER
MAX-ACCESS read-write
STATUS current
DESCRIPTION
"Data value."
::= { dataArray15 20 }

dataValue15_21 OBJECT-TYPE
SYNTAX INTEGER
MAX-ACCESS read-write
STATUS current
DESCRIPTION
"Data value."
::= { dataArray15 21 }

dataValue15_22 OBJECT-TYPE
SYNTAX INTEGER
MAX-ACCESS read-write
STATUS current
DESCRIPTION
"Data value."
::= { dataArray15 22 }

dataValue15_23 OBJECT-TYPE
SYNTAX INTEGER
MAX-ACCESS read-write
STATUS current
DESCRIPTION
"Data value."
::= { dataArray15 23 }

dataValue15_24 OBJECT-TYPE
SYNTAX INTEGER
MAX-ACCESS read-write
STATUS current
DESCRIPTION
"Data value."
::= { dataArray15 24 }

dataValue15_25 OBJECT-TYPE
SYNTAX INTEGER
MAX-ACCESS read-write
STATUS current
DESCRIPTION
"Data value."
::= { dataArray15 25 }

dataValue15_26 OBJECT-TYPE
SYNTAX INTEGER
MAX-ACCESS read-write
STATUS current
DESCRIPTION
"Data value."
::= { dataArray15 26 }

dataValue15_27 OBJECT-TYPE
SYNTAX INTEGER
MAX-ACCESS read-write
STATUS current
DESCRIPTION
"Data value."
::= { dataArray15 27 }

dataValue15_28 OBJECT-TYPE
SYNTAX INTEGER
MAX-ACCESS read-write
STATUS current
DESCRIPTION
"Data value."
::= { dataArray15 28 }

dataValue15_29 OBJECT-TYPE
SYNTAX INTEGER
MAX-ACCESS read-write
STATUS current
DESCRIPTION
"Data value."
::= { dataArray15 29 }

dataValue15_30 OBJECT-TYPE
SYNTAX INTEGER
MAX-ACCESS read-write
STATUS current
DESCRIPTION
"Data value."
::= { dataArray15 30 }

dataValue15_31 OBJECT-TYPE
SYNTAX INTEGER
MAX-ACCESS read-write
STATUS current
DESCRIPTION
"Data value."
::= { dataArray15 31 }

dataValue15_32 OBJECT-TYPE
SYNTAX INTEGER
MAX-ACCESS read-write
STATUS current
DESCRIPTION
"Data value."
::= { dataArray15 32 }

dataValue15_33 OBJECT-TYPE
SYNTAX INTEGER
MAX-ACCESS read-write
STATUS current
DESCRIPTION
"Data value."
::= { dataArray15 33 }

dataValue15_34 OBJECT-TYPE
SYNTAX INTEGER
MAX-ACCESS read-write
STATUS current
DESCRIPTION
"Data value."
::= { dataArray15 34 }

dataValue15_35 OBJECT-TYPE
SYNTAX INTEGER
MAX-ACCESS read-write
STATUS current
DESCRIPTION
"Data value."
::= { dataArray15 35 }

dataValue15_36 OBJECT-TYPE
SYNTAX INTEGER
MAX-ACCESS read-write
STATUS current
DESCRIPTION
"Data value."
::= { dataArray15 36 }

dataValue15_37 OBJECT-TYPE
SYNTAX INTEGER
MAX-ACCESS read-write
STATUS current
DESCRIPTION
"Data value."
::= { dataArray15 37 }

dataValue15_38 OBJECT-TYPE
SYNTAX INTEGER
MAX-ACCESS read-write
STATUS current
DESCRIPTION
"Data value."
::= { dataArray15 38 }

dataValue15_39 OBJECT-TYPE
SYNTAX INTEGER
MAX-ACCESS read-write
STATUS current
DESCRIPTION
"Data value."
::= { dataArray15 39 }

dataValue15_40 OBJECT-TYPE
SYNTAX INTEGER
MAX-ACCESS read-write
STATUS current
DESCRIPTION
"Data value."
::= { dataArray15 40 }

dataValue15_41 OBJECT-TYPE
SYNTAX INTEGER
MAX-ACCESS read-write
STATUS current
DESCRIPTION
"Data value."
::= { dataArray15 41 }

dataValue15_42 OBJECT-TYPE
SYNTAX INTEGER
MAX-ACCESS read-write
STATUS current
DESCRIPTION
"Data value."
::= { dataArray15 42 }

dataValue15_43 OBJECT-TYPE
SYNTAX INTEGER
MAX-ACCESS read-write
STATUS current
DESCRIPTION
"Data value."
::= { dataArray15 43 }

dataValue15_44 OBJECT-TYPE
SYNTAX INTEGER
MAX-ACCESS read-write
STATUS current
DESCRIPTION
"Data value."
::= { dataArray15 44 }

dataValue15_45 OBJECT-TYPE
SYNTAX INTEGER
MAX-ACCESS read-write
STATUS current
DESCRIPTION
"Data value."
::= { dataArray15 45 }

dataValue15_46 OBJECT-TYPE
SYNTAX INTEGER
MAX-ACCESS read-write
STATUS current
DESCRIPTION
"Data value."
::= { dataArray15 46 }

dataValue15_47 OBJECT-TYPE
SYNTAX INTEGER
MAX-ACCESS read-write
STATUS current
DESCRIPTION
"Data value."
::= { dataArray15 47 }

dataValue15_48 OBJECT-TYPE
SYNTAX INTEGER
MAX-ACCESS read-write
STATUS current
DESCRIPTION
"Data value."
::= { dataArray15 48 }

dataValue15_49 OBJECT-TYPE
SYNTAX INTEGER
MAX-ACCESS read-write
STATUS current
DESCRIPTION
"Data value."
::= { dataArray15 49 }

dataValue15_50 OBJECT-TYPE
SYNTAX INTEGER
MAX-ACCESS read-write
STATUS current
DESCRIPTION
"Data value."
::= { dataArray15 50 }

dataValue15_51 OBJECT-TYPE
SYNTAX INTEGER
MAX-ACCESS read-write
STATUS current
DESCRIPTION
"Data value."
::= { dataArray15 51 }

dataValue15_52 OBJECT-TYPE
SYNTAX INTEGER
MAX-ACCESS read-write
STATUS current
DESCRIPTION
"Data value."
::= { dataArray15 52 }

dataValue15_53 OBJECT-TYPE
SYNTAX INTEGER
MAX-ACCESS read-write
STATUS current
DESCRIPTION
"Data value."
::= { dataArray15 53 }

dataValue15_54 OBJECT-TYPE
SYNTAX INTEGER
MAX-ACCESS read-write
STATUS current
DESCRIPTION
"Data value."
::= { dataArray15 54 }

dataValue15_55 OBJECT-TYPE
SYNTAX INTEGER
MAX-ACCESS read-write
STATUS current
DESCRIPTION
"Data value."
::= { dataArray15 55 }

dataValue15_56 OBJECT-TYPE
SYNTAX INTEGER
MAX-ACCESS read-write
STATUS current
DESCRIPTION
"Data value."
::= { dataArray15 56 }

dataValue15_57 OBJECT-TYPE
SYNTAX INTEGER
MAX-ACCESS read-write
STATUS current
DESCRIPTION
"Data value."
::= { dataArray15 57 }

dataValue15_58 OBJECT-TYPE
SYNTAX INTEGER
MAX-ACCESS read-write
STATUS current
DESCRIPTION
"Data value."
::= { dataArray15 58 }

dataValue15_59 OBJECT-TYPE
SYNTAX INTEGER
MAX-ACCESS read-write
STATUS current
DESCRIPTION
"Data value."
::= { dataArray15 59 }

dataValue15_60 OBJECT-TYPE
SYNTAX INTEGER
MAX-ACCESS read-write
STATUS current
DESCRIPTION
"Data value."
::= { dataArray15 60 }

dataValue15_61 OBJECT-TYPE
SYNTAX INTEGER
MAX-ACCESS read-write
STATUS current
DESCRIPTION
"Data value."
::= { dataArray15 61 }

dataValue15_62 OBJECT-TYPE
SYNTAX INTEGER
MAX-ACCESS read-write
STATUS current
DESCRIPTION
"Data value."
::= { dataArray15 62 }

dataValue15_63 OBJECT-TYPE
SYNTAX INTEGER
MAX-ACCESS read-write
STATUS current
DESCRIPTION
"Data value."
::= { dataArray15 63 }

dataValue15_64 OBJECT-TYPE
SYNTAX INTEGER
MAX-ACCESS read-write
STATUS current
DESCRIPTION
"Data value."
::= { dataArray15 64 }

dataValue15_65 OBJECT-TYPE
SYNTAX INTEGER
MAX-ACCESS read-write
STATUS current
DESCRIPTION
"Data value."
::= { dataArray15 65 }

dataValue15_66 OBJECT-TYPE
SYNTAX INTEGER
MAX-ACCESS read-write
STATUS current
DESCRIPTION
"Data value."
::= { dataArray15 66 }

dataValue15_67 OBJECT-TYPE
SYNTAX INTEGER
MAX-ACCESS read-write
STATUS current
DESCRIPTION
"Data value."
::= { dataArray15 67 }

dataValue15_68 OBJECT-TYPE
SYNTAX INTEGER
MAX-ACCESS read-write
STATUS current
DESCRIPTION
"Data value."
::= { dataArray15 68 }

dataValue15_69 OBJECT-TYPE
SYNTAX INTEGER
MAX-ACCESS read-write
STATUS current
DESCRIPTION
"Data value."
::= { dataArray15 69 }

dataValue15_70 OBJECT-TYPE
SYNTAX INTEGER
MAX-ACCESS read-write
STATUS current
DESCRIPTION
"Data value."
::= { dataArray15 70 }

dataValue15_71 OBJECT-TYPE
SYNTAX INTEGER
MAX-ACCESS read-write
STATUS current
DESCRIPTION
"Data value."
::= { dataArray15 71 }

dataValue15_72 OBJECT-TYPE
SYNTAX INTEGER
MAX-ACCESS read-write
STATUS current
DESCRIPTION
"Data value."
::= { dataArray15 72 }

dataValue15_73 OBJECT-TYPE
SYNTAX INTEGER
MAX-ACCESS read-write
STATUS current
DESCRIPTION
"Data value."
::= { dataArray15 73 }

dataValue15_74 OBJECT-TYPE
SYNTAX INTEGER
MAX-ACCESS read-write
STATUS current
DESCRIPTION
"Data value."
::= { dataArray15 74 }

dataValue15_75 OBJECT-TYPE
SYNTAX INTEGER
MAX-ACCESS read-write
STATUS current
DESCRIPTION
"Data value."
::= { dataArray15 75 }

dataValue15_76 OBJECT-TYPE
SYNTAX INTEGER
MAX-ACCESS read-write
STATUS current
DESCRIPTION
"Data value."
::= { dataArray15 76 }

dataValue15_77 OBJECT-TYPE
SYNTAX INTEGER
MAX-ACCESS read-write
STATUS current
DESCRIPTION
"Data value."
::= { dataArray15 77 }

dataValue15_78 OBJECT-TYPE
SYNTAX INTEGER
MAX-ACCESS read-write
STATUS current
DESCRIPTION
"Data value."
::= { dataArray15 78 }

dataValue15_79 OBJECT-TYPE
SYNTAX INTEGER
MAX-ACCESS read-write
STATUS current
DESCRIPTION
"Data value."
::= { dataArray15 79 }

dataValue15_80 OBJECT-TYPE
SYNTAX INTEGER
MAX-ACCESS read-write
STATUS current
DESCRIPTION
"Data value."
::= { dataArray15 80 }

dataValue15_81 OBJECT-TYPE
SYNTAX INTEGER
MAX-ACCESS read-write
STATUS current
DESCRIPTION
"Data value."
::= { dataArray15 81 }

dataValue15_82 OBJECT-TYPE
SYNTAX INTEGER
MAX-ACCESS read-write
STATUS current
DESCRIPTION
"Data value."
::= { dataArray15 82 }

dataValue15_83 OBJECT-TYPE
SYNTAX INTEGER
MAX-ACCESS read-write
STATUS current
DESCRIPTION
"Data value."
::= { dataArray15 83 }

dataValue15_84 OBJECT-TYPE
SYNTAX INTEGER
MAX-ACCESS read-write
STATUS current
DESCRIPTION
"Data value."
::= { dataArray15 84 }

dataValue15_85 OBJECT-TYPE
SYNTAX INTEGER
MAX-ACCESS read-write
STATUS current
DESCRIPTION
"Data value."
::= { dataArray15 85 }

dataValue15_86 OBJECT-TYPE
SYNTAX INTEGER
MAX-ACCESS read-write
STATUS current
DESCRIPTION
"Data value."
::= { dataArray15 86 }

dataValue15_87 OBJECT-TYPE
SYNTAX INTEGER
MAX-ACCESS read-write
STATUS current
DESCRIPTION
"Data value."
::= { dataArray15 87 }

dataValue15_88 OBJECT-TYPE
SYNTAX INTEGER
MAX-ACCESS read-write
STATUS current
DESCRIPTION
"Data value."
::= { dataArray15 88 }

dataValue15_89 OBJECT-TYPE
SYNTAX INTEGER
MAX-ACCESS read-write
STATUS current
DESCRIPTION
"Data value."
::= { dataArray15 89 }

dataValue15_90 OBJECT-TYPE
SYNTAX INTEGER
MAX-ACCESS read-write
STATUS current
DESCRIPTION
"Data value."
::= { dataArray15 90 }

dataValue15_91 OBJECT-TYPE
SYNTAX INTEGER
MAX-ACCESS read-write
STATUS current
DESCRIPTION
"Data value."
::= { dataArray15 91 }

dataValue15_92 OBJECT-TYPE
SYNTAX INTEGER
MAX-ACCESS read-write
STATUS current
DESCRIPTION
"Data value."
::= { dataArray15 92 }

dataValue15_93 OBJECT-TYPE
SYNTAX INTEGER
MAX-ACCESS read-write
STATUS current
DESCRIPTION
"Data value."
::= { dataArray15 93 }

dataValue15_94 OBJECT-TYPE
SYNTAX INTEGER
MAX-ACCESS read-write
STATUS current
DESCRIPTION
"Data value."
::= { dataArray15 94 }

dataValue15_95 OBJECT-TYPE
SYNTAX INTEGER
MAX-ACCESS read-write
STATUS current
DESCRIPTION
"Data value."
::= { dataArray15 95 }

dataValue15_96 OBJECT-TYPE
SYNTAX INTEGER
MAX-ACCESS read-write
STATUS current
DESCRIPTION
"Data value."
::= { dataArray15 96 }

dataValue15_97 OBJECT-TYPE
SYNTAX INTEGER
MAX-ACCESS read-write
STATUS current
DESCRIPTION
"Data value."
::= { dataArray15 97 }

dataValue15_98 OBJECT-TYPE
SYNTAX INTEGER
MAX-ACCESS read-write
STATUS current
DESCRIPTION
"Data value."
::= { dataArray15 98 }

dataValue15_99 OBJECT-TYPE
SYNTAX INTEGER
MAX-ACCESS read-write
STATUS current
DESCRIPTION
"Data value."
::= { dataArray15 99 }

END
