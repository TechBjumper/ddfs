GEISTMFG-EM8GM1-MIB DEFINITIONS ::= BEGIN

IMPORTS
	MODULE-IDENTITY, OBJECT-TYPE, enterprises, Unsigned32 FROM SNMPv2-SMI;

geistmfg MODULE-IDENTITY
	LAST-UPDATED "200612140000Z"
	ORGANIZATION "Geist Manufacturing"
	CONTACT-INFO "support@geistmfg.com/800.432.3219"
	DESCRIPTION "The MIB for EM8/GM1"
	::= { enterprises 21239 }
	

em8gm1 OBJECT IDENTIFIER
	::=  { geistmfg 12 }


productInfo OBJECT IDENTIFIER
	::= { em8gm1 1 }

totalDeciAmps OBJECT IDENTIFIER
	::= { em8gm1 2 }




productTitle    OBJECT-TYPE
   SYNTAX DisplayString
   ACCESS read-only
   STATUS mandatory
   DESCRIPTION
      "Name of product"
   ::= { productInfo 1 }
   
productVersion    OBJECT-TYPE
   SYNTAX DisplayString
   ACCESS read-only
   STATUS mandatory
   DESCRIPTION
      "Firmware version"
   ::= { productInfo 2 }

productName    OBJECT-TYPE
   SYNTAX DisplayString
   ACCESS read-only
   STATUS mandatory
   DESCRIPTION
      "Unit friendly name"
   ::= { productInfo 3 }

productMAC    OBJECT-TYPE
   SYNTAX DisplayString
   ACCESS read-only
   STATUS mandatory
   DESCRIPTION
      "Unit MAC address"
   ::= { productInfo 4 }

productIP    OBJECT-TYPE
   SYNTAX DisplayString
   ACCESS read-only
   STATUS mandatory
   DESCRIPTION
      "IP address of the unit"
   ::= { productInfo 5 }




totalDeciAmpsCircuit1   OBJECT-TYPE
   SYNTAX INTEGER(0..300)
   UNITS "0.1 Amps"
   ACCESS read-only
   STATUS mandatory
   DESCRIPTION
   "Total Amps consumed by Circuit1, in units of 0.1 amps"
   ::= { totalDeciAmps 1 }



totalDeciAmpsCircuit1TRAP TRAP-TYPE
ENTERPRISE geistmfg
VARIABLES { totalDeciAmpsCircuit1 }
DESCRIPTION "Amps Circuit1 Trap"
::= 1





END
