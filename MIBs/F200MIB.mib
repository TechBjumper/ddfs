--
--defines FALCONF200-MIB for SNMP agent extension of Falcon F200
--Contents:	Global Registration Module
--		Falcon F200 OIDs - Enterprise 3184
--Version:	2.0.5 
--Date:		31 Mar 2014

--
--

F200-MIB DEFINITIONS ::= BEGIN


IMPORTS
	enterprises, IpAddress, Counter, TimeTicks
		FROM RFC1155-SMI
	OBJECT-TYPE
		FROM RFC-1212
	TRAP-TYPE 
		FROM RFC-1215
	DisplayString
		FROM RFC1213-MIB;


rle      OBJECT IDENTIFIER ::= { enterprises 3184 }
products      OBJECT IDENTIFIER ::= { rle 1 }
f200		OBJECT IDENTIFIER ::= { products 14 }
productInfo	OBJECT IDENTIFIER ::= { f200 1 }
sensors		OBJECT IDENTIFIER ::= { f200 2 }
leakCables	OBJECT IDENTIFIER ::= { f200 3 }
digInputs	OBJECT IDENTIFIER ::= { f200 4 }
relays		OBJECT IDENTIFIER ::= { f200 5 }
f200Trap	OBJECT IDENTIFIER ::= { f200 6 }

sensor1		OBJECT IDENTIFIER ::= { sensors 1 }
sensor2		OBJECT IDENTIFIER ::= { sensors 2 }
sensor3		OBJECT IDENTIFIER ::= { sensors 3 }
sensor4		OBJECT IDENTIFIER ::= { sensors 4 }

relay1		OBJECT IDENTIFIER ::= { relays 1 }

digInput1	OBJECT IDENTIFIER ::= { digInputs 1 }
digInput2	OBJECT IDENTIFIER ::= { digInputs 2 }
digInput3	OBJECT IDENTIFIER ::= { digInputs 3 }
digInput4	OBJECT IDENTIFIER ::= { digInputs 4 }
digInput5	OBJECT IDENTIFIER ::= { digInputs 5 }
digInput6	OBJECT IDENTIFIER ::= { digInputs 6 }
digInput7	OBJECT IDENTIFIER ::= { digInputs 7 }
digInput8	OBJECT IDENTIFIER ::= { digInputs 8 }

leak1		OBJECT IDENTIFIER ::= { leakCables 1 }


-- Relay --
relay1State OBJECT-TYPE
	SYNTAX  	INTEGER {
				off(0),
				energized(1)
			}
	ACCESS		read-only
	STATUS		mandatory
	DESCRIPTION	"The current state of the relay. 1 = Energized, 0 = De-Energized"
::= { relay1 1 }


-- Digital Inputs --
----------------------------------------------------------------------
digInput1State OBJECT-TYPE
	SYNTAX  	INTEGER {
				open(0),
				closed(1)
			}
	ACCESS		read-only
	STATUS		mandatory
	DESCRIPTION	"The current state of Digital Input #1. 1 = Closed, 0 = Open"
::= { digInput1 1 }

digInput1Alarm OBJECT-TYPE
	SYNTAX  	INTEGER {
				normal(0),
				alarm(1)
			}
	ACCESS		read-only
	STATUS		mandatory
	DESCRIPTION	"The current state of Digital Input #1. 1 = Closed, 0 = Open"
::= { digInput1 2 }

digInput2State OBJECT-TYPE
	SYNTAX  	INTEGER {
				open(0),
				closed(1)
			}
	ACCESS		read-only
	STATUS		mandatory
	DESCRIPTION	"The current state of Digital Input #2. 1 = Closed, 0 = Open"
::= { digInput2 1 }

digInput2Alarm OBJECT-TYPE
	SYNTAX  	INTEGER {
				normal(0),
				alarm(1)
			}
	ACCESS		read-only
	STATUS		mandatory
	DESCRIPTION	"The current state of Digital Input #2. 1 = Closed, 0 = Open"
::= { digInput2 2 }

digInput3State OBJECT-TYPE
	SYNTAX  	INTEGER {
				open(0),
				closed(1)
			}
	ACCESS		read-only
	STATUS		mandatory
	DESCRIPTION	"The current state of Digital Input #3. 1 = Closed, 0 = Open"
::= { digInput3 1 }

digInput3Alarm OBJECT-TYPE
	SYNTAX  	INTEGER {
				normal(0),
				alarm(1)
			}
	ACCESS		read-only
	STATUS		mandatory
	DESCRIPTION	"The current state of Digital Input #3. 1 = Closed, 0 = Open"
::= { digInput3 2 }

digInput4State OBJECT-TYPE
	SYNTAX  	INTEGER {
				open(0),
				closed(1)
			}
	ACCESS		read-only
	STATUS		mandatory
	DESCRIPTION	"The current state of Digital Input #4. 1 = Closed, 0 = Open"
::= { digInput4 1 }

digInput4Alarm OBJECT-TYPE
	SYNTAX  	INTEGER {
				normal(0),
				alarm(1)
			}
	ACCESS		read-only
	STATUS		mandatory
	DESCRIPTION	"The current state of Digital Input #4. 1 = Closed, 0 = Open"
::= { digInput4 2 }

digInput5State OBJECT-TYPE
	SYNTAX  	INTEGER {
				open(0),
				closed(1)
			}
	ACCESS		read-only
	STATUS		mandatory
	DESCRIPTION	"The current state of Digital Input #5. 1 = Closed, 0 = Open"
::= { digInput5 1 }

digInput5Alarm OBJECT-TYPE
	SYNTAX  	INTEGER {
				normal(0),
				alarm(1)
			}
	ACCESS		read-only
	STATUS		mandatory
	DESCRIPTION	"The current state of Digital Input #5. 1 = Closed, 0 = Open"
::= { digInput5 2 }

digInput6State OBJECT-TYPE
	SYNTAX  	INTEGER {
				open(0),
				closed(1)
			}
	ACCESS		read-only
	STATUS		mandatory
	DESCRIPTION	"The current state of Digital Input #6. 1 = Closed, 0 = Open"
::= { digInput6 1 }

digInput6Alarm OBJECT-TYPE
	SYNTAX  	INTEGER {
				normal(0),
				alarm(1)
			}
	ACCESS		read-only
	STATUS		mandatory
	DESCRIPTION	"The current state of Digital Input #6. 1 = Closed, 0 = Open"
::= { digInput6 2 }

digInput7State OBJECT-TYPE
	SYNTAX  	INTEGER {
				open(0),
				closed(1)
			}
	ACCESS		read-only
	STATUS		mandatory
	DESCRIPTION	"The current state of Digital Input #7. 1 = Closed, 0 = Open"
::= { digInput7 1 }

digInput7Alarm OBJECT-TYPE
	SYNTAX  	INTEGER {
				normal(0),
				alarm(1)
			}
	ACCESS		read-only
	STATUS		mandatory
	DESCRIPTION	"The current state of Digital Input #7. 1 = Closed, 0 = Open"
::= { digInput7 2 }

digInput8State OBJECT-TYPE
	SYNTAX  	INTEGER {
				open(0),
				closed(1)
			}
	ACCESS		read-only
	STATUS		mandatory
	DESCRIPTION	"The current state of Digital Input #8. 1 = Closed, 0 = Open"
::= { digInput8 1 }

digInput8Alarm OBJECT-TYPE
	SYNTAX  	INTEGER {
				normal(0),
				alarm(1)
			}
	ACCESS		read-only
	STATUS		mandatory
	DESCRIPTION	"The alarm state of Digital Input #8. 1 = Closed, 0 = Open"
::= { digInput8 2 }

-- Leak Cable --
---------------------------------------------------------------
leak1CableFound OBJECT-TYPE
	SYNTAX  	DisplayString
	ACCESS		read-only
	STATUS		mandatory
	DESCRIPTION	"This indicates that a cable is connected to the unit, even if leak detection is disabled. 1=Conneced, 0=No Cable"
::= { leak1 1 }

leak1Current OBJECT-TYPE
	SYNTAX  	INTEGER (0..200)
	ACCESS		read-only
	STATUS		mandatory
	DESCRIPTION	"The current conducting through the leak cable in uA"
::= { leak1 2 }

leak1Alarm OBJECT-TYPE
	SYNTAX  	INTEGER {
				noLeak(0),
				leakDetected(1)
			}
	ACCESS		read-only
	STATUS		mandatory
	DESCRIPTION	"This is set to 1 when a leak is detected"
::= { leak1 3 }

leak1CableBreak OBJECT-TYPE
	SYNTAX  	INTEGER {
				cableNormal(0),
				cableBreakDetected(1)
			}
	ACCESS		read-only
	STATUS		mandatory
	DESCRIPTION	"This value get set to 1 if one of the loops in the cable is broken"
::= { leak1 4 }

-- Product Info --
------------------------------------------------------------------------

firmwareVersion OBJECT-TYPE
	SYNTAX  	INTEGER 
	ACCESS		read-only
	STATUS		mandatory
	DESCRIPTION	"The current firmware version for this product"
::= { productInfo 1 }

unitName OBJECT-TYPE
	SYNTAX  	DisplayString
	ACCESS		read-only
	STATUS		mandatory
	DESCRIPTION	"The name of this unit as defined by the user in the user interface"
::= { productInfo 2 }

unitMacID OBJECT-TYPE
	SYNTAX  	DisplayString
	ACCESS		read-only
	STATUS		mandatory
	DESCRIPTION	"The MAC ID of the unit"
::= { productInfo 3 }

unitSerial OBJECT-TYPE
	SYNTAX  	DisplayString
	ACCESS		read-only
	STATUS		mandatory
	DESCRIPTION	"The RLE serial number for this unit"
::= { productInfo 4 }



-- Sensors --
------------------------------------------------------------------------
sensor1Name OBJECT-TYPE
	SYNTAX  	DisplayString
	ACCESS		read-only
	STATUS		mandatory
	DESCRIPTION	"User defined name of sensor attatched to port #1"
::= { sensor1 1}

sensor2Name OBJECT-TYPE
	SYNTAX  	DisplayString
	ACCESS		read-only
	STATUS		mandatory
	DESCRIPTION	"User defined name of sensor attatched to port #2"
::= { sensor2 1}

sensor3Name OBJECT-TYPE
	SYNTAX  	DisplayString
	ACCESS		read-only
	STATUS		mandatory
	DESCRIPTION	"User defined name of sensor attatched to port #3"
::= { sensor3 1}

sensor4Name OBJECT-TYPE
	SYNTAX  	DisplayString
	ACCESS		read-only
	STATUS		mandatory
	DESCRIPTION	"User defined name of sensor attatched to port #4"
::= { sensor4 1}

sensor1Location OBJECT-TYPE
	SYNTAX  	DisplayString
	ACCESS		read-only
	STATUS		mandatory
	DESCRIPTION	"User defined location of sensor attatched to port #1"
::= { sensor1 2}

sensor2Location OBJECT-TYPE
	SYNTAX  	DisplayString
	ACCESS		read-only
	STATUS		mandatory
	DESCRIPTION	"User defined location of sensor attatched to port #2"
::= { sensor2 2}

sensor3Location OBJECT-TYPE
	SYNTAX  	DisplayString
	ACCESS		read-only
	STATUS		mandatory
	DESCRIPTION	"User defined location of sensor attatched to port #3"
::= { sensor3 2}

sensor4Location OBJECT-TYPE
	SYNTAX  	DisplayString
	ACCESS		read-only
	STATUS		mandatory
	DESCRIPTION	"User defined location of sensor attatched to port #4"
::= { sensor4 2}

sensor1Type OBJECT-TYPE
	SYNTAX  		INTEGER
	ACCESS		read-only
	STATUS		mandatory
	DESCRIPTION	"Type of Sensor attatched to Port 1"
::= { sensor1 3}

sensor2Type OBJECT-TYPE
	SYNTAX  		INTEGER
	ACCESS		read-only
	STATUS		mandatory
	DESCRIPTION	"Type of Sensor attatched to Port 2"
::= { sensor2 3}

sensor3Type OBJECT-TYPE
	SYNTAX  		INTEGER
	ACCESS		read-only
	STATUS		mandatory
	DESCRIPTION	"Type of Sensor attatched to Port 3"
::= { sensor3 3}

sensor4Type OBJECT-TYPE
	SYNTAX  		INTEGER
	ACCESS		read-only
	STATUS		mandatory
	DESCRIPTION	"Type of Sensor attatched to Port 4"
::= { sensor4 3}

sensor1Temperature OBJECT-TYPE
	SYNTAX  		INTEGER
	ACCESS		read-only
	STATUS		mandatory
	DESCRIPTION	"Temperature reading of sensor on Port 1 in Degrees Celsius multiplied by 100"
::= { sensor1 4}

sensor2Temperature OBJECT-TYPE
	SYNTAX  		INTEGER
	ACCESS		read-only
	STATUS		mandatory
	DESCRIPTION	"Temperature reading of sensor on Port 2 in Degrees Celsius multiplied by 100"
::= { sensor2 4}

sensor3Temperature OBJECT-TYPE
	SYNTAX  		INTEGER
	ACCESS		read-only
	STATUS		mandatory
	DESCRIPTION	"Temperature reading of sensor on Port 3 in Degrees Celsius multiplied by 100"
::= { sensor3 4}

sensor4Temperature OBJECT-TYPE
	SYNTAX  		INTEGER
	ACCESS		read-only
	STATUS		mandatory
	DESCRIPTION	"Temperature reading of sensor on Port 4 in Degrees Celsius multiplied by 100"
::= { sensor4 4}

sensor1Humidity OBJECT-TYPE
	SYNTAX  		INTEGER
	ACCESS		read-only
	STATUS		mandatory
	DESCRIPTION	"Percent relative humidity read by sensor on Port 1"
::= { sensor1 5}

sensor2Humidity OBJECT-TYPE
	SYNTAX  		INTEGER
	ACCESS		read-only
	STATUS		mandatory
	DESCRIPTION	"Percent relative humidity read by sensor on Port 2"
::= { sensor2 5}

sensor3Humidity OBJECT-TYPE
	SYNTAX  		INTEGER
	ACCESS		read-only
	STATUS		mandatory
	DESCRIPTION	"Percent relative humidity read by sensor on Port 3"
::= { sensor3 5}

sensor4Humidity OBJECT-TYPE
	SYNTAX  		INTEGER
	ACCESS		read-only
	STATUS		mandatory
	DESCRIPTION	"Percent relative humidity read by sensor on Port 4"
::= { sensor4 5}

sensor1MaxTemp OBJECT-TYPE
	SYNTAX  		INTEGER
	ACCESS		read-only
	STATUS		mandatory
	DESCRIPTION	"Maximum temperature alarm point for sensor on Port 1 in Degrees Celsius multiplied by 100"
::= { sensor1 6}

sensor2MaxTemp OBJECT-TYPE
	SYNTAX  		INTEGER
	ACCESS		read-only
	STATUS		mandatory
	DESCRIPTION	"Maximum temperature alarm point for sensor on Port 2 in Degrees Celsius multiplied by 100"
::= { sensor2 6}

sensor3MaxTemp OBJECT-TYPE
	SYNTAX  		INTEGER
	ACCESS		read-only
	STATUS		mandatory
	DESCRIPTION	"Maximum temperature alarm point for sensor on Port 3 in Degrees Celsius multiplied by 100"
::= { sensor3 6}

sensor4MaxTemp OBJECT-TYPE
	SYNTAX  		INTEGER
	ACCESS		read-only
	STATUS		mandatory
	DESCRIPTION	"Maximum temperature alarm point for sensor on Port 4 in Degrees Celsius multiplied by 100"
::= { sensor4 6}

sensor1MinTemp OBJECT-TYPE
	SYNTAX  		INTEGER
	ACCESS		read-only
	STATUS		mandatory
	DESCRIPTION	"Minimum temperature alarm point for sensor on Port 1 in Degrees Celsius multiplied by 100"
::= { sensor1 7}

sensor2MinTemp OBJECT-TYPE
	SYNTAX  		INTEGER
	ACCESS		read-only
	STATUS		mandatory
	DESCRIPTION	"Minimum temperature alarm point for sensor on Port 2 in Degrees Celsius multiplied by 100"
::= { sensor2 7}

sensor3MinTemp OBJECT-TYPE
	SYNTAX  		INTEGER
	ACCESS		read-only
	STATUS		mandatory
	DESCRIPTION	"Minimum temperature alarm point for sensor on Port 3 in Degrees Celsius multiplied by 100"
::= { sensor3 7}

sensor4MinTemp OBJECT-TYPE
	SYNTAX  		INTEGER
	ACCESS		read-only
	STATUS		mandatory
	DESCRIPTION	"Minimum temperature alarm point for sensor on Port 4 in Degrees Celsius multiplied by 100"
::= { sensor4 7}

sensor1MaxHumidity OBJECT-TYPE
	SYNTAX  		INTEGER
	ACCESS		read-only
	STATUS		mandatory
	DESCRIPTION	"Maximum Humidity alarm point for sensor on Port 1"
::= { sensor1 8}

sensor2MaxHumidity OBJECT-TYPE
	SYNTAX  		INTEGER
	ACCESS		read-only
	STATUS		mandatory
	DESCRIPTION	"Maximum Humidity alarm point for sensor on Port 2"
::= { sensor2 8}

sensor3MaxHumidity OBJECT-TYPE
	SYNTAX  		INTEGER
	ACCESS		read-only
	STATUS		mandatory
	DESCRIPTION	"Maximum Humidity alarm point for sensor on Port 3"
::= { sensor3 8}

sensor4MaxHumidity OBJECT-TYPE
	SYNTAX  		INTEGER
	ACCESS		read-only
	STATUS		mandatory
	DESCRIPTION	"Maximum Humidity alarm point for sensor on Port 4"
::= { sensor4 8}

sensor1MinHumidity OBJECT-TYPE
	SYNTAX  		INTEGER
	ACCESS		read-only
	STATUS		mandatory
	DESCRIPTION	"Minimum Humidity alarm point for sensor on Port 1"
::= { sensor1 9}

sensor2MinHumidity OBJECT-TYPE
	SYNTAX  		INTEGER
	ACCESS		read-only
	STATUS		mandatory
	DESCRIPTION	"Minimum Humidity alarm point for sensor on Port 2"
::= { sensor2 9}

sensor3MinHumidity OBJECT-TYPE
	SYNTAX  		INTEGER
	ACCESS		read-only
	STATUS		mandatory
	DESCRIPTION	"Minimum Humidity alarm point for sensor on Port 3"
::= { sensor3 9}

sensor4MinHumidity OBJECT-TYPE
	SYNTAX  		INTEGER
	ACCESS		read-only
	STATUS		mandatory
	DESCRIPTION	"Minimum Humidity alarm point for sensor on Port 4"
::= { sensor4 9}

sensor1AlarmStatus OBJECT-TYPE
	SYNTAX  		INTEGER
	ACCESS		read-only
	STATUS		mandatory
	DESCRIPTION	"Alarm status for port 1. 1=In Alarm, 0=Normal"
::= { sensor1 10}

sensor2AlarmStatus OBJECT-TYPE
	SYNTAX  		INTEGER
	ACCESS		read-only
	STATUS		mandatory
	DESCRIPTION	"Alarm status for port 2. 1=In Alarm, 0=Normal"
::= { sensor2 10}

sensor3AlarmStatus OBJECT-TYPE
	SYNTAX  		INTEGER
	ACCESS		read-only
	STATUS		mandatory
	DESCRIPTION	"Alarm status for port 3.  1=In Alarm, 0=Normal"
::= { sensor3 10}

sensor4AlarmStatus OBJECT-TYPE
	SYNTAX  		INTEGER
	ACCESS		read-only
	STATUS		mandatory
	DESCRIPTION	"Alarm status for port 4.  1=In Alarm, 0=Normal"
::= { sensor4 10}



--digitalInAlarm Traps
-------------------------------------------------------
digitalIn1Alarm TRAP-TYPE
	ENTERPRISE	f200Trap
	VARIABLES	{ unitName }
	DESCRIPTION	"A digitalIn1Alarm trap indicates that digital input 1 has either opened or closed to cause an alarm"
::= 1


digitalIn2Alarm TRAP-TYPE
	ENTERPRISE	f200Trap
	VARIABLES	{ unitName }
	DESCRIPTION	"A digitalIn2Alarm trap indicates that digital input 2 has either opened or closed to cause an alarm"
::= 2


digitalIn3Alarm TRAP-TYPE
	ENTERPRISE	f200Trap
	VARIABLES	{ unitName }
	DESCRIPTION	"A digitalIn3Alarm trap indicates that digital input 3 has either opened or closed to cause an alarm"
::= 3


digitalIn4Alarm TRAP-TYPE
	ENTERPRISE	f200Trap
	VARIABLES	{ unitName }
	DESCRIPTION	"A digitalIn4Alarm trap indicates that digital input 4 has either opened or closed to cause an alarm"
::= 4


digitalIn5Alarm TRAP-TYPE
	ENTERPRISE	f200Trap
	VARIABLES	{ unitName }
	DESCRIPTION	"A digitalIn5Alarm trap indicates that digital input 5 has either opened or closed to cause an alarm"
::= 5


digitalIn6Alarm TRAP-TYPE
	ENTERPRISE	f200Trap
	VARIABLES	{ unitName }
	DESCRIPTION	"A digitalIn6Alarm trap indicates that digital input 6 has either opened or closed to cause an alarm"
::= 6


digitalIn7Alarm TRAP-TYPE
	ENTERPRISE	f200Trap
	VARIABLES	{ unitName }
	DESCRIPTION	"A digitalIn7Alarm trap indicates that digital input 7 has either opened or closed to cause an alarm"
::= 7


digitalIn8Alarm TRAP-TYPE
	ENTERPRISE	f200Trap
	VARIABLES	{ unitName }
	DESCRIPTION	"A digitalIn8Alarm trap indicates that digital input 8 has either opened or closed to cause an alarm"
::= 8


--digitalInNormal Traps
-------------------------------------------------------
digitalIn1Normal TRAP-TYPE
	ENTERPRISE	f200Trap
	VARIABLES	{ unitName }
	DESCRIPTION	"A digitalIn1Normal trap indicates that digital input 1 has returned to normal"
::= 9


digitalIn2Normal TRAP-TYPE
	ENTERPRISE	f200Trap
	VARIABLES	{ unitName }
	DESCRIPTION	"A digitalIn2Normal trap indicates that digital input 2 has returned to normal"
::= 10


digitalIn3Normal TRAP-TYPE
	ENTERPRISE	f200Trap
	VARIABLES	{ unitName }
	DESCRIPTION	"A digitalIn3Normal trap indicates that digital input 3 has returned to normal"
::= 11


digitalIn4Normal TRAP-TYPE
	ENTERPRISE	f200Trap
	VARIABLES	{ unitName }
	DESCRIPTION	"A digitalIn4Normal trap indicates that digital input 4 has returned to normal"
::= 12


digitalIn5Normal TRAP-TYPE
	ENTERPRISE	f200Trap
	VARIABLES	{ unitName }
	DESCRIPTION	"A digitalIn5Normal trap indicates that digital input 5 has returned to normal"
::= 13


digitalIn6Normal TRAP-TYPE
	ENTERPRISE	f200Trap
	VARIABLES	{ unitName }
	DESCRIPTION	"A digitalIn6Normal trap indicates that digital input 6 has returned to normal"
::= 14


digitalIn7Normal TRAP-TYPE
	ENTERPRISE	f200Trap
	VARIABLES	{ unitName }
	DESCRIPTION	"A digitalIn7Normal trap indicates that digital input 7 has returned to normal"
::= 15


digitalIn8Normal TRAP-TYPE
	ENTERPRISE	f200Trap
	VARIABLES	{ unitName }
	DESCRIPTION	"A digitalIn8Normal trap indicates that digital input 8 has returned to normal"
::= 16


--digitalInOpened Traps
-------------------------------------------------------
digitalIn1Opened TRAP-TYPE
	ENTERPRISE	f200Trap
	VARIABLES	{ unitName }
	DESCRIPTION	"A digitalIn1Opened trap indicates that digital input 1 has just been Opened"
::= 17


digitalIn2Opened TRAP-TYPE
	ENTERPRISE	f200Trap
	VARIABLES	{ unitName }
	DESCRIPTION	"A digitalIn2Opened trap indicates that digital input 2 has just been Opened"
::= 18


digitalIn3Opened TRAP-TYPE
	ENTERPRISE	f200Trap
	VARIABLES	{ unitName }
	DESCRIPTION	"A digitalIn3Opened trap indicates that digital input 3 has just been Opened"
::= 19


digitalIn4Opened TRAP-TYPE
	ENTERPRISE	f200Trap
	VARIABLES	{ unitName }
	DESCRIPTION	"A digitalIn4Opened trap indicates that digital input 4 has just been Opened"
::= 20


digitalIn5Opened TRAP-TYPE
	ENTERPRISE	f200Trap
	VARIABLES	{ unitName }
	DESCRIPTION	"A digitalIn5Opened trap indicates that digital input 5 has just been Opened"
::= 21


digitalIn6Opened TRAP-TYPE
	ENTERPRISE	f200Trap
	VARIABLES	{ unitName }
	DESCRIPTION	"A digitalIn6Opened trap indicates that digital input 6 has just been Opened"
::= 22


digitalIn7Opened TRAP-TYPE
	ENTERPRISE	f200Trap
	VARIABLES	{ unitName }
	DESCRIPTION	"A digitalIn7Opened trap indicates that digital input 7 has just been Opened"
::= 23


digitalIn8Opened TRAP-TYPE
	ENTERPRISE	f200Trap
	VARIABLES	{ unitName }
	DESCRIPTION	"A digitalIn8Opened trap indicates that digital input 8 has just been Opened"
::= 24


--digitalInClosed Traps
-------------------------------------------------------
digitalIn1Closed TRAP-TYPE
	ENTERPRISE	f200Trap
	VARIABLES	{ unitName }
	DESCRIPTION	"A digitalIn1Closed trap indicates that digital input 1 has just been Closed"
::= 25


digitalIn2Closed TRAP-TYPE
	ENTERPRISE	f200Trap
	VARIABLES	{ unitName }
	DESCRIPTION	"A digitalIn2Closed trap indicates that digital input 2 has just been Closed"
::= 26


digitalIn3Closed TRAP-TYPE
	ENTERPRISE	f200Trap
	VARIABLES	{ unitName }
	DESCRIPTION	"A digitalIn3Closed trap indicates that digital input 3 has just been Closed"
::= 27


digitalIn4Closed TRAP-TYPE
	ENTERPRISE	f200Trap
	VARIABLES	{ unitName }
	DESCRIPTION	"A digitalIn4Closed trap indicates that digital input 4 has just been Closed"
::= 28


digitalIn5Closed TRAP-TYPE
	ENTERPRISE	f200Trap
	VARIABLES	{ unitName }
	DESCRIPTION	"A digitalIn5Closed trap indicates that digital input 5 has just been Closed"
::= 29


digitalIn6Closed TRAP-TYPE
	ENTERPRISE	f200Trap
	VARIABLES	{ unitName }
	DESCRIPTION	"A digitalIn6Closed trap indicates that digital input 6 has just been Closed"
::= 30


digitalIn7Closed TRAP-TYPE
	ENTERPRISE	f200Trap
	VARIABLES	{ unitName }
	DESCRIPTION	"A digitalIn7Closed trap indicates that digital input 7 has just been Closed"
::= 31


digitalIn8Closed TRAP-TYPE
	ENTERPRISE	f200Trap
	VARIABLES	{ unitName }
	DESCRIPTION	"A digitalIn8Closed trap indicates that digital input 8 has just been Closed"
::= 32


--leakDetected Traps
-------------------------------------------------------
leakDetected TRAP-TYPE
	ENTERPRISE	f200Trap
	VARIABLES	{ unitName }
	DESCRIPTION	"A leakDetected trap indicates a leak has been detected on the cable"
::= 33


--leakCleared Traps
-------------------------------------------------------
leakCleared TRAP-TYPE
	ENTERPRISE	f200Trap
	VARIABLES	{ unitName }
	DESCRIPTION	"A leakCleared trap indicates a leak is no longer detected"
::= 34


--leakCableBreak Traps
-------------------------------------------------------
leakCableBreak TRAP-TYPE
	ENTERPRISE	f200Trap
	VARIABLES	{ unitName }
	DESCRIPTION	"A leakCableBreak trap indicates a leak cable has been disconnected or broken"
::= 35


--leakCableConnected Traps
-------------------------------------------------------
leakCableConnected TRAP-TYPE
	ENTERPRISE	f200Trap
	VARIABLES	{ unitName }
	DESCRIPTION	"A leakCableConnected trap indicates a leak cable has been connected or repaired"
::= 36


--sensorTempAlarm Traps
-------------------------------------------------------
sensor1TempAlarm TRAP-TYPE
	ENTERPRISE	f200Trap
	VARIABLES	{ unitName }
	DESCRIPTION	"A sensor1TempAlarm trap indicates the temperature has exceeded the given range"
::= 37


sensor2TempAlarm TRAP-TYPE
	ENTERPRISE	f200Trap
	VARIABLES	{ unitName }
	DESCRIPTION	"A sensor2TempAlarm trap indicates the temperature has exceeded the given range"
::= 38


sensor3TempAlarm TRAP-TYPE
	ENTERPRISE	f200Trap
	VARIABLES	{ unitName }
	DESCRIPTION	"A sensor3TempAlarm trap indicates the temperature has exceeded the given range"
::= 39


sensor4TempAlarm TRAP-TYPE
	ENTERPRISE	f200Trap
	VARIABLES	{ unitName }
	DESCRIPTION	"A sensor4TempAlarm trap indicates the temperature has exceeded the given range"
::= 40


--sensorTempNormal Traps
-------------------------------------------------------
sensor1TempNormal TRAP-TYPE
	ENTERPRISE	f200Trap
	VARIABLES	{ unitName }
	DESCRIPTION	"A sensor1TempNormal trap indicates the temperature has returned to the given range"
::= 41


sensor2TempNormal TRAP-TYPE
	ENTERPRISE	f200Trap
	VARIABLES	{ unitName }
	DESCRIPTION	"A sensor2TempNormal trap indicates the temperature has returned to the given range"
::= 42


sensor3TempNormal TRAP-TYPE
	ENTERPRISE	f200Trap
	VARIABLES	{ unitName }
	DESCRIPTION	"A sensor3TempNormal trap indicates the temperature has returned to the given range"
::= 43


sensor4TempNormal TRAP-TYPE
	ENTERPRISE	f200Trap
	VARIABLES	{ unitName }
	DESCRIPTION	"A sensor4TempNormal trap indicates the temperature has returned to the given range"
::= 44


--sensorHumidityAlarm Traps
-------------------------------------------------------
sensor1HumidityAlarm TRAP-TYPE
	ENTERPRISE	f200Trap
	VARIABLES	{ unitName }
	DESCRIPTION	"A sensor1HumidityAlarm trap indicates the humidity is out of range"
::= 45


sensor2HumidityAlarm TRAP-TYPE
	ENTERPRISE	f200Trap
	VARIABLES	{ unitName }
	DESCRIPTION	"A sensor2HumidityAlarm trap indicates the humidity is out of range"
::= 46


sensor3HumidityAlarm TRAP-TYPE
	ENTERPRISE	f200Trap
	VARIABLES	{ unitName }
	DESCRIPTION	"A sensor3HumidityAlarm trap indicates the humidity is out of range"
::= 47


sensor4HumidityAlarm TRAP-TYPE
	ENTERPRISE	f200Trap
	VARIABLES	{ unitName }
	DESCRIPTION	"A sensor4HumidityAlarm trap indicates the humidity is out of range"
::= 48


--sensorHumidityNormal Traps
-------------------------------------------------------
sensor1HumidityNormal TRAP-TYPE
	ENTERPRISE	f200Trap
	VARIABLES	{ unitName }
	DESCRIPTION	"A sensor1HumidityNormal trap indicates the humidity has returned to within range"
::= 49


sensor2HumidityNormal TRAP-TYPE
	ENTERPRISE	f200Trap
	VARIABLES	{ unitName }
	DESCRIPTION	"A sensor2HumidityNormal trap indicates the humidity has returned to within range"
::= 50


sensor3HumidityNormal TRAP-TYPE
	ENTERPRISE	f200Trap
	VARIABLES	{ unitName }
	DESCRIPTION	"A sensor3HumidityNormal trap indicates the humidity has returned to within range"
::= 51


sensor4HumidityNormal TRAP-TYPE
	ENTERPRISE	f200Trap
	VARIABLES	{ unitName }
	DESCRIPTION	"A sensor4HumidityNormal trap indicates the humidity has returned to within range"
::= 52


--relayClosed Traps
-------------------------------------------------------
relay1Closed TRAP-TYPE
	ENTERPRISE	f200Trap
	VARIABLES	{ unitName }
	DESCRIPTION	"A relay1Closed trap indicates the relay has been energized (Closed)"
::= 53


--relayOpened Traps
-------------------------------------------------------
relay1Opened TRAP-TYPE
	ENTERPRISE	f200Trap
	VARIABLES	{ unitName }
	DESCRIPTION	"A relay1Opened trap indicates the relay has been energized (Opened)"
::= 54


--f200Alarm Traps
-------------------------------------------------------
f200Alarm TRAP-TYPE
	ENTERPRISE	f200Trap
	VARIABLES	{ unitName }
	DESCRIPTION	"A f200Alarm trap indicates the F200 has at least one alarm"
::= 55


--f200Normal Traps
-------------------------------------------------------
f200Normal TRAP-TYPE
	ENTERPRISE	f200Trap
	VARIABLES	{ unitName }
	DESCRIPTION	"A f200Normal trap indicates the F200 has returned to normal, ther are no alarms"
::= 56





END
