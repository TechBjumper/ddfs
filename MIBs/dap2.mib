DAP2-MIB DEFINITIONS ::= BEGIN

IMPORTS
        enterprises
            FROM RFC1155-SMI
         DisplayString
                FROM RFC1213-MIB
        OBJECT-TYPE
            FROM RFC-1212;

dataaire          OBJECT IDENTIFIER ::= { enterprises 22731 }
mibs              OBJECT IDENTIFIER ::= { dataaire 1 }
dap2              OBJECT IDENTIFIER ::= { mibs 1 }
base-board        OBJECT IDENTIFIER ::= { dap2 1 }
relay-card        OBJECT IDENTIFIER ::= { dap2 2 }
analog-card       OBJECT IDENTIFIER ::= { dap2 3 }

dehumidifying OBJECT-TYPE
        SYNTAX  INTEGER
        ACCESS  read-only
        STATUS  mandatory
        DESCRIPTION
                "Non-zero if the unit is currently dehumidifying"
        ::= { base-board 1 }

humidifying OBJECT-TYPE
        SYNTAX  INTEGER
        ACCESS  read-only
        STATUS  mandatory
        DESCRIPTION
                "Non-zero if the unit is currently humidifying"
        ::= { base-board 2 }

energySaver OBJECT-TYPE
        SYNTAX  INTEGER
        ACCESS  read-only
        STATUS  mandatory
        DESCRIPTION
                "Non-zero if energy-saver is currently active"
        ::= { base-board 3 }

coolingHeld OBJECT-TYPE
        SYNTAX  INTEGER
        ACCESS  read-only
        STATUS  mandatory
        DESCRIPTION
                "Non-zero if cooling is currently held off"
        ::= { base-board 4 }

heatingHeld OBJECT-TYPE
        SYNTAX  INTEGER
        ACCESS  read-only
        STATUS  mandatory
        DESCRIPTION
                "Non-zero if heating is currently held off"
        ::= { base-board 5 }

humidHeld OBJECT-TYPE
        SYNTAX  INTEGER
        ACCESS  read-only
        STATUS  mandatory
        DESCRIPTION
                "Non-zero if humidifying is currently held off"
        ::= { base-board 6 }

dehumHeld OBJECT-TYPE
        SYNTAX  INTEGER
        ACCESS  read-only
        STATUS  mandatory
        DESCRIPTION
                "Non-zero if dehumidifying is currently held off"
        ::= { base-board 7 }

reheatDuringDehum OBJECT-TYPE
        SYNTAX  INTEGER
        ACCESS  read-only
        STATUS  mandatory
        DESCRIPTION
                "Non-zero if heating during dehumidification"
        ::= { base-board 8 }

unitType OBJECT-TYPE
        SYNTAX  INTEGER  {
                        unknown(1),
                        dap2(2),
                        dap2WithRelay(3),
                        dap2WithAnalog(4),
                        dap2WithRelayAndAnalog(5)
                }
        ACCESS  read-only
        STATUS  mandatory
        DESCRIPTION
                "Unit Type"
        ::= { base-board 9 }

returnTemp OBJECT-TYPE
        SYNTAX  INTEGER
        ACCESS  read-only
        STATUS  mandatory
        DESCRIPTION
                "Current return air temperature in 0.1 deg F"
        ::= { base-board 10 }

discTemp OBJECT-TYPE
        SYNTAX  INTEGER
        ACCESS  read-only
        STATUS  mandatory
        DESCRIPTION
                "Current discharge air temperature in 0.1 deg F"
        ::= { base-board 11 }

humidity OBJECT-TYPE
        SYNTAX  INTEGER
        ACCESS  read-only
        STATUS  mandatory
        DESCRIPTION
                "Current relative humidity in 0.1 percent"
        ::= { base-board 12 }

coolingStagesOn OBJECT-TYPE
        SYNTAX  INTEGER (0..5)
        ACCESS  read-only
        STATUS  mandatory
        DESCRIPTION
                "Cooling stages on"
        ::= { base-board 13 }

heatingStagesOn OBJECT-TYPE
        SYNTAX  INTEGER (0..4)
        ACCESS  read-only
        STATUS  mandatory
        DESCRIPTION
                "Heating stages on"
        ::= { base-board 14 }

valve OBJECT-TYPE
        SYNTAX  INTEGER
        ACCESS  read-only
        STATUS  mandatory
        DESCRIPTION
                "Water valve percent open"
        ::= { base-board 15 }

hValve OBJECT-TYPE
        SYNTAX  INTEGER
        ACCESS  read-only
        STATUS  mandatory
        DESCRIPTION
                "Humidifier valve percent open"
        ::= { base-board 16 }

histHighTemp OBJECT-TYPE
        SYNTAX  INTEGER
        ACCESS  read-only
        STATUS  mandatory
        DESCRIPTION
                "High temperature for last 24 hours in 0.1 deg F"
        ::= { base-board 17 }

histLowTemp OBJECT-TYPE
        SYNTAX  INTEGER
        ACCESS  read-only
        STATUS  mandatory
        DESCRIPTION
                "Low temperature for last 24 hours in 0.1 deg F"
        ::= { base-board 18 }

histHighHumid OBJECT-TYPE
        SYNTAX  INTEGER
        ACCESS  read-only
        STATUS  mandatory
        DESCRIPTION
                "High humidity for last 24 hours in 0.1 percent"
        ::= { base-board 19 }

histLowHumid OBJECT-TYPE
        SYNTAX  INTEGER
        ACCESS  read-only
        STATUS  mandatory
        DESCRIPTION
                "Low humidity for last 24 hours in 0.1 percent"
        ::= { base-board 20 }

utilCooling OBJECT-TYPE
        SYNTAX  INTEGER
        ACCESS  read-only
        STATUS  mandatory
        DESCRIPTION
                "Percent cooling utilization during last 24 hours"
        ::= { base-board 21 }

utilHeating OBJECT-TYPE
        SYNTAX  INTEGER
        ACCESS  read-only
        STATUS  mandatory
        DESCRIPTION
                "Percent heating utilization during last 24 hours"
        ::= { base-board 22 }

utilChilledWater OBJECT-TYPE
        SYNTAX  INTEGER
        ACCESS  read-only
        STATUS  mandatory
        DESCRIPTION
                "Percent chilled water utilization during last 24 hours"
        ::= { base-board 23 }

utilHumidifier OBJECT-TYPE
        SYNTAX  INTEGER
        ACCESS  read-only
        STATUS  mandatory
        DESCRIPTION
                "Percent humidifier utilization during last 24 hours"
        ::= { base-board 24 }

runtimeComp1 OBJECT-TYPE
        SYNTAX  INTEGER
        ACCESS  read-only
        STATUS  mandatory
        DESCRIPTION
                "Compressor 1 runtime in hours"
        ::= { base-board 25 }

runtimeComp2 OBJECT-TYPE
        SYNTAX  INTEGER
        ACCESS  read-only
        STATUS  mandatory
        DESCRIPTION
                "Compressor 2 runtime in hours"
        ::= { base-board 26 }

runtimeComp3 OBJECT-TYPE
        SYNTAX  INTEGER
        ACCESS  read-only
        STATUS  mandatory
        DESCRIPTION
                "Compressor 3 runtime in hours"
        ::= { base-board 27 }

runtimeComp4 OBJECT-TYPE
        SYNTAX  INTEGER
        ACCESS  read-only
        STATUS  mandatory
        DESCRIPTION
                "Compressor 4 runtime in hours"
        ::= { base-board 28 }

runtimeHeater1 OBJECT-TYPE
        SYNTAX  INTEGER
        ACCESS  read-only
        STATUS  mandatory
        DESCRIPTION
                "Heater 1 runtime in hours"
        ::= { base-board 29 }

runtimeHeater2 OBJECT-TYPE
        SYNTAX  INTEGER
        ACCESS  read-only
        STATUS  mandatory
        DESCRIPTION
                "Heater 2 runtime in hours"
        ::= { base-board 30 }

runtimeHeater3 OBJECT-TYPE
        SYNTAX  INTEGER
        ACCESS  read-only
        STATUS  mandatory
        DESCRIPTION
                "Heater 3 runtime in hours"
        ::= { base-board 31 }

runtimeHumidifier OBJECT-TYPE
        SYNTAX  INTEGER
        ACCESS  read-only
        STATUS  mandatory
        DESCRIPTION
                "Humidifier runtime in hours"
        ::= { base-board 32 }

runtimeEvapBlower OBJECT-TYPE
        SYNTAX  INTEGER
        ACCESS  read-only
        STATUS  mandatory
        DESCRIPTION
                "Evap blower runtime in hours"
        ::= { base-board 33 }

runtimeCondenser OBJECT-TYPE
        SYNTAX  INTEGER
        ACCESS  read-only
        STATUS  mandatory
        DESCRIPTION
                "Condenser runtime in hours"
        ::= { base-board 34 }

runtimeDehumidifier OBJECT-TYPE
        SYNTAX  INTEGER
        ACCESS  read-only
        STATUS  mandatory
        DESCRIPTION
                "Dehumidifier runtime in hours"
        ::= { base-board 35 }

runtimeEnergySaver OBJECT-TYPE
        SYNTAX  INTEGER
        ACCESS  read-only
        STATUS  mandatory
        DESCRIPTION
                "Energy saver runtime in hours"
        ::= { base-board 36 }

runtimeChilledWater OBJECT-TYPE
        SYNTAX  INTEGER
        ACCESS  read-only
        STATUS  mandatory
        DESCRIPTION
                "Chilled water runtime in hours"
        ::= { base-board 37 }

alarms OBJECT-TYPE
        SYNTAX OCTET STRING
        ACCESS read-only
        STATUS mandatory
        DESCRIPTION
            "Current alarm table"
        ::= { base-board 38 }

-- alarmTable would be better implemented as a SEQUENCE OF INTEGER,
-- but to maintain SMI compatibility, it has been encoded as an
-- OCTET STRING.  Each octet represents the index of one current
-- alarm from the following table.
--                        reheatAndHumidInhibited(1),
--                        shortCycle(2),
--                        customAlarm1(3),
--                        customAlarm2(4),
--                        customAlarm3(5),
--                        customAlarm4(6),
--                        dirtyFilter(7),
--                        dischargeSensor(8),
--                        fanOverload(9),
--                        fireAlarm(10),
--                        highHumidity(11),
--                        highPressureC1(12),
--                        highPressureC2(13),
--                        highTemperature(14),
--                        humidInhibited(15),
--                        humidifierProblem(16),
--                        humiditySensor(17),
--                        localAlarm1(18),
--                        localAlarm2(19),
--                        localAlarm3(20),
--                        localAlarm4(21),
--                        lowHumidity(22),
--                        lowPressureC1(23),
--                        lowPressureC2(24),
--                        lowTemperature(25),
--                        lowDischargeAlarm(26),
--                        lowVoltage(27),
--                        maintenanceRequired(28),
--                        manualOverride(29),
--                        noAirFlow(30),
--                        noWaterFlow(31),
--                        powerProblem(32),
--                        reheatInhibited(33),
--                        smokeDetect(34),
--                        standbyPumpOn(35),
--                        temperatureSensor(36),
--                        upsOn(37),
--                        waterDetected(38),
--                        highCondensate(39),
--                        unitInStandbyHeldOff(40)

inhibitCooling OBJECT-TYPE
        SYNTAX  INTEGER
        ACCESS  read-write
        STATUS  mandatory
        DESCRIPTION
                "Non-zero value inhibits cooling"
        ::= { base-board 39 }

inhibitHeating OBJECT-TYPE
        SYNTAX  INTEGER
        ACCESS  read-write
        STATUS  mandatory
        DESCRIPTION
                "Non-zero value inhibits heating"
        ::= { base-board 40 }

inhibitHumid OBJECT-TYPE
        SYNTAX  INTEGER
        ACCESS  read-write
        STATUS  mandatory
        DESCRIPTION
                "Non-zero value inhibits humidification"
        ::= { base-board 41 }

inhibitDehum OBJECT-TYPE
        SYNTAX  INTEGER
        ACCESS  read-write
        STATUS  mandatory
        DESCRIPTION
                "Non-zero value inhibits dehumidification"
        ::= { base-board 42 }

inhibitFan OBJECT-TYPE
        SYNTAX  INTEGER
        ACCESS  read-write
        STATUS  mandatory
        DESCRIPTION
                "Non-zero value inhibits fan"
        ::= { base-board 43 }

inhibitStandby OBJECT-TYPE
        SYNTAX  INTEGER  {
                        on(1),
                        off(2),
                        standby(3)
                }
        ACCESS  read-write
        STATUS  mandatory
        DESCRIPTION
                "Unit standby mode"
        ::= { base-board 44 }

timeSecond OBJECT-TYPE
        SYNTAX  INTEGER (0..59)
        ACCESS  write-only
        STATUS  mandatory
        DESCRIPTION
                "Local time second"
        ::= { base-board 45 }

timeMinute OBJECT-TYPE
        SYNTAX  INTEGER (0..59)
        ACCESS  write-only
        STATUS  mandatory
        DESCRIPTION
                "Local time minute"
        ::= { base-board 46 }

timeHour OBJECT-TYPE
        SYNTAX  INTEGER (0..23)
        ACCESS  write-only
        STATUS  mandatory
        DESCRIPTION
                "Local time hour"
        ::= { base-board 47 }

timeDay OBJECT-TYPE
        SYNTAX  INTEGER (0..31)
        ACCESS  write-only
        STATUS  mandatory
        DESCRIPTION
                "Local time day of month"
        ::= { base-board 48 }

timeMonth OBJECT-TYPE
        SYNTAX  INTEGER (0..12)
        ACCESS  write-only
        STATUS  mandatory
        DESCRIPTION
                "Local time month"
        ::= { base-board 49 }

timeYear OBJECT-TYPE
        SYNTAX  INTEGER
        ACCESS  write-only
        STATUS  mandatory
        DESCRIPTION
                "Local time year"
        ::= { base-board 50 }

timeDow OBJECT-TYPE
        SYNTAX  INTEGER {
                        sunday(1),
                        monday(2),
                        tuesday(3),
                        wednesday(4),
                        thursday(5),
                        friday(6),
                        saturday(7)
                }
        ACCESS  write-only
        STATUS  mandatory
        DESCRIPTION
                "Local time day of week"
        ::= { base-board 51 }

autoflushTime OBJECT-TYPE
        SYNTAX  INTEGER {
                        none(1),
                        every6hours(2),
                        every12hours(3),
                        every24hours(4),
                        every36hours(5),
                        every48hours(6),
                        every60hours(7),
                        every72hours(8),
                        every84hours(9),
                        every96hours(10)
                }
        ACCESS  read-write
        STATUS  mandatory
        DESCRIPTION
                "Autoflush time"
        ::= { base-board 52 }

fireTempLimit OBJECT-TYPE
        SYNTAX  INTEGER (100..150)
        ACCESS  read-write
        STATUS  mandatory
        DESCRIPTION
                "Fire temperature limit in deg F"
        ::= { base-board 53 }

highHumidityLimit OBJECT-TYPE
        SYNTAX  INTEGER (10..90)
        ACCESS  read-write
        STATUS  mandatory
        DESCRIPTION
                "High humidity limit in percent"
        ::= { base-board 54 }

highTempLimit OBJECT-TYPE
        SYNTAX  INTEGER (50..90)
        ACCESS  read-write
        STATUS  mandatory
        DESCRIPTION
                "High return air temperature limit in deg F"
        ::= { base-board 55 }

lowDiscTempLimit OBJECT-TYPE
        SYNTAX  INTEGER (45..61)
        ACCESS  read-write
        STATUS  mandatory
        DESCRIPTION
                "Low discharge air temperature limit in deg F"
        ::= { base-board 56 }

lowHumidityLimit OBJECT-TYPE
        SYNTAX  INTEGER (10..90)
        ACCESS  read-write
        STATUS  mandatory
        DESCRIPTION
                "Low humidity limit in percent"
        ::= { base-board 57 }

lowTempLimit OBJECT-TYPE
        SYNTAX  INTEGER (50..90)
        ACCESS  read-write
        STATUS  mandatory
        DESCRIPTION
                "Low return air temperature limit in deg F"
        ::= { base-board 58 }

humidityDeadband OBJECT-TYPE
        SYNTAX  INTEGER (1..15)
        ACCESS  read-write
        STATUS  mandatory
        DESCRIPTION
                "Humidity deadband in percent"
        ::= { base-board 59 }

humiditySetpoint OBJECT-TYPE
        SYNTAX  INTEGER (25..70)
        ACCESS  read-write
        STATUS  mandatory
        DESCRIPTION
                "Humidity setpoint in percent"
        ::= { base-board 60 }

tempDeadband OBJECT-TYPE
        SYNTAX  INTEGER (1..5)
        ACCESS  read-write
        STATUS  mandatory
        DESCRIPTION
                "Temperature deadband in deg F"
        ::= { base-board 61 }

tempSetpoint OBJECT-TYPE
        SYNTAX  INTEGER (65..85)
        ACCESS  read-write
        STATUS  mandatory
        DESCRIPTION
                "Temperature setpoint in deg F"
        ::= { base-board 62 }

startDelay OBJECT-TYPE
        SYNTAX  INTEGER (5..600)
        ACCESS  read-write
        STATUS  mandatory
        DESCRIPTION
                "Start delay in seconds"
        ::= { base-board 63 }

humidAnt OBJECT-TYPE
        SYNTAX  INTEGER {
                        off(1),
                        on(2)
                }
        ACCESS  read-only
        STATUS  mandatory
        DESCRIPTION
                "Humidity anticipation enable"
        ::= { base-board 64 }

autoAck OBJECT-TYPE
        SYNTAX  INTEGER {
                        off(1),
                        on(2)
                }
        ACCESS  read-only
        STATUS  mandatory
        DESCRIPTION
                "Self-test auto acknowledge"
        ::= { base-board 65 }

temperatureMode OBJECT-TYPE
        SYNTAX  INTEGER {
                        fahrenheit(1),
                        centigrade(2)
                }
        ACCESS  read-only
        STATUS  mandatory
        DESCRIPTION
                "Temperature units"
        ::= { base-board 66 }

shortCycle OBJECT-TYPE
        SYNTAX  INTEGER {
                        off(1),
                        on(2)
                }
        ACCESS  read-only
        STATUS  mandatory
        DESCRIPTION
                "Short cycle alarm enable"
        ::= { base-board 67 }

customAlarm1 OBJECT-TYPE
        SYNTAX  DisplayString (SIZE (0..40))
        ACCESS  read-only
        STATUS  mandatory
        DESCRIPTION
                "Custom alarm message 1"
        ::= { base-board 68 }

customAlarm2 OBJECT-TYPE
        SYNTAX  DisplayString (SIZE (0..40))
        ACCESS  read-only
        STATUS  mandatory
        DESCRIPTION
                "Custom alarm message 2"
        ::= { base-board 69 }

customAlarm3 OBJECT-TYPE
        SYNTAX  DisplayString (SIZE (0..40))
        ACCESS  read-only
        STATUS  mandatory
        DESCRIPTION
                "Custom alarm message 3"
        ::= { base-board 70 }

customAlarm4 OBJECT-TYPE
        SYNTAX  DisplayString (SIZE (0..40))
        ACCESS  read-only
        STATUS  mandatory
        DESCRIPTION
                "Custom alarm message 4"
        ::= { base-board 71 }

customContact OBJECT-TYPE
        SYNTAX  DisplayString (SIZE (0..25))
        ACCESS  read-only
        STATUS  mandatory
        DESCRIPTION
                "Custom contact message"
        ::= { base-board 72 }

adjustRate OBJECT-TYPE
        SYNTAX  INTEGER (0..5)
        ACCESS  read-only
        STATUS  mandatory
        DESCRIPTION
                "Adjustment rate in minutes"
        ::= { base-board 73 }

optAlarm1Delay OBJECT-TYPE
        SYNTAX  INTEGER (0..900)
        ACCESS  read-only
        STATUS  mandatory
        DESCRIPTION
                "Optional alarm 1 delay in seconds"
        ::= { base-board 74 }

optAlarm2Delay OBJECT-TYPE
        SYNTAX  INTEGER (0..900)
        ACCESS  read-only
        STATUS  mandatory
        DESCRIPTION
                "Optional alarm 2 delay in seconds"
        ::= { base-board 75 }

optAlarm3Delay OBJECT-TYPE
        SYNTAX  INTEGER (0..900)
        ACCESS  read-only
        STATUS  mandatory
        DESCRIPTION
                "Optional alarm 3 delay in seconds"
        ::= { base-board 76 }

optAlarm4Delay OBJECT-TYPE
        SYNTAX  INTEGER (0..900)
        ACCESS  read-only
        STATUS  mandatory
        DESCRIPTION
                "Optional alarm 4 delay in seconds"
        ::= { base-board 77 }

optAlarm1Config OBJECT-TYPE
        SYNTAX  INTEGER {
                        customAlarm1(1),
                        fanMotorOverload(2),
                        humidLockout(3),
                        localAlarm(4),
                        heatAndHumidLockout(5),
                        heatLockout(6),
                        standbyPumpOn(7),
                        upsOn(8),
                        unitInStandby(9)
                }
        ACCESS  read-only
        STATUS  mandatory
        DESCRIPTION
                "Optional alarm 1 configuration"
        ::= { base-board 78 }

optAlarm2Config OBJECT-TYPE
        SYNTAX  INTEGER {
                        customAlarm2(1),
                        fanMotorOverload(2),
                        humidLockout(3),
                        localAlarm(4),
                        heatAndHumidLockout(5),
                        heatLockout(6),
                        standbyPumpOn(7),
                        upsOn(8)
                }
        ACCESS  read-only
        STATUS  mandatory
        DESCRIPTION
                "Optional alarm 2 configuration"
        ::= { base-board 79 }

optAlarm3Config OBJECT-TYPE
        SYNTAX  INTEGER {
                        customAlarm3(1),
                        fanMotorOverload(2),
                        humidLockout(3),
                        localAlarm(4),
                        heatAndHumidLockout(5),
                        heatLockout(6),
                        standbyPumpOn(7),
                        upsOn(8)
                }
        ACCESS  read-only
        STATUS  mandatory
        DESCRIPTION
                "Optional alarm 3 configuration"
        ::= { base-board 80 }

optAlarm4Config OBJECT-TYPE
        SYNTAX  INTEGER {
                        customAlarm4(1),
                        fanMotorOverload(2),
                        humidLockout(3),
                        localAlarm(4),
                        heatAndHumidLockout(5),
                        heatLockout(6),
                        standbyPumpOn(7),
                        upsOn(8),
                        highCondensateLevel(9)
                }
        ACCESS  read-only
        STATUS  mandatory
        DESCRIPTION
                "Optional alarm 4 configuration"
        ::= { base-board 81 }

discTempCalibration OBJECT-TYPE
        SYNTAX  INTEGER
        ACCESS  read-only
        STATUS  mandatory
        DESCRIPTION
                "Discharge temperature sensor calibration in 0.1 deg F"
        ::= { base-board 82 }

humidCalibration OBJECT-TYPE
        SYNTAX  INTEGER
        ACCESS  read-only
        STATUS  mandatory
        DESCRIPTION
                "Humidity sensor calibration in 0.1 percent"
        ::= { base-board 83 }

tempCalibration OBJECT-TYPE
        SYNTAX  INTEGER
        ACCESS  read-only
        STATUS  mandatory
        DESCRIPTION
                "Return temperature sensor calibration in 0.1 deg F"
        ::= { base-board 84 }

compressorConfig OBJECT-TYPE
        SYNTAX  INTEGER {
                        none(1),
                        pri(2),
                        pri-sec(3),
                        pri-pri(4),
                        pri-sec-pri-sec(5)
                }
        ACCESS  read-only
        STATUS  mandatory
        DESCRIPTION
                "Compressor configuration"
        ::= { base-board 85 }

dehumidifierConfig OBJECT-TYPE
        SYNTAX  INTEGER {
                        off(1),
                        one-with-limits(2),
                        two-with-limits(3),
                        one-no-limits(4),
                        two-no-limits(5)
                }
        ACCESS  read-only
        STATUS  mandatory
        DESCRIPTION
                "Dehumidifier configuration"
        ::= { base-board 86 }

energySaverConfig OBJECT-TYPE
        SYNTAX  INTEGER {
                        none(1),
                        one-compressor(2),
                        two-compressors(3)
                }
        ACCESS  read-only
        STATUS  mandatory
        DESCRIPTION
                "Energy saver configuration"
        ::= { base-board 87 }

heaterConfig OBJECT-TYPE
        SYNTAX  INTEGER {
                        none(1),
                        one-heat-strip(2),
                        two-heat-strips(3),
                        three-heat-strips(4),
                        hot-water(5)
                }
        ACCESS  read-only
        STATUS  mandatory
        DESCRIPTION
                "Heater configuration"
        ::= { base-board 88 }

humidifierConfig OBJECT-TYPE
        SYNTAX  INTEGER {
                        none(1),
                        computer-non-modutating(2),
                        computer-modulating(3),
                        comfort-non-modulating(4),
                        comfort-modulating(5)
                }
        ACCESS  read-only
        STATUS  mandatory
        DESCRIPTION
                "Humidifier configuration"
        ::= { base-board 89 }

chilledWaterConfig OBJECT-TYPE
        SYNTAX  INTEGER {
                        none(1),
                        chilled-water(2),
                        energy-saver(3),
                        aux-chilled-water(4)
                }
        ACCESS  read-only
        STATUS  mandatory
        DESCRIPTION
                "Chilled water configuration"
        ::= { base-board 90 }

valveRange OBJECT-TYPE
        SYNTAX  INTEGER {
                        vDC-0-10(1),
                        vDC-4-7(2),
                        vDC-6-9(3),
                        vDC-7-10(4)
                }
        ACCESS  read-only
        STATUS  mandatory
        DESCRIPTION
                "Water valve voltage range configuration"
        ::= { base-board 91 }

reverseValve OBJECT-TYPE
        SYNTAX  INTEGER {
                        normal(1),
                        reverse(2)
                }
        ACCESS  read-only
        STATUS  mandatory
        DESCRIPTION
                "Reverse water valve configuration"
        ::= { base-board 92 }

controlType OBJECT-TYPE
        SYNTAX  INTEGER {
                        smart(1),
                        pid(2),
                        setpoint-deviation(3)
                }
        ACCESS  read-only
        STATUS  mandatory
        DESCRIPTION
                "Control logic configuration"
        ::= { base-board 93 }

leadLag OBJECT-TYPE
        SYNTAX  INTEGER {
                        auto(1),
                        one-leads(2),
                        two-leads(3)
                }
        ACCESS  read-only
        STATUS  mandatory
        DESCRIPTION
                "Leag lag configuration"
        ::= { base-board 94 }

maintInt OBJECT-TYPE
        SYNTAX  INTEGER (0..1000)
        ACCESS  read-only
        STATUS  mandatory
        DESCRIPTION
                "Maintenance interval configuration in hours"
        ::= { base-board 95 }

password OBJECT-TYPE
        SYNTAX  INTEGER (0..99)
        ACCESS  read-only
        STATUS  mandatory
        DESCRIPTION
                "Front panel password configuration"
        ::= { base-board 96 }

personToContact OBJECT-TYPE
        SYNTAX  INTEGER {
                        not-used(1),
                        data-processing-manager(2),
                        maintenance-engineer(3),
                        service-company(4),
                        custom-contact-message(5)
                }
        ACCESS  read-only
        STATUS  mandatory
        DESCRIPTION
                "Person to contact configuration"
        ::= { base-board 97 }

resetMode OBJECT-TYPE
        SYNTAX  INTEGER {
                        auto-no-message-or-alarm(1),
                        auto-message-and-alarm(2),
                        manual-message-alarm-and-relay(3)
                }
        ACCESS  read-only
        STATUS  mandatory
        DESCRIPTION
                "Reset mode configuration"
        ::= { base-board 98 }

buzzer OBJECT-TYPE
        SYNTAX  INTEGER {
                        off(1),
                        short(2),
                        long(3),
                        full(4)
                }
        ACCESS  read-only
        STATUS  mandatory
        DESCRIPTION
                "Buzzer configuration"
        ::= { base-board 99 }

-- alarmRelayXSelections would be better implemented as a SEQUENCE OF INTEGER,
-- but to maintain SMI compatibility, they have been encoded as an
-- OCTET STRING.  Each octet represents one alarm selection.  See
-- the definition of alarms for more information on decoding these objects.

alarmRelay1Selections OBJECT-TYPE
        SYNTAX OCTET STRING
        ACCESS read-only
        STATUS mandatory
        DESCRIPTION
            "Alarm relay 1 table"
        ::= { base-board 100 }

alarmRelay2Selections OBJECT-TYPE
        SYNTAX OCTET STRING
        ACCESS read-only
        STATUS mandatory
        DESCRIPTION
            "Alarm relay 2 table"
        ::= { relay-card 1 }

alarmRelay3Selections OBJECT-TYPE
        SYNTAX OCTET STRING
        ACCESS read-only
        STATUS mandatory
        DESCRIPTION
            "Alarm relay 3 table"
        ::= { relay-card 2 }

analog1Value OBJECT-TYPE
        SYNTAX  INTEGER
        ACCESS  read-only
        STATUS  mandatory
        DESCRIPTION
                "Analog module sensor 1 value"
        ::= { analog-card 1 }

analog1Name OBJECT-TYPE
        SYNTAX  INTEGER {
                        not-installed(1),
                        input-voltage-a-b(2),
                        input-voltage-a-c(3),
                        input-voltage-b-c(4),
                        output-voltage-a-b(5),
                        output-voltage-a-c(6),
                        output-voltage-b-c(7),
                        input-current-a(8),
                        input-current-b(9),
                        input-current-c(10),
                        output-current-a(11),
                        output-current-b(12),
                        output-current-c(13),
                        neutral-current(14),
                        ground-current(15),
                        frequency(16),
                        power(17),
                        cond-water-supply-temp(18),
                        cond-water-return-temp(19),
                        chill-water-supply-temp(20),
                        chill-water-return-temp(21),
                        supply-air-temp(22),
                        return-air-temp(23),
                        cond-water-flow(24),
                        chill-water-flow(25),
                        zone-air-temp(26),
                        zone-air-humidity(27),
                        outside-air-temp(28),
                        outside-air-humidity(29),
                        discharge-pressure(30),
                        suction-pressure(31),
                        diff-pressure(32),
                        pressure(33),
                        flow(34)
                }
        ACCESS  read-only
        STATUS  mandatory
        DESCRIPTION
                "Analog module sensor 1 name"
        ::= { analog-card 2 }

analog1Units OBJECT-TYPE
        SYNTAX  INTEGER {
                        vAC(1),
                        amps(2),
                        hz(3),
                        kW(4),
                        degF(5),
                        degC(6),
                        gpm(7),
                        percent-RH(8),
                        psig(9),
                        inches-water(10),
                        psi(11)
                }
        ACCESS  read-only
        STATUS  mandatory
        DESCRIPTION
                "Analog module sensor 1 units"
        ::= { analog-card 3 }

analog1Type OBJECT-TYPE
        SYNTAX  INTEGER {
                        vDC-0-10(1),
                        vDC-0-5(2),
                        mA-4-20(3)
                }
        ACCESS  read-only
        STATUS  mandatory
        DESCRIPTION
                "Analog module sensor 1 type"
        ::= { analog-card 4 }

analog1Min OBJECT-TYPE
        SYNTAX  INTEGER
        ACCESS  read-only
        STATUS  mandatory
        DESCRIPTION
                "Analog module sensor 1 minimum value"
        ::= { analog-card 5 }

analog1Max OBJECT-TYPE
        SYNTAX  INTEGER
        ACCESS  read-only
        STATUS  mandatory
        DESCRIPTION
                "Analog module sensor 1 maximum value"
        ::= { analog-card 6 }

analog1Calibration OBJECT-TYPE
        SYNTAX  INTEGER
        ACCESS  read-only
        STATUS  mandatory
        DESCRIPTION
                "Analog module sensor 1 calibration"
        ::= { analog-card 7 }

analog2Value OBJECT-TYPE
        SYNTAX  INTEGER
        ACCESS  read-only
        STATUS  mandatory
        DESCRIPTION
                "Analog module sensor 2 value"
        ::= { analog-card 8 }

analog2Name OBJECT-TYPE
        SYNTAX  INTEGER {
                        not-installed(1),
                        input-voltage-a-b(2),
                        input-voltage-a-c(3),
                        input-voltage-b-c(4),
                        output-voltage-a-b(5),
                        output-voltage-a-c(6),
                        output-voltage-b-c(7),
                        input-current-a(8),
                        input-current-b(9),
                        input-current-c(10),
                        output-current-a(11),
                        output-current-b(12),
                        output-current-c(13),
                        neutral-current(14),
                        ground-current(15),
                        frequency(16),
                        power(17),
                        cond-water-supply-temp(18),
                        cond-water-return-temp(19),
                        chill-water-supply-temp(20),
                        chill-water-return-temp(21),
                        supply-air-temp(22),
                        return-air-temp(23),
                        cond-water-flow(24),
                        chill-water-flow(25),
                        zone-air-temp(26),
                        zone-air-humidity(27),
                        outside-air-temp(28),
                        outside-air-humidity(29),
                        discharge-pressure(30),
                        suction-pressure(31),
                        diff-pressure(32),
                        pressure(33),
                        flow(34)
                }
        ACCESS  read-only
        STATUS  mandatory
        DESCRIPTION
                "Analog module sensor 2 name"
        ::= { analog-card 9 }

analog2Units OBJECT-TYPE
        SYNTAX  INTEGER {
                        vAC(1),
                        amps(2),
                        hz(3),
                        kW(4),
                        degF(5),
                        degC(6),
                        gpm(7),
                        percent-RH(8),
                        psig(9),
                        inches-water(10),
                        psi(11)
                }
        ACCESS  read-only
        STATUS  mandatory
        DESCRIPTION
                "Analog module sensor 2 units"
        ::= { analog-card 10 }

analog2Type OBJECT-TYPE
        SYNTAX  INTEGER {
                        vDC-0-10(1),
                        vDC-0-5(2),
                        mA-4-20(3)
                }
        ACCESS  read-only
        STATUS  mandatory
        DESCRIPTION
                "Analog module sensor 2 type"
        ::= { analog-card 11 }

analog2Min OBJECT-TYPE
        SYNTAX  INTEGER
        ACCESS  read-only
        STATUS  mandatory
        DESCRIPTION
                "Analog module sensor 2 minimum value"
        ::= { analog-card 12 }

analog2Max OBJECT-TYPE
        SYNTAX  INTEGER
        ACCESS  read-only
        STATUS  mandatory
        DESCRIPTION
                "Analog module sensor 2 maximum value"
        ::= { analog-card 13 }

analog2Calibration OBJECT-TYPE
        SYNTAX  INTEGER
        ACCESS  read-only
        STATUS  mandatory
        DESCRIPTION
                "Analog module sensor 2 calibration"
        ::= { analog-card 14 }

analogRopeValue OBJECT-TYPE
        SYNTAX  INTEGER
        ACCESS  read-only
        STATUS  mandatory
        DESCRIPTION
                "Analog module water detect rope value"
        ::= { analog-card 15 }

analogRopeThreshold OBJECT-TYPE
        SYNTAX  INTEGER {
                        r-1K(1),
                        r-2K(2),
                        r-5K(3),
                        r-10K(4),
                        r-20K(5),
                        r-50K(6),
                        r-100K(7),
                        r-200K(8),
                        r-500K(9),
                        r-1000K(10),
                        r-2000K(11),
                        r-5000K(12),
                        r-10000K(13),
                        r-20000K(14),
                        r-50000K(15)
                }
        ACCESS  read-only
        STATUS  mandatory
        DESCRIPTION
                "Analog module water detect rope threshold"
        ::= { analog-card 16 }

END
