-- 934904-001.mib
-- MIB generated by MG-SOFT Visual MIB Builder Version 7.0  Build 240
-- Thursday, December 08, 2011 at 14:26:15
--

	ASCOSNMP-934904-001 DEFINITIONS ::= BEGIN
 
		IMPORTS
			enterprises, Integer32, OBJECT-TYPE			
				FROM SNMPv2-SMI			
			DisplayString			
				FROM SNMPv2-TC;
	
	
	
--
-- Node definitions
--
	
		-- 1.3.6.1.4.1.7777
		asco OBJECT IDENTIFIER ::= { enterprises 7777 }

		
		-- 1.3.6.1.4.1.7777.1
		devices OBJECT IDENTIFIER ::= { asco 1 }

		
		-- 1.3.6.1.4.1.7777.1.2
		connectivity OBJECT IDENTIFIER ::= { devices 2 }

		
		-- 1.3.6.1.4.1.7777.1.2.1
		readings OBJECT IDENTIFIER ::= { connectivity 1 }

		
		-- 1.3.6.1.4.1.7777.1.2.1.1
		psCP OBJECT-TYPE
			SYNTAX DisplayString (SIZE (0..128))
			MAX-ACCESS read-only
			STATUS current
			DESCRIPTION
				"CP address and protocol setting."
			::= { readings 1 }

		
		-- 1.3.6.1.4.1.7777.1.2.1.2
		psPM OBJECT-TYPE
			SYNTAX DisplayString (SIZE (0..128))
			MAX-ACCESS read-only
			STATUS current
			DESCRIPTION
				"PM address and protocol setting."
			::= { readings 2 }

		
		-- 1.3.6.1.4.1.7777.1.2.1.3
		psPowerReading OBJECT-TYPE
			SYNTAX Integer32
			MAX-ACCESS read-only
			STATUS current
			DESCRIPTION
				"Total real power."
			::= { readings 3 }

		
		-- 1.3.6.1.4.1.7777.1.2.1.4
		psVoltageReading OBJECT-TYPE
			SYNTAX Integer32
			MAX-ACCESS read-only
			STATUS current
			DESCRIPTION
				"Average line to line voltage."
			::= { readings 4 }

		
		-- 1.3.6.1.4.1.7777.1.2.1.5
		psCurrentReading OBJECT-TYPE
			SYNTAX Integer32
			MAX-ACCESS read-only
			STATUS current
			DESCRIPTION
				"Average phase current."
			::= { readings 5 }

		
		-- 1.3.6.1.4.1.7777.1.2.1.6
		psFrequency OBJECT-TYPE
			SYNTAX Integer32
			MAX-ACCESS read-only
			STATUS current
			DESCRIPTION
				"Frequency reading divided by 100."
			::= { readings 6 }

		
		-- 1.3.6.1.4.1.7777.1.2.1.7
		psPowerfactor OBJECT-TYPE
			SYNTAX Integer32
			MAX-ACCESS read-only
			STATUS current
			DESCRIPTION
				"Pf reading divided by 100."
			::= { readings 7 }

		
		-- 1.3.6.1.4.1.7777.1.2.1.8
		psNormalVca OBJECT-TYPE
			SYNTAX Integer32
			MAX-ACCESS read-only
			STATUS current
			DESCRIPTION
				"Normal source voltage."
			::= { readings 8 }

		
		-- 1.3.6.1.4.1.7777.1.2.1.9
		psEmergVca OBJECT-TYPE
			SYNTAX Integer32
			MAX-ACCESS read-only
			STATUS current
			DESCRIPTION
				"Emergency source voltage."
			::= { readings 9 }

		
		-- 1.3.6.1.4.1.7777.1.2.1.10
		psATSType OBJECT-TYPE
			SYNTAX DisplayString (SIZE (0..128))
			MAX-ACCESS read-only
			STATUS current
			DESCRIPTION
				"ATS type."
			::= { readings 10 }

		
		-- 1.3.6.1.4.1.7777.1.2.2
		settings OBJECT IDENTIFIER ::= { connectivity 2 }

		
		-- 1.3.6.1.4.1.7777.1.2.2.1
		psFirmware OBJECT-TYPE
			SYNTAX DisplayString (SIZE (0..128))
			MAX-ACCESS read-only
			STATUS current
			DESCRIPTION
				"Firmware version."
			::= { settings 1 }

		
		-- 1.3.6.1.4.1.7777.1.2.2.2
		psTCPPort OBJECT-TYPE
			SYNTAX Integer32
			MAX-ACCESS read-only
			STATUS current
			DESCRIPTION
				"TCP/IP port."
			::= { settings 2 }

		
		-- 1.3.6.1.4.1.7777.1.2.2.3
		psSerialBaud OBJECT-TYPE
			SYNTAX Integer32
			MAX-ACCESS read-only
			STATUS current
			DESCRIPTION
				"Serial baudrate in bps."
			::= { settings 3 }

		
		-- 1.3.6.1.4.1.7777.1.2.2.4
		psSerialReply OBJECT-TYPE
			SYNTAX Integer32
			MAX-ACCESS read-only
			STATUS current
			DESCRIPTION
				"Serial reply in milliseconds."
			::= { settings 4 }

		
		-- 1.3.6.1.4.1.7777.1.2.2.5
		psSerialRetry OBJECT-TYPE
			SYNTAX Integer32
			MAX-ACCESS read-only
			STATUS current
			DESCRIPTION
				"Serial Retry max of 3."
			::= { settings 5 }

		
		-- 1.3.6.1.4.1.7777.1.2.3
		traps OBJECT IDENTIFIER ::= { connectivity 3 }

		
		-- 1.3.6.1.4.1.7777.1.2.3.1
		psMessageString OBJECT-TYPE
			SYNTAX DisplayString
			MAX-ACCESS read-only
			STATUS current
			DESCRIPTION
				"Please replace this text with your description."
			::= { traps 1 }

		
		-- 1.3.6.1.4.1.7777.1.2.3.2
		psATSOnNormal OBJECT-TYPE
			SYNTAX Integer32
			MAX-ACCESS read-only
			STATUS current
			DESCRIPTION
				"ATS on Emergency"
			::= { traps 2 }

		
		-- 1.3.6.1.4.1.7777.1.2.3.3
		psATSOnEmergency OBJECT-TYPE
			SYNTAX Integer32
			MAX-ACCESS read-only
			STATUS current
			DESCRIPTION
				"ATS retransferred back to Normal."
			::= { traps 3 }

		
		-- 1.3.6.1.4.1.7777.1.2.3.4
		psNormalAvailable OBJECT-TYPE
			SYNTAX Integer32
			MAX-ACCESS read-only
			STATUS current
			DESCRIPTION
				"Normal source unavailable."
			::= { traps 4 }

		
		-- 1.3.6.1.4.1.7777.1.2.3.5
		psEmergencyAvailable OBJECT-TYPE
			SYNTAX Integer32
			MAX-ACCESS read-only
			STATUS current
			DESCRIPTION
				"Emergency source unavailable."
			::= { traps 5 }

		
		-- 1.3.6.1.4.1.7777.1.2.3.6
		psEngineRunning OBJECT-TYPE
			SYNTAX Integer32
			MAX-ACCESS read-only
			STATUS current
			DESCRIPTION
				"Engine running signal is detected."
			::= { traps 6 }

		
		-- 1.3.6.1.4.1.7777.1.2.3.7
		psInput_01 OBJECT-TYPE
			SYNTAX Integer32
			MAX-ACCESS read-only
			STATUS current
			DESCRIPTION
				"Digital Input 01 status."
			::= { traps 7 }

		
		-- 1.3.6.1.4.1.7777.1.2.3.8
		psInput_02 OBJECT-TYPE
			SYNTAX Integer32
			MAX-ACCESS read-only
			STATUS current
			DESCRIPTION
				"Digital Input 02 status."
			::= { traps 8 }

		
		-- 1.3.6.1.4.1.7777.1.2.3.9
		psInput_03 OBJECT-TYPE
			SYNTAX Integer32
			MAX-ACCESS read-only
			STATUS current
			DESCRIPTION
				"Digital Input 03 status."
			::= { traps 9 }

		
		-- 1.3.6.1.4.1.7777.1.2.3.10
		psInput_04 OBJECT-TYPE
			SYNTAX Integer32
			MAX-ACCESS read-only
			STATUS current
			DESCRIPTION
				"Digital Input 04 status."
			::= { traps 10 }

		
		-- 1.3.6.1.4.1.7777.1.2.3.11
		psInput_05 OBJECT-TYPE
			SYNTAX Integer32
			MAX-ACCESS read-only
			STATUS current
			DESCRIPTION
				"Digital Input 05 status."
			::= { traps 11 }

		
		-- 1.3.6.1.4.1.7777.1.2.3.12
		psInput_06 OBJECT-TYPE
			SYNTAX Integer32
			MAX-ACCESS read-only
			STATUS current
			DESCRIPTION
				"Digital Input 06 status."
			::= { traps 12 }

		
		-- 1.3.6.1.4.1.7777.1.2.3.13
		psInput_07 OBJECT-TYPE
			SYNTAX Integer32
			MAX-ACCESS read-only
			STATUS current
			DESCRIPTION
				"Digital Input 07 status."
			::= { traps 13 }

		
		-- 1.3.6.1.4.1.7777.1.2.3.14
		psInput_08 OBJECT-TYPE
			SYNTAX Integer32
			MAX-ACCESS read-only
			STATUS current
			DESCRIPTION
				"Digital Input 08 status."
			::= { traps 14 }

		
		-- 1.3.6.1.4.1.7777.1.2.3.15
		psOutput_01 OBJECT-TYPE
			SYNTAX Integer32
			MAX-ACCESS read-only
			STATUS current
			DESCRIPTION
				"Digital Output 01 status."
			::= { traps 15 }

		
		-- 1.3.6.1.4.1.7777.1.2.3.16
		psOutput_02 OBJECT-TYPE
			SYNTAX Integer32
			MAX-ACCESS read-only
			STATUS current
			DESCRIPTION
				"Digital Output 02 status."
			::= { traps 16 }

		
		-- 1.3.6.1.4.1.7777.1.2.3.17
		psOutput_03 OBJECT-TYPE
			SYNTAX Integer32
			MAX-ACCESS read-only
			STATUS current
			DESCRIPTION
				"Digital Output 03 status."
			::= { traps 17 }

		
		-- 1.3.6.1.4.1.7777.1.2.3.18
		psOutput_04 OBJECT-TYPE
			SYNTAX Integer32
			MAX-ACCESS read-only
			STATUS current
			DESCRIPTION
				"Digital Output 04 status."
			::= { traps 18 }

		
	
	END

--
-- 934904-001.mib
--
</PRE></BODY></HTML>
