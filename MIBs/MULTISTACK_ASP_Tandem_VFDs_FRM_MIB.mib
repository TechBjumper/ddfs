Carel-MULTISTACK_ASP_Tandem_VFDs_MIB DEFINITIONS ::= BEGIN
-- MIB Definition for ASP_X Tandem VFDs FRM
--
-- Revision: 201003161600"
-- Contact: brole@multistack.com
--
--

IMPORTS
    MODULE-IDENTITY, OBJECT-TYPE, Integer32, enterprises FROM SNMPv2-SMI
    TEXTUAL-CONVENTION FROM SNMPv2-TC;

carel              OBJECT IDENTIFIER ::= { enterprises 9839 }
carel-System       OBJECT IDENTIFIER ::= { carel 1 }
carel-Instruments  OBJECT IDENTIFIER ::= { carel 2 }
pCO-Variables	   OBJECT IDENTIFIER ::= { carel-Instruments 1}
digital		   OBJECT IDENTIFIER ::= { pCO-Variables 1 }
analog		   OBJECT IDENTIFIER ::= { pCO-Variables 2 }
integers		   OBJECT IDENTIFIER ::= { pCO-Variables 3 }

    FaultCode ::= TEXTUAL-CONVENTION
        STATUS    current
        DESCRIPTION        "Fault Codes"
        SYNTAX     INTEGER {    autoModeNoFaults(0),
                                highPressure(1),
                                lowPressure(2),
                                circuit1Fault(3),
                                circuit2Fault(4),
                                lowSuctionTemp(5),
                                suctionSensorFail(6),
                                lchwSensorFail(7),
                                lowLchwTemp(8),
                                lpDelay(9),
                                manualMode(10),
                                disabled(11),
                                hpSensorFail(12),
                                lpSensorFail(13)
                       }


    ControlMode ::= TEXTUAL-CONVENTION
	STATUS		current
	DESCRIPTION	"Control Modes"
	SYNTAX		INTEGER {	auto(1),
					manual(2),
					disabled(3)
			}
			

--
--

-- ANALOG POINTS (Divide by 10 for result)

systemEchw OBJECT-TYPE
	SYNTAX		Integer32 (0..65535)
	MAX-ACCESS		read-only
	STATUS		current
	DESCRIPTION
		"System ECHW Temperature"
::= {analog 1}

systemLchw OBJECT-TYPE
	SYNTAX		Integer32 (0..65535)
	MAX-ACCESS		read-only
	STATUS		current
	DESCRIPTION
		"System LCHW Temperature"
::= {analog 2}

chwOffset OBJECT-TYPE
	SYNTAX		Integer32 (0..65535)
	MAX-ACCESS		read-only
	STATUS		current
	DESCRIPTION
		"Chilled Water Offset"
::= {analog 3}

upperSetpointSV OBJECT-TYPE
	SYNTAX		Integer32 (250..800)
	MAX-ACCESS		read-write
	STATUS		current
	DESCRIPTION
		"Upper Setpoint"
::= {analog 4}

lowerSetpointSV OBJECT-TYPE
	SYNTAX		Integer32 (200..700)
	MAX-ACCESS		read-write
	STATUS		current
	DESCRIPTION
		"Lower Setpoint"
::= {analog 5}

manualSetpointSV OBJECT-TYPE
	SYNTAX		Integer32 (250..700)
	MAX-ACCESS		read-write
	STATUS		current
	DESCRIPTION
		"Manual Setpoint"
::= {analog 6}

manualRangeSV OBJECT-TYPE
	SYNTAX		Integer32 (20..200)
	MAX-ACCESS		read-write
	STATUS		current
	DESCRIPTION
		"Manual Range"
::= {analog 7}

manualOffsetSV OBJECT-TYPE
	SYNTAX		Integer32 (0..50)
	MAX-ACCESS		read-write
	STATUS		current
	DESCRIPTION
		"Manual Offset"
::= {analog 8}

m1LchwTemp OBJECT-TYPE
	SYNTAX		Integer32 (0..65535)
	MAX-ACCESS		read-only
	STATUS		current
	DESCRIPTION
		"Module 1 LCHW Temp"
::= {analog 9}

m1SuctTemp OBJECT-TYPE
	SYNTAX		Integer32 (0..65535)
	MAX-ACCESS		read-only
	STATUS		current
	DESCRIPTION
		"Module 1 Suction Temp"
::= {analog 10}

m1VfdPct OBJECT-TYPE
	SYNTAX		Integer32 (0..65535)
	MAX-ACCESS		read-only
	STATUS		current
	DESCRIPTION
		"Module 1 VFD Percent"
::= {analog 11}

m2LchwTemp OBJECT-TYPE
	SYNTAX		Integer32 (0..65535)
	MAX-ACCESS		read-only
	STATUS		current
	DESCRIPTION
		"Module 2 LCHW Temp"
::= {analog 12}

m2SuctTemp OBJECT-TYPE
	SYNTAX		Integer32 (0..65535)
	MAX-ACCESS		read-only
	STATUS		current
	DESCRIPTION
		"Module 2 Suction Temp"
::= {analog 13}

m2VfdPct OBJECT-TYPE
	SYNTAX		Integer32 (0..65535)
	MAX-ACCESS		read-only
	STATUS		current
	DESCRIPTION
		"Module 2 VFD Percent"
::= {analog 14}

m3LchwTemp OBJECT-TYPE
	SYNTAX		Integer32 (0..65535)
	MAX-ACCESS		read-only
	STATUS		current
	DESCRIPTION
		"Module 3 LCHW Temp"
::= {analog 15}

m3SuctTemp OBJECT-TYPE
	SYNTAX		Integer32 (0..65535)
	MAX-ACCESS		read-only
	STATUS		current
	DESCRIPTION
		"Module 3 Suction Temp"
::= {analog 16}

m3VfdPct OBJECT-TYPE
	SYNTAX		Integer32 (0..65535)
	MAX-ACCESS		read-only
	STATUS		current
	DESCRIPTION
		"Module 3 VFD Percent"
::= {analog 17}

m4LchwTemp OBJECT-TYPE
	SYNTAX		Integer32 (0..65535)
	MAX-ACCESS		read-only
	STATUS		current
	DESCRIPTION
		"Module 4 LCHW Temp"
::= {analog 18}

m4SuctTemp OBJECT-TYPE
	SYNTAX		Integer32 (0..65535)
	MAX-ACCESS		read-only
	STATUS		current
	DESCRIPTION
		"Module 4 Suction Temp"
::= {analog 19}

m4VfdPct OBJECT-TYPE
	SYNTAX		Integer32 (0..65535)
	MAX-ACCESS		read-only
	STATUS		current
	DESCRIPTION
		"Module 4 VFD Percent"
::= {analog 20}

m5LchwTemp OBJECT-TYPE
	SYNTAX		Integer32 (0..65535)
	MAX-ACCESS		read-only
	STATUS		current
	DESCRIPTION
		"Module 5 LCHW Temp"
::= {analog 21}

m5SuctTemp OBJECT-TYPE
	SYNTAX		Integer32 (0..65535)
	MAX-ACCESS		read-only
	STATUS		current
	DESCRIPTION
		"Module 5 Suction Temp"
::= {analog 22}

m5VfdPct OBJECT-TYPE
	SYNTAX		Integer32 (0..65535)
	MAX-ACCESS		read-only
	STATUS		current
	DESCRIPTION
		"Module 5 VFD Percent"
::= {analog 23}

m6LchwTemp OBJECT-TYPE
	SYNTAX		Integer32 (0..65535)
	MAX-ACCESS		read-only
	STATUS		current
	DESCRIPTION
		"Module 6 LCHW Temp"
::= {analog 24}

m6SuctTemp OBJECT-TYPE
	SYNTAX		Integer32 (0..65535)
	MAX-ACCESS		read-only
	STATUS		current
	DESCRIPTION
		"Module 6 Suction Temp"
::= {analog 25}

m6VfdPct OBJECT-TYPE
	SYNTAX		Integer32 (0..65535)
	MAX-ACCESS		read-only
	STATUS		current
	DESCRIPTION
		"Module 6 VFD Percent"
::= {analog 26}

m7LchwTemp OBJECT-TYPE
	SYNTAX		Integer32 (0..65535)
	MAX-ACCESS		read-only
	STATUS		current
	DESCRIPTION
		"Module 7 LCHW Temp"
::= {analog 27}

m7SuctTemp OBJECT-TYPE
	SYNTAX		Integer32 (0..65535)
	MAX-ACCESS		read-only
	STATUS		current
	DESCRIPTION
		"Module 7 Suction Temp"
::= {analog 28}

m7VfdPct OBJECT-TYPE
	SYNTAX		Integer32 (0..65535)
	MAX-ACCESS		read-only
	STATUS		current
	DESCRIPTION
		"Module 7 VFD Percent"
::= {analog 29}

m8LchwTemp OBJECT-TYPE
	SYNTAX		Integer32 (0..65535)
	MAX-ACCESS		read-only
	STATUS		current
	DESCRIPTION
		"Module 8 LCHW Temp"
::= {analog 30}

m8SuctTemp OBJECT-TYPE
	SYNTAX		Integer32 (0..65535)
	MAX-ACCESS		read-only
	STATUS		current
	DESCRIPTION
		"Module 8 Suction Temp"
::= {analog 31}

m8VfdPct OBJECT-TYPE
	SYNTAX		Integer32 (0..65535)
	MAX-ACCESS		read-only
	STATUS		current
	DESCRIPTION
		"Module 8 VFD Percent"
::= {analog 32}

m9LchwTemp OBJECT-TYPE
	SYNTAX		Integer32 (0..65535)
	MAX-ACCESS		read-only
	STATUS		current
	DESCRIPTION
		"Module 9 LCHW Temp"
::= {analog 33}

m9SuctTemp OBJECT-TYPE
	SYNTAX		Integer32 (0..65535)
	MAX-ACCESS		read-only
	STATUS		current
	DESCRIPTION
		"Module 9 Suction Temp"
::= {analog 34}

m9VfdPct OBJECT-TYPE
	SYNTAX		Integer32 (0..65535)
	MAX-ACCESS		read-only
	STATUS		current
	DESCRIPTION
		"Module 9 VFD Percent"
::= {analog 35}

m10LchwTemp OBJECT-TYPE
	SYNTAX		Integer32 (0..65535)
	MAX-ACCESS		read-only
	STATUS		current
	DESCRIPTION
		"Module 10 LCHW Temp"
::= {analog 36}

m10SuctTemp OBJECT-TYPE
	SYNTAX		Integer32 (0..65535)
	MAX-ACCESS		read-only
	STATUS		current
	DESCRIPTION
		"Module 10 Suction Temp"
::= {analog 37}

m10VfdPct OBJECT-TYPE
	SYNTAX		Integer32 (0..65535)
	MAX-ACCESS		read-only
	STATUS		current
	DESCRIPTION
		"Module 10 VFD Percent"
::= {analog 38}

m11LchwTemp OBJECT-TYPE
	SYNTAX		Integer32 (0..65535)
	MAX-ACCESS		read-only
	STATUS		current
	DESCRIPTION
		"Module 11 LCHW Temp"
::= {analog 39}

m11SuctTemp OBJECT-TYPE
	SYNTAX		Integer32 (0..65535)
	MAX-ACCESS		read-only
	STATUS		current
	DESCRIPTION
		"Module 11 Suction Temp"
::= {analog 40}

m11VfdPct OBJECT-TYPE
	SYNTAX		Integer32 (0..65535)
	MAX-ACCESS		read-only
	STATUS		current
	DESCRIPTION
		"Module 11 VFD Percent"
::= {analog 41}

m12LchwTemp OBJECT-TYPE
	SYNTAX		Integer32 (0..65535)
	MAX-ACCESS		read-only
	STATUS		current
	DESCRIPTION
		"Module 12 LCHW Temp"
::= {analog 42}

m12SuctTemp OBJECT-TYPE
	SYNTAX		Integer32 (0..65535)
	MAX-ACCESS		read-only
	STATUS		current
	DESCRIPTION
		"Module 12 Suction Temp"
::= {analog 43}

m12VfdPct OBJECT-TYPE
	SYNTAX		Integer32 (0..65535)
	MAX-ACCESS		read-only
	STATUS		current
	DESCRIPTION
		"Module 12 VFD Percent"
::= {analog 44}

m13LchwTemp OBJECT-TYPE
	SYNTAX		Integer32 (0..65535)
	MAX-ACCESS		read-only
	STATUS		current
	DESCRIPTION
		"Module 13 LCHW Temp"
::= {analog 45}

m13SuctTemp OBJECT-TYPE
	SYNTAX		Integer32 (0..65535)
	MAX-ACCESS		read-only
	STATUS		current
	DESCRIPTION
		"Module 13 Suction Temp"
::= {analog 46}

m13VfdPct OBJECT-TYPE
	SYNTAX		Integer32 (0..65535)
	MAX-ACCESS		read-only
	STATUS		current
	DESCRIPTION
		"Module 13 VFD Percent"
::= {analog 47}

m14LchwTemp OBJECT-TYPE
	SYNTAX		Integer32 (0..65535)
	MAX-ACCESS		read-only
	STATUS		current
	DESCRIPTION
		"Module 14 LCHW Temp"
::= {analog 48}

m14SuctTemp OBJECT-TYPE
	SYNTAX		Integer32 (0..65535)
	MAX-ACCESS		read-only
	STATUS		current
	DESCRIPTION
		"Module 14 Suction Temp"
::= {analog 49}

m14VfdPct OBJECT-TYPE
	SYNTAX		Integer32 (0..65535)
	MAX-ACCESS		read-only
	STATUS		current
	DESCRIPTION
		"Module 14 VFD Percent"
::= {analog 50}
--
--

-- DIGITAL READ POINTS

chillerStatus OBJECT-TYPE
	SYNTAX		Integer32 (0..1)
	MAX-ACCESS		read-only
	STATUS		current
	DESCRIPTION	
		"Chiller On/Off Status"
::= {digital 1}

lowChwFlow OBJECT-TYPE
	SYNTAX		Integer32 (0..1)
	MAX-ACCESS		read-only
	STATUS		current
	DESCRIPTION	
		"Chilled Water Flow Input"
::= {digital 2}

powerPhaseMonitor OBJECT-TYPE
	SYNTAX		Integer32 (0..1)
	MAX-ACCESS		read-only
	STATUS		current
	DESCRIPTION	
		"Power Phase Monitor Input"
::= {digital 3}

remoteStartStop OBJECT-TYPE
	SYNTAX		Integer32 (0..1)
	MAX-ACCESS		read-only
	STATUS		current
	DESCRIPTION	
		"Remote Start/Stop Input"
::= {digital 4}

ex1Fault OBJECT-TYPE
	SYNTAX		Integer32 (0..1)
	MAX-ACCESS		read-only
	STATUS		current
	DESCRIPTION	
		"EX1 Input"
::= {digital 5}

lowLchwTempSystem OBJECT-TYPE
	SYNTAX		Integer32 (0..1)
	MAX-ACCESS		read-only
	STATUS		current
	DESCRIPTION	
		"System Low LCHW Temperature"
::= {digital 6}

lchwSysSensorFail OBJECT-TYPE
	SYNTAX		Integer32 (0..1)
	MAX-ACCESS		read-only
	STATUS		current
	DESCRIPTION	
		"System LCHW Sensor Failure"
::= {digital 7}

echwSysSensorFail OBJECT-TYPE
	SYNTAX		Integer32 (0..1)
	MAX-ACCESS		read-only
	STATUS		current
	DESCRIPTION	
		"System ECHW Sensor Failure"
::= {digital 8}

globalAlarm OBJECT-TYPE
	SYNTAX		Integer32 (0..1)
	MAX-ACCESS		read-only
	STATUS		current
	DESCRIPTION	
		"Global Alarm"
::= {digital 9}

chillerOnOffControl OBJECT-TYPE
	SYNTAX		INTEGER {
				ChillerOff(0),
				ChillerOn(1) }
	MAX-ACCESS		read-write
	STATUS		current
	DESCRIPTION	
		"Chiller On/Off Control"
::= {digital 10}

sequencingSV OBJECT-TYPE
	SYNTAX		INTEGER {
				Standard(0),
				OddEven(1) }
	MAX-ACCESS		read-write
	STATUS		current
	DESCRIPTION	
		"Sequencing SV"
::= {digital 11}

indexingSV OBJECT-TYPE
	SYNTAX		INTEGER {
				Off(0),
				On(1) }
	MAX-ACCESS		read-write
	STATUS		current
	DESCRIPTION	
		"Indexing SV"
::= {digital 12}

customerResetActive OBJECT-TYPE
	SYNTAX		Integer32 (0..1)
	MAX-ACCESS		read-only
	STATUS		current
	DESCRIPTION	
		"Customer Reset Active"
::= {digital 13}

lLResetActive OBJECT-TYPE
	SYNTAX		Integer32 (0..1)
	MAX-ACCESS		read-only
	STATUS		current
	DESCRIPTION	
		"Load Limit Reset Active"
::= {digital 14}

cHWResetActive OBJECT-TYPE
	SYNTAX		Integer32 (0..1)
	MAX-ACCESS		read-only
	STATUS		current
	DESCRIPTION	
		"Chilled Water Reset Active"
::= {digital 15}

systemVariablesLock OBJECT-TYPE
	SYNTAX		Integer32 (0..1)
	MAX-ACCESS		read-only
	STATUS		current
	DESCRIPTION	
		"System Variables Locked"
::= {digital 16}

fahrenheitCelsius OBJECT-TYPE
	SYNTAX		Integer32 (0..1)
	MAX-ACCESS		read-only
	STATUS		current
	DESCRIPTION	
		"Fahrenheit/Celsius Readings"
::= {digital 17}

m1-1RunStatus OBJECT-TYPE
	SYNTAX		Integer32 (0..1)
	MAX-ACCESS		read-only
	STATUS		current
	DESCRIPTION	
		"Module 1 Compressor 1 Run Status"
::= {digital 18}

m1-2RunStatus OBJECT-TYPE
	SYNTAX		Integer32 (0..1)
	MAX-ACCESS		read-only
	STATUS		current
	DESCRIPTION	
		"Module 1 Compressor 2 Run Status"
::= {digital 19}

m1CommError OBJECT-TYPE
	SYNTAX		Integer32 (0..1)
	MAX-ACCESS		read-only
	STATUS		current
	DESCRIPTION	
		"Module 1 Communication Error"
::= {digital 20}

m1FanStatus OBJECT-TYPE
	SYNTAX		Integer32 (0..1)
	MAX-ACCESS		read-only
	STATUS		current
	DESCRIPTION	
		"Module 1 Fan Status"
::= {digital 21}

m2-1RunStatus OBJECT-TYPE
	SYNTAX		Integer32 (0..1)
	MAX-ACCESS		read-only
	STATUS		current
	DESCRIPTION	
		"Module 2 Compressor 1 Run Status"
::= {digital 22}

m2-2RunStatus OBJECT-TYPE
	SYNTAX		Integer32 (0..1)
	MAX-ACCESS		read-only
	STATUS		current
	DESCRIPTION	
		"Module 2 Compressor 2 Run Status"
::= {digital 23}

m2CommError OBJECT-TYPE
	SYNTAX		Integer32 (0..1)
	MAX-ACCESS		read-only
	STATUS		current
	DESCRIPTION	
		"Module 2 Communication Error"
::= {digital 24}

m2FanStatus OBJECT-TYPE
	SYNTAX		Integer32 (0..1)
	MAX-ACCESS		read-only
	STATUS		current
	DESCRIPTION	
		"Module 2 Fan Status"
::= {digital 25}

m3-1RunStatus OBJECT-TYPE
	SYNTAX		Integer32 (0..1)
	MAX-ACCESS		read-only
	STATUS		current
	DESCRIPTION	
		"Module 3 Compressor 1 Run Status"
::= {digital 26}

m3-2RunStatus OBJECT-TYPE
	SYNTAX		Integer32 (0..1)
	MAX-ACCESS		read-only
	STATUS		current
	DESCRIPTION	
		"Module 3 Compressor 2 Run Status"
::= {digital 27}

m3CommError OBJECT-TYPE
	SYNTAX		Integer32 (0..1)
	MAX-ACCESS		read-only
	STATUS		current
	DESCRIPTION	
		"Module 3 Communication Error"
::= {digital 28}

m3FanStatus OBJECT-TYPE
	SYNTAX		Integer32 (0..1)
	MAX-ACCESS		read-only
	STATUS		current
	DESCRIPTION	
		"Module 3 Fan Status"
::= {digital 29}

m4-1RunStatus OBJECT-TYPE
	SYNTAX		Integer32 (0..1)
	MAX-ACCESS		read-only
	STATUS		current
	DESCRIPTION	
		"Module 4 Compressor 1 Run Status"
::= {digital 30}

m4-2RunStatus OBJECT-TYPE
	SYNTAX		Integer32 (0..1)
	MAX-ACCESS		read-only
	STATUS		current
	DESCRIPTION	
		"Module 4 Compressor 2 Run Status"
::= {digital 31}

m4CommError OBJECT-TYPE
	SYNTAX		Integer32 (0..1)
	MAX-ACCESS		read-only
	STATUS		current
	DESCRIPTION	
		"Module 4 Communication Error"
::= {digital 32}

m4FanStatus OBJECT-TYPE
	SYNTAX		Integer32 (0..1)
	MAX-ACCESS		read-only
	STATUS		current
	DESCRIPTION	
		"Module 4 Fan Status"
::= {digital 33}

m5-1RunStatus OBJECT-TYPE
	SYNTAX		Integer32 (0..1)
	MAX-ACCESS		read-only
	STATUS		current
	DESCRIPTION	
		"Module 5 Compressor 1 Run Status"
::= {digital 34}

m5-2RunStatus OBJECT-TYPE
	SYNTAX		Integer32 (0..1)
	MAX-ACCESS		read-only
	STATUS		current
	DESCRIPTION	
		"Module 5 Compressor 2 Run Status"
::= {digital 35}

m5CommError OBJECT-TYPE
	SYNTAX		Integer32 (0..1)
	MAX-ACCESS		read-only
	STATUS		current
	DESCRIPTION	
		"Module 5 Communication Error"
::= {digital 36}

m5FanStatus OBJECT-TYPE
	SYNTAX		Integer32 (0..1)
	MAX-ACCESS		read-only
	STATUS		current
	DESCRIPTION	
		"Module 5 Fan Status"
::= {digital 37}

m6-1RunStatus OBJECT-TYPE
	SYNTAX		Integer32 (0..1)
	MAX-ACCESS		read-only
	STATUS		current
	DESCRIPTION	
		"Module 6 Compressor 1 Run Status"
::= {digital 38}

m6-2RunStatus OBJECT-TYPE
	SYNTAX		Integer32 (0..1)
	MAX-ACCESS		read-only
	STATUS		current
	DESCRIPTION	
		"Module 6 Compressor 2 Run Status"
::= {digital 39}

m6CommError OBJECT-TYPE
	SYNTAX		Integer32 (0..1)
	MAX-ACCESS		read-only
	STATUS		current
	DESCRIPTION	
		"Module 6 Communication Error"
::= {digital 40}

m6FanStatus OBJECT-TYPE
	SYNTAX		Integer32 (0..1)
	MAX-ACCESS		read-only
	STATUS		current
	DESCRIPTION	
		"Module 6 Fan Status"
::= {digital 41}

m7-1RunStatus OBJECT-TYPE
	SYNTAX		Integer32 (0..1)
	MAX-ACCESS		read-only
	STATUS		current
	DESCRIPTION	
		"Module 7 Compressor 1 Run Status"
::= {digital 42}

m7-2RunStatus OBJECT-TYPE
	SYNTAX		Integer32 (0..1)
	MAX-ACCESS		read-only
	STATUS		current
	DESCRIPTION	
		"Module 7 Compressor 2 Run Status"
::= {digital 43}

m7CommError OBJECT-TYPE
	SYNTAX		Integer32 (0..1)
	MAX-ACCESS		read-only
	STATUS		current
	DESCRIPTION	
		"Module 7 Communication Error"
::= {digital 44}

m7FanStatus OBJECT-TYPE
	SYNTAX		Integer32 (0..1)
	MAX-ACCESS		read-only
	STATUS		current
	DESCRIPTION	
		"Module 7 Fan Status"
::= {digital 45}

m8-1RunStatus OBJECT-TYPE
	SYNTAX		Integer32 (0..1)
	MAX-ACCESS		read-only
	STATUS		current
	DESCRIPTION	
		"Module 8 Compressor 1 Run Status"
::= {digital 46}

m8-2RunStatus OBJECT-TYPE
	SYNTAX		Integer32 (0..1)
	MAX-ACCESS		read-only
	STATUS		current
	DESCRIPTION	
		"Module 8 Compressor 2 Run Status"
::= {digital 47}

m8CommError OBJECT-TYPE
	SYNTAX		Integer32 (0..1)
	MAX-ACCESS		read-only
	STATUS		current
	DESCRIPTION	
		"Module 8 Communication Error"
::= {digital 48}

m8FanStatus OBJECT-TYPE
	SYNTAX		Integer32 (0..1)
	MAX-ACCESS		read-only
	STATUS		current
	DESCRIPTION	
		"Module 8 Fan Status"
::= {digital 49}

m9-1RunStatus OBJECT-TYPE
	SYNTAX		Integer32 (0..1)
	MAX-ACCESS		read-only
	STATUS		current
	DESCRIPTION	
		"Module 9 Compressor 1 Run Status"
::= {digital 50}

m9-2RunStatus OBJECT-TYPE
	SYNTAX		Integer32 (0..1)
	MAX-ACCESS		read-only
	STATUS		current
	DESCRIPTION	
		"Module 9 Compressor 2 Run Status"
::= {digital 51}

m9CommError OBJECT-TYPE
	SYNTAX		Integer32 (0..1)
	MAX-ACCESS		read-only
	STATUS		current
	DESCRIPTION	
		"Module 9 Communication Error"
::= {digital 52}

m9FanStatus OBJECT-TYPE
	SYNTAX		Integer32 (0..1)
	MAX-ACCESS		read-only
	STATUS		current
	DESCRIPTION	
		"Module 9 Fan Status"
::= {digital 53}

m10-1RunStatus OBJECT-TYPE
	SYNTAX		Integer32 (0..1)
	MAX-ACCESS		read-only
	STATUS		current
	DESCRIPTION	
		"Module 10 Compressor 1 Run Status"
::= {digital 54}

m10-2RunStatus OBJECT-TYPE
	SYNTAX		Integer32 (0..1)
	MAX-ACCESS		read-only
	STATUS		current
	DESCRIPTION	
		"Module 10 Compressor 2 Run Status"
::= {digital 55}

m10CommError OBJECT-TYPE
	SYNTAX		Integer32 (0..1)
	MAX-ACCESS		read-only
	STATUS		current
	DESCRIPTION	
		"Module 10 Communication Error"
::= {digital 56}

m10FanStatus OBJECT-TYPE
	SYNTAX		Integer32 (0..1)
	MAX-ACCESS		read-only
	STATUS		current
	DESCRIPTION	
		"Module 10 Fan Status"
::= {digital 57}

m11-1RunStatus OBJECT-TYPE
	SYNTAX		Integer32 (0..1)
	MAX-ACCESS		read-only
	STATUS		current
	DESCRIPTION	
		"Module 11 Compressor 1 Run Status"
::= {digital 58}

m11-2RunStatus OBJECT-TYPE
	SYNTAX		Integer32 (0..1)
	MAX-ACCESS		read-only
	STATUS		current
	DESCRIPTION	
		"Module 11 Compressor 2 Run Status"
::= {digital 59}

m11CommError OBJECT-TYPE
	SYNTAX		Integer32 (0..1)
	MAX-ACCESS		read-only
	STATUS		current
	DESCRIPTION	
		"Module 11 Communication Error"
::= {digital 60}

m11FanStatus OBJECT-TYPE
	SYNTAX		Integer32 (0..1)
	MAX-ACCESS		read-only
	STATUS		current
	DESCRIPTION	
		"Module 11 Fan Status"
::= {digital 61}

m12-1RunStatus OBJECT-TYPE
	SYNTAX		Integer32 (0..1)
	MAX-ACCESS		read-only
	STATUS		current
	DESCRIPTION	
		"Module 12 Compressor 1 Run Status"
::= {digital 62}

m12-2RunStatus OBJECT-TYPE
	SYNTAX		Integer32 (0..1)
	MAX-ACCESS		read-only
	STATUS		current
	DESCRIPTION	
		"Module 12 Compressor 2 Run Status"
::= {digital 63}

m12CommError OBJECT-TYPE
	SYNTAX		Integer32 (0..1)
	MAX-ACCESS		read-only
	STATUS		current
	DESCRIPTION	
		"Module 12 Communication Error"
::= {digital 64}

m12FanStatus OBJECT-TYPE
	SYNTAX		Integer32 (0..1)
	MAX-ACCESS		read-only
	STATUS		current
	DESCRIPTION	
		"Module 12 Fan Status"
::= {digital 65}

m13-1RunStatus OBJECT-TYPE
	SYNTAX		Integer32 (0..1)
	MAX-ACCESS		read-only
	STATUS		current
	DESCRIPTION	
		"Module 13 Compressor 1 Run Status"
::= {digital 66}

m13-2RunStatus OBJECT-TYPE
	SYNTAX		Integer32 (0..1)
	MAX-ACCESS		read-only
	STATUS		current
	DESCRIPTION	
		"Module 13 Compressor 2 Run Status"
::= {digital 67}

m13CommError OBJECT-TYPE
	SYNTAX		Integer32 (0..1)
	MAX-ACCESS		read-only
	STATUS		current
	DESCRIPTION	
		"Module 13 Communication Error"
::= {digital 68}

m13FanStatus OBJECT-TYPE
	SYNTAX		Integer32 (0..1)
	MAX-ACCESS		read-only
	STATUS		current
	DESCRIPTION	
		"Module 13 Fan Status"
::= {digital 69}

m14-1RunStatus OBJECT-TYPE
	SYNTAX		Integer32 (0..1)
	MAX-ACCESS		read-only
	STATUS		current
	DESCRIPTION	
		"Module 14 Compressor 1 Run Status"
::= {digital 70}

m14-2RunStatus OBJECT-TYPE
	SYNTAX		Integer32 (0..1)
	MAX-ACCESS		read-only
	STATUS		current
	DESCRIPTION	
		"Module 14 Compressor 2 Run Status"
::= {digital 71}

m14CommError OBJECT-TYPE
	SYNTAX		Integer32 (0..1)
	MAX-ACCESS		read-only
	STATUS		current
	DESCRIPTION	
		"Module 14 Communication Error"
::= {digital 72}

m14FanStatus OBJECT-TYPE
	SYNTAX		Integer32 (0..1)
	MAX-ACCESS		read-only
	STATUS		current
	DESCRIPTION	
		"Module 14 Fan Status"
::= {digital 73}

fullLoad OBJECT-TYPE
	SYNTAX		Integer32 (0..1)
	MAX-ACCESS		read-only
	STATUS		current
	DESCRIPTION	
		"Full Load Relay"
::= {digital 74}

--
--

-- INTEGER POINTS

capacity OBJECT-TYPE
	SYNTAX		Integer32 (0..65535)
	MAX-ACCESS		read-only
	STATUS		current
	DESCRIPTION	
		"Capacity"
::= {integers 1}

demand OBJECT-TYPE
	SYNTAX		Integer32 (0..65535)
	MAX-ACCESS		read-only
	STATUS		current
	DESCRIPTION	
		"Demand"
::= {integers 2}

tdiffCountdown OBJECT-TYPE
	SYNTAX		Integer32 (0..65535)
	MAX-ACCESS		read-only
	STATUS		current
	DESCRIPTION	
		"T-Diff Countdown"
::= {integers 3}

systemCountdown OBJECT-TYPE
	SYNTAX		Integer32 (0..65535)
	MAX-ACCESS		read-only
	STATUS		current
	DESCRIPTION	
		"System Countdown"
::= {integers 4}

numOfFaults OBJECT-TYPE
	SYNTAX		Integer32 (0..65535)
	MAX-ACCESS		read-only
	STATUS		current
	DESCRIPTION	
		"Number Of Faults"
::= {integers 5}

leadCompressor OBJECT-TYPE
	SYNTAX		Integer32 (0..65535)
	MAX-ACCESS		read-only
	STATUS		current
	DESCRIPTION	
		"Lead Compressor"
::= {integers 6}

loadLimit OBJECT-TYPE
	SYNTAX		Integer32 (0..65535)
	MAX-ACCESS		read-only
	STATUS		current
	DESCRIPTION	
		"Load Limit"
::= {integers 7}

vspSetpointSV OBJECT-TYPE
	SYNTAX		Integer32 (0..80)
	MAX-ACCESS		read-write
	STATUS		current
	DESCRIPTION	
		"VSP Setpoint SV"
::= {integers 8}

loadLimitSV OBJECT-TYPE
	SYNTAX		Integer32 (0..100)
	MAX-ACCESS		read-write
	STATUS		current
	DESCRIPTION	
		"Load Limit SV"
::= {integers 9}

tdiffSV OBJECT-TYPE
	SYNTAX		Integer32 (15..200)
	MAX-ACCESS		read-write
	STATUS		current
	DESCRIPTION	
		"T-Diff SV"
::= {integers 10}

failIndicatorSV OBJECT-TYPE
	SYNTAX		Integer32 (0..90)
	MAX-ACCESS		read-write
	STATUS		current
	DESCRIPTION	
		"Fail Indicator SV"
::= {integers 11}

leadCompressorSV OBJECT-TYPE
	SYNTAX		Integer32 (0..65535)
	MAX-ACCESS		read-only
	STATUS		current
	DESCRIPTION	
		"Lead Compressor SV"
::= {integers 12}

numberOfModulesSV OBJECT-TYPE
	SYNTAX		Integer32 (0..65535)
	MAX-ACCESS		read-only
	STATUS		current
	DESCRIPTION	
		"Number of Modules SV"
::= {integers 13}

fanSetpointSV OBJECT-TYPE
	SYNTAX		Integer32 (170..350)
	MAX-ACCESS		read-write
	STATUS		current
	DESCRIPTION	
		"Fan Setpoint SV"
::= {integers 14}

fanOffsetSV OBJECT-TYPE
	SYNTAX		Integer32 (20..60)
	MAX-ACCESS		read-write
	STATUS		current
	DESCRIPTION	
		"Fan Offset SV"
::= {integers 15}

hpCutoutSV OBJECT-TYPE
	SYNTAX		Integer32 (300..425)
	MAX-ACCESS		read-write
	STATUS		current
	DESCRIPTION	
		"High Pressure Cutout SV"
::= {integers 16}

hour OBJECT-TYPE
	SYNTAX		Integer32 (0..65535)
	MAX-ACCESS		read-only
	STATUS		current
	DESCRIPTION	
		"Hour"
::= {integers 17}

minute OBJECT-TYPE
	SYNTAX		Integer32 (0..65535)
	MAX-ACCESS		read-only
	STATUS		current
	DESCRIPTION	
		"Minute"
::= {integers 18}

month OBJECT-TYPE
	SYNTAX		Integer32 (0..65535)
	MAX-ACCESS		read-only
	STATUS		current
	DESCRIPTION	
		"Month"
::= {integers 19}

day OBJECT-TYPE
	SYNTAX		Integer32 (0..65535)
	MAX-ACCESS		read-only
	STATUS		current
	DESCRIPTION	
		"Day"
::= {integers 20}

year OBJECT-TYPE
	SYNTAX		Integer32 (0..65535)
	MAX-ACCESS		read-only
	STATUS		current
	DESCRIPTION	
		"Year"
::= {integers 21}

loadProfile0to9 OBJECT-TYPE
	SYNTAX		Integer32 (0..65535)
	MAX-ACCESS		read-only
	STATUS		current
	DESCRIPTION	
		"0-9% Load Profile"
::= {integers 22}

loadProfile10to19 OBJECT-TYPE
	SYNTAX		Integer32 (0..65535)
	MAX-ACCESS		read-only
	STATUS		current
	DESCRIPTION	
		"10-19% Load Profile"
::= {integers 23}

loadProfile20to29 OBJECT-TYPE
	SYNTAX		Integer32 (0..65535)
	MAX-ACCESS		read-only
	STATUS		current
	DESCRIPTION	
		"20-29% Load Profile"
::= {integers 24}

loadProfile30to39 OBJECT-TYPE
	SYNTAX		Integer32 (0..65535)
	MAX-ACCESS		read-only
	STATUS		current
	DESCRIPTION	
		"30-39% Load Profile"
::= {integers 25}

loadProfile40to49 OBJECT-TYPE
	SYNTAX		Integer32 (0..65535)
	MAX-ACCESS		read-only
	STATUS		current
	DESCRIPTION	
		"40-49% Load Profile"
::= {integers 26}

loadProfile50to59 OBJECT-TYPE
	SYNTAX		Integer32 (0..65535)
	MAX-ACCESS		read-only
	STATUS		current
	DESCRIPTION	
		"50-59% Load Profile"
::= {integers 27}

loadProfile60to69 OBJECT-TYPE
	SYNTAX		Integer32 (0..65535)
	MAX-ACCESS		read-only
	STATUS		current
	DESCRIPTION	
		"60-69% Load Profile"
::= {integers 28}

loadProfile70to79 OBJECT-TYPE
	SYNTAX		Integer32 (0..65535)
	MAX-ACCESS		read-only
	STATUS		current
	DESCRIPTION	
		"70-79% Load Profile"
::= {integers 29}

loadProfile80to89 OBJECT-TYPE
	SYNTAX		Integer32 (0..65535)
	MAX-ACCESS		read-only
	STATUS		current
	DESCRIPTION	
		"80-89% Load Profile"
::= {integers 30}

loadProfile90to100 OBJECT-TYPE
	SYNTAX		Integer32 (0..65535)
	MAX-ACCESS		read-only
	STATUS		current
	DESCRIPTION	
		"90-100% Load Profile"
::= {integers 31}

totalLoadProfile OBJECT-TYPE
	SYNTAX		Integer32 (0..65535)
	MAX-ACCESS		read-only
	STATUS		current
	DESCRIPTION	
		"Total Load Profile Hours"
::= {integers 32}

m1Fault OBJECT-TYPE
	SYNTAX		FaultCode
	MAX-ACCESS		read-only
	STATUS		current
	DESCRIPTION	
		"Module 1 Fault"
::= {integers 33}

m1c1RunHours OBJECT-TYPE
	SYNTAX		Integer32 (0..65535)
	MAX-ACCESS		read-only
	STATUS		current
	DESCRIPTION	
		"Module 1 Compressor 1 Run Hours"
::= {integers 34} 

m1c2RunHours OBJECT-TYPE
	SYNTAX		Integer32 (0..65535)
	MAX-ACCESS		read-only
	STATUS		current
	DESCRIPTION	
		"Module 1 Compressor 2 Run Hours"
::= {integers 35}

m1HighPressure OBJECT-TYPE
	SYNTAX		Integer32 (0..65535)
	MAX-ACCESS		read-only
	STATUS		current
	DESCRIPTION	
		"Module 1 High Pressure"
::= {integers 36}

m1LowPressure OBJECT-TYPE
	SYNTAX		Integer32 (0..65535)
	MAX-ACCESS		read-only
	STATUS		current
	DESCRIPTION	
		"Module 1 Low Pressure"
::= {integers 37}

m1ControlMode OBJECT-TYPE
	SYNTAX		ControlMode
	MAX-ACCESS		read-only
	STATUS		current
	DESCRIPTION	
		"Module 1 Control Mode"
::= {integers 38}

m2Fault OBJECT-TYPE
	SYNTAX		FaultCode
	MAX-ACCESS		read-only
	STATUS		current
	DESCRIPTION	
		"Module 2 Fault"
::= {integers 39}

m2c1RunHours OBJECT-TYPE
	SYNTAX		Integer32 (0..65535)
	MAX-ACCESS		read-only
	STATUS		current
	DESCRIPTION	
		"Module 2 Compressor 1 Run Hours"
::= {integers 40} 

m2c2RunHours OBJECT-TYPE
	SYNTAX		Integer32 (0..65535)
	MAX-ACCESS		read-only
	STATUS		current
	DESCRIPTION	
		"Module 2 Compressor 2 Run Hours"
::= {integers 41}

m2HighPressure OBJECT-TYPE
	SYNTAX		Integer32 (0..65535)
	MAX-ACCESS		read-only
	STATUS		current
	DESCRIPTION	
		"Module 2 High Pressure"
::= {integers 42}

m2LowPressure OBJECT-TYPE
	SYNTAX		Integer32 (0..65535)
	MAX-ACCESS		read-only
	STATUS		current
	DESCRIPTION	
		"Module 2 Low Pressure"
::= {integers 43}

m2ControlMode OBJECT-TYPE
	SYNTAX		ControlMode
	MAX-ACCESS		read-only
	STATUS		current
	DESCRIPTION	
		"Module 2 Control Mode"
::= {integers 44}


m3Fault OBJECT-TYPE
	SYNTAX		FaultCode
	MAX-ACCESS		read-only
	STATUS		current
	DESCRIPTION	
		"Module 3 Fault"
::= {integers 45}

m3c1RunHours OBJECT-TYPE
	SYNTAX		Integer32 (0..65535)
	MAX-ACCESS		read-only
	STATUS		current
	DESCRIPTION	
		"Module 3 Compressor 1 Run Hours"
::= {integers 46} 

m3c2RunHours OBJECT-TYPE
	SYNTAX		Integer32 (0..65535)
	MAX-ACCESS		read-only
	STATUS		current
	DESCRIPTION	
		"Module 3 Compressor 2 Run Hours"
::= {integers 47}

m3HighPressure OBJECT-TYPE
	SYNTAX		Integer32 (0..65535)
	MAX-ACCESS		read-only
	STATUS		current
	DESCRIPTION	
		"Module 3 High Pressure"
::= {integers 48}

m3LowPressure OBJECT-TYPE
	SYNTAX		Integer32 (0..65535)
	MAX-ACCESS		read-only
	STATUS		current
	DESCRIPTION	
		"Module 3 Low Pressure"
::= {integers 49}

m3ControlMode OBJECT-TYPE
	SYNTAX		ControlMode
	MAX-ACCESS		read-only
	STATUS		current
	DESCRIPTION	
		"Module 3 Control Mode"
::= {integers 50}

m4Fault OBJECT-TYPE
	SYNTAX		FaultCode
	MAX-ACCESS		read-only
	STATUS		current
	DESCRIPTION	
		"Module 4 Fault"
::= {integers 51}

m4c1RunHours OBJECT-TYPE
	SYNTAX		Integer32 (0..65535)
	MAX-ACCESS		read-only
	STATUS		current
	DESCRIPTION	
		"Module 4 Compressor 1 Run Hours"
::= {integers 52} 

m4c2RunHours OBJECT-TYPE
	SYNTAX		Integer32 (0..65535)
	MAX-ACCESS		read-only
	STATUS		current
	DESCRIPTION	
		"Module 4 Compressor 2 Run Hours"
::= {integers 53}

m4HighPressure OBJECT-TYPE
	SYNTAX		Integer32 (0..65535)
	MAX-ACCESS		read-only
	STATUS		current
	DESCRIPTION	
		"Module 4 High Pressure"
::= {integers 54}

m4LowPressure OBJECT-TYPE
	SYNTAX		Integer32 (0..65535)
	MAX-ACCESS		read-only
	STATUS		current
	DESCRIPTION	
		"Module 4 Low Pressure"
::= {integers 55}

m4ControlMode OBJECT-TYPE
	SYNTAX		ControlMode
	MAX-ACCESS		read-only
	STATUS		current
	DESCRIPTION	
		"Module 4 Control Mode"
::= {integers 56}

m5Fault OBJECT-TYPE
	SYNTAX		FaultCode
	MAX-ACCESS		read-only
	STATUS		current
	DESCRIPTION	
		"Module 5 Fault"
::= {integers 57}

m5c1RunHours OBJECT-TYPE
	SYNTAX		Integer32 (0..65535)
	MAX-ACCESS		read-only
	STATUS		current
	DESCRIPTION	
		"Module 5 Compressor 1 Run Hours"
::= {integers 58} 

m5c2RunHours OBJECT-TYPE
	SYNTAX		Integer32 (0..65535)
	MAX-ACCESS		read-only
	STATUS		current
	DESCRIPTION	
		"Module 5 Compressor 2 Run Hours"
::= {integers 59}

m5HighPressure OBJECT-TYPE
	SYNTAX		Integer32 (0..65535)
	MAX-ACCESS		read-only
	STATUS		current
	DESCRIPTION	
		"Module 5 High Pressure"
::= {integers 60}

m5LowPressure OBJECT-TYPE
	SYNTAX		Integer32 (0..65535)
	MAX-ACCESS		read-only
	STATUS		current
	DESCRIPTION	
		"Module 5 Low Pressure"
::= {integers 61}

m5ControlMode OBJECT-TYPE
	SYNTAX		ControlMode
	MAX-ACCESS		read-only
	STATUS		current
	DESCRIPTION	
		"Module 5 Control Mode"
::= {integers 62}

m6Fault OBJECT-TYPE
	SYNTAX		FaultCode
	MAX-ACCESS		read-only
	STATUS		current
	DESCRIPTION	
		"Module 6 Fault"
::= {integers 63}

m6c1RunHours OBJECT-TYPE
	SYNTAX		Integer32 (0..65535)
	MAX-ACCESS		read-only
	STATUS		current
	DESCRIPTION	
		"Module 6 Compressor 1 Run Hours"
::= {integers 64} 

m6c2RunHours OBJECT-TYPE
	SYNTAX		Integer32 (0..65535)
	MAX-ACCESS		read-only
	STATUS		current
	DESCRIPTION	
		"Module 6 Compressor 2 Run Hours"
::= {integers 65}

m6HighPressure OBJECT-TYPE
	SYNTAX		Integer32 (0..65535)
	MAX-ACCESS		read-only
	STATUS		current
	DESCRIPTION	
		"Module 6 High Pressure"
::= {integers 66}

m6LowPressure OBJECT-TYPE
	SYNTAX		Integer32 (0..65535)
	MAX-ACCESS		read-only
	STATUS		current
	DESCRIPTION	
		"Module 6 Low Pressure"
::= {integers 67}

m6ControlMode OBJECT-TYPE
	SYNTAX		ControlMode
	MAX-ACCESS		read-only
	STATUS		current
	DESCRIPTION	
		"Module 6 Control Mode"
::= {integers 68}

m7Fault OBJECT-TYPE
	SYNTAX		FaultCode
	MAX-ACCESS		read-only
	STATUS		current
	DESCRIPTION	
		"Module 7 Fault"
::= {integers 69}

m7c1RunHours OBJECT-TYPE
	SYNTAX		Integer32 (0..65535)
	MAX-ACCESS		read-only
	STATUS		current
	DESCRIPTION	
		"Module 7 Compressor 1 Run Hours"
::= {integers 70} 

m7c2RunHours OBJECT-TYPE
	SYNTAX		Integer32 (0..65535)
	MAX-ACCESS		read-only
	STATUS		current
	DESCRIPTION	
		"Module 7 Compressor 2 Run Hours"
::= {integers 71}

m7HighPressure OBJECT-TYPE
	SYNTAX		Integer32 (0..65535)
	MAX-ACCESS		read-only
	STATUS		current
	DESCRIPTION	
		"Module 7 High Pressure"
::= {integers 72}

m7LowPressure OBJECT-TYPE
	SYNTAX		Integer32 (0..65535)
	MAX-ACCESS		read-only
	STATUS		current
	DESCRIPTION	
		"Module 7 Low Pressure"
::= {integers 73}

m7ControlMode OBJECT-TYPE
	SYNTAX		ControlMode
	MAX-ACCESS		read-only
	STATUS		current
	DESCRIPTION	
		"Module 7 Control Mode"
::= {integers 74}

m8Fault OBJECT-TYPE
	SYNTAX		FaultCode
	MAX-ACCESS		read-only
	STATUS		current
	DESCRIPTION	
		"Module 8 Fault"
::= {integers 75}

m8c1RunHours OBJECT-TYPE
	SYNTAX		Integer32 (0..65535)
	MAX-ACCESS		read-only
	STATUS		current
	DESCRIPTION	
		"Module 8 Compressor 1 Run Hours"
::= {integers 76} 

m8c2RunHours OBJECT-TYPE
	SYNTAX		Integer32 (0..65535)
	MAX-ACCESS		read-only
	STATUS		current
	DESCRIPTION	
		"Module 8 Compressor 2 Run Hours"
::= {integers 77}

m8HighPressure OBJECT-TYPE
	SYNTAX		Integer32 (0..65535)
	MAX-ACCESS		read-only
	STATUS		current
	DESCRIPTION	
		"Module 8 High Pressure"
::= {integers 78}

m8LowPressure OBJECT-TYPE
	SYNTAX		Integer32 (0..65535)
	MAX-ACCESS		read-only
	STATUS		current
	DESCRIPTION	
		"Module 8 Low Pressure"
::= {integers 79}

m8ControlMode OBJECT-TYPE
	SYNTAX		ControlMode
	MAX-ACCESS		read-only
	STATUS		current
	DESCRIPTION	
		"Module 8 Control Mode"
::= {integers 80}

m9Fault OBJECT-TYPE
	SYNTAX		FaultCode
	MAX-ACCESS		read-only
	STATUS		current
	DESCRIPTION	
		"Module 9 Fault"
::= {integers 81}

m9c1RunHours OBJECT-TYPE
	SYNTAX		Integer32 (0..65535)
	MAX-ACCESS		read-only
	STATUS		current
	DESCRIPTION	
		"Module 9 Compressor 1 Run Hours"
::= {integers 82} 

m9c2RunHours OBJECT-TYPE
	SYNTAX		Integer32 (0..65535)
	MAX-ACCESS		read-only
	STATUS		current
	DESCRIPTION	
		"Module 9 Compressor 2 Run Hours"
::= {integers 83}

m9HighPressure OBJECT-TYPE
	SYNTAX		Integer32 (0..65535)
	MAX-ACCESS		read-only
	STATUS		current
	DESCRIPTION	
		"Module 9 High Pressure"
::= {integers 84}

m9LowPressure OBJECT-TYPE
	SYNTAX		Integer32 (0..65535)
	MAX-ACCESS		read-only
	STATUS		current
	DESCRIPTION	
		"Module 9 Low Pressure"
::= {integers 85}

m9ControlMode OBJECT-TYPE
	SYNTAX		ControlMode
	MAX-ACCESS		read-only
	STATUS		current
	DESCRIPTION	
		"Module 9 Control Mode"
::= {integers 86}

m10Fault OBJECT-TYPE
	SYNTAX		FaultCode
	MAX-ACCESS		read-only
	STATUS		current
	DESCRIPTION	
		"Module 10 Fault"
::= {integers 87}

m10c1RunHours OBJECT-TYPE
	SYNTAX		Integer32 (0..65535)
	MAX-ACCESS		read-only
	STATUS		current
	DESCRIPTION	
		"Module 10 Compressor 1 Run Hours"
::= {integers 88} 

m10c2RunHours OBJECT-TYPE
	SYNTAX		Integer32 (0..65535)
	MAX-ACCESS		read-only
	STATUS		current
	DESCRIPTION	
		"Module 10 Compressor 2 Run Hours"
::= {integers 89}

m10HighPressure OBJECT-TYPE
	SYNTAX		Integer32 (0..65535)
	MAX-ACCESS		read-only
	STATUS		current
	DESCRIPTION	
		"Module 10 High Pressure"
::= {integers 90}

m10LowPressure OBJECT-TYPE
	SYNTAX		Integer32 (0..65535)
	MAX-ACCESS		read-only
	STATUS		current
	DESCRIPTION	
		"Module 10 Low Pressure"
::= {integers 91}

m10ControlMode OBJECT-TYPE
	SYNTAX		ControlMode
	MAX-ACCESS		read-only
	STATUS		current
	DESCRIPTION	
		"Module 10 Control Mode"
::= {integers 92}

m11Fault OBJECT-TYPE
	SYNTAX		FaultCode
	MAX-ACCESS		read-only
	STATUS		current
	DESCRIPTION	
		"Module 11 Fault"
::= {integers 93}

m11c1RunHours OBJECT-TYPE
	SYNTAX		Integer32 (0..65535)
	MAX-ACCESS		read-only
	STATUS		current
	DESCRIPTION	
		"Module 11 Compressor 1 Run Hours"
::= {integers 94} 

m11c2RunHours OBJECT-TYPE
	SYNTAX		Integer32 (0..65535)
	MAX-ACCESS		read-only
	STATUS		current
	DESCRIPTION	
		"Module 11 Compressor 2 Run Hours"
::= {integers 95}

m11HighPressure OBJECT-TYPE
	SYNTAX		Integer32 (0..65535)
	MAX-ACCESS		read-only
	STATUS		current
	DESCRIPTION	
		"Module 11 High Pressure"
::= {integers 96}

m11LowPressure OBJECT-TYPE
	SYNTAX		Integer32 (0..65535)
	MAX-ACCESS		read-only
	STATUS		current
	DESCRIPTION	
		"Module 11 Low Pressure"
::= {integers 97}

m11ControlMode OBJECT-TYPE
	SYNTAX		ControlMode
	MAX-ACCESS		read-only
	STATUS		current
	DESCRIPTION	
		"Module 11 Control Mode"
::= {integers 98}

m12Fault OBJECT-TYPE
	SYNTAX		FaultCode
	MAX-ACCESS		read-only
	STATUS		current
	DESCRIPTION	
		"Module 12 Fault"
::= {integers 99}

m12c1RunHours OBJECT-TYPE
	SYNTAX		Integer32 (0..65535)
	MAX-ACCESS		read-only
	STATUS		current
	DESCRIPTION	
		"Module 12 Compressor 1 Run Hours"
::= {integers 100} 

m12c2RunHours OBJECT-TYPE
	SYNTAX		Integer32 (0..65535)
	MAX-ACCESS		read-only
	STATUS		current
	DESCRIPTION	
		"Module 12 Compressor 2 Run Hours"
::= {integers 101}

m12HighPressure OBJECT-TYPE
	SYNTAX		Integer32 (0..65535)
	MAX-ACCESS		read-only
	STATUS		current
	DESCRIPTION	
		"Module 12 High Pressure"
::= {integers 102}

m12LowPressure OBJECT-TYPE
	SYNTAX		Integer32 (0..65535)
	MAX-ACCESS		read-only
	STATUS		current
	DESCRIPTION	
		"Module 12 Low Pressure"
::= {integers 103}

m12ControlMode OBJECT-TYPE
	SYNTAX		ControlMode
	MAX-ACCESS		read-only
	STATUS		current
	DESCRIPTION	
		"Module 12 Control Mode"
::= {integers 104}

m13Fault OBJECT-TYPE
	SYNTAX		FaultCode
	MAX-ACCESS		read-only
	STATUS		current
	DESCRIPTION	
		"Module 13 Fault"
::= {integers 105}

m13c1RunHours OBJECT-TYPE
	SYNTAX		Integer32 (0..65535)
	MAX-ACCESS		read-only
	STATUS		current
	DESCRIPTION	
		"Module 13 Compressor 1 Run Hours"
::= {integers 106} 

m13c2RunHours OBJECT-TYPE
	SYNTAX		Integer32 (0..65535)
	MAX-ACCESS		read-only
	STATUS		current
	DESCRIPTION	
		"Module 13 Compressor 2 Run Hours"
::= {integers 107}

m13HighPressure OBJECT-TYPE
	SYNTAX		Integer32 (0..65535)
	MAX-ACCESS		read-only
	STATUS		current
	DESCRIPTION	
		"Module 13 High Pressure"
::= {integers 108}

m13LowPressure OBJECT-TYPE
	SYNTAX		Integer32 (0..65535)
	MAX-ACCESS		read-only
	STATUS		current
	DESCRIPTION	
		"Module 13 Low Pressure"
::= {integers 109}

m13ControlMode OBJECT-TYPE
	SYNTAX		ControlMode
	MAX-ACCESS		read-only
	STATUS		current
	DESCRIPTION	
		"Module 13 Control Mode"
::= {integers 110}

m14Fault OBJECT-TYPE
	SYNTAX		FaultCode
	MAX-ACCESS		read-only
	STATUS		current
	DESCRIPTION	
		"Module 14 Fault"
::= {integers 111}

m14c1RunHours OBJECT-TYPE
	SYNTAX		Integer32 (0..65535)
	MAX-ACCESS		read-only
	STATUS		current
	DESCRIPTION	
		"Module 14 Compressor 1 Run Hours"
::= {integers 112} 

m14c2RunHours OBJECT-TYPE
	SYNTAX		Integer32 (0..65535)
	MAX-ACCESS		read-only
	STATUS		current
	DESCRIPTION	
		"Module 14 Compressor 2 Run Hours"
::= {integers 113}

m14HighPressure OBJECT-TYPE
	SYNTAX		Integer32 (0..65535)
	MAX-ACCESS		read-only
	STATUS		current
	DESCRIPTION	
		"Module 14 High Pressure"
::= {integers 114}

m14LowPressure OBJECT-TYPE
	SYNTAX		Integer32 (0..65535)
	MAX-ACCESS		read-only
	STATUS		current
	DESCRIPTION	
		"Module 14 Low Pressure"
::= {integers 115}

m14ControlMode OBJECT-TYPE
	SYNTAX		ControlMode
	MAX-ACCESS		read-only
	STATUS		current
	DESCRIPTION	
		"Module 14 Control Mode"
::= {integers 116}

END
