-- ==================================================================
-- Copyright (C) 2002 by  HUAWEI TECHNOLOGIES. All rights reserved.
-- 
-- Description：  HUAWEI Lan Switch Device Physical Information MIB
-- Reference:
-- Version: V2.7
-- History:
--    v1.0 (1) Created by Hou Qiang, 2001.5.15
--         (2) Revised by Qi Zhenglin, 2002.01.08 ----r003 revision
--    v1.1 2004-7-12 add some card type define(hwLswSlotType 119-138)
--    v1.2 add enum value from 42 to 49 in hwLswPortType.
--    v1.3 2004-7-29 add some port type define(hwLswPortType 50-58)
--    v1.4 2004-8-11 add some slot type define
--                    (hwLswSlotType    type_LSA1FP8U(139))
--                    (hwLswSubslotType type_LSA1FP8U(139))
--    v1.5 2004-08-25 change emunation name
--                     from type_LS81SFCA(120) to type_LS81SRPG0(120),
--                     from type_LS81SFCB(121) to type_LS81SRPG1(121),
--                     from type_LS81SFCC(122) to type_LS81SRPG2(122),
--                     from type_LS81SFCD(123) to type_LS81SRPG3(123).
--                    modify comments for these emunations as well.
--    v1.6 2004-8-26 add some port types define(h2LswPortType 59-71)
--    v1.7 2004-09-08 add enum value from 140 to 148 in hwLswSlotType and hwLswSubSlotType by kangyinan
--    v1.8 2004-09-14 add enum value from 149 to 157 in hwLswSlotType and hwLswSubSlotType by wangyahui
--                    add enum value from 158 to 159 in hwLswSlotType and hwLswSubSlotType by kangyinan
--                    add enum value from 72 to 93 in hwLswPortType by wangyahui
--                    add enum value from 94 to 96 in hwLswPortType by kangyinan
--                    add type description for type_SP4, type_UP1, type_XP4 by kangyinan
--    v1.9 2004-10-12 updated by gaolong
--         Change all underscore('_') characters to hyphen characters('-') because underscore character is not allowed in MIB module.
--         The change refers to the value of hwLswSlotType, hwLswSlotAdminStatus, hwLswSubslotType, hwLswPortType, hwLswSubslotAdminStatus
--         Change MAX-ACCESS clause value of hwLswPortLoopbackOperate from write-only to read-write, and
--         update its DESCRIPTION.
--    v2.0 2004-10-19 add enum value from 160 to 162 in hwLswSlotType and hwLswSubSlotType by kangyinan
--                    add enum value 97 in hwLswPortType by kangyinan 
--    v2.1 2004-11-23 add enum value from 163 to 166 in hwLswSlotType and hwLswSubSlotType by zhangchengmei
--    V2.2  2004-12-23 add enum value from 167 to 169 in hwLswSlotType and hwLswSubSlotType by zhangjianfeng
--    V2.3  2004-12-26 add enum value 170 in hwLswSlotType and hwLswSubSlotType by wangyahui
--    V2.4  2004-12-23 add enum value from 171 to 172 in hwLswSlotType and hwLswSubSlotType 
--                     add enum value from 98 to 99 hwLswPortType by liyue
--    V2.5  2004-12-29 add enum value 173 in hwLswSlotType and hwLswSubSlotType by zhangjianfeng
--                     add enum value from 100 in hwLswPortType by zhangjianfeng
--    V2.6  2005-01-07 add enum value 174 and 175 in hwLswSlotType and hwLswSubSlotType by wangyahui
--    V2.7  2005-01-31 add enum value 176 in hwLswSlotType and hwLswSubSlotType by wangyahui
-- ==================================================================
-- ==================================================================
-- 
-- Varibles and types be imported
--
-- ==================================================================
A3COM-HUAWEI-DEVICE-MIB DEFINITIONS ::= BEGIN
IMPORTS
    DisplayString, DateAndTime
        FROM SNMPv2-TC
  
    MODULE-IDENTITY,OBJECT-TYPE,IpAddress
        FROM SNMPv2-SMI
    lswCommon
        FROM A3COM-HUAWEI-OID-MIB;

-- ==================================================================
--
-- ======================= definition begin =========================
--
-- ==================================================================

-- system information: hwLswDeviceAdmin
-- ==================================================================
    hwLswDeviceAdmin MODULE-IDENTITY
        LAST-UPDATED "200101040000Z"
        ORGANIZATION ""
        CONTACT-INFO
        ""
        DESCRIPTION
        ""
        REVISION "200104040000Z"
        DESCRIPTION
        ""
        ::= { lswCommon  18 }

    hwLswSystemPara OBJECT IDENTIFIER ::= {  hwLswDeviceAdmin 1  }

-- ==================================================================

    hwLswSysIpAddr OBJECT-TYPE
        SYNTAX IpAddress
        MAX-ACCESS read-only
        STATUS current
        DESCRIPTION
        " System IP address, which is the smallest IP address of the VLAN interface. "
        ::= { hwLswSystemPara 1 }
    
    hwLswSysIpMask OBJECT-TYPE
        SYNTAX IpAddress
        MAX-ACCESS read-only
        STATUS current
        DESCRIPTION
        " Mask of the system IP address"
        ::= { hwLswSystemPara 2 }    

    hwLswSysCpuRatio OBJECT-TYPE
        SYNTAX INTEGER
        MAX-ACCESS read-only
        STATUS current
        DESCRIPTION
        " System CPU occupation ratio at the accuracy of 1%, ranging from 1 to 100."
        ::= { hwLswSystemPara 3 }

    hwLswSysVersion OBJECT-TYPE
        SYNTAX DisplayString (SIZE(1..64))
        MAX-ACCESS read-only
        STATUS current
        DESCRIPTION
        "System version, revision version number"
        ::= { hwLswSystemPara 4 }
        
     hwLswSysTime OBJECT-TYPE
        SYNTAX DateAndTime 
        MAX-ACCESS read-write
        STATUS current
        DESCRIPTION
        "System time"
        ::= { hwLswSystemPara 5 }   
        
     hwLswSysUNMCastDropEnable OBJECT-TYPE
        SYNTAX INTEGER
        {
            disable (0),
            enable  (1)
        } 
        MAX-ACCESS read-write
        STATUS current
        DESCRIPTION
        "Enable or disable unknown multicast packet discard"
        ::= { hwLswSystemPara 6 }    
        
     hwLswSysManagementVlan OBJECT-TYPE
        SYNTAX INTEGER (1..4094)
        MAX-ACCESS read-write
        STATUS current
        DESCRIPTION
        "System management-vlan"
        ::= { hwLswSystemPara 7 }   

     hwLswSysVlanRange OBJECT-TYPE
        SYNTAX DisplayString (SIZE(1..10))
        MAX-ACCESS read-write
        STATUS current
        DESCRIPTION
        "System vlan range, if set vlan range, must bind mangement IP/Mask"
        ::= { hwLswSystemPara 8 }   
          
     hwLswSysManagementIpAddr OBJECT-TYPE
        SYNTAX IpAddress
        MAX-ACCESS read-write
        STATUS current
        DESCRIPTION
        " System IP address,  "
        ::= { hwLswSystemPara 9 }
    
    hwLswSysManagementIpMask OBJECT-TYPE
        SYNTAX IpAddress
        MAX-ACCESS read-write
        STATUS current
        DESCRIPTION
        " Mask of the system IP address"
        ::= { hwLswSystemPara 10 }                   

    hwMacAddressCountPort OBJECT-TYPE
        SYNTAX INTEGER 
        MAX-ACCESS read-only
        STATUS current
        DESCRIPTION
        " Supportted MAC address number on port"
        ::= { hwLswSystemPara 11 } 
        
    hwMacAddressCountMachine OBJECT-TYPE
        SYNTAX INTEGER 
        MAX-ACCESS read-only
        STATUS current
        DESCRIPTION
        " Supportted MAC address number on machine"
        ::= { hwLswSystemPara 12 }  
                        

        
-- ==================================================================
--
-- slot and port management group 
--
-- ==================================================================

    hwLswSlotConf OBJECT IDENTIFIER ::= { hwLswDeviceAdmin 4 }

-- ==================================================================
--
-- Frame information table 
--
-- ==================================================================

    hwLswFrameTable    OBJECT-TYPE
        SYNTAX     SEQUENCE OF HwLswFrameEntry
        MAX-ACCESS     not-accessible
        STATUS     current
        DESCRIPTION
        "Frame information table"
        ::= {hwLswSlotConf 2}

    hwLswFrameEntry    OBJECT-TYPE
        SYNTAX     HwLswFrameEntry
        MAX-ACCESS     not-accessible
        STATUS     current
        DESCRIPTION
        "Frame description table entry"
        INDEX { hwLswFrameIndex }
        ::= {hwLswFrameTable 1}

   HwLswFrameEntry ::= SEQUENCE
    {
        hwLswFrameIndex        INTEGER,
        hwLswFrameDesc         DisplayString,
        hwLswFrameType         INTEGER,
        hwLswSlotNumber        INTEGER,
        hwLswFrameAdminStatus  INTEGER
    }

    hwLswFrameIndex    OBJECT-TYPE
        SYNTAX     INTEGER
        MAX-ACCESS     read-only
        STATUS     current
        DESCRIPTION
        "The unique index of frame"
        ::= {hwLswFrameEntry 1}
    
    hwLswFrameType    OBJECT-TYPE
        SYNTAX     INTEGER
        MAX-ACCESS     read-only
        STATUS     current
        DESCRIPTION
        "Frame type"
        ::= {hwLswFrameEntry 2}    

    hwLswFrameDesc    OBJECT-TYPE 
        SYNTAX       DisplayString (SIZE(0..64))
        MAX-ACCESS     read-write
        STATUS     current
        DESCRIPTION
        "Frame description with a character string not exceeding 64."
        ::= {hwLswFrameEntry 3}

    hwLswSlotNumber    OBJECT-TYPE
        SYNTAX     INTEGER
        MAX-ACCESS     read-only
        STATUS     current
        DESCRIPTION
        "Number of slots of the current frame"
        ::= {hwLswFrameEntry 4}
    
    hwLswFrameAdminStatus    OBJECT-TYPE
        SYNTAX     INTEGER
        {
              normal (1),
              fault  (2),
              other  (3)              
        }
        MAX-ACCESS     read-only
        STATUS     current
        DESCRIPTION
        "The Status of frame"
        ::= {hwLswFrameEntry 5}

    
-- ==================================================================
-- 
-- slot information table
--
-- ==================================================================

    hwLswSlotTable    OBJECT-TYPE
        SYNTAX     SEQUENCE OF HwLswSlotEntry
        MAX-ACCESS     not-accessible
        STATUS     current
        DESCRIPTION
        "Slot description table"
        ::= {hwLswSlotConf 3}

    hwLswSlotEntry    OBJECT-TYPE
        SYNTAX     HwLswSlotEntry
        MAX-ACCESS     not-accessible
        STATUS     current
        DESCRIPTION
        " Slot description table entry"
        INDEX { hwLswFrameIndex, hwLswSlotIndex }
        ::= {hwLswSlotTable 1}

   HwLswSlotEntry ::= SEQUENCE
    {
        hwLswSlotIndex                INTEGER,
        hwLswSlotType                 INTEGER,
        hwLswSlotDesc                 DisplayString,
        hwLswSlotCpuRatio             INTEGER,
        hwLswSlotPcbVersion           DisplayString,
        hwLswSlotSoftwareVersion      DisplayString,
        hwLswSubslotNumber            INTEGER,
        hwLswSlotAdminStatus          INTEGER,
        hwLswSlotOperStatus           INTEGER     
       
   }

    hwLswSlotIndex    OBJECT-TYPE
        SYNTAX     INTEGER
        MAX-ACCESS     read-only
        STATUS     current
        DESCRIPTION
        "Slot index. When the slot is empty, listed as vacant slot. "
        ::= {hwLswSlotEntry 1}
        
    hwLswSlotType    OBJECT-TYPE
        SYNTAX     INTEGER
        {
            type-NULL(0),			-- NULL
            type-10OR100M(1),			-- 10M/100M Ethernet Copper Interface Module
            type-1000BASE-LX-SM(2),		-- 1000BASE-X Module (SMF, LC)
            type-1000BASE-SX-MM(3),		-- 1000BASE-X Module (MMF, LC)
            type-1000BASE-TX(4),		-- 
            type-100M-SINGLEMODE-FX(5),		-- 100M Ethernet Single Mode Optical Interface Module
            type-100M-MULTIMODE-FX(6),		-- 100M Ethernet Multi-mode Optical Interface Module
            type-100M-100BASE-TX(7),		-- 100M Ethernet copper Interface Module(RJ45
            type-100M-HUB(8),			-- 100M Base-TX transportation Interface Module
            type-VDSL(9),			-- VDSL
            type-STACK(10),			-- GigaStack Module
            type-1000BASE-ZENITH-FX(11),	-- 1000M Ethernet Single Mode Optical Interface Module(1550nm,70km,LC)
            type-1000BASE-LONG-FX(12),		-- 1000M Ethernet Single Mode Optical Interface Module(1550nm,40km,LC)
            type-ADSL(13),			-- ADSL
            type-4T10OR100-4FX100SM(14),	-- 4-Port Single Mode Optical Interface and 4-Port 10M/100M Ethernet Interface Module
            type-4T10OR100-4FX100MM(15),	-- 4-Port Multi-mode Optical Interface and 4-Port 10M/100M Ethernet Interface Module
            type-VSPL(16),			-- VDSL Board
            type-ASPL(17),			-- ADSL Board
            type-1000M-SFP(18),			-- 1000BASE-X SFP Module
            type-LS82O2CM(19),			-- ATM OC-3c/STM-1 Daughter Card (SFP)
            type-LS82P2CM(20),			-- POS OC-3c/STM-1 Daughter Card (SFP)
            type-LS82O4GM(21),			-- MPLS 1000BASE-X Daughter Card (GBIC)
            type-LS82GB4C(22),			-- 1000BASE-X Daughter Card (GBIC)
            type-LS82GT4C(23),			-- 1000BASE-T Daughter Card (RJ-45)
            type-LS82ST4C(24),			-- GigaStack Daughter Card
            bOARD-TYPE-LS82DSPU(25),		-- Dual Service Processing Module
            bOARD-TYPE-LS81GP8U(26),		-- Gigabit Ethernet Interface Process Module
            bOARD-TYPE-LS82GT20(27),		-- 1000BASE-T Module (RJ-45)
            bOARD-TYPE-LS82FE48(28),		-- 10/100BASE-TX Module (RJ-45)
            type-LS82T24B(29),			-- 24-Port 10/100BASE-TX (RJ-45) and 2 Port 1000BASE-X (GBIC) Module
            type-LSB1SRPA(30),			-- 
            type-LSB1FT48A(31),			-- 48-Port 10Base-T/100Base-TX Auto-sensing Fast Ethernet Board A
            type-LSB1FT48B(32),			-- 48-Port 10Base-T/100Base-TX Auto-sensing Fast Ethernet Board B
            type-LSB1F48GA(33),			-- 32-Port 10Base-T/100Base-TX Auto-sensing Fast Ethernet and 4-Port 1000Base-X (SFP) GE Board A
            type-LSB1F48GB(34),			-- 32-Port 10Base-T/100Base-TX Auto-sensing Fast Ethernet and 4-Port 1000Base-X (SFP) GE Board B
            type-LSB1FP20A(35),			-- 20-Port 100Base-FX (SFP) Fast Ethernet Board A
            type-LSB1FP20B(36),			-- 20-Port 100Base-FX (SFP) Fast Ethernet Board B
            type-FT48A(37),			-- 48-Port 10Base-T/100Base-TX Auto-sensing Fast Ethernet Interface Module
            type-GP4U(38),			-- 1000Base-X (SFP)  GE Interface Module
            type-GP2U(39),			-- 1000Base-X (SFP)  GE Interface Module
            type-TGX1A(40),			-- 10GBASE-R  (XENPAK) Interface Module
            type-1000BASE-LX-SM-IR-SC(41),	-- 1000M Ethernet Single Mode Optical Interface Module(1310nm,10km,SC)
            type-1000BASE-SX-MM-SR-SC(42),	-- 1000M Ethernet Multi-mode Optical Interface Module(850nm,500m,SC)
            type-1000BASE-T-RJ45(43),		-- 1000M Ethernet Copper Interface Module(RJ45)
            type-100BASE-FX-SM-IR-SC(44),	-- 100M Ethernet Single Mode Optical SubCard
            type-100BASE-FX-MM-SR-SC(45),	-- 100M Ethernet Multi-mode Optical SubCard
            type-GIGA-STACK-1M-PC(46),		-- GigaStack Daughter SubCard
            type-1000BASE-LX-SM-VLR-LC(47),	-- 1000M Ethernet Single Mode Optical SubCard(1550nm,70km,LC)
            type-1000BASE-LX-SM-LR-LC(48),	-- 1000M Ethernet Single Mode Optical SubCard(1550nm,40km,LC)
            type-100BASE-FX-SM-LR-SC(49),	-- 100M Ethernet Single Mode Optical SubCard(1310nm,15km,SC)
            type-1000BASE-X-GBIC(50),		-- 
            type-100M-SINGLEMODE-FX-LC(51),	-- 100M Ethernet Single-mode Optical SubCard(1310nm,2km,SC)
            type-100M-MULTIMODE-FX-LC(52),	-- 100M Ethernet Multi-mode Optical SubCard(1310nm,2km,SC)
            type-1000BASE-4SFP(53),		-- 4-Port 1000BASE-FX Single Mode Fiber Optic Transceivers LR with SC Connector
            type-1000BASE-4GBIC(54),		-- 4-Port 1000BASE-X Module(GBIC)
            type-1000BASE-FIXED-4SFP(55),	-- 4-Port 1000BASE-FX Single Mode Fiber Optic Transceivers LR with SC Connector
            type-1000BASE-FIXED-4GBIC(56),	-- 4-Port 1000BASE-X Module(GBIC)
            type-LSB1GP12A(57),			-- 12-Port 1000Base-X (SFP) GE Board A
            type-LSB1GP12B(58),			-- 12-Port 1000Base-X (SFP) GE Board B
            type-LSB1TGX1A(59),			-- 1-Port 10GBASE-R (XENPAK) Board A
            type-LSB1TGX1B(60),			-- 1-Port 10GBASE-R (XENPAK) Board B
            type-LSB1P4G8A(61),			-- 4*155M POS Optical Interface Module 8-Port 1000Base-X (SFP) GE and 4-Port 155M POS Board A
            type-LSB1P4G8B(62),			-- 4*155M POS Optical Interface Module 8-Port 1000Base-X (SFP) GE and 4-Port 155M POS Board B
            type-LSB1A4G8A(63),			-- 4*155M ATM Optical Interface Module 8-Port 1000Base-X (SFP) GE and 4-Port 155M ATM Board A
            type-LSB1A4G8B(64),			-- 4*155M ATM Optical Interface Module 8-Port 1000Base-X (SFP) GE and 4-Port 155M ATM Board B
            type-FT48C(65),			-- 48-Port 10Base-T/100Base-TX Auto-sensing Fast Ethernet Board C
            type-FP20(66),            		-- 20-port 100BASE-TX Module
            bOARD-TYPE-LS81FT48(67),		-- 48-Port 10/100BASE-TX Module (RJ-45)
            bOARD-TYPE-LS81GB8U(68),		-- 8-Port 1000BASE-X Module (GBIC)
            bOARD-TYPE-LS81GT8U(69),		-- 8-Port 1000BASE-T Module (RJ-45)
            bOARD-TYPE-LS81FS24(70),		-- 24-Port 100BASE-FX Module (SMF,MT-RJ)
            bOARD-TYPE-LS81FM24(71),		-- 24-Port 100BASE-FX Module (MMF,MT-RJ)
            bOARD-TYPE-LS82GP20(72),		-- Switching and Route Processing Board B (main board)
            type-LSB1SRPB(73),			-- 
            type-LSB1F32GA(74),			-- 32-Port Fast Ethernet + 4-Port Gigabit Ethernet module A
            type-LSB1F32GB(75),			-- 32-Port Fast Ethernet + 4-Port Gigabit Ethernet module B
            type-LSB2FT48A(76),			-- 48-Port 10Base-T/100Base-TX Auto-sensing Fast Ethernet Board A (ver 2)
            type-LSB2FT48B(77),			-- 48-Port 10Base-T/100Base-TX Auto-sensing Fast Ethernet Board B (ver 2)
            type-LSB1GT12A(78),			-- 12 Port 10/100/1000 Base-T  Interface Module
            type-LSB1GT12B(79),			-- 12 Port 10/100/1000 Base-T  Interface Module
            type-PC4U(80),			-- 4 Port155M POS(SFP) Interface Module
            type-FT32A(81),			-- 32 Port 10/100 Base-T FE Interface Module
            type-GT4U(82),			-- 4 Port 10/100/1000 Base-T  Interface Module
            bOARD-TYPE-LS83FP20A(83),		-- 
            bOARD-TYPE-LS82HGMU(84),		-- 
            type-LSB1GP8TB(85),			-- 
            type-LSB1GP8TC(86),			-- 
            type-LSB1GT8PB(87),			-- 
            type-LSB1GT8PC(88),			-- 
            type-LSB1FT48C(89),			-- 48-Port 100Base-TX Ethernet Interface module C
            type-LSB1FP20C(90),			-- 20-Port 100Base-FX(SFP) Fast Ethernet Interface Module C
            type-LSB1F32GC(91),			-- 32-Port Fast Ethernet + 4-Port Gigabit Ethernet interface module C
            type-LSB1GT12C(92),			-- 12-Port 10/100/1000 Base-T  Interface Module C
            type-LSB1GP12C(93),			-- 12-Port 1000Base-X(SFP) GE Interface Module C
            type-LSB1P4G8C(94),			-- 8-Port 1000Base-X(SFP) GE + 4-Port 155M POS Interface Module C
            type-LSB1TGX1C(95),			-- 1-Port 10GBase-R/X  Ethernet XENPAK Optical Interface Module C
            type-LSB1GT24B(96),			-- 24-Ports 10/100/1000Base-T Ethernet Interface Module B
            type-LSB1GT24C(97),			-- 24-Ports 10/100/1000Base-T Ethernet Interface Module C
            type-LSB1GP24B(98),			-- 24-Ports 1000Base-X Ethernet Interface Module B
            type-LSB1GP24C(99),			-- 24-Ports 1000Base-X Ethernet Interface Module C
            type-LSB1XP2B(100),			-- 2-Port 10GBase-R/W Ethernet XFP Optical Interface Module B
            type-LSB1XP2C(101),			-- 2-Port 10GBase-R/W Ethernet XFP Optical Interface Module C
            type-LSB1GV48B(102),		-- 48-Ports 10/100/1000Base-T Ethernet Interface Module B
            type-LSB1GV48C(103),		-- 48-Ports 10/100/1000Base-T Ethernet Interface Module C
            type-LSB1SRPC(104),			-- Switching and Route Processing Board C
            type-LSB1SRP1N0(105),		-- Switching and Route Processing Board 1N0
            type-LSB1SRP1N1(106),		-- Switching and Route Processing Board 1N1
            type-LSB1SRP1N2(107),		-- Switching and Route Processing Board 1N2
            type-GT24(108),			-- 
            type-GP24(109),			-- 
            type-XP2(110),			-- 
            type-GV48(111),			-- 
            type-LSG1GP8U(112),			-- 8 Port 1000BASE Module (SFP)
            type-LSG1GT8U(113),			-- 8 Port 1000BASE-T Module (RJ45)
            type-LSG1TG1U(114),			-- 1 Port 10GBASE Module(XENPAK)
            type-LSG1TD1U(115),			-- 1 Port 10GBASE-CX4 Module(IB4X)
            type-LSB2FT48C(116),		-- 48-Ports 100Base-TX Ethernet Interface module C
            type-LSB1GT48B(117),		-- 48-Ports 10/100/1000Base-T Ethernet Interface Module B
            type-LSB1GT48C(118),		-- 48-Ports 10/100/1000Base-T Ethernet Interface Module C
            type-LS81GT48(119),		        -- 48 Port Gigabit Ethernet Electric Interface Unit

            type-LS81SRPG0(120),		-- Salience III, Switch and Route Processing Board
            type-LS81SRPG1(121),		-- Salience III Plus
            type-LS81SRPG2(122),		-- Salience III Lite
            type-LS81SRPG3(123),		-- Salience III Edge

--          type-LS81SRPG(124),		         Switch And Route Processing Unit,Salience III. not used. not used.

            type-SR01SRPUB(125),                -- SR8812 Switching and Route Processing Unit
            type-SR01SRPUA(126),                -- SR8805 Switching and Route Processing Unit
            type-SR01GP12L(127),                -- 12-Port 1000Base-X Ethernet SFP Optical Interface Line Card(L)
            type-SR01GP12W(128),                -- 12-Port 1000Base-X Ethernet SFP Optical Interface Line Card(W)
            type-SR01FT48L(129),                -- 48-Port 10/100Base-TX Ethernet RJ45 Electrical Interface Line Card (L)
            type-SR01FT48W(130),                -- 48-Port 10/100Base-TX Ethernet RJ45 Electrical Interface Line Card (W)
            type-SR01XK1W(131),                 -- 1-Port 10GBase-R Ethernet XENPAK Optical Interface Line Card (W)
            type-SR01FP20W(132),                -- 20-Port 100Base-FX Ethernet SFP Optical Interface Line Card (W)
            type-SR01GT12W(133),                -- 12-Port 10/100/1000Base-T Ethernet RJ45 Electrical Interface Line Card (W)
            type-SR01F32GL(134),                -- 32-Port 10/100Base-TX Ethernet RJ45 Electrical Interface + 4-Port 1000Base-X Ethernet SFP Optical interface Line Card (L)
            type-SR01F32GW(135),                -- 32-Port 10/100Base-TX Ethernet RJ45 Electrical Interface  + 4-Port 1000Base-X  Ethernet SFP Optical interface Line Card (W)
            type-SR01GT8PL(136),                -- 8-Port 10/100/1000Base-T Ethernet RJ45 Electrical Interface + 4-Port 1000Base-X Ethernet SFP Optical Line Card (L)
            type-SR01GT8PW(137),                -- 8-Port 10/100/1000Base-T Ethernet RJ45 Electrical Interface + 4-Port 1000Base-X Ethernet SFP Optical Line Card (W)
            type-SR01P4G8W(138),                -- 4-Port 155M POS Optical Interface + 8-Port 1000Base-X Ethernet SFP Optical Interface Line Card (W)
            type-LSA1FP8U(139),                 -- 8 Ports 100Base-FX Ethernet SFP Card 

            type-LSB1SP4B(140),                 -- 4-Port OC-48 POS SFP Optical Interface Board B
            type-LSB1SP4C(141),                 -- 4-Port OC-48 POS SFP Optical Interface Board C
            type-LSB1UP1B(142),                 -- 1-Port OC-192 POS XFP Optical Interface Board B
            type-LSB1UP1C(143),                 -- 1-Port OC-192 POS XFP Optical Interface Board C
            type-LSB1XP4B(144),                 -- 4-Port 10GBase Ethernet XFP Optical Interface Board B
            type-LSB1XP4C(145),                 -- 4-Port 10GBase Ethernet XFP Optical Interface Board C
            type-SP4(146),                      -- 4-Port OC-48 POS SFP Optical Interface Module
            type-UP1(147),                      -- 1-Port OC-192 POS XFP Optical Interface Module
            type-XP4(148),                      -- 4-Port 10GBase Ethernet XFP Optical Interface Module
            
            type-LS81VSNP(149),                 -- VerSatile Network Processing Board
            type-LS81T12P(150),                 -- 12-Port 1000Base-T Gigabit Ethernet Interface(RJ45)+4-Port 1000BASE-X  Gigabit Ethernet Optical Interface Board(SFP,LC)
            type-LS81P12T(151),                 -- 12-Port 1000BASE-X Gigabit Ethernet Optical Interface(SFP,LC)+4-Port 1000BASE-T Gigabit Ethernet Interface Board(RJ45)
            type-LS81GP8UB(152),                -- 8-Port 1000M Ethernet Optical Interface Board(SFP,LC),LC Connector
            type-LS81FT48E(153),                -- 48-Port 100M Ethernet Electrical Interface Switch Unit(RJ45)
            type-LS81GP4UB(154),                -- 4-Port 1000M Ethernet Optical Interface Board(SFP,LC)
            type-LS81GT8UE(155),                -- 8-Port 1000M Ethernet Electrical Interface Switch Unit (RJ45)
            type-LS81GT48A(156),                -- 48 Port Gigabit Ethernet Electric Interface Unit
            type-LS81FP48(157),                 -- 48 Port 100M Ethernet Optical Interface Board(SFP,LC)

            type-LSB1XK1B(158),                 -- 1-Port 10GBase-R Ethernet XENPAK Optical Interface Board B
            type-LSB1XK1C(159),                 -- 1-Port 10GBase-R Ethernet XENPAK Optical Interface Board C
            
            type-SR01SRPUC(160),                -- Switching and Route Processing Unit C
            type-SR01SRPUD(161),                -- Switching and Route Processing Unit D
            type-SR01SRPUE(162),                -- Switching and Route Processing Unit E
            
            type-LSB1SRP1N3(163),               -- Switching and Route Process Unit,Clock Module
            type-LSB1VP2B(164),                 -- 2*10G Resilient Packet Ring Interface Line Card (B)
            type-LSB1NATB(165),                 -- NAT Service Processing Card (B)
            type-LSB1VPNB(166),                 -- VPN Service Processing Card (B)

            type-LSGP8P(167),                   -- 8-Port 1000M SFP Module 
            type-LSXK1P(168),                   -- 1-Port 10G Xenpak Module
            type-LSXP2P(169),                   -- 2-Port 10G XFP Module

            type-LS81FT48F(170),                -- 48-Port 100M Ethernet Electrical Interface Switch Unit(RJ45)

            type-LS81PT8G(171),                 -- 8 Port 1000BASE-X Gigabit Passive Optical Line Interface Board
            type-LS81PT4G(172),                 -- 4 Port 1000BASE-X Gigabit Passive Optical Line Interface Board
                        
            type-LSSTK24G(173),                 -- 2-Port 24G Cascade Port Module
            
            type-LS82GT20A(174),                -- 20-Port 1000Base-T Gigabit Ethernet Electrical Interface Board(RJ45), BCM5697
            type-LS82GP20A(175),                -- 20-Port 1000BASE-X Gigabit Ethernet Optical Interface Board(SFP,LC), BCM5697
            type-LS81TGX1C(176),                -- 1-Port 10G Base-R Ethernet Board

            bOARD-TYPE-LS82SRPB(254),		-- 
            bORAD-TYPE-LS83SRPC(255),		-- 
            type-Main(256)			-- 
        }
        MAX-ACCESS     read-only
        STATUS     current
        DESCRIPTION
        "Slot type. BOM number is recommended. "
        ::= {hwLswSlotEntry 2}    
    
    hwLswSlotDesc    OBJECT-TYPE
        SYNTAX     DisplayString(SIZE(0..64))
        MAX-ACCESS     read-write   
        STATUS     current
        DESCRIPTION
        "Slot description"
        ::= {hwLswSlotEntry 3}    

    hwLswSlotCpuRatio     OBJECT-TYPE
        SYNTAX         INTEGER
        MAX-ACCESS     read-only
        STATUS         current
        DESCRIPTION
        "CPU ratio occupied by the slot at the accuracy of 1%, ranging from 1 to 100. O indicates no CPU occupied. "
        ::= {hwLswSlotEntry 4}    

    hwLswSlotPcbVersion    OBJECT-TYPE
    	SYNTAX       DisplayString (SIZE(0..64))
        MAX-ACCESS      read-only
        STATUS          current
        DESCRIPTION
        "Hardware version of the card"
        ::= {hwLswSlotEntry 5}
    
    hwLswSlotSoftwareVersion    OBJECT-TYPE
        SYNTAX               DisplayString (SIZE(0..64))
        MAX-ACCESS           read-only
        STATUS               current
        DESCRIPTION
        " Software version of the card"
        ::= {hwLswSlotEntry 6}  
    
    hwLswSubslotNumber    OBJECT-TYPE
        SYNTAX         INTEGER
        MAX-ACCESS     read-only
        STATUS     current
        DESCRIPTION
        "Sub slot on the card"
        ::= {hwLswSlotEntry 7}      

    hwLswSlotAdminStatus    OBJECT-TYPE
        SYNTAX           INTEGER
        {
            not-install (1),
            normal      (2),
            fault       (3),
            forbidden   (4)
        }
        MAX-ACCESS       read-only
        STATUS           current
        DESCRIPTION
        "Slot status"
        ::= {hwLswSlotEntry 8}

    hwLswSlotOperStatus    OBJECT-TYPE
        SYNTAX          INTEGER
        {
            disable (1),
            enable  (2),
            reset   (3),
            test    (4)
        } 
        MAX-ACCESS      read-write
        STATUS          current
        DESCRIPTION
        "Slot operation status"
        ::= {hwLswSlotEntry 9}
        
-- ==================================================================
-- 
-- sub slot information table
--
-- ==================================================================

    hwLswSubslotTable    OBJECT-TYPE
        SYNTAX     SEQUENCE OF HwLswSubslotEntry
        MAX-ACCESS     not-accessible
        STATUS     current
        DESCRIPTION
        "Subslot description table "
        ::= {hwLswSlotConf 4}

    hwLswSubslotEntry    OBJECT-TYPE
        SYNTAX     HwLswSubslotEntry
        MAX-ACCESS     not-accessible
        STATUS     current
        DESCRIPTION
        " Subslot description table entry"
        INDEX {
            hwLswFrameIndex,
            hwLswSlotIndex,
            hwLswSubslotIndex
        }
        ::= {hwLswSubslotTable 1}

   HwLswSubslotEntry ::= SEQUENCE
    {
        hwLswSubslotIndex       INTEGER,
        hwLswSubslotType        INTEGER,
        hwLswSubslotPortNum     INTEGER,        
        hwLswSubslotAdminStatus INTEGER,
        hwLswSubslotFirstIfIndex INTEGER
   }
   
   hwLswSubslotIndex      OBJECT-TYPE
        SYNTAX         INTEGER
        MAX-ACCESS     read-only
        STATUS         current
        DESCRIPTION
        "Subslot index"
        ::= {hwLswSubslotEntry 1}

-- value list of hwLswSubslotType are identical with the value list of hwLswSlotType.
    hwLswSubslotType      OBJECT-TYPE
        SYNTAX         INTEGER
        {
            type-NULL(0),			-- NULL
            type-10OR100M(1),			-- 10M/100M Ethernet Copper Interface Module
            type-1000BASE-LX-SM(2),		-- 1000BASE-X Module (SMF, LC)
            type-1000BASE-SX-MM(3),		-- 1000BASE-X Module (MMF, LC)
            type-1000BASE-TX(4),		-- 
            type-100M-SINGLEMODE-FX(5),		-- 100M Ethernet Single Mode Optical Interface Module
            type-100M-MULTIMODE-FX(6),		-- 100M Ethernet Multi-mode Optical Interface Module
            type-100M-100BASE-TX(7),		-- 100M Ethernet copper Interface Module(RJ45
            type-100M-HUB(8),			-- 100M Base-TX transportation Interface Module
            type-VDSL(9),			-- VDSL
            type-STACK(10),			-- GigaStack Module
            type-1000BASE-ZENITH-FX(11),	-- 1000M Ethernet Single Mode Optical Interface Module(1550nm,70km,LC)
            type-1000BASE-LONG-FX(12),		-- 1000M Ethernet Single Mode Optical Interface Module(1550nm,40km,LC)
            type-ADSL(13),			-- ADSL
            type-4T10OR100-4FX100SM(14),	-- 4-Port Single Mode Optical Interface and 4-Port 10M/100M Ethernet Interface Module
            type-4T10OR100-4FX100MM(15),	-- 4-Port Multi-mode Optical Interface and 4-Port 10M/100M Ethernet Interface Module
            type-VSPL(16),			-- VDSL Board
            type-ASPL(17),			-- ADSL Board
            type-1000M-SFP(18),			-- 1000BASE-X SFP Module
            type-LS82O2CM(19),			-- ATM OC-3c/STM-1 Daughter Card (SFP)
            type-LS82P2CM(20),			-- POS OC-3c/STM-1 Daughter Card (SFP)
            type-LS82O4GM(21),			-- MPLS 1000BASE-X Daughter Card (GBIC)
            type-LS82GB4C(22),			-- 1000BASE-X Daughter Card (GBIC)
            type-LS82GT4C(23),			-- 1000BASE-T Daughter Card (RJ-45)
            type-LS82ST4C(24),			-- GigaStack Daughter Card
            bOARD-TYPE-LS82DSPU(25),		-- Dual Service Processing Module
            bOARD-TYPE-LS81GP8U(26),		-- Gigabit Ethernet Interface Process Module
            bOARD-TYPE-LS82GT20(27),		-- 1000BASE-T Module (RJ-45)
            bOARD-TYPE-LS82FE48(28),		-- 10/100BASE-TX Module (RJ-45)
            type-LS82T24B(29),			-- 24-Port 10/100BASE-TX (RJ-45) and 2 Port 1000BASE-X (GBIC) Module
            type-LSB1SRPA(30),			-- 
            type-LSB1FT48A(31),			-- 48-Port 10Base-T/100Base-TX Auto-sensing Fast Ethernet Board A
            type-LSB1FT48B(32),			-- 48-Port 10Base-T/100Base-TX Auto-sensing Fast Ethernet Board B
            type-LSB1F48GA(33),			-- 32-Port 10Base-T/100Base-TX Auto-sensing Fast Ethernet and 4-Port 1000Base-X (SFP) GE Board A
            type-LSB1F48GB(34),			-- 32-Port 10Base-T/100Base-TX Auto-sensing Fast Ethernet and 4-Port 1000Base-X (SFP) GE Board B
            type-LSB1FP20A(35),			-- 20-Port 100Base-FX (SFP) Fast Ethernet Board A
            type-LSB1FP20B(36),			-- 20-Port 100Base-FX (SFP) Fast Ethernet Board B
            type-FT48A(37),			-- 48-Port 10Base-T/100Base-TX Auto-sensing Fast Ethernet Interface Module
            type-GP4U(38),			-- 1000Base-X (SFP)  GE Interface Module
            type-GP2U(39),			-- 1000Base-X (SFP)  GE Interface Module
            type-TGX1A(40),			-- 10GBASE-R  (XENPAK) Interface Module
            type-1000BASE-LX-SM-IR-SC(41),	-- 1000M Ethernet Single Mode Optical Interface Module(1310nm,10km,SC)
            type-1000BASE-SX-MM-SR-SC(42),	-- 1000M Ethernet Multi-mode Optical Interface Module(850nm,500m,SC)
            type-1000BASE-T-RJ45(43),		-- 1000M Ethernet Copper Interface Module(RJ45)
            type-100BASE-FX-SM-IR-SC(44),	-- 100M Ethernet Single Mode Optical SubCard
            type-100BASE-FX-MM-SR-SC(45),	-- 100M Ethernet Multi-mode Optical SubCard
            type-GIGA-STACK-1M-PC(46),		-- GigaStack Daughter SubCard
            type-1000BASE-LX-SM-VLR-LC(47),	-- 1000M Ethernet Single Mode Optical SubCard(1550nm,70km,LC)
            type-1000BASE-LX-SM-LR-LC(48),	-- 1000M Ethernet Single Mode Optical SubCard(1550nm,40km,LC)
            type-100BASE-FX-SM-LR-SC(49),	-- 100M Ethernet Single Mode Optical SubCard(1310nm,15km,SC)
            type-1000BASE-X-GBIC(50),		-- 
            type-100M-SINGLEMODE-FX-LC(51),	-- 100M Ethernet Single-mode Optical SubCard(1310nm,2km,SC)
            type-100M-MULTIMODE-FX-LC(52),	-- 100M Ethernet Multi-mode Optical SubCard(1310nm,2km,SC)
            type-1000BASE-4SFP(53),		-- 4-Port 1000BASE-FX Single Mode Fiber Optic Transceivers LR with SC Connector
            type-1000BASE-4GBIC(54),		-- 4-Port 1000BASE-X Module(GBIC)
            type-1000BASE-FIXED-4SFP(55),	-- 4-Port 1000BASE-FX Single Mode Fiber Optic Transceivers LR with SC Connector
            type-1000BASE-FIXED-4GBIC(56),	-- 4-Port 1000BASE-X Module(GBIC)
            type-LSB1GP12A(57),			-- 12-Port 1000Base-X (SFP) GE Board A
            type-LSB1GP12B(58),			-- 12-Port 1000Base-X (SFP) GE Board B
            type-LSB1TGX1A(59),			-- 1-Port 10GBASE-R (XENPAK) Board A
            type-LSB1TGX1B(60),			-- 1-Port 10GBASE-R (XENPAK) Board B
            type-LSB1P4G8A(61),			-- 4*155M POS Optical Interface Module 8-Port 1000Base-X (SFP) GE and 4-Port 155M POS Board A
            type-LSB1P4G8B(62),			-- 4*155M POS Optical Interface Module 8-Port 1000Base-X (SFP) GE and 4-Port 155M POS Board B
            type-LSB1A4G8A(63),			-- 4*155M ATM Optical Interface Module 8-Port 1000Base-X (SFP) GE and 4-Port 155M ATM Board A
            type-LSB1A4G8B(64),			-- 4*155M ATM Optical Interface Module 8-Port 1000Base-X (SFP) GE and 4-Port 155M ATM Board B
            type-FT48C(65),			-- 48-Port 10Base-T/100Base-TX Auto-sensing Fast Ethernet Board C
            type-FP20(66),            		-- 20-port 100BASE-TX Module
            bOARD-TYPE-LS81FT48(67),		-- 48-Port 10/100BASE-TX Module (RJ-45)
            bOARD-TYPE-LS81GB8U(68),		-- 8-Port 1000BASE-X Module (GBIC)
            bOARD-TYPE-LS81GT8U(69),		-- 8-Port 1000BASE-T Module (RJ-45)
            bOARD-TYPE-LS81FS24(70),		-- 24-Port 100BASE-FX Module (SMF,MT-RJ)
            bOARD-TYPE-LS81FM24(71),		-- 24-Port 100BASE-FX Module (MMF,MT-RJ)
            bOARD-TYPE-LS82GP20(72),		-- Switching and Route Processing Board B (main board)
            type-LSB1SRPB(73),			-- 
            type-LSB1F32GA(74),			-- 32-Port Fast Ethernet + 4-Port Gigabit Ethernet module A
            type-LSB1F32GB(75),			-- 32-Port Fast Ethernet + 4-Port Gigabit Ethernet module B
            type-LSB2FT48A(76),			-- 48-Port 10Base-T/100Base-TX Auto-sensing Fast Ethernet Board A (ver 2)
            type-LSB2FT48B(77),			-- 48-Port 10Base-T/100Base-TX Auto-sensing Fast Ethernet Board B (ver 2)
            type-LSB1GT12A(78),			-- 12 Port 10/100/1000 Base-T  Interface Module
            type-LSB1GT12B(79),			-- 12 Port 10/100/1000 Base-T  Interface Module
            type-PC4U(80),			-- 4 Port155M POS(SFP) Interface Module
            type-FT32A(81),			-- 32 Port 10/100 Base-T FE Interface Module
            type-GT4U(82),			-- 4 Port 10/100/1000 Base-T  Interface Module
            bOARD-TYPE-LS83FP20A(83),		-- 
            bOARD-TYPE-LS82HGMU(84),		-- 
            type-LSB1GP8TB(85),			-- 
            type-LSB1GP8TC(86),			-- 
            type-LSB1GT8PB(87),			-- 
            type-LSB1GT8PC(88),			-- 
            type-LSB1FT48C(89),			-- 48-Port 100Base-TX Ethernet Interface module C
            type-LSB1FP20C(90),			-- 20-Port 100Base-FX(SFP) Fast Ethernet Interface Module C
            type-LSB1F32GC(91),			-- 32-Port Fast Ethernet + 4-Port Gigabit Ethernet interface module C
            type-LSB1GT12C(92),			-- 12-Port 10/100/1000 Base-T  Interface Module C
            type-LSB1GP12C(93),			-- 12-Port 1000Base-X(SFP) GE Interface Module C
            type-LSB1P4G8C(94),			-- 8-Port 1000Base-X(SFP) GE + 4-Port 155M POS Interface Module C
            type-LSB1TGX1C(95),			-- 1-Port 10GBase-R/X  Ethernet XENPAK Optical Interface Module C
            type-LSB1GT24B(96),			-- 24-Ports 10/100/1000Base-T Ethernet Interface Module B
            type-LSB1GT24C(97),			-- 24-Ports 10/100/1000Base-T Ethernet Interface Module C
            type-LSB1GP24B(98),			-- 24-Ports 1000Base-X Ethernet Interface Module B
            type-LSB1GP24C(99),			-- 24-Ports 1000Base-X Ethernet Interface Module C
            type-LSB1XP2B(100),			-- 2-Port 10GBase-R/W Ethernet XFP Optical Interface Module B
            type-LSB1XP2C(101),			-- 2-Port 10GBase-R/W Ethernet XFP Optical Interface Module C
            type-LSB1GV48B(102),		-- 48-Ports 10/100/1000Base-T Ethernet Interface Module B
            type-LSB1GV48C(103),		-- 48-Ports 10/100/1000Base-T Ethernet Interface Module C
            type-LSB1SRPC(104),			-- Switching and Route Processing Board C
            type-LSB1SRP1N0(105),		-- Switching and Route Processing Board 1N0
            type-LSB1SRP1N1(106),		-- Switching and Route Processing Board 1N1
            type-LSB1SRP1N2(107),		-- Switching and Route Processing Board 1N2
            type-GT24(108),			-- 
            type-GP24(109),			-- 
            type-XP2(110),			-- 
            type-GV48(111),			-- 
            type-LSG1GP8U(112),			-- 8 Port 1000BASE Module (SFP)
            type-LSG1GT8U(113),			-- 8 Port 1000BASE-T Module (RJ45)
            type-LSG1TG1U(114),			-- 1 Port 10GBASE Module(XENPAK)
            type-LSG1TD1U(115),			-- 1 Port 10GBASE-CX4 Module(IB4X)
            type-LSB2FT48C(116),		-- 48-Ports 100Base-TX Ethernet Interface module C
            type-LSB1GT48B(117),		-- 48-Ports 10/100/1000Base-T Ethernet Interface Module B
            type-LSB1GT48C(118),		-- 48-Ports 10/100/1000Base-T Ethernet Interface Module C
            type-LS81GT48(119),		        -- 48 Port Gigabit Ethernet Electric Interface Unit

            type-LS81SRPG0(120),		-- Salience III, Switch and Route Processing Board
            type-LS81SRPG1(121),		-- Salience III Plus
            type-LS81SRPG2(122),		-- Salience III Lite
            type-LS81SRPG3(123),		-- Salience III Edge

--          type-LS81SRPG(124),		         Switch And Route Processing Unit,Salience III.

            type-SR01SRPUB(125),                -- SR8812 Switching and Route Processing Unit
            type-SR01SRPUA(126),                -- SR8805 Switching and Route Processing Unit
            type-SR01GP12L(127),                -- 12-Port 1000Base-X Ethernet SFP Optical Interface Line Card(L)
            type-SR01GP12W(128),                -- 12-Port 1000Base-X Ethernet SFP Optical Interface Line Card(W)
            type-SR01FT48L(129),                -- 48-Port 10/100Base-TX Ethernet RJ45 Electrical Interface Line Card (L)
            type-SR01FT48W(130),                -- 48-Port 10/100Base-TX Ethernet RJ45 Electrical Interface Line Card (W)
            type-SR01XK1W(131),                 -- 1-Port 10GBase-R Ethernet XENPAK Optical Interface Line Card (W)
            type-SR01FP20W(132),                -- 20-Port 100Base-FX Ethernet SFP Optical Interface Line Card (W)
            type-SR01GT12W(133),                -- 12-Port 10/100/1000Base-T Ethernet RJ45 Electrical Interface Line Card (W)
            type-SR01F32GL(134),                -- 32-Port 10/100Base-TX Ethernet RJ45 Electrical Interface + 4-Port 1000Base-X Ethernet SFP Optical interface Line Card (L)
            type-SR01F32GW(135),                -- 32-Port 10/100Base-TX Ethernet RJ45 Electrical Interface  + 4-Port 1000Base-X  Ethernet SFP Optical interface Line Card (W)
            type-SR01GT8PL(136),                -- 8-Port 10/100/1000Base-T Ethernet RJ45 Electrical Interface + 4-Port 1000Base-X Ethernet SFP Optical Line Card (L)
            type-SR01GT8PW(137),                -- 8-Port 10/100/1000Base-T Ethernet RJ45 Electrical Interface + 4-Port 1000Base-X Ethernet SFP Optical Line Card (W)
            type-SR01P4G8W(138),                -- 4-Port 155M POS Optical Interface + 8-Port 1000Base-X Ethernet SFP Optical Interface Line Card (W)
            type-LSA1FP8U(139),                 -- 8 Ports 100Base-FX Ethernet SFP Card
            
            type-LSB1SP4B(140),                 -- 4-Port OC-48 POS SFP Optical Interface Board B
            type-LSB1SP4C(141),                 -- 4-Port OC-48 POS SFP Optical Interface Board C
            type-LSB1UP1B(142),                 -- 1-Port OC-192 POS XFP Optical Interface Board B
            type-LSB1UP1C(143),                 -- 1-Port OC-192 POS XFP Optical Interface Board C
            type-LSB1XP4B(144),                 -- 4-Port 10GBase Ethernet XFP Optical Interface Board B
            type-LSB1XP4C(145),                 -- 4-Port 10GBase Ethernet XFP Optical Interface Board C
            type-SP4(146),                      -- 4-Port OC-48 POS SFP Optical Interface Module
            type-UP1(147),                      -- 1-Port OC-192 POS XFP Optical Interface Module
            type-XP4(148),                      -- 4-Port 10GBase Ethernet XFP Optical Interface Module

            type-LS81VSNP(149),                 -- VerSatile Network Processing Board
            type-LS81T12P(150),                 -- 12-Port 1000Base-T Gigabit Ethernet Interface(RJ45)+4-Port 1000BASE-X  Gigabit Ethernet Optical Interface Board(SFP,LC)
            type-LS81P12T(151),                 -- 12-Port 1000BASE-X Gigabit Ethernet Optical Interface(SFP,LC)+4-Port 1000BASE-T Gigabit Ethernet Interface Board(RJ45)
            type-LS81GP8UB(152),                -- 8-Port 1000M Ethernet Optical Interface Board(SFP,LC),LC Connector
            type-LS81FT48E(153),                -- 48-Port 100M Ethernet Electrical Interface Switch Unit(RJ45)
            type-LS81GP4UB(154),                -- 4-Port 1000M Ethernet Optical Interface Board(SFP,LC)
            type-LS81GT8UE(155),                -- 8-Port 1000M Ethernet Electrical Interface Switch Unit (RJ45)
            type-LS81GT48A(156),                -- 48 Port Gigabit Ethernet Electric Interface Unit
            type-LS81FP48(157),                 -- 48 Port 100M Ethernet Optical Interface Board(SFP,LC)

            type-LSB1XK1B(158),                 -- 1-Port 10GBase-R Ethernet XENPAK Optical Interface Board B
            type-LSB1XK1C(159),                 -- 1-Port 10GBase-R Ethernet XENPAK Optical Interface Board C
            
            type-SR01SRPUC(160),                -- Switching and Route Processing Unit C
            type-SR01SRPUD(161),                -- Switching and Route Processing Unit D
            type-SR01SRPUE(162),                -- Switching and Route Processing Unit E

            type-LSB1SRP1N3(163),               -- Switching and Route Process Unit,Clock Module
            type-LSB1VP2B(164),                 -- 2*10G Resilient Packet Ring Interface Line Card (B)
            type-LSB1NATB(165),                 -- NAT Service Processing Card (B)
            type-LSB1VPNB(166),                 -- VPN Service Processing Card (B)

            type-LSGP8P(167),                   -- 8-Port 1000M SFP Module 
            type-LSXK1P(168),                   -- 1-Port 10G Xenpak Module
            type-LSXP2P(169),                   -- 2-Port 10G XFP Module

            type-LS81FT48F(170),                -- 48-Port 100M Ethernet Electrical Interface Switch Unit(RJ45)

            type-LS81PT8G(171),                 -- 8 Port 1000BASE-X Gigabit Passive Optical Line Interface Board
            type-LS81PT4G(172),                 -- 4 Port 1000BASE-X Gigabit Passive Optical Line Interface Board
            
            type-LSSTK24G(173),                 -- 2-Port 24G Cascade Port Module
            
            type-LS82GT20A(174),                -- 20-Port 1000Base-T Gigabit Ethernet Electrical Interface Board(RJ45), BCM5697
            type-LS82GP20A(175),                -- 20-Port 1000BASE-X Gigabit Ethernet Optical Interface Board(SFP,LC), BCM5697
            type-LS81TGX1C(176),                -- 1-Port 10G Base-R Ethernet Board

            bOARD-TYPE-LS82SRPB(254),		-- 
            bORAD-TYPE-LS83SRPC(255),		-- 
            type-Main(256)			-- 
        }
        MAX-ACCESS     read-only
        STATUS         current
        DESCRIPTION
        "Type of the pinch board in the subslot "
        ::= {hwLswSubslotEntry 2}
        
    hwLswSubslotPortNum   OBJECT-TYPE
        SYNTAX         INTEGER
        MAX-ACCESS     read-only
        STATUS         current
        DESCRIPTION
        "Number of physical ports in the pinch board"
        ::= {hwLswSubslotEntry 3}      
        
        
    hwLswSubslotAdminStatus    OBJECT-TYPE
        SYNTAX              INTEGER
        {
            not-install (1),
            normal      (2),
            fault       (3),
            forbidden   (4)        
        }
        MAX-ACCESS          read-only
        STATUS              current
        DESCRIPTION
        "Status of the pinch board in the subslot"
        ::= {hwLswSubslotEntry 4}
        
    hwLswSubslotFirstIfIndex   OBJECT-TYPE
        SYNTAX         INTEGER
        MAX-ACCESS     read-only
        STATUS         current
        DESCRIPTION
        " ifIndex of the first physical port in the pinch board"
        ::= {hwLswSubslotEntry 5}                  
-- ==================================================================
--
-- port information table 
--
-- ==================================================================

    hwLswPortTable    OBJECT-TYPE
        SYNTAX     SEQUENCE OF HwLswPortEntry
        MAX-ACCESS     not-accessible
        STATUS     current
        DESCRIPTION
        "Port configuration table"
        ::= {hwLswSlotConf 5}

    hwLswPortEntry    OBJECT-TYPE
        SYNTAX     HwLswPortEntry
        MAX-ACCESS     not-accessible
        STATUS     current
        DESCRIPTION
        " Port configuration table entry"
        INDEX {
            hwLswFrameIndex,
            hwLswSlotIndex,
            hwLswSubslotIndex,
            hwLswPortIndex
        }
        ::= {hwLswPortTable 1}

    HwLswPortEntry ::= SEQUENCE
    {
        hwLswPortIndex             INTEGER,
        hwLswPortType              INTEGER,
        hwLswPortIfindex           INTEGER,
        hwLswPortIsPlugged         INTEGER
     }

    hwLswPortIndex    OBJECT-TYPE
        SYNTAX     INTEGER
        MAX-ACCESS     read-only
        STATUS     current
        DESCRIPTION
        "The port number on the device. 1~ is the first port number, which is reserved if the port does not exit."
        ::= {hwLswPortEntry 1}
        
    hwLswPortType   OBJECT-TYPE
        SYNTAX     INTEGER
        {
            type-NULL(0),			-- NULL
            type-10OR100M(1),			-- 10BASE-T or 100BASE-TX  Electrical Interface
            type-1000BASE-LX-SM(2),		-- 1000BASE-LX Single Mode Fiber Optic Transceivers IR
            type-1000BASE-SX-MM(3),		-- 1000BASE-SX Multi Mode Fiber Optic Transceivers SR
            type-1000BASE-TX(4),		-- 1000BASE-T Electrical Interface
            type-100M-SINGLEMODE-FX(5),		-- 100BASE-FX Single Mode Fiber Optic Transceivers
            type-100M-MULTIMODE-FX(6),		-- 100BASE-FX Multi Mode Fiber Optic Transceivers
            type-100M-100BASE-TX(7),		-- 100BASE-TX Electrical Interface
            type-100M-HUB(8),			-- 100M HUB
            type-VDSL(9),			-- Very High Speed DSL
            type-STACK(10),			-- Gigabit STACK
            type-1000BASE-ZENITH-FX(11),	-- 1000BASE-LX Single Mode Fiber Optic Transceivers VLR
            type-1000BASE-LONG-FX(12),		-- 1000BASE-LX Single Mode Fiber Optic Transceivers LR
            type-ADSL(13),			-- Asymmetric Digital Subscriber Line
            type-10OR100M-db(14),		-- 10/100M ethernet electric port,each RJ-45 has 2 ethernet ports
            type-10GBASE-LR-SM(15),		-- 10GBASE-LR  Single Mode Fiber Optic Transceivers
            type-10GBASE-LX4-MM(16),		-- 10GBASE-LX4 Multi Mode Fiber Optic Transceivers
            type-10GBASE-LX4-SM(17),		-- 10GBASE-LX4 Single Mode Fiber Optic Transceivers
            type-100M-LONG-FX(18),		-- 100BASE-FX Single Mode Fiber Optic Transceivers LR SC
            type-1000BASE-CX(19),		-- 1000BASE-CX
            type-1000BASE-ZENITH-FX-LC(20),	-- 1000BASE-LX Single Mode Fiber Optic Transceivers VLR with LC Connector
            type-1000BASE-LONG-FX-LC(21),	-- 1000BASE-LX Single Mode Fiber Optic Transceivers LR with LC Connector
            type-100M-SM-FX-SC(22),		-- 100BASE-FX Single Mode Fiber Optic Transceivers with SC Connector
            type-100M-MM-FX-SC(23),		-- 100BASE-FX Multi Mode Fiber Optic Transceivers with SC Connector
            type-100M-SM-FX-LC(24),		-- 100BASE-FX Single Mode Fiber Optic Transceivers with LC Connector
            type-100M-MM-FX-LC(25),		-- 100BASE-FX Multi Mode Fiber Optic Transceivers with LC Connector
            type-GBIC-NO-CONNECTOR(26),		-- 
            type-GBIC-1000-BASE-T(27),		-- 
            type-GBIC-1000-BASE-LX(28),		-- 
            type-GBIC-1000-BASE-SX(29),		-- 
            type-GBIC-1000-BASE-ZX(30),		-- 
            type-COMBO-NO-CONNECTOR(31),	-- 
            type-COMBO-1000-BASE-LX(32),	-- 
            type-COMBO-1000-BASE-LX-FIBER(33),	-- 
            type-COMBO-1000-BASE-LX-COPPER(34),	-- 
            type-COMBO-1000-BASE-SX(35),	-- 
            type-COMBO-1000-BASE-SX-FIBER(36),	-- 
            type-COMBO-1000-BASE-SX-COPPER(37),	-- 
            type-COMBO-1000-BASE-ZX(38),	-- 
            type-COMBO-1000-BASE-ZX-FIBER(39),	-- 
            type-COMBO-1000-BASE-ZX-COPPER(40),	-- 
            type-155-POS-SX-MMF(41),		-- 
            type-155-POS-LX-SMF(42),		-- 
            type-1000BASE-T(43),		-- 1000 Base-T Port
            type-1000BASE-SX-SFP(44),		-- 1000 Base-SX SFP Port
            type-1000BASE-LX-SFP(45),		-- 1000 Base-SX SFP Port
            type-1000BASE-T-AN-SFP(46),		-- 1000 Base-T AN SFP Port
            type-10GBASE-LX4-XENPAK(47),	-- 10G Base-LX4 XENPAK Port
            type-10GBASE-LR-XENPAK(48),		-- 10G Base-LR XENPAK Port
            type-10GBASE-CX4(49),		-- 10G Base-CX4 Port
            type-1000BASE-ZX-SFP(50),           -- 1000 Base-ZX SFP Port
            type-1000BASE-MM-SFP(51),           -- 1000 Base-MM SFP Port
            type-100BASE-SX-SFP(52),            -- 100 Base-SX SFP Port
            type-100BASE-LX-SFP(53),            -- 100 Base-LX SFP Port
            type-100BASE-T-AN-SFP(54),          -- 100 Base-T SFP Port
            type-100BASE-ZX-SFP(55),            -- 100 Base-ZX SFP Port
            type-100BASE-MM-SFP(56),            -- 100 Base-MM SFP Port
            type-SFP-NO-CONNECTOR(57),          -- No Connector SFP Port 
            type-SFP-UNKNOWN-CONNECTOR(58),     --  Unknown SFP Port
            type-POS-NO-CONNECTOR(59),          -- POS no connector
            type-10G-BASE-SR(60),               -- 10GBASE-SR Fiber Optic Transceivers with SC Connector
            type-10G-BASE-ER(61),               -- 10GBASE-ER Fiber Optic Transceivers with SC Connector
            type-10G-BASE-LX4(62),              -- 10GBASE-LX4 Fiber Optic Transceivers with SC Connector
            type-10G-BASE-SW(63),               -- 10GBASE-SW Fiber Optic Transceivers with SC Connector
            type-10G-BASE-LW(64),               -- 10GBASE-LW Fiber Optic Transceivers with SC Connector
            type-10G-BASE-EW(65),               -- 10GBASE-EW Fiber Optic Transceivers with SC Connector
            type-10G-LR-SM-LC(66),              -- 10GBASE-LR Single Mode Fiber Optic Transceivers with LC Connector
            type-10G-SR-MM-LC(67),              -- 10GBASE-SR Multi Mode Fiber Optic Transceivers with LC Connector
            type-10G-ER-SM-LC(68),              -- 10GBASE-ER Single Mode Fiber Optic Transceivers with LC Connector
            type-10G-LW-SM-LC(69),              -- 10GBASE-LW Single Mode Fiber Optic Transceivers with LC Connector
            type-10G-SW-MM-LC(70),              -- 10GBASE-SW Multi Mode Fiber Optic Transceivers with LC Connector
            type-10G-EW-SM-LC(71),              -- 10GBASE-EW Single Mode Fiber Optic Transceivers with LC Connector

            type-100BASE-SM-MTRJ(72),           -- 100 Base-SM MTRJ Port
            type-100BASE-MM-MTRJ(73),           -- 100 Base-MM MTRJ Port

            type-XFP-NO-CONNECTOR(74),          -- XFP without Transceiver       
            type-XFP-10GBASE-SR(75),            -- 10GBASE-SR XFP Transceiver    
            type-XFP-10GBASE-LR(76),            -- 10GBASE-LR XFP Transceiver    
            type-XFP-10GBASE-ER(77),            -- 10GBASE-ER XFP Transceiver    
            type-XFP-10GBASE-SW(78),            -- 10GBASE-SW XFP Transceiver    
            type-XFP-10GBASE-LW(79),            -- 10GBASE-LW XFP Transceiver    
            type-XFP-10GBASE-EW(80),            -- 10GBASE-EW XFP Transceiver    
            type-XFP-10GBASE-CX4(81),           -- 10GBASE-CX4 XFP Transceiver   
            type-XFP-10GBASE-LX4(82),           -- 10GBASE-LX4 XFP Transceiver   
            type-XFP-UNKNOWN(83),               -- Unknown  XFP Transceiver      
                                      
            type-XPK-NOCONNECTOR(84),           -- Xenpak without Transceiver    
            type-XPK-10GBASE-SR(85),            -- 10GBASE-SR Xenpak Transceiver 
            type-XPK-10GBASE-LR(86),            -- 10GBASE-LR Xenpak Transceiver 
            type-XPK-10GBASE-ER(87),            -- 10GBASE-ER Xenpak Transceiver 
            type-XPK-10GBASE-SW(88),            -- 10GBASE-SW Xenpak Transceiver 
            type-XPK-10GBASE-LW(89),            -- 10GBASE-LW Xenpak Transceiver 
            type-XPK-10GBASE-EW(90),            -- 10GBASE-EW Xenpak Transceiver 
            type-XPK-10GBASE-CX4(91),           -- 10GBASE-CX4 Xenpak Transceiver
            type-XPK-10GBASE-LX4(92),           -- 10GBASE-LX4 Xenpak Transceiver
            type-XPK-UNKNOWN(93),               -- Unknown Xenpak Transceiver

            type-POS-OC48-SR-SM-LC(94),         -- OC48-SR Single Mode Fiber Optic Transceivers with LC Connector
            type-POS-OC48-IR-SM-LC(95),         -- OC48-IR Single Mode Fiber Optic Transceivers with LC Connector
            type-POS-OC48-LR-SM-LC(96),         -- OC48-LR Single Mode Fiber Optic Transceivers with LC Connector
            
            type-10G-BASE-CX4(97),              -- 10G BASE-CX4 Electrical Interface 

            type-OLT-1000BASE-BX-SFF-SC(98),    -- 1000 BASE-BX SFF SC OLT Port
            type-ONU-1000BASE-BX-SFF-SC(99),    -- 1000 BASE-BX SFF SC ONU Port

            type-24G-CASCADE(100)               -- 24G Cascade port
        }
            
        MAX-ACCESS     read-only
        STATUS     current
        DESCRIPTION
        "Normally the port type is the same as its card type. When there are different types of ports in one card, use the actual port type. "
        ::= {hwLswPortEntry 2}    

        
     hwLswPortIfindex OBJECT-TYPE
        SYNTAX     INTEGER
        MAX-ACCESS     read-only
        STATUS     current
        DESCRIPTION
        " ifIndex (ifTable) corresponding to the port"
        ::= {hwLswPortEntry 3}
     
     
     hwLswPortIsPlugged   OBJECT-TYPE
        SYNTAX     INTEGER
        {
            unplugged(0),
            plugged(1)
        }
            
        MAX-ACCESS     read-only
        STATUS     current
        DESCRIPTION
        "Port is plugged or not:  unplugged(0)   plugged(1)"
        ::= {hwLswPortEntry 4}
        
        
-- ==================================================================
--
-- port loopback test table 
--
-- ==================================================================

    hwLswPortLoopbackTable    OBJECT-TYPE
        SYNTAX     SEQUENCE OF HwLswPortLoopbackEntry
        MAX-ACCESS     not-accessible
        STATUS     current
        DESCRIPTION
        "Port loopback test table."
        ::= {hwLswSlotConf 6}

    hwLswPortLoopbackEntry  OBJECT-TYPE
        SYNTAX     HwLswPortLoopbackEntry
        MAX-ACCESS     not-accessible
        STATUS     current
        DESCRIPTION
        " Port loopback test table entry."
      AUGMENTS    {hwLswPortEntry }   
      ::= {hwLswPortLoopbackTable 1}
      
    HwLswPortLoopbackEntry ::= SEQUENCE
    {
        hwLswPortLoopbackIsSupport        INTEGER,
        hwLswPortLoopbackOperate          INTEGER,
        hwLswPortLoopbackResult           INTEGER,
    	hwLswPortLoopbackAutoStopSupport  INTEGER,
        hwLswPortLoopbackRemoteResult     INTEGER,
	hwLswPortLoopbackLocalResult      INTEGER,        
	hwLswPortLoopbackInternalResult   INTEGER,	
	hwLswPortLoopbackExternalResult   INTEGER	
     }
     
      hwLswPortLoopbackIsSupport  OBJECT-TYPE
        SYNTAX     INTEGER
        {
            neither(1),
            both(2),
            internalOnly(3),
            externalOnly(4)
        }
        MAX-ACCESS  read-only
        STATUS      current
        DESCRIPTION
        "The loopback type can be supported by current port."
        ::= {hwLswPortLoopbackEntry 1}        
 
    hwLswPortLoopbackOperate OBJECT-TYPE
        SYNTAX     INTEGER
        {
            stopRemoteOrLocalLoopBack(0),
            internalLoopback(1),
            externalLoopback(2),
            remoteLoopback(3),
            localLoopback(4)
        }
        MAX-ACCESS     read-write
        STATUS     current
        DESCRIPTION
        "Port loopback operate type. Read operation not supported."
        ::= {hwLswPortLoopbackEntry 2}

     hwLswPortLoopbackResult OBJECT-TYPE
        SYNTAX     INTEGER
        {
            testing (0),
            testok (1),
            testfailed (2)
        }            
        MAX-ACCESS     read-only
        STATUS     current
        DESCRIPTION
        "The loopback test result of the port, used for checking if the test is successful. Only after the testing will the query value on the node make sense. "
        ::= {hwLswPortLoopbackEntry 3}        
   
      hwLswPortLoopbackAutoStopSupport  OBJECT-TYPE
        SYNTAX     INTEGER
        {
            support(1),
            notSupport(2)
        }
        MAX-ACCESS  read-only
        STATUS      current
        DESCRIPTION
        "Whether this port support NEED-MANNUL-NOLOOP mode or not."
        ::= {hwLswPortLoopbackEntry 4}   
             
     hwLswPortLoopbackRemoteResult OBJECT-TYPE
        SYNTAX     INTEGER
        {
            loopbackTestInit(0),
            loopbackTesting(1),
            loopbackTestSuccessed (2),
            loopbackTestFailed (3),
            loopbackTestTestAndFailed (4)
        }            
        MAX-ACCESS     read-write
        STATUS     current
        DESCRIPTION
        "The remote loopback test result of the port, used for checking if the test is successful. Only after the testing will the query value on the node make sense. "
        ::= {hwLswPortLoopbackEntry 5}   

     hwLswPortLoopbackLocalResult OBJECT-TYPE
        SYNTAX     INTEGER
        {
            loopbackTestInit(0),
            loopbackTesting(1),
            loopbackTestSuccessed (2),
            loopbackTestFailed (3),
            loopbackTestTestAndFailed (4)
        }            
        MAX-ACCESS     read-write
        STATUS     current
        DESCRIPTION
        "The local loopback test result of the port, used for checking if the test is successful. Only after the testing will the query value on the node make sense. "
        ::= {hwLswPortLoopbackEntry 6}   

     hwLswPortLoopbackInternalResult OBJECT-TYPE
        SYNTAX     INTEGER
        {
            loopbackTestInit(0),
            loopbackTesting(1),
            loopbackTestSuccessed (2),
            loopbackTestFailed (3),
            loopbackTestTestAndFailed (4)
        }            
        MAX-ACCESS     read-write
        STATUS     current
        DESCRIPTION
        "The internal loopback test result of the port, used for checking if the test is successful. Only after the testing will the query value on the node make sense. "
        ::= {hwLswPortLoopbackEntry 7}  

     hwLswPortLoopbackExternalResult OBJECT-TYPE
        SYNTAX     INTEGER
        {
            loopbackTestInit(0),
            loopbackTesting(1),
            loopbackTestSuccessed (2),
            loopbackTestFailed (3),
            loopbackTestTestAndFailed (4)
        }            
        MAX-ACCESS     read-write
        STATUS     current
        DESCRIPTION
        "The external loopback test result of the port, used for checking if the test is successful. Only after the testing will the query value on the node make sense. "
        ::= {hwLswPortLoopbackEntry 8}                               
END
