--
-- CAREL-nrl.MIB
-- MIB generated by CAREL
-- Friday, 10 May 2019
--

    CAREL-nrl-MIB DEFINITIONS ::= BEGIN
 
		IMPORTS
			OBJECT-GROUP
				FROM SNMPv2-CONF			
			sysContact, sysName, sysLocation			
				FROM SNMPv2-MIB
			enterprises, MODULE-IDENTITY, OBJECT-TYPE, Integer32			
				FROM SNMPv2-SMI
			DisplayString
				FROM SNMPv2-TC;
		
        nrlMIB MODULE-IDENTITY
      		LAST-UPDATED  "201905101126Z"		-- May 10, 2019 at 11:26 GMT
      		ORGANIZATION  "CAREL Industries S.r.l."
      		CONTACT-INFO
                "
                        Carel Industries S.r.l.
                        Via dell'Industria, 11
                        35020 Brugine (PD) Italy
                        Tel: +39 049 9716611
                        E-mail: carel@carel.com
                "
      		DESCRIPTION
                "This is the MIB module for the nrl device."
			REVISION "201905101126Z"
			DESCRIPTION
				"version4pCOweb"
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
   			DESCRIPTION "Code of the Agent. 2=pCOWeb."
		::= { systm 2 }
		
		-- 1.3.6.1.4.1.9839.2
		instruments OBJECT IDENTIFIER ::= { carel 2 }
		
		-- 1.3.6.1.4.1.9839.2.0
 		pCOWebInfo OBJECT IDENTIFIER ::= { instruments 0 }
		

		-- 1.3.6.1.4.1.9839.2.0.10
		pCOStatusgroup OBJECT IDENTIFIER ::= { pCOWebInfo 10 }
		
		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }
		
		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.

	-- 1.3.6.1.4.1.9839.2.1.1
	digitalObjects OBJECT IDENTIFIER ::= { nrlMIB 1 }

        -- 1.3.6.1.4.1.9839.2.1.1.1
        sys-on OBJECT-TYPE
                    SYNTAX Integer32 (0..1)
                    UNITS "N/A"
                    MAX-ACCESS read-only
                    STATUS current
                    DESCRIPTION "Execute application's startup jump (0: normal execution; 1: apllication's jump)"
                    DEFVAL { 0 }
                    ::= { digitalObjects 1 }

        -- 1.3.6.1.4.1.9839.2.1.1.2
        bms-sumwin OBJECT-TYPE
                    SYNTAX Integer32 (0..1)
                    UNITS "N/A"
                    MAX-ACCESS read-write
                    STATUS current
                    DESCRIPTION "Supervisor (BMS) On-Off. Show the state OFFbyBMS in main mask (0: Off; 1: On)"
                    DEFVAL { 1 }
                    ::= { digitalObjects 2 }

        -- 1.3.6.1.4.1.9839.2.1.1.3
        reset-alarm OBJECT-TYPE
                    SYNTAX Integer32 (0..1)
                    UNITS "N/A"
                    MAX-ACCESS read-write
                    STATUS current
                    DESCRIPTION "Reset Alarms (1: reset) "
                    DEFVAL { 0 }
                    ::= { digitalObjects 3 }

        -- 1.3.6.1.4.1.9839.2.1.1.4
        din-on-off OBJECT-TYPE
                    SYNTAX Integer32 (0..1)
                    UNITS "N/A"
                    MAX-ACCESS read-only
                    STATUS current
                    DESCRIPTION "OnOff by digit input"
                    DEFVAL { 0 }
                    ::= { digitalObjects 4 }

        -- 1.3.6.1.4.1.9839.2.1.1.5
        din-cool-heat OBJECT-TYPE
                    SYNTAX Integer32 (0..1)
                    UNITS "N/A"
                    MAX-ACCESS read-only
                    STATUS current
                    DESCRIPTION "Cool/Heat change by DIN"
                    DEFVAL { 0 }
                    ::= { digitalObjects 5 }

        -- 1.3.6.1.4.1.9839.2.1.1.6
        richiestasanitaria OBJECT-TYPE
                    SYNTAX Integer32 (0..1)
                    UNITS "N/A"
                    MAX-ACCESS read-write
                    STATUS current
                    DESCRIPTION "Auto On Off (0: Off; 1: On)"
                    DEFVAL { 0 }
                    ::= { digitalObjects 6 }

        -- 1.3.6.1.4.1.9839.2.1.1.7
        cooling-heating OBJECT-TYPE
                    SYNTAX Integer32 (0..1)
                    UNITS "N/A"
                    MAX-ACCESS read-only
                    STATUS current
                    DESCRIPTION "Cool/Heat mode (0-Cooling; 1-Heating)"
                    DEFVAL { 0 }
                    ::= { digitalObjects 7 }

        -- 1.3.6.1.4.1.9839.2.1.1.8
        forzasolofreecooling OBJECT-TYPE
                    SYNTAX Integer32 (0..1)
                    UNITS "N/A"
                    MAX-ACCESS read-write
                    STATUS current
                    DESCRIPTION "N/A"
                    DEFVAL { 0 }
                    ::= { digitalObjects 8 }

        -- 1.3.6.1.4.1.9839.2.1.1.9
        bms-onoff-rec OBJECT-TYPE
                    SYNTAX Integer32 (0..1)
                    UNITS "N/A"
                    MAX-ACCESS read-write
                    STATUS current
                    DESCRIPTION "Supervisor (BMS) On-Off. Show the state OFFbyBMS in main mask (0: Off; 1: On)"
                    DEFVAL { 1 }
                    ::= { digitalObjects 9 }

        -- 1.3.6.1.4.1.9839.2.1.1.10
        bms-onoff-plant OBJECT-TYPE
                    SYNTAX Integer32 (0..1)
                    UNITS "N/A"
                    MAX-ACCESS read-write
                    STATUS current
                    DESCRIPTION "Supervisor (BMS) On-Off. Show the state OFFbyBMS in main mask (0: Off; 1: On)"
                    DEFVAL { 1 }
                    ::= { digitalObjects 10 }

        -- 1.3.6.1.4.1.9839.2.1.1.11
        autodiff-plant-en OBJECT-TYPE
                    SYNTAX Integer32 (0..1)
                    UNITS "N/A"
                    MAX-ACCESS read-write
                    STATUS current
                    DESCRIPTION "N/A"
                    DEFVAL { 0 }
                    ::= { digitalObjects 11 }

        -- 1.3.6.1.4.1.9839.2.1.1.12
        type-set-cool-plant OBJECT-TYPE
                    SYNTAX Integer32 (0..1)
                    UNITS "N/A"
                    MAX-ACCESS read-write
                    STATUS current
                    DESCRIPTION "Enable setpoint compensation"
                    DEFVAL { 0 }
                    ::= { digitalObjects 12 }

        -- 1.3.6.1.4.1.9839.2.1.1.13
        type-set-heat-plant OBJECT-TYPE
                    SYNTAX Integer32 (0..1)
                    UNITS "N/A"
                    MAX-ACCESS read-write
                    STATUS current
                    DESCRIPTION "Enable setpoint compensation"
                    DEFVAL { 0 }
                    ::= { digitalObjects 13 }

        -- 1.3.6.1.4.1.9839.2.1.1.14
        type-set-rec OBJECT-TYPE
                    SYNTAX Integer32 (0..1)
                    UNITS "N/A"
                    MAX-ACCESS read-write
                    STATUS current
                    DESCRIPTION "Enable setpoint compensation"
                    DEFVAL { 0 }
                    ::= { digitalObjects 14 }

        -- 1.3.6.1.4.1.9839.2.1.1.15
        req-pump-plant-by-modbus OBJECT-TYPE
                    SYNTAX Integer32 (0..1)
                    UNITS "N/A"
                    MAX-ACCESS read-write
                    STATUS current
                    DESCRIPTION "N/A"
                    DEFVAL { 0 }
                    ::= { digitalObjects 15 }

        -- 1.3.6.1.4.1.9839.2.1.1.16
        cod-write-nrc OBJECT-TYPE
                    SYNTAX Integer32 (0..1)
                    UNITS "N/A"
                    MAX-ACCESS read-write
                    STATUS current
                    DESCRIPTION "N/A"
                    DEFVAL { 0 }
                    ::= { digitalObjects 16 }

        -- 1.3.6.1.4.1.9839.2.1.1.17
        forceoff-configuratore OBJECT-TYPE
                    SYNTAX Integer32 (0..1)
                    UNITS "N/A"
                    MAX-ACCESS read-write
                    STATUS current
                    DESCRIPTION "Reset Alarms (1: reset) "
                    DEFVAL { 0 }
                    ::= { digitalObjects 17 }

        -- 1.3.6.1.4.1.9839.2.1.1.18
        keyboard-onoff-sys OBJECT-TYPE
                    SYNTAX Integer32 (0..1)
                    UNITS "N/A"
                    MAX-ACCESS read-write
                    STATUS current
                    DESCRIPTION "N/A"
                    DEFVAL { 0 }
                    ::= { digitalObjects 18 }

        -- 1.3.6.1.4.1.9839.2.1.1.19
        ovrl-compscirc2 OBJECT-TYPE
                    SYNTAX Integer32 (0..1)
                    UNITS "N/A"
                    MAX-ACCESS read-only
                    STATUS current
                    DESCRIPTION "N/A"
                    DEFVAL { 0 }
                    ::= { digitalObjects 19 }

        -- 1.3.6.1.4.1.9839.2.1.1.21
        autodiff-rec-en OBJECT-TYPE
                    SYNTAX Integer32 (0..1)
                    UNITS "N/A"
                    MAX-ACCESS read-write
                    STATUS current
                    DESCRIPTION "N/A"
                    DEFVAL { 0 }
                    ::= { digitalObjects 21 }

        -- 1.3.6.1.4.1.9839.2.1.1.22
        entermostatoremoto OBJECT-TYPE
                    SYNTAX Integer32 (0..1)
                    UNITS "N/A"
                    MAX-ACCESS read-write
                    STATUS current
                    DESCRIPTION "Power request"
                    DEFVAL { 0 }
                    ::= { digitalObjects 22 }

        -- 1.3.6.1.4.1.9839.2.1.1.23
        en-fahrenheit-bms OBJECT-TYPE
                    SYNTAX Integer32 (0..1)
                    UNITS "N/A"
                    MAX-ACCESS read-write
                    STATUS current
                    DESCRIPTION "Unit of measure type (0: Standard (_C - barg); Anglo-saxon (_F - psig))"
                    DEFVAL { 0 }
                    ::= { digitalObjects 23 }

        -- 1.3.6.1.4.1.9839.2.1.1.24
        monocircuito OBJECT-TYPE
                    SYNTAX Integer32 (0..1)
                    UNITS "N/A"
                    MAX-ACCESS read-write
                    STATUS current
                    DESCRIPTION "N/A"
                    DEFVAL { 0 }
                    ::= { digitalObjects 24 }

        -- 1.3.6.1.4.1.9839.2.1.1.25
        bicircuito OBJECT-TYPE
                    SYNTAX Integer32 (0..1)
                    UNITS "N/A"
                    MAX-ACCESS read-write
                    STATUS current
                    DESCRIPTION "N/A"
                    DEFVAL { 0 }
                    ::= { digitalObjects 25 }

        -- 1.3.6.1.4.1.9839.2.1.1.26
        cod-write-nrl-default OBJECT-TYPE
                    SYNTAX Integer32 (0..1)
                    UNITS "N/A"
                    MAX-ACCESS read-write
                    STATUS current
                    DESCRIPTION "N/A"
                    DEFVAL { 0 }
                    ::= { digitalObjects 26 }

        -- 1.3.6.1.4.1.9839.2.1.1.27
        al-flow-glicolefree OBJECT-TYPE
                    SYNTAX Integer32 (0..1)
                    UNITS "N/A"
                    MAX-ACCESS read-only
                    STATUS current
                    DESCRIPTION "N/A"
                    DEFVAL { 0 }
                    ::= { digitalObjects 27 }

        -- 1.3.6.1.4.1.9839.2.1.1.28
        low-charge-rec OBJECT-TYPE
                    SYNTAX Integer32 (0..1)
                    UNITS "N/A"
                    MAX-ACCESS read-only
                    STATUS current
                    DESCRIPTION "N/A"
                    DEFVAL { 0 }
                    ::= { digitalObjects 28 }

        -- 1.3.6.1.4.1.9839.2.1.1.29
        low-charge-plant OBJECT-TYPE
                    SYNTAX Integer32 (0..1)
                    UNITS "N/A"
                    MAX-ACCESS read-only
                    STATUS current
                    DESCRIPTION "N/A"
                    DEFVAL { 0 }
                    ::= { digitalObjects 29 }

        -- 1.3.6.1.4.1.9839.2.1.1.30
        evap-pump1 OBJECT-TYPE
                    SYNTAX Integer32 (0..1)
                    UNITS "N/A"
                    MAX-ACCESS read-only
                    STATUS current
                    DESCRIPTION "Evaporator pump1"
                    DEFVAL { 0 }
                    ::= { digitalObjects 30 }

        -- 1.3.6.1.4.1.9839.2.1.1.31
        evap-pump2 OBJECT-TYPE
                    SYNTAX Integer32 (0..1)
                    UNITS "N/A"
                    MAX-ACCESS read-only
                    STATUS current
                    DESCRIPTION "Evaporator pump1"
                    DEFVAL { 0 }
                    ::= { digitalObjects 31 }

        -- 1.3.6.1.4.1.9839.2.1.1.32
        forzapompaoffdatermostato OBJECT-TYPE
                    SYNTAX Integer32 (0..1)
                    UNITS "N/A"
                    MAX-ACCESS read-write
                    STATUS current
                    DESCRIPTION "N/A"
                    DEFVAL { 0 }
                    ::= { digitalObjects 32 }

        -- 1.3.6.1.4.1.9839.2.1.1.33
        reset-alarm-bms OBJECT-TYPE
                    SYNTAX Integer32 (0..1)
                    UNITS "N/A"
                    MAX-ACCESS read-write
                    STATUS current
                    DESCRIPTION "Reset Alarms (1: reset) "
                    DEFVAL { 0 }
                    ::= { digitalObjects 33 }

        -- 1.3.6.1.4.1.9839.2.1.1.34
        pomparecupero OBJECT-TYPE
                    SYNTAX Integer32 (0..1)
                    UNITS "N/A"
                    MAX-ACCESS read-only
                    STATUS current
                    DESCRIPTION "Evaporator pump1"
                    DEFVAL { 0 }
                    ::= { digitalObjects 34 }

        -- 1.3.6.1.4.1.9839.2.1.1.35
        rec-pump2 OBJECT-TYPE
                    SYNTAX Integer32 (0..1)
                    UNITS "N/A"
                    MAX-ACCESS read-only
                    STATUS current
                    DESCRIPTION "Pompa recupero 1"
                    DEFVAL { 0 }
                    ::= { digitalObjects 35 }

        -- 1.3.6.1.4.1.9839.2.1.1.36
        comp1-circ1 OBJECT-TYPE
                    SYNTAX Integer32 (0..1)
                    UNITS "N/A"
                    MAX-ACCESS read-only
                    STATUS current
                    DESCRIPTION "Compressor1 circuit1 (0: Off; 1: On)"
                    DEFVAL { 0 }
                    ::= { digitalObjects 36 }

        -- 1.3.6.1.4.1.9839.2.1.1.37
        comp2-circ1 OBJECT-TYPE
                    SYNTAX Integer32 (0..1)
                    UNITS "N/A"
                    MAX-ACCESS read-only
                    STATUS current
                    DESCRIPTION "Compressor1 circuit1 (0: Off; 1: On)"
                    DEFVAL { 0 }
                    ::= { digitalObjects 37 }

        -- 1.3.6.1.4.1.9839.2.1.1.38
        comp3-circ1 OBJECT-TYPE
                    SYNTAX Integer32 (0..1)
                    UNITS "N/A"
                    MAX-ACCESS read-only
                    STATUS current
                    DESCRIPTION "Compressor1 circuit1 (0: Off; 1: On)"
                    DEFVAL { 0 }
                    ::= { digitalObjects 38 }

        -- 1.3.6.1.4.1.9839.2.1.1.39
        comp1-circ2 OBJECT-TYPE
                    SYNTAX Integer32 (0..1)
                    UNITS "N/A"
                    MAX-ACCESS read-only
                    STATUS current
                    DESCRIPTION "Compressor1 circuit1 (0: Off; 1: On)"
                    DEFVAL { 0 }
                    ::= { digitalObjects 39 }

        -- 1.3.6.1.4.1.9839.2.1.1.40
        comp2-circ2 OBJECT-TYPE
                    SYNTAX Integer32 (0..1)
                    UNITS "N/A"
                    MAX-ACCESS read-only
                    STATUS current
                    DESCRIPTION "Compressor1 circuit1 (0: Off; 1: On)"
                    DEFVAL { 0 }
                    ::= { digitalObjects 40 }

        -- 1.3.6.1.4.1.9839.2.1.1.41
        comp3-circ2 OBJECT-TYPE
                    SYNTAX Integer32 (0..1)
                    UNITS "N/A"
                    MAX-ACCESS read-only
                    STATUS current
                    DESCRIPTION "Compressor1 circuit1 (0: Off; 1: On)"
                    DEFVAL { 0 }
                    ::= { digitalObjects 41 }

        -- 1.3.6.1.4.1.9839.2.1.1.42
        cond-fan-group1 OBJECT-TYPE
                    SYNTAX Integer32 (0..1)
                    UNITS "N/A"
                    MAX-ACCESS read-only
                    STATUS current
                    DESCRIPTION "Condenser fan group1"
                    DEFVAL { 0 }
                    ::= { digitalObjects 42 }

        -- 1.3.6.1.4.1.9839.2.1.1.43
        cond-fan-group2 OBJECT-TYPE
                    SYNTAX Integer32 (0..1)
                    UNITS "N/A"
                    MAX-ACCESS read-only
                    STATUS current
                    DESCRIPTION "Condenser fan group1"
                    DEFVAL { 0 }
                    ::= { digitalObjects 43 }

        -- 1.3.6.1.4.1.9839.2.1.1.44
        vic-circ1 OBJECT-TYPE
                    SYNTAX Integer32 (0..1)
                    UNITS "N/A"
                    MAX-ACCESS read-only
                    STATUS current
                    DESCRIPTION "N/A"
                    DEFVAL { 0 }
                    ::= { digitalObjects 44 }

        -- 1.3.6.1.4.1.9839.2.1.1.45
        vic-circ2 OBJECT-TYPE
                    SYNTAX Integer32 (0..1)
                    UNITS "N/A"
                    MAX-ACCESS read-only
                    STATUS current
                    DESCRIPTION "N/A"
                    DEFVAL { 0 }
                    ::= { digitalObjects 45 }

        -- 1.3.6.1.4.1.9839.2.1.1.46
        vsl-circ1 OBJECT-TYPE
                    SYNTAX Integer32 (0..1)
                    UNITS "N/A"
                    MAX-ACCESS read-only
                    STATUS current
                    DESCRIPTION "N/A"
                    DEFVAL { 0 }
                    ::= { digitalObjects 46 }

        -- 1.3.6.1.4.1.9839.2.1.1.47
        vsl-circ2 OBJECT-TYPE
                    SYNTAX Integer32 (0..1)
                    UNITS "N/A"
                    MAX-ACCESS read-only
                    STATUS current
                    DESCRIPTION "N/A"
                    DEFVAL { 0 }
                    ::= { digitalObjects 47 }

        -- 1.3.6.1.4.1.9839.2.1.1.48
        antifrezzer-evap-dk OBJECT-TYPE
                    SYNTAX Integer32 (0..1)
                    UNITS "N/A"
                    MAX-ACCESS read-only
                    STATUS current
                    DESCRIPTION "N/A"
                    DEFVAL { 0 }
                    ::= { digitalObjects 48 }

        -- 1.3.6.1.4.1.9839.2.1.1.49
        din6-upc OBJECT-TYPE
                    SYNTAX Integer32 (0..1)
                    UNITS "N/A"
                    MAX-ACCESS read-only
                    STATUS current
                    DESCRIPTION "OnOff by digit input"
                    DEFVAL { 0 }
                    ::= { digitalObjects 49 }

        -- 1.3.6.1.4.1.9839.2.1.1.50
        valvola-vrt-c1 OBJECT-TYPE
                    SYNTAX Integer32 (0..1)
                    UNITS "N/A"
                    MAX-ACCESS read-only
                    STATUS current
                    DESCRIPTION "N/A"
                    DEFVAL { 0 }
                    ::= { digitalObjects 50 }

        -- 1.3.6.1.4.1.9839.2.1.1.51
        valvola-vrt-c2 OBJECT-TYPE
                    SYNTAX Integer32 (0..1)
                    UNITS "N/A"
                    MAX-ACCESS read-only
                    STATUS current
                    DESCRIPTION "N/A"
                    DEFVAL { 0 }
                    ::= { digitalObjects 51 }

        -- 1.3.6.1.4.1.9839.2.1.1.52
        valvola-vb-c1 OBJECT-TYPE
                    SYNTAX Integer32 (0..1)
                    UNITS "N/A"
                    MAX-ACCESS read-only
                    STATUS current
                    DESCRIPTION "N/A"
                    DEFVAL { 0 }
                    ::= { digitalObjects 52 }

        -- 1.3.6.1.4.1.9839.2.1.1.53
        valvola-vb-c2 OBJECT-TYPE
                    SYNTAX Integer32 (0..1)
                    UNITS "N/A"
                    MAX-ACCESS read-only
                    STATUS current
                    DESCRIPTION "N/A"
                    DEFVAL { 0 }
                    ::= { digitalObjects 53 }

        -- 1.3.6.1.4.1.9839.2.1.1.54
        valvola-vr-c1 OBJECT-TYPE
                    SYNTAX Integer32 (0..1)
                    UNITS "N/A"
                    MAX-ACCESS read-only
                    STATUS current
                    DESCRIPTION "N/A"
                    DEFVAL { 0 }
                    ::= { digitalObjects 54 }

        -- 1.3.6.1.4.1.9839.2.1.1.55
        valvola-vr-c2 OBJECT-TYPE
                    SYNTAX Integer32 (0..1)
                    UNITS "N/A"
                    MAX-ACCESS read-only
                    STATUS current
                    DESCRIPTION "N/A"
                    DEFVAL { 0 }
                    ::= { digitalObjects 55 }

        -- 1.3.6.1.4.1.9839.2.1.1.56
        vsbp-circ1 OBJECT-TYPE
                    SYNTAX Integer32 (0..1)
                    UNITS "N/A"
                    MAX-ACCESS read-only
                    STATUS current
                    DESCRIPTION "N/A"
                    DEFVAL { 0 }
                    ::= { digitalObjects 56 }

        -- 1.3.6.1.4.1.9839.2.1.1.57
        vsbp-circ2 OBJECT-TYPE
                    SYNTAX Integer32 (0..1)
                    UNITS "N/A"
                    MAX-ACCESS read-only
                    STATUS current
                    DESCRIPTION "N/A"
                    DEFVAL { 0 }
                    ::= { digitalObjects 57 }

        -- 1.3.6.1.4.1.9839.2.1.1.58
        valvolaritornooliodarecuperoc1 OBJECT-TYPE
                    SYNTAX Integer32 (0..1)
                    UNITS "N/A"
                    MAX-ACCESS read-only
                    STATUS current
                    DESCRIPTION "N/A"
                    DEFVAL { 0 }
                    ::= { digitalObjects 58 }

        -- 1.3.6.1.4.1.9839.2.1.1.59
        valvolaritornooliodarecuperoc2 OBJECT-TYPE
                    SYNTAX Integer32 (0..1)
                    UNITS "N/A"
                    MAX-ACCESS read-only
                    STATUS current
                    DESCRIPTION "N/A"
                    DEFVAL { 0 }
                    ::= { digitalObjects 59 }

        -- 1.3.6.1.4.1.9839.2.1.1.60
        gradinores1 OBJECT-TYPE
                    SYNTAX Integer32 (0..1)
                    UNITS "N/A"
                    MAX-ACCESS read-only
                    STATUS current
                    DESCRIPTION "N/A"
                    DEFVAL { 0 }
                    ::= { digitalObjects 60 }

        -- 1.3.6.1.4.1.9839.2.1.1.61
        gradinores2 OBJECT-TYPE
                    SYNTAX Integer32 (0..1)
                    UNITS "N/A"
                    MAX-ACCESS read-only
                    STATUS current
                    DESCRIPTION "N/A"
                    DEFVAL { 0 }
                    ::= { digitalObjects 61 }

        -- 1.3.6.1.4.1.9839.2.1.1.62
        pomparecuperoavviata OBJECT-TYPE
                    SYNTAX Integer32 (0..1)
                    UNITS "N/A"
                    MAX-ACCESS read-only
                    STATUS current
                    DESCRIPTION "Evaporator pump1"
                    DEFVAL { 0 }
                    ::= { digitalObjects 62 }

        -- 1.3.6.1.4.1.9839.2.1.1.63
        al-sns-tempinfreecooling OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 63 }

        -- 1.3.6.1.4.1.9839.2.1.1.64
        al-sns-tempuscitafreecooling OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 64 }

        -- 1.3.6.1.4.1.9839.2.1.1.65
        al-sns-tempscambintermedio OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 65 }

        -- 1.3.6.1.4.1.9839.2.1.1.66
        al-sns-tempoutrec OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 66 }

        -- 1.3.6.1.4.1.9839.2.1.1.68
        al-sns-tempinscambintermedio OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 68 }

        -- 1.3.6.1.4.1.9839.2.1.1.69
        caricamentosiglaconfiguratore OBJECT-TYPE
                    SYNTAX Integer32 (0..1)
                    UNITS "N/A"
                    MAX-ACCESS read-write
                    STATUS current
                    DESCRIPTION "N/A"
                    DEFVAL { 0 }
                    ::= { digitalObjects 69 }

        -- 1.3.6.1.4.1.9839.2.1.1.70
        al-sns-tempinrec OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 70 }

        -- 1.3.6.1.4.1.9839.2.1.1.71
        al-sns-tempoutrec2 OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 71 }

        -- 1.3.6.1.4.1.9839.2.1.1.72
        mem-al-inlet-low OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 72 }

        -- 1.3.6.1.4.1.9839.2.1.1.74
        mem-al-sns-liq-circ1b OBJECT-TYPE
                    SYNTAX Integer32 (0..1)
                    UNITS "N/A"
                    MAX-ACCESS read-only
                    STATUS current
                    DESCRIPTION "Analog input 5 alarm status "
                    DEFVAL { 0 }
                    ::= { digitalObjects 74 }

        -- 1.3.6.1.4.1.9839.2.1.1.75
        versione-y OBJECT-TYPE
                    SYNTAX Integer32 (0..1)
                    UNITS "N/A"
                    MAX-ACCESS read-write
                    STATUS current
                    DESCRIPTION "Reset Alarms (1: reset) "
                    DEFVAL { 0 }
                    ::= { digitalObjects 75 }

        -- 1.3.6.1.4.1.9839.2.1.1.76
        doppiatermostatica OBJECT-TYPE
                    SYNTAX Integer32 (0..1)
                    UNITS "N/A"
                    MAX-ACCESS read-write
                    STATUS current
                    DESCRIPTION "Reset Alarms (1: reset) "
                    DEFVAL { 0 }
                    ::= { digitalObjects 76 }

        -- 1.3.6.1.4.1.9839.2.1.1.78
        mem-al-sns-pressostatodiff OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 78 }

        -- 1.3.6.1.4.1.9839.2.1.1.79
        mem-al-sns-trasddiff OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 79 }

        -- 1.3.6.1.4.1.9839.2.1.1.80
        al-sns-trasddiff OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 80 }

        -- 1.3.6.1.4.1.9839.2.1.1.95
        al-probe-c1 OBJECT-TYPE
                    SYNTAX Integer32 (0..1)
                    UNITS "N/A"
                    MAX-ACCESS read-only
                    STATUS current
                    DESCRIPTION "N/A"
                    DEFVAL { 0 }
                    ::= { digitalObjects 95 }

        -- 1.3.6.1.4.1.9839.2.1.1.96
        al-sensor-circ1 OBJECT-TYPE
                    SYNTAX Integer32 (0..1)
                    UNITS "N/A"
                    MAX-ACCESS read-only
                    STATUS current
                    DESCRIPTION "N/A"
                    DEFVAL { 0 }
                    ::= { digitalObjects 96 }

        -- 1.3.6.1.4.1.9839.2.1.1.97
        al-circ1 OBJECT-TYPE
                    SYNTAX Integer32 (0..1)
                    UNITS "N/A"
                    MAX-ACCESS read-only
                    STATUS current
                    DESCRIPTION "N/A"
                    DEFVAL { 0 }
                    ::= { digitalObjects 97 }

        -- 1.3.6.1.4.1.9839.2.1.1.98
        al-circ2 OBJECT-TYPE
                    SYNTAX Integer32 (0..1)
                    UNITS "N/A"
                    MAX-ACCESS read-only
                    STATUS current
                    DESCRIPTION "N/A"
                    DEFVAL { 0 }
                    ::= { digitalObjects 98 }

        -- 1.3.6.1.4.1.9839.2.1.1.99
        sbrinamentounita OBJECT-TYPE
                    SYNTAX Integer32 (0..1)
                    UNITS "N/A"
                    MAX-ACCESS read-only
                    STATUS current
                    DESCRIPTION "N/A"
                    DEFVAL { 0 }
                    ::= { digitalObjects 99 }

        -- 1.3.6.1.4.1.9839.2.1.1.100
        alarm-relay OBJECT-TYPE
                    SYNTAX Integer32 (0..1)
                    UNITS "N/A"
                    MAX-ACCESS read-only
                    STATUS current
                    DESCRIPTION "N/A"
                    DEFVAL { 1 }
                    ::= { digitalObjects 100 }

        -- 1.3.6.1.4.1.9839.2.1.1.101
        mem-al-flow-evap-pumps OBJECT-TYPE
                    SYNTAX Integer32 (0..1)
                    UNITS "N/A"
                    MAX-ACCESS read-only
                    STATUS current
                    DESCRIPTION "N/A"
                    DEFVAL { 0 }
                    ::= { digitalObjects 101 }

        -- 1.3.6.1.4.1.9839.2.1.1.102
        mem-al-flow-rec-pumps OBJECT-TYPE
                    SYNTAX Integer32 (0..1)
                    UNITS "N/A"
                    MAX-ACCESS read-only
                    STATUS current
                    DESCRIPTION "N/A"
                    DEFVAL { 0 }
                    ::= { digitalObjects 102 }

        -- 1.3.6.1.4.1.9839.2.1.1.103
        mem-al-overload-evap-pump1 OBJECT-TYPE
                    SYNTAX Integer32 (0..1)
                    UNITS "N/A"
                    MAX-ACCESS read-only
                    STATUS current
                    DESCRIPTION "N/A"
                    DEFVAL { 0 }
                    ::= { digitalObjects 103 }

        -- 1.3.6.1.4.1.9839.2.1.1.104
        mem-al-overload-evap-pump2 OBJECT-TYPE
                    SYNTAX Integer32 (0..1)
                    UNITS "N/A"
                    MAX-ACCESS read-only
                    STATUS current
                    DESCRIPTION "N/A"
                    DEFVAL { 0 }
                    ::= { digitalObjects 104 }

        -- 1.3.6.1.4.1.9839.2.1.1.107
        al-overload-rec-pump1 OBJECT-TYPE
                    SYNTAX Integer32 (0..1)
                    UNITS "N/A"
                    MAX-ACCESS read-only
                    STATUS current
                    DESCRIPTION "N/A"
                    DEFVAL { 0 }
                    ::= { digitalObjects 107 }

        -- 1.3.6.1.4.1.9839.2.1.1.108
        al-overload-rec-pump2 OBJECT-TYPE
                    SYNTAX Integer32 (0..1)
                    UNITS "N/A"
                    MAX-ACCESS read-only
                    STATUS current
                    DESCRIPTION "N/A"
                    DEFVAL { 0 }
                    ::= { digitalObjects 108 }

        -- 1.3.6.1.4.1.9839.2.1.1.110
        al-hour-comp2-circ1 OBJECT-TYPE
                    SYNTAX Integer32 (0..1)
                    UNITS "N/A"
                    MAX-ACCESS read-only
                    STATUS current
                    DESCRIPTION "N/A"
                    DEFVAL { 0 }
                    ::= { digitalObjects 110 }

        -- 1.3.6.1.4.1.9839.2.1.1.111
        al-hour-comp3-circ1 OBJECT-TYPE
                    SYNTAX Integer32 (0..1)
                    UNITS "N/A"
                    MAX-ACCESS read-only
                    STATUS current
                    DESCRIPTION "N/A"
                    DEFVAL { 0 }
                    ::= { digitalObjects 111 }

        -- 1.3.6.1.4.1.9839.2.1.1.112
        al-hour-comp1-circ2 OBJECT-TYPE
                    SYNTAX Integer32 (0..1)
                    UNITS "N/A"
                    MAX-ACCESS read-only
                    STATUS current
                    DESCRIPTION "Comp1 circ2 maitenance warning"
                    DEFVAL { 0 }
                    ::= { digitalObjects 112 }

        -- 1.3.6.1.4.1.9839.2.1.1.113
        al-hour-comp2-circ2 OBJECT-TYPE
                    SYNTAX Integer32 (0..1)
                    UNITS "N/A"
                    MAX-ACCESS read-only
                    STATUS current
                    DESCRIPTION "N/A"
                    DEFVAL { 0 }
                    ::= { digitalObjects 113 }

        -- 1.3.6.1.4.1.9839.2.1.1.114
        al-hour-comp3-circ2 OBJECT-TYPE
                    SYNTAX Integer32 (0..1)
                    UNITS "N/A"
                    MAX-ACCESS read-only
                    STATUS current
                    DESCRIPTION "N/A"
                    DEFVAL { 0 }
                    ::= { digitalObjects 114 }

        -- 1.3.6.1.4.1.9839.2.1.1.115
        mem-al-overl-fan-circ1 OBJECT-TYPE
                    SYNTAX Integer32 (0..1)
                    UNITS "N/A"
                    MAX-ACCESS read-only
                    STATUS current
                    DESCRIPTION "N/A"
                    DEFVAL { 0 }
                    ::= { digitalObjects 115 }

        -- 1.3.6.1.4.1.9839.2.1.1.116
        mem-al-overl-fan-circ2 OBJECT-TYPE
                    SYNTAX Integer32 (0..1)
                    UNITS "N/A"
                    MAX-ACCESS read-only
                    STATUS current
                    DESCRIPTION "N/A"
                    DEFVAL { 0 }
                    ::= { digitalObjects 116 }

        -- 1.3.6.1.4.1.9839.2.1.1.117
        mem-al-antifrezzer-evap OBJECT-TYPE
                    SYNTAX Integer32 (0..1)
                    UNITS "N/A"
                    MAX-ACCESS read-only
                    STATUS current
                    DESCRIPTION "N/A"
                    DEFVAL { 0 }
                    ::= { digitalObjects 117 }

        -- 1.3.6.1.4.1.9839.2.1.1.121
        mem-gen-lp-transducer-circ1 OBJECT-TYPE
                    SYNTAX Integer32 (0..1)
                    UNITS "N/A"
                    MAX-ACCESS read-only
                    STATUS current
                    DESCRIPTION "Circuit 1 Low pressure alarm by transducer"
                    DEFVAL { 0 }
                    ::= { digitalObjects 121 }

        -- 1.3.6.1.4.1.9839.2.1.1.122
        mem-gen-lp-transducer-circ2 OBJECT-TYPE
                    SYNTAX Integer32 (0..1)
                    UNITS "N/A"
                    MAX-ACCESS read-only
                    STATUS current
                    DESCRIPTION "Circuit 1 Low pressure alarm by transducer"
                    DEFVAL { 0 }
                    ::= { digitalObjects 122 }

        -- 1.3.6.1.4.1.9839.2.1.1.123
        mem-al-serius-low-lp-circ1 OBJECT-TYPE
                    SYNTAX Integer32 (0..1)
                    UNITS "N/A"
                    MAX-ACCESS read-only
                    STATUS current
                    DESCRIPTION "N/A"
                    DEFVAL { 0 }
                    ::= { digitalObjects 123 }

        -- 1.3.6.1.4.1.9839.2.1.1.124
        mem-al-serius-low-lp-circ2 OBJECT-TYPE
                    SYNTAX Integer32 (0..1)
                    UNITS "N/A"
                    MAX-ACCESS read-only
                    STATUS current
                    DESCRIPTION "N/A"
                    DEFVAL { 0 }
                    ::= { digitalObjects 124 }

        -- 1.3.6.1.4.1.9839.2.1.1.125
        mem-al-hp-pressostat-circ1 OBJECT-TYPE
                    SYNTAX Integer32 (0..1)
                    UNITS "N/A"
                    MAX-ACCESS read-only
                    STATUS current
                    DESCRIPTION "N/A"
                    DEFVAL { 0 }
                    ::= { digitalObjects 125 }

        -- 1.3.6.1.4.1.9839.2.1.1.126
        mem-al-hp-pressostat-circ2 OBJECT-TYPE
                    SYNTAX Integer32 (0..1)
                    UNITS "N/A"
                    MAX-ACCESS read-only
                    STATUS current
                    DESCRIPTION "N/A"
                    DEFVAL { 0 }
                    ::= { digitalObjects 126 }

        -- 1.3.6.1.4.1.9839.2.1.1.127
        mem-al-hp-transducer-circ1 OBJECT-TYPE
                    SYNTAX Integer32 (0..1)
                    UNITS "N/A"
                    MAX-ACCESS read-only
                    STATUS current
                    DESCRIPTION "N/A"
                    DEFVAL { 0 }
                    ::= { digitalObjects 127 }

        -- 1.3.6.1.4.1.9839.2.1.1.128
        mem-al-hp-transducer-circ2 OBJECT-TYPE
                    SYNTAX Integer32 (0..1)
                    UNITS "N/A"
                    MAX-ACCESS read-only
                    STATUS current
                    DESCRIPTION "N/A"
                    DEFVAL { 0 }
                    ::= { digitalObjects 128 }

        -- 1.3.6.1.4.1.9839.2.1.1.129
        al-phase-alarm OBJECT-TYPE
                    SYNTAX Integer32 (0..1)
                    UNITS "N/A"
                    MAX-ACCESS read-only
                    STATUS current
                    DESCRIPTION "Serious alarm by DIN (0: No alarm; 1: Alarm)"
                    DEFVAL { 0 }
                    ::= { digitalObjects 129 }

        -- 1.3.6.1.4.1.9839.2.1.1.130
        mem-al-prb-out-evap OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 130 }

        -- 1.3.6.1.4.1.9839.2.1.1.131
        mem-al-prb-in-evap OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 131 }

        -- 1.3.6.1.4.1.9839.2.1.1.134
        mem-al-sns-tempoutrec OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 134 }

        -- 1.3.6.1.4.1.9839.2.1.1.135
        mem-al-sns-tempinrec OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 135 }

        -- 1.3.6.1.4.1.9839.2.1.1.136
        mem-al-prb-hp1 OBJECT-TYPE
                    SYNTAX Integer32 (0..1)
                    UNITS "N/A"
                    MAX-ACCESS read-only
                    STATUS current
                    DESCRIPTION "Specify if high pressure probe circuit1 fault or not connected (0: No alarm; 1: Alarm)"
                    DEFVAL { 0 }
                    ::= { digitalObjects 136 }

        -- 1.3.6.1.4.1.9839.2.1.1.137
        mem-al-prb-lp1 OBJECT-TYPE
                    SYNTAX Integer32 (0..1)
                    UNITS "N/A"
                    MAX-ACCESS read-only
                    STATUS current
                    DESCRIPTION "Specify if high pressure probe circuit1 fault or not connected (0: No alarm; 1: Alarm)"
                    DEFVAL { 0 }
                    ::= { digitalObjects 137 }

        -- 1.3.6.1.4.1.9839.2.1.1.138
        mem-al-prb-hp2 OBJECT-TYPE
                    SYNTAX Integer32 (0..1)
                    UNITS "N/A"
                    MAX-ACCESS read-only
                    STATUS current
                    DESCRIPTION "Specify if high pressure probe circuit1 fault or not connected (0: No alarm; 1: Alarm)"
                    DEFVAL { 0 }
                    ::= { digitalObjects 138 }

        -- 1.3.6.1.4.1.9839.2.1.1.139
        mem-al-prb-lp2 OBJECT-TYPE
                    SYNTAX Integer32 (0..1)
                    UNITS "N/A"
                    MAX-ACCESS read-only
                    STATUS current
                    DESCRIPTION "Specify if high pressure probe circuit1 fault or not connected (0: No alarm; 1: Alarm)"
                    DEFVAL { 0 }
                    ::= { digitalObjects 139 }

        -- 1.3.6.1.4.1.9839.2.1.1.140
        mem-al-prb-ext-temp OBJECT-TYPE
                    SYNTAX Integer32 (0..1)
                    UNITS "N/A"
                    MAX-ACCESS read-only
                    STATUS current
                    DESCRIPTION "Specify if external temp.probe fault or not connected (0: No alarm; 1: Alarm)"
                    DEFVAL { 0 }
                    ::= { digitalObjects 140 }

        -- 1.3.6.1.4.1.9839.2.1.1.141
        mem-al-sns-tgp-circ1 OBJECT-TYPE
                    SYNTAX Integer32 (0..1)
                    UNITS "N/A"
                    MAX-ACCESS read-only
                    STATUS current
                    DESCRIPTION "N/A"
                    DEFVAL { 0 }
                    ::= { digitalObjects 141 }

        -- 1.3.6.1.4.1.9839.2.1.1.142
        mem-al-sns-tgp-circ2 OBJECT-TYPE
                    SYNTAX Integer32 (0..1)
                    UNITS "N/A"
                    MAX-ACCESS read-only
                    STATUS current
                    DESCRIPTION "N/A"
                    DEFVAL { 0 }
                    ::= { digitalObjects 142 }

        -- 1.3.6.1.4.1.9839.2.1.1.143
        mem-al-sns-liq-circ1 OBJECT-TYPE
                    SYNTAX Integer32 (0..1)
                    UNITS "N/A"
                    MAX-ACCESS read-only
                    STATUS current
                    DESCRIPTION "Analog input 5 alarm status "
                    DEFVAL { 0 }
                    ::= { digitalObjects 143 }

        -- 1.3.6.1.4.1.9839.2.1.1.144
        mem-al-sns-liq-circ2 OBJECT-TYPE
                    SYNTAX Integer32 (0..1)
                    UNITS "N/A"
                    MAX-ACCESS read-only
                    STATUS current
                    DESCRIPTION "Analog input 5 alarm status "
                    DEFVAL { 0 }
                    ::= { digitalObjects 144 }

        -- 1.3.6.1.4.1.9839.2.1.1.147
        al-clock OBJECT-TYPE
                    SYNTAX Integer32 (0..1)
                    UNITS "N/A"
                    MAX-ACCESS read-only
                    STATUS current
                    DESCRIPTION "Specify if clock board doesn't work or is absent (0: No alarm; 1: Alarm)"
                    DEFVAL { 0 }
                    ::= { digitalObjects 147 }

        -- 1.3.6.1.4.1.9839.2.1.1.148
        al-extd-memory OBJECT-TYPE
                    SYNTAX Integer32 (0..1)
                    UNITS "N/A"
                    MAX-ACCESS read-only
                    STATUS current
                    DESCRIPTION "Specify if P-Memory expansion doesn't work or is absent (0: No alarm; 1: Alarm)"
                    DEFVAL { 0 }
                    ::= { digitalObjects 148 }

        -- 1.3.6.1.4.1.9839.2.1.1.149
        mem-al-sns-tempoutrec2 OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 149 }

        -- 1.3.6.1.4.1.9839.2.1.1.160
        mem-al-antifrezzer-evap-com OBJECT-TYPE
                    SYNTAX Integer32 (0..1)
                    UNITS "N/A"
                    MAX-ACCESS read-only
                    STATUS current
                    DESCRIPTION "N/A"
                    DEFVAL { 0 }
                    ::= { digitalObjects 160 }

        -- 1.3.6.1.4.1.9839.2.1.1.161
        mem-al-antifrezzer-rec OBJECT-TYPE
                    SYNTAX Integer32 (0..1)
                    UNITS "N/A"
                    MAX-ACCESS read-only
                    STATUS current
                    DESCRIPTION "N/A"
                    DEFVAL { 0 }
                    ::= { digitalObjects 161 }

        -- 1.3.6.1.4.1.9839.2.1.1.162
        mem-al-antifrezzer-rec2 OBJECT-TYPE
                    SYNTAX Integer32 (0..1)
                    UNITS "N/A"
                    MAX-ACCESS read-only
                    STATUS current
                    DESCRIPTION "N/A"
                    DEFVAL { 0 }
                    ::= { digitalObjects 162 }

        -- 1.3.6.1.4.1.9839.2.1.1.164
        al-exp-upc-offline OBJECT-TYPE
                    SYNTAX Integer32 (0..1)
                    UNITS "N/A"
                    MAX-ACCESS read-only
                    STATUS current
                    DESCRIPTION "N/A"
                    DEFVAL { 0 }
                    ::= { digitalObjects 164 }

        -- 1.3.6.1.4.1.9839.2.1.1.165
        offline-alarm-pcoe OBJECT-TYPE
                    SYNTAX Integer32 (0..1)
                    UNITS "N/A"
                    MAX-ACCESS read-only
                    STATUS current
                    DESCRIPTION "N/A"
                    DEFVAL { 0 }
                    ::= { digitalObjects 165 }

        -- 1.3.6.1.4.1.9839.2.1.1.166
        hot-forceoff-rec1 OBJECT-TYPE
                    SYNTAX Integer32 (0..1)
                    UNITS "N/A"
                    MAX-ACCESS read-only
                    STATUS current
                    DESCRIPTION "N/A"
                    DEFVAL { 0 }
                    ::= { digitalObjects 166 }

        -- 1.3.6.1.4.1.9839.2.1.1.168
        al-hour-cond-pump2 OBJECT-TYPE
                    SYNTAX Integer32 (0..1)
                    UNITS "N/A"
                    MAX-ACCESS read-only
                    STATUS current
                    DESCRIPTION "N/A"
                    DEFVAL { 0 }
                    ::= { digitalObjects 168 }

        -- 1.3.6.1.4.1.9839.2.1.1.169
        mem-ovrl-comp1-circ1 OBJECT-TYPE
                    SYNTAX Integer32 (0..1)
                    UNITS "N/A"
                    MAX-ACCESS read-only
                    STATUS current
                    DESCRIPTION "N/A"
                    DEFVAL { 0 }
                    ::= { digitalObjects 169 }

        -- 1.3.6.1.4.1.9839.2.1.1.170
        mem-ovrl-comp2-circ1 OBJECT-TYPE
                    SYNTAX Integer32 (0..1)
                    UNITS "N/A"
                    MAX-ACCESS read-only
                    STATUS current
                    DESCRIPTION "N/A"
                    DEFVAL { 0 }
                    ::= { digitalObjects 170 }

        -- 1.3.6.1.4.1.9839.2.1.1.171
        mem-ovrl-comp3-circ1 OBJECT-TYPE
                    SYNTAX Integer32 (0..1)
                    UNITS "N/A"
                    MAX-ACCESS read-only
                    STATUS current
                    DESCRIPTION "N/A"
                    DEFVAL { 0 }
                    ::= { digitalObjects 171 }

        -- 1.3.6.1.4.1.9839.2.1.1.172
        mem-ovrl-comp1-circ2 OBJECT-TYPE
                    SYNTAX Integer32 (0..1)
                    UNITS "N/A"
                    MAX-ACCESS read-only
                    STATUS current
                    DESCRIPTION "N/A"
                    DEFVAL { 0 }
                    ::= { digitalObjects 172 }

        -- 1.3.6.1.4.1.9839.2.1.1.173
        mem-ovrl-comp2-circ2 OBJECT-TYPE
                    SYNTAX Integer32 (0..1)
                    UNITS "N/A"
                    MAX-ACCESS read-only
                    STATUS current
                    DESCRIPTION "N/A"
                    DEFVAL { 0 }
                    ::= { digitalObjects 173 }

        -- 1.3.6.1.4.1.9839.2.1.1.174
        mem-ovrl-comp3-circ2 OBJECT-TYPE
                    SYNTAX Integer32 (0..1)
                    UNITS "N/A"
                    MAX-ACCESS read-only
                    STATUS current
                    DESCRIPTION "N/A"
                    DEFVAL { 0 }
                    ::= { digitalObjects 174 }

        -- 1.3.6.1.4.1.9839.2.1.1.175
        al-slave-offline OBJECT-TYPE
                    SYNTAX Integer32 (0..1)
                    UNITS "N/A"
                    MAX-ACCESS read-only
                    STATUS current
                    DESCRIPTION "Specify if slave offline (0: No alarm; 1: Alarm)"
                    DEFVAL { 0 }
                    ::= { digitalObjects 175 }

        -- 1.3.6.1.4.1.9839.2.1.1.176
        mem-al-sns-out-evap-com OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 176 }

        -- 1.3.6.1.4.1.9839.2.1.1.184
        mem-al-tgp-high-circ1 OBJECT-TYPE
                    SYNTAX Integer32 (0..1)
                    UNITS "N/A"
                    MAX-ACCESS read-only
                    STATUS current
                    DESCRIPTION "N/A"
                    DEFVAL { 0 }
                    ::= { digitalObjects 184 }

        -- 1.3.6.1.4.1.9839.2.1.1.185
        mem-al-tgp-high-circ2 OBJECT-TYPE
                    SYNTAX Integer32 (0..1)
                    UNITS "N/A"
                    MAX-ACCESS read-only
                    STATUS current
                    DESCRIPTION "N/A"
                    DEFVAL { 0 }
                    ::= { digitalObjects 185 }

        -- 1.3.6.1.4.1.9839.2.1.1.190
        mem-al-high-temp-plant OBJECT-TYPE
                    SYNTAX Integer32 (0..1)
                    UNITS "N/A"
                    MAX-ACCESS read-only
                    STATUS current
                    DESCRIPTION "Analog input 1 alarm status "
                    DEFVAL { 0 }
                    ::= { digitalObjects 190 }

        -- 1.3.6.1.4.1.9839.2.1.1.191
        al-sns-sac-msk OBJECT-TYPE
                    SYNTAX Integer32 (0..1)
                    UNITS "N/A"
                    MAX-ACCESS read-only
                    STATUS current
                    DESCRIPTION "Analog input 5 alarm status "
                    DEFVAL { 0 }
                    ::= { digitalObjects 191 }

        -- 1.3.6.1.4.1.9839.2.1.1.192
        masteroffline OBJECT-TYPE
                    SYNTAX Integer32 (0..1)
                    UNITS "N/A"
                    MAX-ACCESS read-only
                    STATUS current
                    DESCRIPTION "N/A"
                    DEFVAL { 0 }
                    ::= { digitalObjects 192 }

        -- 1.3.6.1.4.1.9839.2.1.1.193
        slaveoffline OBJECT-TYPE
                    SYNTAX Integer32 (0..1)
                    UNITS "N/A"
                    MAX-ACCESS read-only
                    STATUS current
                    DESCRIPTION "N/A"
                    DEFVAL { 0 }
                    ::= { digitalObjects 193 }

        -- 1.3.6.1.4.1.9839.2.1.1.194
        allarmeresafreecooling OBJECT-TYPE
                    SYNTAX Integer32 (0..1)
                    UNITS "N/A"
                    MAX-ACCESS read-only
                    STATUS current
                    DESCRIPTION "N/A"
                    DEFVAL { 0 }
                    ::= { digitalObjects 194 }

        -- 1.3.6.1.4.1.9839.2.1.1.195
        alarm-relay-slave OBJECT-TYPE
                    SYNTAX Integer32 (0..1)
                    UNITS "N/A"
                    MAX-ACCESS read-only
                    STATUS current
                    DESCRIPTION "N/A"
                    DEFVAL { 1 }
                    ::= { digitalObjects 195 }

        -- 1.3.6.1.4.1.9839.2.1.1.196
        mem-al-flow-glicolefree OBJECT-TYPE
                    SYNTAX Integer32 (0..1)
                    UNITS "N/A"
                    MAX-ACCESS read-only
                    STATUS current
                    DESCRIPTION "N/A"
                    DEFVAL { 0 }
                    ::= { digitalObjects 196 }

        -- 1.3.6.1.4.1.9839.2.1.1.197
        mem-al-overload-pump-glicolefree OBJECT-TYPE
                    SYNTAX Integer32 (0..1)
                    UNITS "N/A"
                    MAX-ACCESS read-only
                    STATUS current
                    DESCRIPTION "N/A"
                    DEFVAL { 0 }
                    ::= { digitalObjects 197 }

        -- 1.3.6.1.4.1.9839.2.1.1.198
        offline-alarm-pcoe-dk OBJECT-TYPE
                    SYNTAX Integer32 (0..1)
                    UNITS "N/A"
                    MAX-ACCESS read-only
                    STATUS current
                    DESCRIPTION "N/A"
                    DEFVAL { 0 }
                    ::= { digitalObjects 198 }

        -- 1.3.6.1.4.1.9839.2.1.1.199
        mem-al-prb-out-evap-com-dk OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 199 }

        -- 1.3.6.1.4.1.9839.2.1.1.200
        mem-al-prb-out-evap2 OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 200 }

        -- 1.3.6.1.4.1.9839.2.1.1.201
        mem-al-sns-tempinfreecooling OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 201 }

        -- 1.3.6.1.4.1.9839.2.1.1.202
        mem-al-sns-tempuscitafreecooling OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 202 }

        -- 1.3.6.1.4.1.9839.2.1.1.203
        mem-al-sns-tempinscambintermedio OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 203 }

        -- 1.3.6.1.4.1.9839.2.1.1.204
        offline-alarm-pcoe-motoc OBJECT-TYPE
                    SYNTAX Integer32 (0..1)
                    UNITS "N/A"
                    MAX-ACCESS read-only
                    STATUS current
                    DESCRIPTION "N/A"
                    DEFVAL { 0 }
                    ::= { digitalObjects 204 }

        -- 1.3.6.1.4.1.9839.2.1.1.205
        offline-alarm-pcoe-nyb OBJECT-TYPE
                    SYNTAX Integer32 (0..1)
                    UNITS "N/A"
                    MAX-ACCESS read-only
                    STATUS current
                    DESCRIPTION "N/A"
                    DEFVAL { 0 }
                    ::= { digitalObjects 205 }

        -- 1.3.6.1.4.1.9839.2.1.1.206
        mem-al-inlet-lowtemp OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 206 }

        -- 1.3.6.1.4.1.9839.2.1.1.207
        mem-al-vic-circ1 OBJECT-TYPE
                    SYNTAX Integer32 (0..1)
                    UNITS "N/A"
                    MAX-ACCESS read-only
                    STATUS current
                    DESCRIPTION "N/A"
                    DEFVAL { 0 }
                    ::= { digitalObjects 207 }

        -- 1.3.6.1.4.1.9839.2.1.1.208
        mem-al-vic-circ2 OBJECT-TYPE
                    SYNTAX Integer32 (0..1)
                    UNITS "N/A"
                    MAX-ACCESS read-only
                    STATUS current
                    DESCRIPTION "N/A"
                    DEFVAL { 0 }
                    ::= { digitalObjects 208 }

        -- 1.3.6.1.4.1.9839.2.1.1.209
        mod-evdevo-2-1.d8-eev-alarm-ui OBJECT-TYPE
                    SYNTAX Integer32 (0..1)
                    UNITS "N/A"
                    MAX-ACCESS read-only
                    STATUS current
                    DESCRIPTION "EEV motor error - Valve A"
                    DEFVAL { 0 }
                    ::= { digitalObjects 209 }

        -- 1.3.6.1.4.1.9839.2.1.1.210
        mod-evdevo-2-1.d10-lop-alarm-ui OBJECT-TYPE
                    SYNTAX Integer32 (0..1)
                    UNITS "N/A"
                    MAX-ACCESS read-only
                    STATUS current
                    DESCRIPTION "LOP alarm - Valve A"
                    DEFVAL { 0 }
                    ::= { digitalObjects 210 }

        -- 1.3.6.1.4.1.9839.2.1.1.211
        mod-evdevo-2-1.d11-mop-alarm-ui OBJECT-TYPE
                    SYNTAX Integer32 (0..1)
                    UNITS "N/A"
                    MAX-ACCESS read-only
                    STATUS current
                    DESCRIPTION "MOP alarm - Valve A"
                    DEFVAL { 0 }
                    ::= { digitalObjects 211 }

        -- 1.3.6.1.4.1.9839.2.1.1.212
        mod-evdevo-2-1.d12-low-sh-alarm-ui OBJECT-TYPE
                    SYNTAX Integer32 (0..1)
                    UNITS "N/A"
                    MAX-ACCESS read-only
                    STATUS current
                    DESCRIPTION "LowSH (low super heat) alarm - Valve A"
                    DEFVAL { 0 }
                    ::= { digitalObjects 212 }

        -- 1.3.6.1.4.1.9839.2.1.1.213
        mod-evdevo-2-1.d1-low-suct-alarm-ui OBJECT-TYPE
                    SYNTAX Integer32 (0..1)
                    UNITS "N/A"
                    MAX-ACCESS read-only
                    STATUS current
                    DESCRIPTION "Low suction temperature alarm - Valve A"
                    DEFVAL { 0 }
                    ::= { digitalObjects 213 }

        -- 1.3.6.1.4.1.9839.2.1.1.214
        mod-evdevo-2-1.d13-hitcond-alarm-ui OBJECT-TYPE
                    SYNTAX Integer32 (0..1)
                    UNITS "N/A"
                    MAX-ACCESS read-only
                    STATUS current
                    DESCRIPTION "HiTcond alarm"
                    DEFVAL { 0 }
                    ::= { digitalObjects 214 }

        -- 1.3.6.1.4.1.9839.2.1.1.215
        mod-evdevo-2-1.d30-eev-alarm-2nd-ui OBJECT-TYPE
                    SYNTAX Integer32 (0..1)
                    UNITS "N/A"
                    MAX-ACCESS read-only
                    STATUS current
                    DESCRIPTION "EEV motor error - Valve B"
                    DEFVAL { 0 }
                    ::= { digitalObjects 215 }

        -- 1.3.6.1.4.1.9839.2.1.1.216
        mod-evdevo-2-1.d27-lop-alarm-2nd-ui OBJECT-TYPE
                    SYNTAX Integer32 (0..1)
                    UNITS "N/A"
                    MAX-ACCESS read-only
                    STATUS current
                    DESCRIPTION "LOP alarm - Valve B"
                    DEFVAL { 0 }
                    ::= { digitalObjects 216 }

        -- 1.3.6.1.4.1.9839.2.1.1.217
        mod-evdevo-2-1.d28-mop-alarm-2nd-ui OBJECT-TYPE
                    SYNTAX Integer32 (0..1)
                    UNITS "N/A"
                    MAX-ACCESS read-only
                    STATUS current
                    DESCRIPTION "MOP alarm - Valve B"
                    DEFVAL { 0 }
                    ::= { digitalObjects 217 }

        -- 1.3.6.1.4.1.9839.2.1.1.218
        mod-evdevo-2-1.d26-low-sh-alarm-2nd-ui OBJECT-TYPE
                    SYNTAX Integer32 (0..1)
                    UNITS "N/A"
                    MAX-ACCESS read-only
                    STATUS current
                    DESCRIPTION "LowSH (low super heat) alarm - Valve B"
                    DEFVAL { 0 }
                    ::= { digitalObjects 218 }

        -- 1.3.6.1.4.1.9839.2.1.1.219
        mod-evdevo-2-1.d29-low-suct-alarm-2nd-ui OBJECT-TYPE
                    SYNTAX Integer32 (0..1)
                    UNITS "N/A"
                    MAX-ACCESS read-only
                    STATUS current
                    DESCRIPTION "Low suction temperature alarm - Valve B"
                    DEFVAL { 0 }
                    ::= { digitalObjects 219 }

        -- 1.3.6.1.4.1.9839.2.1.1.220
        mod-evdevo-2-1.d4-s1-alarm-ui OBJECT-TYPE
                    SYNTAX Integer32 (0..1)
                    UNITS "N/A"
                    MAX-ACCESS read-only
                    STATUS current
                    DESCRIPTION "Alarm probe S1"
                    DEFVAL { 0 }
                    ::= { digitalObjects 220 }

        -- 1.3.6.1.4.1.9839.2.1.1.221
        mod-evdevo-2-1.d5-s2-alarm-ui OBJECT-TYPE
                    SYNTAX Integer32 (0..1)
                    UNITS "N/A"
                    MAX-ACCESS read-only
                    STATUS current
                    DESCRIPTION "Alarm probe S2"
                    DEFVAL { 0 }
                    ::= { digitalObjects 221 }

        -- 1.3.6.1.4.1.9839.2.1.1.222
        mod-evdevo-2-1.d6-s3-alarm-ui OBJECT-TYPE
                    SYNTAX Integer32 (0..1)
                    UNITS "N/A"
                    MAX-ACCESS read-only
                    STATUS current
                    DESCRIPTION "Alarm probe S3"
                    DEFVAL { 0 }
                    ::= { digitalObjects 222 }

        -- 1.3.6.1.4.1.9839.2.1.1.223
        mod-evdevo-2-1.d7-s4-alarm-ui OBJECT-TYPE
                    SYNTAX Integer32 (0..1)
                    UNITS "N/A"
                    MAX-ACCESS read-only
                    STATUS current
                    DESCRIPTION "Alarm probe S4"
                    DEFVAL { 0 }
                    ::= { digitalObjects 223 }

        -- 1.3.6.1.4.1.9839.2.1.1.224
        mod-evdevo-2-1.d3-eeprom-alarm-ui OBJECT-TYPE
                    SYNTAX Integer32 (0..1)
                    UNITS "N/A"
                    MAX-ACCESS read-only
                    STATUS current
                    DESCRIPTION "EEPROM alarm"
                    DEFVAL { 0 }
                    ::= { digitalObjects 224 }

        -- 1.3.6.1.4.1.9839.2.1.1.225
        mod-evdevo-2-1.evd-al-offline-ui OBJECT-TYPE
                    SYNTAX Integer32 (0..1)
                    UNITS "N/A"
                    MAX-ACCESS read-only
                    STATUS current
                    DESCRIPTION "EVD offline alarm"
                    DEFVAL { 0 }
                    ::= { digitalObjects 225 }

        -- 1.3.6.1.4.1.9839.2.1.1.226
        mod-evdevo-2-1.d25-battery-alarm-ui OBJECT-TYPE
                    SYNTAX Integer32 (0..1)
                    UNITS "N/A"
                    MAX-ACCESS read-only
                    STATUS current
                    DESCRIPTION "Discharge battery alarm"
                    DEFVAL { 0 }
                    ::= { digitalObjects 226 }

        -- 1.3.6.1.4.1.9839.2.1.1.227
        mod-evdevo-2-1.configuration-error OBJECT-TYPE
                    SYNTAX Integer32 (0..1)
                    UNITS "N/A"
                    MAX-ACCESS read-only
                    STATUS current
                    DESCRIPTION "Indicates if: one or more parameters go out of max/min; a decimal part is present for a pressure in imperial system; superparameters have been wrongly configured"
                    DEFVAL { 0 }
                    ::= { digitalObjects 227 }

        -- 1.3.6.1.4.1.9839.2.1.1.228
        mod-evdevo-2-1.fw-compatibility-error OBJECT-TYPE
                    SYNTAX Integer32 (0..1)
                    UNITS "N/A"
                    MAX-ACCESS read-only
                    STATUS current
                    DESCRIPTION "The fw in the EVDEVO connected is not compatible with the module"
                    DEFVAL { 0 }
                    ::= { digitalObjects 228 }

        -- 1.3.6.1.4.1.9839.2.1.1.229
        al-sns-liq-circ1b OBJECT-TYPE
                    SYNTAX Integer32 (0..1)
                    UNITS "N/A"
                    MAX-ACCESS read-only
                    STATUS current
                    DESCRIPTION "Analog input 5 alarm status "
                    DEFVAL { 0 }
                    ::= { digitalObjects 229 }

        -- 1.3.6.1.4.1.9839.2.1.1.230
        offline-alarm-pcoe-nrb OBJECT-TYPE
                    SYNTAX Integer32 (0..1)
                    UNITS "N/A"
                    MAX-ACCESS read-only
                    STATUS current
                    DESCRIPTION "N/A"
                    DEFVAL { 0 }
                    ::= { digitalObjects 230 }

        -- 1.3.6.1.4.1.9839.2.1.1.231
        al-sns-aspirazionec1 OBJECT-TYPE
                    SYNTAX Integer32 (0..1)
                    UNITS "N/A"
                    MAX-ACCESS read-only
                    STATUS current
                    DESCRIPTION "Analog input 5 alarm status "
                    DEFVAL { 0 }
                    ::= { digitalObjects 231 }

        -- 1.3.6.1.4.1.9839.2.1.1.232
        al-sns-aspirazionec2 OBJECT-TYPE
                    SYNTAX Integer32 (0..1)
                    UNITS "N/A"
                    MAX-ACCESS read-only
                    STATUS current
                    DESCRIPTION "Analog input 5 alarm status "
                    DEFVAL { 0 }
                    ::= { digitalObjects 232 }

        -- 1.3.6.1.4.1.9839.2.1.1.233
        offline-alarm-pcoe-vpf OBJECT-TYPE
                    SYNTAX Integer32 (0..1)
                    UNITS "N/A"
                    MAX-ACCESS read-only
                    STATUS current
                    DESCRIPTION "N/A"
                    DEFVAL { 0 }
                    ::= { digitalObjects 233 }

        -- 1.3.6.1.4.1.9839.2.1.1.234
        al-sns-pressostatodiff OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 234 }

        -- 1.3.6.1.4.1.9839.2.1.1.243
        al-sns-liq-circ1 OBJECT-TYPE
                    SYNTAX Integer32 (0..1)
                    UNITS "N/A"
                    MAX-ACCESS read-only
                    STATUS current
                    DESCRIPTION "Analog input 5 alarm status "
                    DEFVAL { 0 }
                    ::= { digitalObjects 243 }

        -- 1.3.6.1.4.1.9839.2.1.1.244
        al-sns-liq-circ2 OBJECT-TYPE
                    SYNTAX Integer32 (0..1)
                    UNITS "N/A"
                    MAX-ACCESS read-only
                    STATUS current
                    DESCRIPTION "Analog input 5 alarm status "
                    DEFVAL { 0 }
                    ::= { digitalObjects 244 }

        -- 1.3.6.1.4.1.9839.2.1.1.245
        al-defr-plant-notavaible OBJECT-TYPE
                    SYNTAX Integer32 (0..1)
                    UNITS "N/A"
                    MAX-ACCESS read-only
                    STATUS current
                    DESCRIPTION "N/A"
                    DEFVAL { 0 }
                    ::= { digitalObjects 245 }

        -- 1.3.6.1.4.1.9839.2.1.1.246
        al-defr-rec-notavaible OBJECT-TYPE
                    SYNTAX Integer32 (0..1)
                    UNITS "N/A"
                    MAX-ACCESS read-only
                    STATUS current
                    DESCRIPTION "N/A"
                    DEFVAL { 0 }
                    ::= { digitalObjects 246 }

        -- 1.3.6.1.4.1.9839.2.1.1.249
        al-sns-out-rec2 OBJECT-TYPE
                    SYNTAX Integer32 (0..1)
                    UNITS "N/A"
                    MAX-ACCESS read-only
                    STATUS current
                    DESCRIPTION "Specify if cond1.outlet probe fault or not connected (0: No alarm; 1: Alarm)"
                    DEFVAL { 0 }
                    ::= { digitalObjects 249 }

        -- 1.3.6.1.4.1.9839.2.1.1.250
        al-sns-out-rec-com OBJECT-TYPE
                    SYNTAX Integer32 (0..1)
                    UNITS "N/A"
                    MAX-ACCESS read-only
                    STATUS current
                    DESCRIPTION "Specify if cond1.outlet probe fault or not connected (0: No alarm; 1: Alarm)"
                    DEFVAL { 1 }
                    ::= { digitalObjects 250 }

        -- 1.3.6.1.4.1.9839.2.1.1.251
        al-hour-comp1-circ1 OBJECT-TYPE
                    SYNTAX Integer32 (0..1)
                    UNITS "N/A"
                    MAX-ACCESS read-only
                    STATUS current
                    DESCRIPTION "Comp1 circ1 maitenance warning"
                    DEFVAL { 0 }
                    ::= { digitalObjects 251 }

        -- 1.3.6.1.4.1.9839.2.1.1.253
        al-hour-cond-pump1 OBJECT-TYPE
                    SYNTAX Integer32 (0..1)
                    UNITS "N/A"
                    MAX-ACCESS read-only
                    STATUS current
                    DESCRIPTION "N/A"
                    DEFVAL { 0 }
                    ::= { digitalObjects 253 }

        -- 1.3.6.1.4.1.9839.2.1.1.254
        al-hour-evap-pump1 OBJECT-TYPE
                    SYNTAX Integer32 (0..1)
                    UNITS "N/A"
                    MAX-ACCESS read-only
                    STATUS current
                    DESCRIPTION "N/A"
                    DEFVAL { 0 }
                    ::= { digitalObjects 254 }

        -- 1.3.6.1.4.1.9839.2.1.1.258
        hp-prevent-circ1 OBJECT-TYPE
                    SYNTAX Integer32 (0..1)
                    UNITS "N/A"
                    MAX-ACCESS read-only
                    STATUS current
                    DESCRIPTION "Circuit 1 Warning High pressure prevent "
                    DEFVAL { 0 }
                    ::= { digitalObjects 258 }

        -- 1.3.6.1.4.1.9839.2.1.1.259
        hp-prevent-circ2 OBJECT-TYPE
                    SYNTAX Integer32 (0..1)
                    UNITS "N/A"
                    MAX-ACCESS read-only
                    STATUS current
                    DESCRIPTION "Circuit 1 Warning High pressure prevent "
                    DEFVAL { 0 }
                    ::= { digitalObjects 259 }

        -- 1.3.6.1.4.1.9839.2.1.1.260
        al-antifrezzer-evap-com OBJECT-TYPE
                    SYNTAX Integer32 (0..1)
                    UNITS "N/A"
                    MAX-ACCESS read-only
                    STATUS current
                    DESCRIPTION "N/A"
                    DEFVAL { 0 }
                    ::= { digitalObjects 260 }

        -- 1.3.6.1.4.1.9839.2.1.1.261
        al-antifrezzer-rec1 OBJECT-TYPE
                    SYNTAX Integer32 (0..1)
                    UNITS "N/A"
                    MAX-ACCESS read-only
                    STATUS current
                    DESCRIPTION "N/A"
                    DEFVAL { 0 }
                    ::= { digitalObjects 261 }

        -- 1.3.6.1.4.1.9839.2.1.1.262
        al-antifrezzer-rec2 OBJECT-TYPE
                    SYNTAX Integer32 (0..1)
                    UNITS "N/A"
                    MAX-ACCESS read-only
                    STATUS current
                    DESCRIPTION "N/A"
                    DEFVAL { 0 }
                    ::= { digitalObjects 262 }

        -- 1.3.6.1.4.1.9839.2.1.1.264
        al-antifrezzer-rec-com OBJECT-TYPE
                    SYNTAX Integer32 (0..1)
                    UNITS "N/A"
                    MAX-ACCESS read-only
                    STATUS current
                    DESCRIPTION "N/A"
                    DEFVAL { 0 }
                    ::= { digitalObjects 264 }

        -- 1.3.6.1.4.1.9839.2.1.1.269
        ovrl-comp1-circ1 OBJECT-TYPE
                    SYNTAX Integer32 (0..1)
                    UNITS "N/A"
                    MAX-ACCESS read-only
                    STATUS current
                    DESCRIPTION "N/A"
                    DEFVAL { 0 }
                    ::= { digitalObjects 269 }

        -- 1.3.6.1.4.1.9839.2.1.1.270
        ovrl-comp2-circ1 OBJECT-TYPE
                    SYNTAX Integer32 (0..1)
                    UNITS "N/A"
                    MAX-ACCESS read-only
                    STATUS current
                    DESCRIPTION "N/A"
                    DEFVAL { 0 }
                    ::= { digitalObjects 270 }

        -- 1.3.6.1.4.1.9839.2.1.1.271
        ovrl-comp3-circ1 OBJECT-TYPE
                    SYNTAX Integer32 (0..1)
                    UNITS "N/A"
                    MAX-ACCESS read-only
                    STATUS current
                    DESCRIPTION "N/A"
                    DEFVAL { 0 }
                    ::= { digitalObjects 271 }

        -- 1.3.6.1.4.1.9839.2.1.1.272
        ovrl-comp1-circ2 OBJECT-TYPE
                    SYNTAX Integer32 (0..1)
                    UNITS "N/A"
                    MAX-ACCESS read-only
                    STATUS current
                    DESCRIPTION "N/A"
                    DEFVAL { 0 }
                    ::= { digitalObjects 272 }

        -- 1.3.6.1.4.1.9839.2.1.1.273
        ovrl-comp2-circ2 OBJECT-TYPE
                    SYNTAX Integer32 (0..1)
                    UNITS "N/A"
                    MAX-ACCESS read-only
                    STATUS current
                    DESCRIPTION "N/A"
                    DEFVAL { 0 }
                    ::= { digitalObjects 273 }

        -- 1.3.6.1.4.1.9839.2.1.1.274
        ovrl-comp3-circ2 OBJECT-TYPE
                    SYNTAX Integer32 (0..1)
                    UNITS "N/A"
                    MAX-ACCESS read-only
                    STATUS current
                    DESCRIPTION "N/A"
                    DEFVAL { 0 }
                    ::= { digitalObjects 274 }

        -- 1.3.6.1.4.1.9839.2.1.1.276
        al-sns-out-evap-com OBJECT-TYPE
                    SYNTAX Integer32 (0..1)
                    UNITS "N/A"
                    MAX-ACCESS read-only
                    STATUS current
                    DESCRIPTION "Specify if evap.outlet probe fault or not connected (0: No alarm; 1: Alarm)"
                    DEFVAL { 0 }
                    ::= { digitalObjects 276 }

        -- 1.3.6.1.4.1.9839.2.1.1.277
        lp-prevent-circ1 OBJECT-TYPE
                    SYNTAX Integer32 (0..1)
                    UNITS "N/A"
                    MAX-ACCESS read-only
                    STATUS current
                    DESCRIPTION "Circuit 1 Warning Low pressure prevent "
                    DEFVAL { 0 }
                    ::= { digitalObjects 277 }

        -- 1.3.6.1.4.1.9839.2.1.1.278
        lp-prevent-circ2 OBJECT-TYPE
                    SYNTAX Integer32 (0..1)
                    UNITS "N/A"
                    MAX-ACCESS read-only
                    STATUS current
                    DESCRIPTION "Circuit 1 Warning Low pressure prevent "
                    DEFVAL { 0 }
                    ::= { digitalObjects 278 }

        -- 1.3.6.1.4.1.9839.2.1.1.280
        hot-forceoff-rec2 OBJECT-TYPE
                    SYNTAX Integer32 (0..1)
                    UNITS "N/A"
                    MAX-ACCESS read-only
                    STATUS current
                    DESCRIPTION "N/A"
                    DEFVAL { 0 }
                    ::= { digitalObjects 280 }

        -- 1.3.6.1.4.1.9839.2.1.1.281
        hot-forceoff-reccom OBJECT-TYPE
                    SYNTAX Integer32 (0..1)
                    UNITS "N/A"
                    MAX-ACCESS read-only
                    STATUS current
                    DESCRIPTION "N/A"
                    DEFVAL { 0 }
                    ::= { digitalObjects 281 }

        -- 1.3.6.1.4.1.9839.2.1.1.282
        tgp-prevent-circ1 OBJECT-TYPE
                    SYNTAX Integer32 (0..1)
                    UNITS "N/A"
                    MAX-ACCESS read-only
                    STATUS current
                    DESCRIPTION "Circuit 1 Warning Low pressure prevent "
                    DEFVAL { 0 }
                    ::= { digitalObjects 282 }

        -- 1.3.6.1.4.1.9839.2.1.1.283
        tgp-prevent-circ2 OBJECT-TYPE
                    SYNTAX Integer32 (0..1)
                    UNITS "N/A"
                    MAX-ACCESS read-only
                    STATUS current
                    DESCRIPTION "Circuit 1 Warning Low pressure prevent "
                    DEFVAL { 0 }
                    ::= { digitalObjects 283 }

        -- 1.3.6.1.4.1.9839.2.1.1.284
        al-tgp-high-circ1 OBJECT-TYPE
                    SYNTAX Integer32 (0..1)
                    UNITS "N/A"
                    MAX-ACCESS read-only
                    STATUS current
                    DESCRIPTION "N/A"
                    DEFVAL { 0 }
                    ::= { digitalObjects 284 }

        -- 1.3.6.1.4.1.9839.2.1.1.285
        al-tgp-high-circ2 OBJECT-TYPE
                    SYNTAX Integer32 (0..1)
                    UNITS "N/A"
                    MAX-ACCESS read-only
                    STATUS current
                    DESCRIPTION "N/A"
                    DEFVAL { 0 }
                    ::= { digitalObjects 285 }

        -- 1.3.6.1.4.1.9839.2.1.1.286
        al-offline-master OBJECT-TYPE
                    SYNTAX Integer32 (0..1)
                    UNITS "N/A"
                    MAX-ACCESS read-only
                    STATUS current
                    DESCRIPTION "N/A"
                    DEFVAL { 0 }
                    ::= { digitalObjects 286 }

        -- 1.3.6.1.4.1.9839.2.1.1.290
        al-high-temp-plant OBJECT-TYPE
                    SYNTAX Integer32 (0..1)
                    UNITS "N/A"
                    MAX-ACCESS read-only
                    STATUS current
                    DESCRIPTION "Analog input 1 alarm status "
                    DEFVAL { 0 }
                    ::= { digitalObjects 290 }

        -- 1.3.6.1.4.1.9839.2.1.1.291
        al-high-temp-rec OBJECT-TYPE
                    SYNTAX Integer32 (0..1)
                    UNITS "N/A"
                    MAX-ACCESS read-only
                    STATUS current
                    DESCRIPTION "Analog input 1 alarm status "
                    DEFVAL { 0 }
                    ::= { digitalObjects 291 }

        -- 1.3.6.1.4.1.9839.2.1.1.300
        force-on-keyb-c1 OBJECT-TYPE
                    SYNTAX Integer32 (0..1)
                    UNITS "N/A"
                    MAX-ACCESS read-write
                    STATUS current
                    DESCRIPTION "N/A"
                    DEFVAL { 1 }
                    ::= { digitalObjects 300 }

        -- 1.3.6.1.4.1.9839.2.1.1.301
        force-on-keyb-c2 OBJECT-TYPE
                    SYNTAX Integer32 (0..1)
                    UNITS "N/A"
                    MAX-ACCESS read-write
                    STATUS current
                    DESCRIPTION "N/A"
                    DEFVAL { 1 }
                    ::= { digitalObjects 301 }



        -- 1.3.6.1.4.1.9839.2.1.2
        analogObjects OBJECT IDENTIFIER ::= { nrlMIB 2 }

        -- 1.3.6.1.4.1.9839.2.1.2.1
        tempoutev-bms OBJECT-TYPE
                    SYNTAX Integer32 (-999..999)
                    UNITS "C x10"
                    MAX-ACCESS read-only
                    STATUS current
                    DESCRIPTION "Outlet water evaporator temp. "
                    DEFVAL { 0 }
                    ::= { analogObjects 1 }

        -- 1.3.6.1.4.1.9839.2.1.2.2
        tempinev-bms OBJECT-TYPE
                    SYNTAX Integer32 (-999..999)
                    UNITS "C x10"
                    MAX-ACCESS read-only
                    STATUS current
                    DESCRIPTION "Inlet water evaporator temp. "
                    DEFVAL { 0 }
                    ::= { analogObjects 2 }

        -- 1.3.6.1.4.1.9839.2.1.2.5
        tempoutrec-bms OBJECT-TYPE
                    SYNTAX Integer32 (-999..999)
                    UNITS "C x10"
                    MAX-ACCESS read-only
                    STATUS current
                    DESCRIPTION "N/A"
                    DEFVAL { 0 }
                    ::= { analogObjects 5 }

        -- 1.3.6.1.4.1.9839.2.1.2.6
        tempinrec-bms OBJECT-TYPE
                    SYNTAX Integer32 (-999..999)
                    UNITS "C x10"
                    MAX-ACCESS read-only
                    STATUS current
                    DESCRIPTION "N/A"
                    DEFVAL { 0 }
                    ::= { analogObjects 6 }

        -- 1.3.6.1.4.1.9839.2.1.2.7
        high-press-circ1-bms OBJECT-TYPE
                    SYNTAX Integer32 (-999..999)
                    UNITS "barg x10"
                    MAX-ACCESS read-only
                    STATUS current
                    DESCRIPTION "High pressue circuit1 (B1)"
                    DEFVAL { 0 }
                    ::= { analogObjects 7 }

        -- 1.3.6.1.4.1.9839.2.1.2.8
        low-press-circ1-bms OBJECT-TYPE
                    SYNTAX Integer32 (-999..999)
                    UNITS "barg x10"
                    MAX-ACCESS read-write
                    STATUS current
                    DESCRIPTION "High pressue circuit1 (B1)"
                    DEFVAL { 0 }
                    ::= { analogObjects 8 }

        -- 1.3.6.1.4.1.9839.2.1.2.9
        high-press-circ2-bms OBJECT-TYPE
                    SYNTAX Integer32 (-999..999)
                    UNITS "barg x10"
                    MAX-ACCESS read-only
                    STATUS current
                    DESCRIPTION "High pressue circuit1 (B1)"
                    DEFVAL { 0 }
                    ::= { analogObjects 9 }

        -- 1.3.6.1.4.1.9839.2.1.2.10
        low-press-circ2-bms OBJECT-TYPE
                    SYNTAX Integer32 (-999..999)
                    UNITS "barg x10"
                    MAX-ACCESS read-only
                    STATUS current
                    DESCRIPTION "High pressue circuit1 (B1)"
                    DEFVAL { 0 }
                    ::= { analogObjects 10 }

        -- 1.3.6.1.4.1.9839.2.1.2.11
        tempairext-bms OBJECT-TYPE
                    SYNTAX Integer32 (-999..999)
                    UNITS "C x10"
                    MAX-ACCESS read-only
                    STATUS current
                    DESCRIPTION "External temperature "
                    DEFVAL { 0 }
                    ::= { analogObjects 11 }

        -- 1.3.6.1.4.1.9839.2.1.2.12
        temp-tgp-circ1-bms OBJECT-TYPE
                    SYNTAX Integer32 (-9999..9999)
                    UNITS "C x10"
                    MAX-ACCESS read-only
                    STATUS current
                    DESCRIPTION "N/A"
                    DEFVAL { 0 }
                    ::= { analogObjects 12 }

        -- 1.3.6.1.4.1.9839.2.1.2.13
        temp-tgp-circ2-bms OBJECT-TYPE
                    SYNTAX Integer32 (-9999..9999)
                    UNITS "C x10"
                    MAX-ACCESS read-only
                    STATUS current
                    DESCRIPTION "N/A"
                    DEFVAL { 0 }
                    ::= { analogObjects 13 }

        -- 1.3.6.1.4.1.9839.2.1.2.14
        temp-liquido-circ1-bms OBJECT-TYPE
                    SYNTAX Integer32 (-999..999)
                    UNITS "C x10"
                    MAX-ACCESS read-only
                    STATUS current
                    DESCRIPTION "N/A"
                    DEFVAL { 0 }
                    ::= { analogObjects 14 }

        -- 1.3.6.1.4.1.9839.2.1.2.15
        temp-liquido-circ2-bms OBJECT-TYPE
                    SYNTAX Integer32 (-999..999)
                    UNITS "C x10"
                    MAX-ACCESS read-only
                    STATUS current
                    DESCRIPTION "N/A"
                    DEFVAL { 0 }
                    ::= { analogObjects 15 }

        -- 1.3.6.1.4.1.9839.2.1.2.16
        temp-board OBJECT-TYPE
                    SYNTAX Integer32 (-300..700)
                    UNITS "N/A"
                    MAX-ACCESS read-only
                    STATUS current
                    DESCRIPTION "Temperature of the controller board"
                    DEFVAL { 0 }
                    ::= { analogObjects 16 }

        -- 1.3.6.1.4.1.9839.2.1.2.17
        temp-liquido-circ1b-bms OBJECT-TYPE
                    SYNTAX Integer32 (-999..999)
                    UNITS "C x10"
                    MAX-ACCESS read-only
                    STATUS current
                    DESCRIPTION "N/A"
                    DEFVAL { 0 }
                    ::= { analogObjects 17 }

        -- 1.3.6.1.4.1.9839.2.1.2.18
        millisecmaintimecycle OBJECT-TYPE
                    SYNTAX Integer32 (0..32767)
                    UNITS "N/A"
                    MAX-ACCESS read-only
                    STATUS current
                    DESCRIPTION "N/A"
                    DEFVAL { 0 }
                    ::= { analogObjects 18 }

        -- 1.3.6.1.4.1.9839.2.1.2.19
        ain-multifunction OBJECT-TYPE
                    SYNTAX Integer32 (-999..999)
                    UNITS "N/A"
                    MAX-ACCESS read-only
                    STATUS current
                    DESCRIPTION "Multifunction input (B8)"
                    DEFVAL { 0 }
                    ::= { analogObjects 19 }

        -- 1.3.6.1.4.1.9839.2.1.2.21
        out-evap-com-bms OBJECT-TYPE
                    SYNTAX Integer32 (-999..999)
                    UNITS "C x10"
                    MAX-ACCESS read-only
                    STATUS current
                    DESCRIPTION "N/A"
                    DEFVAL { 0 }
                    ::= { analogObjects 21 }

        -- 1.3.6.1.4.1.9839.2.1.2.23
        sanitary-temp-bms OBJECT-TYPE
                    SYNTAX Integer32 (-9999..9999)
                    UNITS "C x10"
                    MAX-ACCESS read-only
                    STATUS current
                    DESCRIPTION "Outlet water temperature plant circuit exchanger"
                    DEFVAL { 0 }
                    ::= { analogObjects 23 }

        -- 1.3.6.1.4.1.9839.2.1.2.24
        msk-sw-ver OBJECT-TYPE
                    SYNTAX Integer32 (0..99)
                    UNITS "N/A"
                    MAX-ACCESS read-only
                    STATUS current
                    DESCRIPTION "N/A"
                    DEFVAL { 99 }
                    ::= { analogObjects 24 }

        -- 1.3.6.1.4.1.9839.2.1.2.25
        msk-sw-build OBJECT-TYPE
                    SYNTAX Integer32 (0..99)
                    UNITS "N/A"
                    MAX-ACCESS read-only
                    STATUS current
                    DESCRIPTION "N/A"
                    DEFVAL { 9 }
                    ::= { analogObjects 25 }

        -- 1.3.6.1.4.1.9839.2.1.2.27
        tempoutev2-bms OBJECT-TYPE
                    SYNTAX Integer32 (-999..999)
                    UNITS "C x10"
                    MAX-ACCESS read-only
                    STATUS current
                    DESCRIPTION "Outlet water evaporator temp. (B3)"
                    DEFVAL { 0 }
                    ::= { analogObjects 27 }

        -- 1.3.6.1.4.1.9839.2.1.2.28
        tempoutevcom-dk-bms OBJECT-TYPE
                    SYNTAX Integer32 (-999..999)
                    UNITS "C x10"
                    MAX-ACCESS read-only
                    STATUS current
                    DESCRIPTION "Outlet water evaporator temp. (B3)"
                    DEFVAL { 0 }
                    ::= { analogObjects 28 }

        -- 1.3.6.1.4.1.9839.2.1.2.29
        low-press-highres-circ1-bms OBJECT-TYPE
                    SYNTAX Integer32 (-999..999)
                    UNITS "barg x10"
                    MAX-ACCESS read-write
                    STATUS current
                    DESCRIPTION "High pressue circuit1 (B1)"
                    DEFVAL { 0 }
                    ::= { analogObjects 29 }

        -- 1.3.6.1.4.1.9839.2.1.2.30
        bpmediahighresc1-highres-bms OBJECT-TYPE
                    SYNTAX Integer32 (0..32767)
                    UNITS "N/A"
                    MAX-ACCESS read-only
                    STATUS current
                    DESCRIPTION "N/A"
                    DEFVAL { 0 }
                    ::= { analogObjects 30 }

        -- 1.3.6.1.4.1.9839.2.1.2.31
        delta-lp-act-circ1-highres-bms OBJECT-TYPE
                    SYNTAX Integer32 (-999..999)
                    UNITS "barg x10"
                    MAX-ACCESS read-only
                    STATUS current
                    DESCRIPTION "N/A"
                    DEFVAL { 0 }
                    ::= { analogObjects 31 }

        -- 1.3.6.1.4.1.9839.2.1.2.32
        low-press-highres-circ2-bms OBJECT-TYPE
                    SYNTAX Integer32 (-999..999)
                    UNITS "barg x10"
                    MAX-ACCESS read-write
                    STATUS current
                    DESCRIPTION "High pressue circuit1 (B1)"
                    DEFVAL { 0 }
                    ::= { analogObjects 32 }

        -- 1.3.6.1.4.1.9839.2.1.2.33
        bpmediahighresc2-highres-bms OBJECT-TYPE
                    SYNTAX Integer32 (0..32767)
                    UNITS "N/A"
                    MAX-ACCESS read-only
                    STATUS current
                    DESCRIPTION "N/A"
                    DEFVAL { 0 }
                    ::= { analogObjects 33 }

        -- 1.3.6.1.4.1.9839.2.1.2.34
        delta-lp-act-circ2-highres-bms OBJECT-TYPE
                    SYNTAX Integer32 (-999..999)
                    UNITS "barg x10"
                    MAX-ACCESS read-only
                    STATUS current
                    DESCRIPTION "N/A"
                    DEFVAL { 0 }
                    ::= { analogObjects 34 }

        -- 1.3.6.1.4.1.9839.2.1.2.35
        temp-sac-bms OBJECT-TYPE
                    SYNTAX Integer32 (-999..999)
                    UNITS "C x10"
                    MAX-ACCESS read-only
                    STATUS current
                    DESCRIPTION "N/A"
                    DEFVAL { 0 }
                    ::= { analogObjects 35 }

        -- 1.3.6.1.4.1.9839.2.1.2.37
        tempoutrec2-bms OBJECT-TYPE
                    SYNTAX Integer32 (-999..999)
                    UNITS "C x10"
                    MAX-ACCESS read-write
                    STATUS current
                    DESCRIPTION "N/A"
                    DEFVAL { 0 }
                    ::= { analogObjects 37 }

        -- 1.3.6.1.4.1.9839.2.1.2.38
        tempingressofreecooling-bms OBJECT-TYPE
                    SYNTAX Integer32 (-9990..9999)
                    UNITS "N/A"
                    MAX-ACCESS read-only
                    STATUS current
                    DESCRIPTION "N/A"
                    DEFVAL { 0 }
                    ::= { analogObjects 38 }

        -- 1.3.6.1.4.1.9839.2.1.2.39
        tempuscitafreecooling-bms OBJECT-TYPE
                    SYNTAX Integer32 (-32768..32767)
                    UNITS "N/A"
                    MAX-ACCESS read-only
                    STATUS current
                    DESCRIPTION "N/A"
                    DEFVAL { 0 }
                    ::= { analogObjects 39 }

        -- 1.3.6.1.4.1.9839.2.1.2.40
        tempinscambiatoreintermedio-bms OBJECT-TYPE
                    SYNTAX Integer32 (-32768..32767)
                    UNITS "N/A"
                    MAX-ACCESS read-only
                    STATUS current
                    DESCRIPTION "N/A"
                    DEFVAL { 0 }
                    ::= { analogObjects 40 }

        -- 1.3.6.1.4.1.9839.2.1.2.50
        high-press-circ1-conv-bms OBJECT-TYPE
                    SYNTAX Integer32 (-32768..32767)
                    UNITS "C/F x10"
                    MAX-ACCESS read-only
                    STATUS current
                    DESCRIPTION "High pressure circuit 1 converted to temperature"
                    DEFVAL { 0 }
                    ::= { analogObjects 50 }

        -- 1.3.6.1.4.1.9839.2.1.2.51
        low-press-circ1-conv-bms OBJECT-TYPE
                    SYNTAX Integer32 (-32768..32767)
                    UNITS "C/F x10"
                    MAX-ACCESS read-only
                    STATUS current
                    DESCRIPTION "Low pressure circuit 1 converted to temperature"
                    DEFVAL { 0 }
                    ::= { analogObjects 51 }

        -- 1.3.6.1.4.1.9839.2.1.2.52
        high-press-circ2-conv-bms OBJECT-TYPE
                    SYNTAX Integer32 (-32768..32767)
                    UNITS "C/F x10"
                    MAX-ACCESS read-only
                    STATUS current
                    DESCRIPTION "High pressure circuit 1 converted to temperature"
                    DEFVAL { 0 }
                    ::= { analogObjects 52 }

        -- 1.3.6.1.4.1.9839.2.1.2.53
        low-press-circ2-conv-bms OBJECT-TYPE
                    SYNTAX Integer32 (-32768..32767)
                    UNITS "C/F x10"
                    MAX-ACCESS read-only
                    STATUS current
                    DESCRIPTION "Low pressure circuit 1 converted to temperature"
                    DEFVAL { 0 }
                    ::= { analogObjects 53 }

        -- 1.3.6.1.4.1.9839.2.1.2.100
        mod-evdevo-2-1.a10-sh-sh-msk OBJECT-TYPE
                    SYNTAX Integer32 (-720..3240)
                    UNITS "N/A"
                    MAX-ACCESS read-only
                    STATUS current
                    DESCRIPTION "Superheat"
                    DEFVAL { 0 }
                    ::= { analogObjects 100 }

        -- 1.3.6.1.4.1.9839.2.1.2.101
        mod-evdevo-2-1.a68-sh-sh-2nd-msk OBJECT-TYPE
                    SYNTAX Integer32 (-720..3240)
                    UNITS "N/A"
                    MAX-ACCESS read-only
                    STATUS current
                    DESCRIPTION "Superheat - Valve B"
                    DEFVAL { 0 }
                    ::= { analogObjects 101 }

        -- 1.3.6.1.4.1.9839.2.1.2.102
        sh-suct-temp-bms OBJECT-TYPE
                    SYNTAX Integer32 (0..9999)
                    UNITS "N/A"
                    MAX-ACCESS read-only
                    STATUS current
                    DESCRIPTION "N/A"
                    DEFVAL { 0 }
                    ::= { analogObjects 102 }

        -- 1.3.6.1.4.1.9839.2.1.2.103
        sh-evap-pres-bms OBJECT-TYPE
                    SYNTAX Integer32 (0..9999)
                    UNITS "N/A"
                    MAX-ACCESS read-only
                    STATUS current
                    DESCRIPTION "N/A"
                    DEFVAL { 0 }
                    ::= { analogObjects 103 }

        -- 1.3.6.1.4.1.9839.2.1.2.104
        sh-suct-temp-2nd-bms OBJECT-TYPE
                    SYNTAX Integer32 (0..9999)
                    UNITS "N/A"
                    MAX-ACCESS read-only
                    STATUS current
                    DESCRIPTION "N/A"
                    DEFVAL { 0 }
                    ::= { analogObjects 104 }

        -- 1.3.6.1.4.1.9839.2.1.2.105
        sh-evap-pres-2nd-bms OBJECT-TYPE
                    SYNTAX Integer32 (0..9999)
                    UNITS "N/A"
                    MAX-ACCESS read-only
                    STATUS current
                    DESCRIPTION "N/A"
                    DEFVAL { 0 }
                    ::= { analogObjects 105 }

        -- 1.3.6.1.4.1.9839.2.1.2.106
        mod-evdevo-2-1.a17-eev-position-percent-show OBJECT-TYPE
                    SYNTAX Integer32 (0..1000)
                    UNITS "N/A"
                    MAX-ACCESS read-only
                    STATUS current
                    DESCRIPTION "Valve A opening percent"
                    DEFVAL { 0 }
                    ::= { analogObjects 106 }

        -- 1.3.6.1.4.1.9839.2.1.2.107
        mod-evdevo-2-1.a66-eev-pos-percent-2nd-show OBJECT-TYPE
                    SYNTAX Integer32 (0..1000)
                    UNITS "% x10"
                    MAX-ACCESS read-only
                    STATUS current
                    DESCRIPTION "Opening percent - Valve B"
                    DEFVAL { 0 }
                    ::= { analogObjects 107 }

        -- 1.3.6.1.4.1.9839.2.1.2.120
        temp-aspirazione-circ1-bms OBJECT-TYPE
                    SYNTAX Integer32 (-999..999)
                    UNITS "C x10"
                    MAX-ACCESS read-only
                    STATUS current
                    DESCRIPTION "N/A"
                    DEFVAL { 0 }
                    ::= { analogObjects 120 }

        -- 1.3.6.1.4.1.9839.2.1.2.121
        temp-aspirazione-circ2-bms OBJECT-TYPE
                    SYNTAX Integer32 (-999..999)
                    UNITS "C x10"
                    MAX-ACCESS read-only
                    STATUS current
                    DESCRIPTION "N/A"
                    DEFVAL { 0 }
                    ::= { analogObjects 121 }

        -- 1.3.6.1.4.1.9839.2.1.2.122
        surriscaldamentocalcolatoc1 OBJECT-TYPE
                    SYNTAX Integer32 (-999..999)
                    UNITS "C x10"
                    MAX-ACCESS read-only
                    STATUS current
                    DESCRIPTION "N/A"
                    DEFVAL { 0 }
                    ::= { analogObjects 122 }

        -- 1.3.6.1.4.1.9839.2.1.2.123
        surriscaldamentocalcolatoc2 OBJECT-TYPE
                    SYNTAX Integer32 (-999..999)
                    UNITS "C x10"
                    MAX-ACCESS read-only
                    STATUS current
                    DESCRIPTION "N/A"
                    DEFVAL { 0 }
                    ::= { analogObjects 123 }

        -- 1.3.6.1.4.1.9839.2.1.2.124
        sottoraffreddamentocalcolatoc1 OBJECT-TYPE
                    SYNTAX Integer32 (-999..999)
                    UNITS "C x10"
                    MAX-ACCESS read-only
                    STATUS current
                    DESCRIPTION "N/A"
                    DEFVAL { 0 }
                    ::= { analogObjects 124 }

        -- 1.3.6.1.4.1.9839.2.1.2.125
        sottoraffreddamentocalcolatoc2 OBJECT-TYPE
                    SYNTAX Integer32 (-999..999)
                    UNITS "C x10"
                    MAX-ACCESS read-only
                    STATUS current
                    DESCRIPTION "N/A"
                    DEFVAL { 0 }
                    ::= { analogObjects 125 }

        -- 1.3.6.1.4.1.9839.2.1.2.180
        outkp-rec1 OBJECT-TYPE
                    SYNTAX Integer32 (0..32767)
                    UNITS "N/A"
                    MAX-ACCESS read-only
                    STATUS current
                    DESCRIPTION "N/A"
                    DEFVAL { 0 }
                    ::= { analogObjects 180 }

        -- 1.3.6.1.4.1.9839.2.1.2.181
        outkp-plant OBJECT-TYPE
                    SYNTAX Integer32 (0..32767)
                    UNITS "N/A"
                    MAX-ACCESS read-only
                    STATUS current
                    DESCRIPTION "N/A"
                    DEFVAL { 0 }
                    ::= { analogObjects 181 }

        -- 1.3.6.1.4.1.9839.2.1.2.182
        outki-rec OBJECT-TYPE
                    SYNTAX Integer32 (0..1000)
                    UNITS "N/A"
                    MAX-ACCESS read-only
                    STATUS current
                    DESCRIPTION "N/A"
                    DEFVAL { 0 }
                    ::= { analogObjects 182 }

        -- 1.3.6.1.4.1.9839.2.1.2.183
        outki-plant OBJECT-TYPE
                    SYNTAX Integer32 (0..1000)
                    UNITS "N/A"
                    MAX-ACCESS read-only
                    STATUS current
                    DESCRIPTION "N/A"
                    DEFVAL { 0 }
                    ::= { analogObjects 183 }

        -- 1.3.6.1.4.1.9839.2.1.2.184
        lmt-set-heating-plant OBJECT-TYPE
                    SYNTAX Integer32 (0..1000)
                    UNITS "N/A"
                    MAX-ACCESS read-only
                    STATUS current
                    DESCRIPTION "N/A"
                    DEFVAL { 0 }
                    ::= { analogObjects 184 }

        -- 1.3.6.1.4.1.9839.2.1.2.185
        lmt-set-cooling-plant OBJECT-TYPE
                    SYNTAX Integer32 (0..1000)
                    UNITS "N/A"
                    MAX-ACCESS read-only
                    STATUS current
                    DESCRIPTION "N/A"
                    DEFVAL { 0 }
                    ::= { analogObjects 185 }

        -- 1.3.6.1.4.1.9839.2.1.2.186
        lmt-set-heating-rec OBJECT-TYPE
                    SYNTAX Integer32 (0..1000)
                    UNITS "N/A"
                    MAX-ACCESS read-only
                    STATUS current
                    DESCRIPTION "N/A"
                    DEFVAL { 0 }
                    ::= { analogObjects 186 }

        -- 1.3.6.1.4.1.9839.2.1.2.187
        delta-lp-act-circ1-bms OBJECT-TYPE
                    SYNTAX Integer32 (-999..999)
                    UNITS "barg x10"
                    MAX-ACCESS read-only
                    STATUS current
                    DESCRIPTION "N/A"
                    DEFVAL { 0 }
                    ::= { analogObjects 187 }

        -- 1.3.6.1.4.1.9839.2.1.2.188
        delta-lp-act-circ2-bms OBJECT-TYPE
                    SYNTAX Integer32 (-999..999)
                    UNITS "barg x10"
                    MAX-ACCESS read-only
                    STATUS current
                    DESCRIPTION "N/A"
                    DEFVAL { 0 }
                    ::= { analogObjects 188 }

        -- 1.3.6.1.4.1.9839.2.1.2.189
        kp-fan1-bms OBJECT-TYPE
                    SYNTAX Integer32 (0..999)
                    UNITS "N/A"
                    MAX-ACCESS read-only
                    STATUS current
                    DESCRIPTION "N/A"
                    DEFVAL { 0 }
                    ::= { analogObjects 189 }

        -- 1.3.6.1.4.1.9839.2.1.2.190
        kp-fan2-bms OBJECT-TYPE
                    SYNTAX Integer32 (0..999)
                    UNITS "N/A"
                    MAX-ACCESS read-only
                    STATUS current
                    DESCRIPTION "N/A"
                    DEFVAL { 0 }
                    ::= { analogObjects 190 }

        -- 1.3.6.1.4.1.9839.2.1.2.191
        fan-setpoint-bms OBJECT-TYPE
                    SYNTAX Integer32 (0..9999)
                    UNITS "barg x10"
                    MAX-ACCESS read-only
                    STATUS current
                    DESCRIPTION "Current condenser fan setpoint"
                    DEFVAL { 0 }
                    ::= { analogObjects 191 }

        -- 1.3.6.1.4.1.9839.2.1.2.192
        fan-setpoint2-bms OBJECT-TYPE
                    SYNTAX Integer32 (0..999)
                    UNITS "barg x10"
                    MAX-ACCESS read-only
                    STATUS current
                    DESCRIPTION "Current condenser fan setpoint"
                    DEFVAL { 0 }
                    ::= { analogObjects 192 }

        -- 1.3.6.1.4.1.9839.2.1.2.195
        act-diff-rec OBJECT-TYPE
                    SYNTAX Integer32 (0..999)
                    UNITS "C x10"
                    MAX-ACCESS read-only
                    STATUS current
                    DESCRIPTION "N/A"
                    DEFVAL { 0 }
                    ::= { analogObjects 195 }

        -- 1.3.6.1.4.1.9839.2.1.2.196
        act-set-rec OBJECT-TYPE
                    SYNTAX Integer32 (-999..999)
                    UNITS "C x10"
                    MAX-ACCESS read-only
                    STATUS current
                    DESCRIPTION "N/A"
                    DEFVAL { 0 }
                    ::= { analogObjects 196 }

        -- 1.3.6.1.4.1.9839.2.1.2.197
        diff-plant-act OBJECT-TYPE
                    SYNTAX Integer32 (0..999)
                    UNITS "C x10"
                    MAX-ACCESS read-only
                    STATUS current
                    DESCRIPTION "N/A"
                    DEFVAL { 0 }
                    ::= { analogObjects 197 }

        -- 1.3.6.1.4.1.9839.2.1.2.198
        set-plant-act-bms OBJECT-TYPE
                    SYNTAX Integer32 (-9999..9999)
                    UNITS "C x10"
                    MAX-ACCESS read-only
                    STATUS current
                    DESCRIPTION "Current setpoint"
                    DEFVAL { 0 }
                    ::= { analogObjects 198 }

        -- 1.3.6.1.4.1.9839.2.1.2.199
        setpoint1-rec-bms OBJECT-TYPE
                    SYNTAX Integer32 (0..999)
                    UNITS "C x10"
                    MAX-ACCESS read-write
                    STATUS current
                    DESCRIPTION "N/A"
                    DEFVAL { 0 }
                    ::= { analogObjects 199 }

        -- 1.3.6.1.4.1.9839.2.1.2.200
        setpoint2-rec OBJECT-TYPE
                    SYNTAX Integer32 (0..999)
                    UNITS "C x10"
                    MAX-ACCESS read-write
                    STATUS current
                    DESCRIPTION "N/A"
                    DEFVAL { 0 }
                    ::= { analogObjects 200 }

        -- 1.3.6.1.4.1.9839.2.1.2.201
        diff-recovery-bms OBJECT-TYPE
                    SYNTAX Integer32 (0..999)
                    UNITS "C x10"
                    MAX-ACCESS read-write
                    STATUS current
                    DESCRIPTION "N/A"
                    DEFVAL { 0 }
                    ::= { analogObjects 201 }

        -- 1.3.6.1.4.1.9839.2.1.2.202
        diff-cooling-plant-bms OBJECT-TYPE
                    SYNTAX Integer32 (0..999)
                    UNITS "C x10"
                    MAX-ACCESS read-write
                    STATUS current
                    DESCRIPTION "Cooling temperature setpoint1"
                    DEFVAL { 50 }
                    ::= { analogObjects 202 }

        -- 1.3.6.1.4.1.9839.2.1.2.203
        diff-heating-plant-bms OBJECT-TYPE
                    SYNTAX Integer32 (-9999..9999)
                    UNITS "C x10"
                    MAX-ACCESS read-write
                    STATUS current
                    DESCRIPTION "Cooling temperature setpoint1"
                    DEFVAL { 120 }
                    ::= { analogObjects 203 }

        -- 1.3.6.1.4.1.9839.2.1.2.204
        cooling-temp-set1-bms OBJECT-TYPE
                    SYNTAX Integer32 (-999..999)
                    UNITS "C x10"
                    MAX-ACCESS read-write
                    STATUS current
                    DESCRIPTION "Cooling temperature setpoint1"
                    DEFVAL { 120 }
                    ::= { analogObjects 204 }

        -- 1.3.6.1.4.1.9839.2.1.2.205
        cooling-temp-set2-bms OBJECT-TYPE
                    SYNTAX Integer32 (-999..999)
                    UNITS "C x10"
                    MAX-ACCESS read-write
                    STATUS current
                    DESCRIPTION "Cooling temperature setpoint1"
                    DEFVAL { 120 }
                    ::= { analogObjects 205 }

        -- 1.3.6.1.4.1.9839.2.1.2.206
        heating-temp-set1-bms OBJECT-TYPE
                    SYNTAX Integer32 (-999..999)
                    UNITS "C x10"
                    MAX-ACCESS read-write
                    STATUS current
                    DESCRIPTION "Heating temperature setpoint2"
                    DEFVAL { 400 }
                    ::= { analogObjects 206 }

        -- 1.3.6.1.4.1.9839.2.1.2.207
        heating-temp-set2-bms OBJECT-TYPE
                    SYNTAX Integer32 (-999..999)
                    UNITS "C x10"
                    MAX-ACCESS read-write
                    STATUS current
                    DESCRIPTION "Heating temperature setpoint2"
                    DEFVAL { 400 }
                    ::= { analogObjects 207 }



        -- 1.3.6.1.4.1.9839.2.1.3
        integerObjects OBJECT IDENTIFIER ::= { nrlMIB 3 }

        -- 1.3.6.1.4.1.9839.2.1.3.1
        onoff-mode-plant OBJECT-TYPE
                    SYNTAX Integer32 (0..3)
                    UNITS "N/A"
                    MAX-ACCESS read-write
                    STATUS current
                    DESCRIPTION "N/A"
                    DEFVAL { 0 }
                    ::= { integerObjects 1 }

        -- 1.3.6.1.4.1.9839.2.1.3.2
        onoff-mode-rec OBJECT-TYPE
                    SYNTAX Integer32 (0..3)
                    UNITS "N/A"
                    MAX-ACCESS read-write
                    STATUS current
                    DESCRIPTION "N/A"
                    DEFVAL { 0 }
                    ::= { integerObjects 2 }

        -- 1.3.6.1.4.1.9839.2.1.3.3
        sum-winter-select OBJECT-TYPE
                    SYNTAX Integer32 (0..3)
                    UNITS "N/A"
                    MAX-ACCESS read-write
                    STATUS current
                    DESCRIPTION "N/A"
                    DEFVAL { 0 }
                    ::= { integerObjects 3 }

        -- 1.3.6.1.4.1.9839.2.1.3.4
        demandlimitbms OBJECT-TYPE
                    SYNTAX Integer32 (0..1000)
                    UNITS "N/A"
                    MAX-ACCESS read-write
                    STATUS current
                    DESCRIPTION "N/A"
                    DEFVAL { 0 }
                    ::= { integerObjects 4 }

        -- 1.3.6.1.4.1.9839.2.1.3.5
        termostatoremoto OBJECT-TYPE
                    SYNTAX Integer32 (0..9999)
                    UNITS "%"
                    MAX-ACCESS read-write
                    STATUS current
                    DESCRIPTION "Power request"
                    DEFVAL { 0 }
                    ::= { integerObjects 5 }

        -- 1.3.6.1.4.1.9839.2.1.3.6
        poweract-plant OBJECT-TYPE
                    SYNTAX Integer32 (0..100)
                    UNITS "%"
                    MAX-ACCESS read-only
                    STATUS current
                    DESCRIPTION "N/A"
                    DEFVAL { 0 }
                    ::= { integerObjects 6 }

        -- 1.3.6.1.4.1.9839.2.1.3.7
        poweract-rec OBJECT-TYPE
                    SYNTAX Integer32 (0..100)
                    UNITS "%"
                    MAX-ACCESS read-only
                    STATUS current
                    DESCRIPTION "N/A"
                    DEFVAL { 0 }
                    ::= { integerObjects 7 }

        -- 1.3.6.1.4.1.9839.2.1.3.8
        orepompa1-h OBJECT-TYPE
                    SYNTAX Integer32 (0..32767)
                    UNITS "N/A"
                    MAX-ACCESS read-only
                    STATUS current
                    DESCRIPTION "N/A"
                    DEFVAL { 0 }
                    ::= { integerObjects 8 }

        -- 1.3.6.1.4.1.9839.2.1.3.9
        orepompa1-l OBJECT-TYPE
                    SYNTAX Integer32 (0..32767)
                    UNITS "N/A"
                    MAX-ACCESS read-only
                    STATUS current
                    DESCRIPTION "N/A"
                    DEFVAL { 0 }
                    ::= { integerObjects 9 }

        -- 1.3.6.1.4.1.9839.2.1.3.10
        orepompa2-h OBJECT-TYPE
                    SYNTAX Integer32 (0..32767)
                    UNITS "N/A"
                    MAX-ACCESS read-only
                    STATUS current
                    DESCRIPTION "N/A"
                    DEFVAL { 0 }
                    ::= { integerObjects 10 }

        -- 1.3.6.1.4.1.9839.2.1.3.11
        orepompa2-l OBJECT-TYPE
                    SYNTAX Integer32 (0..32767)
                    UNITS "N/A"
                    MAX-ACCESS read-only
                    STATUS current
                    DESCRIPTION "N/A"
                    DEFVAL { 0 }
                    ::= { integerObjects 11 }

        -- 1.3.6.1.4.1.9839.2.1.3.12
        orecp1-h OBJECT-TYPE
                    SYNTAX Integer32 (0..32767)
                    UNITS "N/A"
                    MAX-ACCESS read-only
                    STATUS current
                    DESCRIPTION "N/A"
                    DEFVAL { 0 }
                    ::= { integerObjects 12 }

        -- 1.3.6.1.4.1.9839.2.1.3.13
        orecp1-l OBJECT-TYPE
                    SYNTAX Integer32 (0..32767)
                    UNITS "N/A"
                    MAX-ACCESS read-only
                    STATUS current
                    DESCRIPTION "N/A"
                    DEFVAL { 0 }
                    ::= { integerObjects 13 }

        -- 1.3.6.1.4.1.9839.2.1.3.14
        orecp1a-h OBJECT-TYPE
                    SYNTAX Integer32 (0..32767)
                    UNITS "N/A"
                    MAX-ACCESS read-only
                    STATUS current
                    DESCRIPTION "N/A"
                    DEFVAL { 0 }
                    ::= { integerObjects 14 }

        -- 1.3.6.1.4.1.9839.2.1.3.15
        orecp1a-l OBJECT-TYPE
                    SYNTAX Integer32 (0..32767)
                    UNITS "N/A"
                    MAX-ACCESS read-only
                    STATUS current
                    DESCRIPTION "N/A"
                    DEFVAL { 0 }
                    ::= { integerObjects 15 }

        -- 1.3.6.1.4.1.9839.2.1.3.16
        orecp1b-h OBJECT-TYPE
                    SYNTAX Integer32 (0..32767)
                    UNITS "N/A"
                    MAX-ACCESS read-only
                    STATUS current
                    DESCRIPTION "N/A"
                    DEFVAL { 0 }
                    ::= { integerObjects 16 }

        -- 1.3.6.1.4.1.9839.2.1.3.17
        orecp1b-l OBJECT-TYPE
                    SYNTAX Integer32 (0..32767)
                    UNITS "N/A"
                    MAX-ACCESS read-only
                    STATUS current
                    DESCRIPTION "N/A"
                    DEFVAL { 0 }
                    ::= { integerObjects 17 }

        -- 1.3.6.1.4.1.9839.2.1.3.18
        orecp2-h OBJECT-TYPE
                    SYNTAX Integer32 (0..32767)
                    UNITS "N/A"
                    MAX-ACCESS read-only
                    STATUS current
                    DESCRIPTION "N/A"
                    DEFVAL { 0 }
                    ::= { integerObjects 18 }

        -- 1.3.6.1.4.1.9839.2.1.3.19
        orecp2-l OBJECT-TYPE
                    SYNTAX Integer32 (0..32767)
                    UNITS "N/A"
                    MAX-ACCESS read-only
                    STATUS current
                    DESCRIPTION "N/A"
                    DEFVAL { 0 }
                    ::= { integerObjects 19 }

        -- 1.3.6.1.4.1.9839.2.1.3.20
        orecp2a-h OBJECT-TYPE
                    SYNTAX Integer32 (0..32767)
                    UNITS "N/A"
                    MAX-ACCESS read-only
                    STATUS current
                    DESCRIPTION "N/A"
                    DEFVAL { 0 }
                    ::= { integerObjects 20 }

        -- 1.3.6.1.4.1.9839.2.1.3.21
        orecp2a-l OBJECT-TYPE
                    SYNTAX Integer32 (0..32767)
                    UNITS "N/A"
                    MAX-ACCESS read-only
                    STATUS current
                    DESCRIPTION "N/A"
                    DEFVAL { 0 }
                    ::= { integerObjects 21 }

        -- 1.3.6.1.4.1.9839.2.1.3.22
        orecp2b-h OBJECT-TYPE
                    SYNTAX Integer32 (0..32767)
                    UNITS "N/A"
                    MAX-ACCESS read-only
                    STATUS current
                    DESCRIPTION "N/A"
                    DEFVAL { 0 }
                    ::= { integerObjects 22 }

        -- 1.3.6.1.4.1.9839.2.1.3.23
        orecp2b-l OBJECT-TYPE
                    SYNTAX Integer32 (0..32767)
                    UNITS "N/A"
                    MAX-ACCESS read-only
                    STATUS current
                    DESCRIPTION "N/A"
                    DEFVAL { 0 }
                    ::= { integerObjects 23 }

        -- 1.3.6.1.4.1.9839.2.1.3.24
        mediamaintimecycle OBJECT-TYPE
                    SYNTAX Integer32 (0..32767)
                    UNITS "N/A"
                    MAX-ACCESS read-only
                    STATUS current
                    DESCRIPTION "N/A"
                    DEFVAL { 0 }
                    ::= { integerObjects 24 }

        -- 1.3.6.1.4.1.9839.2.1.3.25
        not-used-x OBJECT-TYPE
                    SYNTAX Integer32 (-32768..32767)
                    UNITS "N/A"
                    MAX-ACCESS read-only
                    STATUS current
                    DESCRIPTION "N/A"
                    DEFVAL { 0 }
                    ::= { integerObjects 25 }

        -- 1.3.6.1.4.1.9839.2.1.3.26
        msk-cond-fan-group1 OBJECT-TYPE
                    SYNTAX Integer32 (0..100)
                    UNITS "%"
                    MAX-ACCESS read-only
                    STATUS current
                    DESCRIPTION "N/A"
                    DEFVAL { 0 }
                    ::= { integerObjects 26 }

        -- 1.3.6.1.4.1.9839.2.1.3.27
        msk-cond-fan-group2 OBJECT-TYPE
                    SYNTAX Integer32 (0..100)
                    UNITS "%"
                    MAX-ACCESS read-only
                    STATUS current
                    DESCRIPTION "N/A"
                    DEFVAL { 0 }
                    ::= { integerObjects 27 }

        -- 1.3.6.1.4.1.9839.2.1.3.28
        msk-cond-fan-group3 OBJECT-TYPE
                    SYNTAX Integer32 (0..100)
                    UNITS "%"
                    MAX-ACCESS read-only
                    STATUS current
                    DESCRIPTION "N/A"
                    DEFVAL { 0 }
                    ::= { integerObjects 28 }

        -- 1.3.6.1.4.1.9839.2.1.3.29
        plant-request-mask OBJECT-TYPE
                    SYNTAX Integer32 (0..100)
                    UNITS "%"
                    MAX-ACCESS read-only
                    STATUS current
                    DESCRIPTION "Power request"
                    DEFVAL { 0 }
                    ::= { integerObjects 29 }

        -- 1.3.6.1.4.1.9839.2.1.3.30
        power-request-rec-mask OBJECT-TYPE
                    SYNTAX Integer32 (0..100)
                    UNITS "%"
                    MAX-ACCESS read-only
                    STATUS current
                    DESCRIPTION "Power request"
                    DEFVAL { 0 }
                    ::= { integerObjects 30 }

        -- 1.3.6.1.4.1.9839.2.1.3.31
        speed-fan4 OBJECT-TYPE
                    SYNTAX Integer32 (0..1000)
                    UNITS "N/A"
                    MAX-ACCESS read-only
                    STATUS current
                    DESCRIPTION "Condenser fan group1 modulating output"
                    DEFVAL { 0 }
                    ::= { integerObjects 31 }

        -- 1.3.6.1.4.1.9839.2.1.3.32
        speed-fan5 OBJECT-TYPE
                    SYNTAX Integer32 (0..1000)
                    UNITS "N/A"
                    MAX-ACCESS read-only
                    STATUS current
                    DESCRIPTION "Condenser fan group1 modulating output"
                    DEFVAL { 0 }
                    ::= { integerObjects 32 }

        -- 1.3.6.1.4.1.9839.2.1.3.35
        spuntipompa1-h OBJECT-TYPE
                    SYNTAX Integer32 (0..32767)
                    UNITS "N/A"
                    MAX-ACCESS read-only
                    STATUS current
                    DESCRIPTION "N/A"
                    DEFVAL { 0 }
                    ::= { integerObjects 35 }

        -- 1.3.6.1.4.1.9839.2.1.3.36
        spuntipompa1-l OBJECT-TYPE
                    SYNTAX Integer32 (0..32767)
                    UNITS "N/A"
                    MAX-ACCESS read-only
                    STATUS current
                    DESCRIPTION "N/A"
                    DEFVAL { 0 }
                    ::= { integerObjects 36 }

        -- 1.3.6.1.4.1.9839.2.1.3.37
        spuntipompa2-h OBJECT-TYPE
                    SYNTAX Integer32 (0..32767)
                    UNITS "N/A"
                    MAX-ACCESS read-only
                    STATUS current
                    DESCRIPTION "N/A"
                    DEFVAL { 0 }
                    ::= { integerObjects 37 }

        -- 1.3.6.1.4.1.9839.2.1.3.38
        spuntipompa2-l OBJECT-TYPE
                    SYNTAX Integer32 (0..32767)
                    UNITS "N/A"
                    MAX-ACCESS read-only
                    STATUS current
                    DESCRIPTION "N/A"
                    DEFVAL { 0 }
                    ::= { integerObjects 38 }

        -- 1.3.6.1.4.1.9839.2.1.3.43
        spunticp1-h OBJECT-TYPE
                    SYNTAX Integer32 (0..32767)
                    UNITS "N/A"
                    MAX-ACCESS read-only
                    STATUS current
                    DESCRIPTION "N/A"
                    DEFVAL { 0 }
                    ::= { integerObjects 43 }

        -- 1.3.6.1.4.1.9839.2.1.3.44
        spunticp1-l OBJECT-TYPE
                    SYNTAX Integer32 (0..32767)
                    UNITS "N/A"
                    MAX-ACCESS read-only
                    STATUS current
                    DESCRIPTION "N/A"
                    DEFVAL { 0 }
                    ::= { integerObjects 44 }

        -- 1.3.6.1.4.1.9839.2.1.3.45
        spunticp1a-h OBJECT-TYPE
                    SYNTAX Integer32 (0..32767)
                    UNITS "N/A"
                    MAX-ACCESS read-only
                    STATUS current
                    DESCRIPTION "N/A"
                    DEFVAL { 0 }
                    ::= { integerObjects 45 }

        -- 1.3.6.1.4.1.9839.2.1.3.46
        spunticp1a-l OBJECT-TYPE
                    SYNTAX Integer32 (0..32767)
                    UNITS "N/A"
                    MAX-ACCESS read-only
                    STATUS current
                    DESCRIPTION "N/A"
                    DEFVAL { 0 }
                    ::= { integerObjects 46 }

        -- 1.3.6.1.4.1.9839.2.1.3.47
        spunticp1b-h OBJECT-TYPE
                    SYNTAX Integer32 (0..32767)
                    UNITS "N/A"
                    MAX-ACCESS read-only
                    STATUS current
                    DESCRIPTION "N/A"
                    DEFVAL { 0 }
                    ::= { integerObjects 47 }

        -- 1.3.6.1.4.1.9839.2.1.3.48
        spunticp1b-l OBJECT-TYPE
                    SYNTAX Integer32 (0..32767)
                    UNITS "N/A"
                    MAX-ACCESS read-only
                    STATUS current
                    DESCRIPTION "N/A"
                    DEFVAL { 0 }
                    ::= { integerObjects 48 }

        -- 1.3.6.1.4.1.9839.2.1.3.49
        spunticp2-h OBJECT-TYPE
                    SYNTAX Integer32 (0..32767)
                    UNITS "N/A"
                    MAX-ACCESS read-only
                    STATUS current
                    DESCRIPTION "N/A"
                    DEFVAL { 0 }
                    ::= { integerObjects 49 }

        -- 1.3.6.1.4.1.9839.2.1.3.50
        spunticp2-l OBJECT-TYPE
                    SYNTAX Integer32 (0..32767)
                    UNITS "N/A"
                    MAX-ACCESS read-only
                    STATUS current
                    DESCRIPTION "N/A"
                    DEFVAL { 0 }
                    ::= { integerObjects 50 }

        -- 1.3.6.1.4.1.9839.2.1.3.51
        spunticp2a-h OBJECT-TYPE
                    SYNTAX Integer32 (0..32767)
                    UNITS "N/A"
                    MAX-ACCESS read-only
                    STATUS current
                    DESCRIPTION "N/A"
                    DEFVAL { 0 }
                    ::= { integerObjects 51 }

        -- 1.3.6.1.4.1.9839.2.1.3.52
        spunticp2a-l OBJECT-TYPE
                    SYNTAX Integer32 (0..32767)
                    UNITS "N/A"
                    MAX-ACCESS read-only
                    STATUS current
                    DESCRIPTION "N/A"
                    DEFVAL { 0 }
                    ::= { integerObjects 52 }

        -- 1.3.6.1.4.1.9839.2.1.3.53
        spunticp2b-h OBJECT-TYPE
                    SYNTAX Integer32 (0..32767)
                    UNITS "N/A"
                    MAX-ACCESS read-only
                    STATUS current
                    DESCRIPTION "N/A"
                    DEFVAL { 0 }
                    ::= { integerObjects 53 }

        -- 1.3.6.1.4.1.9839.2.1.3.54
        spunticp2b-l OBJECT-TYPE
                    SYNTAX Integer32 (0..32767)
                    UNITS "N/A"
                    MAX-ACCESS read-only
                    STATUS current
                    DESCRIPTION "N/A"
                    DEFVAL { 0 }
                    ::= { integerObjects 54 }

        -- 1.3.6.1.4.1.9839.2.1.3.60
        cod-size OBJECT-TYPE
                    SYNTAX Integer32 (0..99)
                    UNITS "N/A"
                    MAX-ACCESS read-only
                    STATUS current
                    DESCRIPTION "N/A"
                    DEFVAL { 0 }
                    ::= { integerObjects 60 }

        -- 1.3.6.1.4.1.9839.2.1.3.61
        cod-type-comp OBJECT-TYPE
                    SYNTAX Integer32 (0..9)
                    UNITS "N/A"
                    MAX-ACCESS read-only
                    STATUS current
                    DESCRIPTION "N/A"
                    DEFVAL { 0 }
                    ::= { integerObjects 61 }

        -- 1.3.6.1.4.1.9839.2.1.3.62
        cod-valve OBJECT-TYPE
                    SYNTAX Integer32 (0..9)
                    UNITS "N/A"
                    MAX-ACCESS read-only
                    STATUS current
                    DESCRIPTION "N/A"
                    DEFVAL { 0 }
                    ::= { integerObjects 62 }

        -- 1.3.6.1.4.1.9839.2.1.3.63
        cod-model OBJECT-TYPE
                    SYNTAX Integer32 (0..10)
                    UNITS "N/A"
                    MAX-ACCESS read-only
                    STATUS current
                    DESCRIPTION "N/A"
                    DEFVAL { 0 }
                    ::= { integerObjects 63 }

        -- 1.3.6.1.4.1.9839.2.1.3.64
        cod-recovery OBJECT-TYPE
                    SYNTAX Integer32 (0..9)
                    UNITS "N/A"
                    MAX-ACCESS read-only
                    STATUS current
                    DESCRIPTION "N/A"
                    DEFVAL { 0 }
                    ::= { integerObjects 64 }

        -- 1.3.6.1.4.1.9839.2.1.3.65
        cod-coils OBJECT-TYPE
                    SYNTAX Integer32 (0..9)
                    UNITS "N/A"
                    MAX-ACCESS read-only
                    STATUS current
                    DESCRIPTION "N/A"
                    DEFVAL { 0 }
                    ::= { integerObjects 65 }

        -- 1.3.6.1.4.1.9839.2.1.3.66
        cod-battery OBJECT-TYPE
                    SYNTAX Integer32 (0..3)
                    UNITS "N/A"
                    MAX-ACCESS read-only
                    STATUS current
                    DESCRIPTION "N/A"
                    DEFVAL { 0 }
                    ::= { integerObjects 66 }

        -- 1.3.6.1.4.1.9839.2.1.3.67
        cod-fan OBJECT-TYPE
                    SYNTAX Integer32 (0..3)
                    UNITS "N/A"
                    MAX-ACCESS read-only
                    STATUS current
                    DESCRIPTION "N/A"
                    DEFVAL { 0 }
                    ::= { integerObjects 67 }

        -- 1.3.6.1.4.1.9839.2.1.3.68
        cod-powersply OBJECT-TYPE
                    SYNTAX Integer32 (0..2)
                    UNITS "N/A"
                    MAX-ACCESS read-only
                    STATUS current
                    DESCRIPTION "N/A"
                    DEFVAL { 0 }
                    ::= { integerObjects 68 }

        -- 1.3.6.1.4.1.9839.2.1.3.69
        cod-pump-plant OBJECT-TYPE
                    SYNTAX Integer32 (0..80)
                    UNITS "N/A"
                    MAX-ACCESS read-only
                    STATUS current
                    DESCRIPTION "N/A"
                    DEFVAL { 0 }
                    ::= { integerObjects 69 }

        -- 1.3.6.1.4.1.9839.2.1.3.70
        cod-unittype OBJECT-TYPE
                    SYNTAX Integer32 (0..999)
                    UNITS "N/A"
                    MAX-ACCESS read-only
                    STATUS current
                    DESCRIPTION "N/A"
                    DEFVAL { 0 }
                    ::= { integerObjects 70 }

        -- 1.3.6.1.4.1.9839.2.1.3.100
        orecp1-lon OBJECT-TYPE
                    SYNTAX Integer32 (-32768..32767)
                    UNITS "N/A"
                    MAX-ACCESS read-only
                    STATUS current
                    DESCRIPTION "N/A"
                    DEFVAL { 0 }
                    ::= { integerObjects 100 }

        -- 1.3.6.1.4.1.9839.2.1.3.101
        orecp1a-lon OBJECT-TYPE
                    SYNTAX Integer32 (-32768..32767)
                    UNITS "N/A"
                    MAX-ACCESS read-only
                    STATUS current
                    DESCRIPTION "N/A"
                    DEFVAL { 0 }
                    ::= { integerObjects 101 }

        -- 1.3.6.1.4.1.9839.2.1.3.102
        orecp1b-lon OBJECT-TYPE
                    SYNTAX Integer32 (-32768..32767)
                    UNITS "N/A"
                    MAX-ACCESS read-only
                    STATUS current
                    DESCRIPTION "N/A"
                    DEFVAL { 0 }
                    ::= { integerObjects 102 }

        -- 1.3.6.1.4.1.9839.2.1.3.103
        orecp2-lon OBJECT-TYPE
                    SYNTAX Integer32 (-32768..32767)
                    UNITS "N/A"
                    MAX-ACCESS read-only
                    STATUS current
                    DESCRIPTION "N/A"
                    DEFVAL { 0 }
                    ::= { integerObjects 103 }

        -- 1.3.6.1.4.1.9839.2.1.3.104
        orecp2a-lon OBJECT-TYPE
                    SYNTAX Integer32 (-32768..32767)
                    UNITS "N/A"
                    MAX-ACCESS read-only
                    STATUS current
                    DESCRIPTION "N/A"
                    DEFVAL { 0 }
                    ::= { integerObjects 104 }

        -- 1.3.6.1.4.1.9839.2.1.3.105
        orecp2b-lon OBJECT-TYPE
                    SYNTAX Integer32 (-32768..32767)
                    UNITS "N/A"
                    MAX-ACCESS read-only
                    STATUS current
                    DESCRIPTION "N/A"
                    DEFVAL { 0 }
                    ::= { integerObjects 105 }

        -- 1.3.6.1.4.1.9839.2.1.3.108
        mod-evdevo-2-1.i8-reg-status-msk OBJECT-TYPE
                    SYNTAX Integer32 (1..100)
                    UNITS "N/A"
                    MAX-ACCESS read-only
                    STATUS current
                    DESCRIPTION "EVD status"
                    ::= { integerObjects 108 }

        -- 1.3.6.1.4.1.9839.2.1.3.109
        mod-evdevo-2-1.i51-reg-status-2nd-msk OBJECT-TYPE
                    SYNTAX Integer32 (1..100)
                    UNITS "N/A"
                    MAX-ACCESS read-only
                    STATUS current
                    DESCRIPTION "EEV status - Valve B"
                    ::= { integerObjects 109 }

        -- 1.3.6.1.4.1.9839.2.1.3.150
        tokenresetalarmi OBJECT-TYPE
                    SYNTAX Integer32 (0..32767)
                    UNITS "N/A"
                    MAX-ACCESS read-only
                    STATUS current
                    DESCRIPTION "N/A"
                    DEFVAL { 0 }
                    ::= { integerObjects 150 }

        -- 1.3.6.1.4.1.9839.2.1.3.152
        eventotipoguasto OBJECT-TYPE
                    SYNTAX Integer32 (0..999)
                    UNITS "N/A"
                    MAX-ACCESS read-only
                    STATUS current
                    DESCRIPTION "N/A"
                    DEFVAL { 0 }
                    ::= { integerObjects 152 }

        -- 1.3.6.1.4.1.9839.2.1.3.192
        countdowncp1 OBJECT-TYPE
                    SYNTAX Integer32 (0..32767)
                    UNITS "N/A"
                    MAX-ACCESS read-only
                    STATUS current
                    DESCRIPTION "N/A"
                    DEFVAL { 0 }
                    ::= { integerObjects 192 }

        -- 1.3.6.1.4.1.9839.2.1.3.193
        countdowncp1a OBJECT-TYPE
                    SYNTAX Integer32 (0..32767)
                    UNITS "N/A"
                    MAX-ACCESS read-only
                    STATUS current
                    DESCRIPTION "N/A"
                    DEFVAL { 0 }
                    ::= { integerObjects 193 }

        -- 1.3.6.1.4.1.9839.2.1.3.194
        countdowncp1b OBJECT-TYPE
                    SYNTAX Integer32 (0..32767)
                    UNITS "N/A"
                    MAX-ACCESS read-only
                    STATUS current
                    DESCRIPTION "N/A"
                    DEFVAL { 0 }
                    ::= { integerObjects 194 }

        -- 1.3.6.1.4.1.9839.2.1.3.195
        countdowncp2 OBJECT-TYPE
                    SYNTAX Integer32 (0..32767)
                    UNITS "N/A"
                    MAX-ACCESS read-only
                    STATUS current
                    DESCRIPTION "N/A"
                    DEFVAL { 0 }
                    ::= { integerObjects 195 }

        -- 1.3.6.1.4.1.9839.2.1.3.196
        countdowncp2a OBJECT-TYPE
                    SYNTAX Integer32 (0..32767)
                    UNITS "N/A"
                    MAX-ACCESS read-only
                    STATUS current
                    DESCRIPTION "N/A"
                    DEFVAL { 0 }
                    ::= { integerObjects 196 }

        -- 1.3.6.1.4.1.9839.2.1.3.197
        countdowncp2b OBJECT-TYPE
                    SYNTAX Integer32 (0..32767)
                    UNITS "N/A"
                    MAX-ACCESS read-only
                    STATUS current
                    DESCRIPTION "N/A"
                    DEFVAL { 0 }
                    ::= { integerObjects 197 }

        -- 1.3.6.1.4.1.9839.2.1.3.198
        potenzadisponibilefc-mask OBJECT-TYPE
                    SYNTAX Integer32 (0..32767)
                    UNITS "N/A"
                    MAX-ACCESS read-only
                    STATUS current
                    DESCRIPTION "N/A"
                    DEFVAL { 0 }
                    ::= { integerObjects 198 }

        -- 1.3.6.1.4.1.9839.2.1.3.199
        potenzafcreale-mask OBJECT-TYPE
                    SYNTAX Integer32 (0..32767)
                    UNITS "N/A"
                    MAX-ACCESS read-only
                    STATUS current
                    DESCRIPTION "N/A"
                    DEFVAL { 0 }
                    ::= { integerObjects 199 }

        -- 1.3.6.1.4.1.9839.2.1.3.200
        msk-power-circ1 OBJECT-TYPE
                    SYNTAX Integer32 (0..999)
                    UNITS "%"
                    MAX-ACCESS read-only
                    STATUS current
                    DESCRIPTION "N/A"
                    DEFVAL { 0 }
                    ::= { integerObjects 200 }

        -- 1.3.6.1.4.1.9839.2.1.3.201
        msk-power-circ2 OBJECT-TYPE
                    SYNTAX Integer32 (0..999)
                    UNITS "%"
                    MAX-ACCESS read-only
                    STATUS current
                    DESCRIPTION "N/A"
                    DEFVAL { 0 }
                    ::= { integerObjects 201 }

        -- 1.3.6.1.4.1.9839.2.1.3.202
        statosbrinamentoc1 OBJECT-TYPE
                    SYNTAX Integer32 (0..32767)
                    UNITS "N/A"
                    MAX-ACCESS read-only
                    STATUS current
                    DESCRIPTION "N/A"
                    DEFVAL { 0 }
                    ::= { integerObjects 202 }

        -- 1.3.6.1.4.1.9839.2.1.3.203
        eventisbrinamentoc1 OBJECT-TYPE
                    SYNTAX Integer32 (0..32767)
                    UNITS "N/A"
                    MAX-ACCESS read-only
                    STATUS current
                    DESCRIPTION "N/A"
                    DEFVAL { 0 }
                    ::= { integerObjects 203 }

        -- 1.3.6.1.4.1.9839.2.1.3.204
        statosbrinamentoc2 OBJECT-TYPE
                    SYNTAX Integer32 (0..32767)
                    UNITS "N/A"
                    MAX-ACCESS read-only
                    STATUS current
                    DESCRIPTION "N/A"
                    DEFVAL { 0 }
                    ::= { integerObjects 204 }

        -- 1.3.6.1.4.1.9839.2.1.3.205
        eventisbrinamentoc2 OBJECT-TYPE
                    SYNTAX Integer32 (0..32767)
                    UNITS "N/A"
                    MAX-ACCESS read-only
                    STATUS current
                    DESCRIPTION "N/A"
                    DEFVAL { 0 }
                    ::= { integerObjects 205 }

        -- 1.3.6.1.4.1.9839.2.1.3.206
        countdownpompemask OBJECT-TYPE
                    SYNTAX Integer32 (0..32767)
                    UNITS "N/A"
                    MAX-ACCESS read-only
                    STATUS current
                    DESCRIPTION "N/A"
                    DEFVAL { 0 }
                    ::= { integerObjects 206 }

        -- 1.3.6.1.4.1.9839.2.1.3.292
        configuratorecampo1 OBJECT-TYPE
                    SYNTAX Integer32 (0..32767)
                    UNITS "N/A"
                    MAX-ACCESS read-only
                    STATUS current
                    DESCRIPTION "N/A"
                    DEFVAL { 0 }
                    ::= { integerObjects 292 }

        -- 1.3.6.1.4.1.9839.2.1.3.293
        configuratorecampo2 OBJECT-TYPE
                    SYNTAX Integer32 (0..32767)
                    UNITS "N/A"
                    MAX-ACCESS read-only
                    STATUS current
                    DESCRIPTION "N/A"
                    DEFVAL { 0 }
                    ::= { integerObjects 293 }

        -- 1.3.6.1.4.1.9839.2.1.3.294
        configuratorecampo3 OBJECT-TYPE
                    SYNTAX Integer32 (0..32767)
                    UNITS "N/A"
                    MAX-ACCESS read-only
                    STATUS current
                    DESCRIPTION "N/A"
                    DEFVAL { 0 }
                    ::= { integerObjects 294 }

        -- 1.3.6.1.4.1.9839.2.1.3.295
        configuratorecampo4 OBJECT-TYPE
                    SYNTAX Integer32 (0..32767)
                    UNITS "N/A"
                    MAX-ACCESS read-only
                    STATUS current
                    DESCRIPTION "N/A"
                    DEFVAL { 0 }
                    ::= { integerObjects 295 }

        -- 1.3.6.1.4.1.9839.2.1.3.296
        configuratorecampo5 OBJECT-TYPE
                    SYNTAX Integer32 (0..32767)
                    UNITS "N/A"
                    MAX-ACCESS read-only
                    STATUS current
                    DESCRIPTION "N/A"
                    DEFVAL { 0 }
                    ::= { integerObjects 296 }

        -- 1.3.6.1.4.1.9839.2.1.3.297
        configuratorecampo6 OBJECT-TYPE
                    SYNTAX Integer32 (0..32767)
                    UNITS "N/A"
                    MAX-ACCESS read-only
                    STATUS current
                    DESCRIPTION "N/A"
                    DEFVAL { 0 }
                    ::= { integerObjects 297 }

        -- 1.3.6.1.4.1.9839.2.1.3.298
        configuratorecampo7 OBJECT-TYPE
                    SYNTAX Integer32 (0..32767)
                    UNITS "N/A"
                    MAX-ACCESS read-only
                    STATUS current
                    DESCRIPTION "N/A"
                    DEFVAL { 0 }
                    ::= { integerObjects 298 }

        -- 1.3.6.1.4.1.9839.2.1.3.299
        configuratorecampo8 OBJECT-TYPE
                    SYNTAX Integer32 (0..32767)
                    UNITS "N/A"
                    MAX-ACCESS read-only
                    STATUS current
                    DESCRIPTION "N/A"
                    DEFVAL { 0 }
                    ::= { integerObjects 299 }

        -- 1.3.6.1.4.1.9839.2.1.3.300
        configuratorecampo9 OBJECT-TYPE
                    SYNTAX Integer32 (0..32767)
                    UNITS "N/A"
                    MAX-ACCESS read-only
                    STATUS current
                    DESCRIPTION "N/A"
                    DEFVAL { 0 }
                    ::= { integerObjects 300 }

        -- 1.3.6.1.4.1.9839.2.1.3.301
        configuratorecampo10 OBJECT-TYPE
                    SYNTAX Integer32 (0..32767)
                    UNITS "N/A"
                    MAX-ACCESS read-only
                    STATUS current
                    DESCRIPTION "N/A"
                    DEFVAL { 0 }
                    ::= { integerObjects 301 }

        -- 1.3.6.1.4.1.9839.2.1.3.302
        configuratorecampo11 OBJECT-TYPE
                    SYNTAX Integer32 (0..32767)
                    UNITS "N/A"
                    MAX-ACCESS read-only
                    STATUS current
                    DESCRIPTION "N/A"
                    DEFVAL { 0 }
                    ::= { integerObjects 302 }

        -- 1.3.6.1.4.1.9839.2.1.3.303
        configuratorecampo12 OBJECT-TYPE
                    SYNTAX Integer32 (0..32767)
                    UNITS "N/A"
                    MAX-ACCESS read-only
                    STATUS current
                    DESCRIPTION "N/A"
                    DEFVAL { 0 }
                    ::= { integerObjects 303 }

        -- 1.3.6.1.4.1.9839.2.1.3.304
        configuratorecampo13 OBJECT-TYPE
                    SYNTAX Integer32 (0..32767)
                    UNITS "N/A"
                    MAX-ACCESS read-only
                    STATUS current
                    DESCRIPTION "N/A"
                    DEFVAL { 0 }
                    ::= { integerObjects 304 }

        -- 1.3.6.1.4.1.9839.2.1.3.305
        configuratorecampo14 OBJECT-TYPE
                    SYNTAX Integer32 (0..32767)
                    UNITS "N/A"
                    MAX-ACCESS read-only
                    STATUS current
                    DESCRIPTION "N/A"
                    DEFVAL { 0 }
                    ::= { integerObjects 305 }

        -- 1.3.6.1.4.1.9839.2.1.3.306
        configuratorecampo15 OBJECT-TYPE
                    SYNTAX Integer32 (0..32767)
                    UNITS "N/A"
                    MAX-ACCESS read-only
                    STATUS current
                    DESCRIPTION "N/A"
                    DEFVAL { 0 }
                    ::= { integerObjects 306 }

        -- 1.3.6.1.4.1.9839.2.1.3.307
        configuratorecampo16 OBJECT-TYPE
                    SYNTAX Integer32 (0..32767)
                    UNITS "N/A"
                    MAX-ACCESS read-only
                    STATUS current
                    DESCRIPTION "N/A"
                    DEFVAL { 0 }
                    ::= { integerObjects 307 }

        -- 1.3.6.1.4.1.9839.2.1.3.308
        configuratorecampo17 OBJECT-TYPE
                    SYNTAX Integer32 (0..32767)
                    UNITS "N/A"
                    MAX-ACCESS read-only
                    STATUS current
                    DESCRIPTION "N/A"
                    DEFVAL { 0 }
                    ::= { integerObjects 308 }

        -- 1.3.6.1.4.1.9839.2.1.3.309
        configuratorecampo18 OBJECT-TYPE
                    SYNTAX Integer32 (0..32767)
                    UNITS "N/A"
                    MAX-ACCESS read-only
                    STATUS current
                    DESCRIPTION "N/A"
                    DEFVAL { 0 }
                    ::= { integerObjects 309 }

        -- 1.3.6.1.4.1.9839.2.1.3.310
        configuratorecampo19 OBJECT-TYPE
                    SYNTAX Integer32 (0..32767)
                    UNITS "N/A"
                    MAX-ACCESS read-only
                    STATUS current
                    DESCRIPTION "N/A"
                    DEFVAL { 0 }
                    ::= { integerObjects 310 }

        -- 1.3.6.1.4.1.9839.2.1.3.311
        configuratorecampo20 OBJECT-TYPE
                    SYNTAX Integer32 (0..32767)
                    UNITS "N/A"
                    MAX-ACCESS read-only
                    STATUS current
                    DESCRIPTION "N/A"
                    DEFVAL { 0 }
                    ::= { integerObjects 311 }

        -- 1.3.6.1.4.1.9839.2.1.3.312
        default-req-remote OBJECT-TYPE
                    SYNTAX Integer32 (-32768..32767)
                    UNITS "N/A"
                    MAX-ACCESS read-write
                    STATUS current
                    DESCRIPTION "Default require by manufacturer menu"
                    DEFVAL { 0 }
                    ::= { integerObjects 312 }

        -- 1.3.6.1.4.1.9839.2.1.3.313
        configuratoreok OBJECT-TYPE
                    SYNTAX Integer32 (-32768..32767)
                    UNITS "N/A"
                    MAX-ACCESS read-write
                    STATUS current
                    DESCRIPTION "N/A"
                    DEFVAL { 0 }
                    ::= { integerObjects 313 }


	
	END

--
-- CAREL-nrl.MIB
--
