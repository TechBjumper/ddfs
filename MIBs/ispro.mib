-- Jacarta interSeptor Pro MIB
-- MIB for interSeptor Pro Environmental Monitoring System
--
-- { iso org(3) dod(6) internet(1) private(4) enterprises(1) jacarta(19011)
-- product(1) webAppliance(3) ispro(2) }
-- ==========================================================================
--
ISPRO-MIB DEFINITIONS ::= BEGIN

IMPORTS
    enterprises, IpAddress
        FROM RFC1155-SMI
    OBJECT-TYPE
        FROM RFC-1212
    DisplayString
        FROM RFC1213-MIB;

jacarta         OBJECT IDENTIFIER ::= { enterprises 19011 }
product         OBJECT IDENTIFIER ::= { jacarta 1 }
webAppliance    OBJECT IDENTIFIER ::= { product 3 }
ispro           OBJECT IDENTIFIER ::= { webAppliance 2 }

-- ==========================================================================
-- top level structure
-- ==========================================================================

isObjects                OBJECT IDENTIFIER ::=  { ispro 1 }
isTraps                  OBJECT IDENTIFIER ::=  { ispro 2 }

isIdent                  OBJECT IDENTIFIER ::=  { isObjects 1 }
isConfig                 OBJECT IDENTIFIER ::=  { isObjects 2 }
isDevice                 OBJECT IDENTIFIER ::=  { isObjects 3 }
isDeviceMonitor          OBJECT IDENTIFIER ::=  { isDevice 1 }
isDeviceConfig           OBJECT IDENTIFIER ::=  { isDevice 2 }

-- ==========================================================================
-- Enumeration Data Type Declaration
-- ==========================================================================

IsproEnuEnable	    ::= INTEGER {
    enabled(1),
    disabled(2)
    }
IsproEnuReset	    ::= INTEGER {
    reset(1), 
    nothing(2)
    }						
IsproEnuRestart	    ::= INTEGER { 
    restart(1), 
    nothing(2) 
    }
IsproEnuSeverity	::= INTEGER {
    information(1),
    warning(2),
    severe(3)
    }						
IsproEnuAccess	    ::= INTEGER { 
    noAccess(1),
    readonly(2), 
    readwrite(3)
    }						
IsproEnuTempUnit	::= INTEGER { 
    celsius(1), 
    fahrenheit(2) 
    }						
IsproEnuDateFormat	::= INTEGER { 
    dd-mm-yyyy(1), 
    mm-dd-yyyy(2) 
    }						
IsproEnuTimeZone	::= INTEGER { 
    gMT-1200(1), 
    gMT-1100(2), 
    gMT-1000(3), 
    gMT-0900(4), 
    gMT-0800(5), 
    gMT-0700(6),
    gMT-0600(7), 
    gMT-0500(8), 
    gMT-0400(9), 
    gMT-0330(10), 
    gMT-0300(11), 
    gMT-0200(12),
    gMT-0100(13), 
    gMT-0000(14), 
    gMT0100(15),
    gMT0200(16),
    gMT0300(17), 
    gMT0330(18),
    gMT0400(19), 
    gMT0500(20), 
    gMT0530(21),
    gMT0600(22), 
    gMT0700(23), 
    gMT0800(24), 
    gMT0900(25), 
    gMT1000(26), 
    gMT1100(27), 
    gMT1200(28)
    }						
IsproEnuSensorType	::= INTEGER {
    unknown(1), 
    sensorHT(2) 
    }						
IsproEnuThresholdStatus	::= INTEGER {
    unknown(1),
    disable(2),
    normal(3),
    below-low-warning(4), 
    below-low-critical(5),
    above-high-warning(6),
    above-high-critical(7)
    }	
IsproEnuDigitalStatus	    ::= INTEGER { 
    active(1), 
    inactive(2) 
    }						
IsproEnuSensorState	    ::= INTEGER { 
    auto(1), 
    disable(2) 
    }						
IsproEnuTempCalibration    ::= INTEGER {
    temperatureIncrease0Point0(1), 
    temperatureIncrease0Point5(2),  
    temperatureIncrease1Point0(3), 
    temperatureIncrease1Point5(4),
    temperatureIncrease2Point0(5), 
    temperatureIncrease2Point5(6),  
    temperatureIncrease3Point0(7), 
    temperatureDecrease0Point5(8),
    temperatureDecrease1Point0(9), 
    temperatureDecrease1Point5(10), 
    temperatureDecrease2Point0(11), 
    temperatureDecrease2Point5(12),
    temperatureDecrease3Point0(13)
    }
IsproEnuHumidityCalibration    ::= INTEGER {
    humidityIncrease0Point0(1), 
    humidityIncrease0Point5(2),  
    humidityIncrease1Point0(3), 
    humidityIncrease1Point5(4),
    humidityIncrease2Point0(5), 
    humidityIncrease2Point5(6),  
    humidityIncrease3Point0(7), 
    humidityDecrease0Point5(8),
    humidityDecrease1Point0(9), 
    humidityDecrease1Point5(10), 
    humidityDecrease2Point0(11), 
    humidityDecrease2Point5(12),
    humidityDecrease3Point0(13)
    }
IsproEnuAlarmState	::= INTEGER { 
    disabled(1), 
    normalOpen(2), 
    normalClose(3)
    }						
IsproEnuOnOff	    ::= INTEGER { 
    on(1), 
    off(2) 
    }
IsproEnuTurnOnOff	    ::= INTEGER { 
    turnOn(1), 
    turnOff(2) 
    }	
IsproEnuPresent	::= INTEGER { 
    present(1), 
    absent(2) 
    }
IsproEnuDO	::= INTEGER { 
    none(1), 
    digitalOutput1(2),
    digitalOutput2(3) 
    }
IsproEnuHighLow	::= INTEGER { 
    high(1), 
    low(2) 
    }
IsproLogType ::= INTEGER {
    historyLog(1),
    extendedLog(2),
    deviceEventLog(3),
    systemEventLog(4)
}


-- ===========================================================================
--
-- isIdent
--      Contains the identification of ispro device
--      1.3.6.1.4.1.2468.1.3.2.1.1
--
-- ===========================================================================

isIdentManufacturer OBJECT-TYPE
      SYNTAX DisplayString (SIZE (0..31))
      ACCESS read-only
      STATUS mandatory
      DESCRIPTION
          "The name of the ispro manufacturer."
      ::= { isIdent 1 }

isIdentModel OBJECT-TYPE
      SYNTAX DisplayString (SIZE (0..31))
      ACCESS read-only
      STATUS mandatory
      DESCRIPTION
          "The ispro Model designation."
      ::= { isIdent 2 }

isIdentAgentSoftwareVersion OBJECT-TYPE
      SYNTAX DisplayString (SIZE(0..63))
      ACCESS read-only
      STATUS mandatory
      DESCRIPTION
          "The ispro software/firmware version.  This variable may or
          may not have the same value as upsIdentUPSSoftwareVersion in some 
          implementations."
      ::= { isIdent 3 }

isIdentName OBJECT-TYPE
      SYNTAX DisplayString (SIZE(0..31))
      ACCESS read-write
      STATUS mandatory
      DESCRIPTION
          "A string identifying the ispro.  This object should be
          set by the administrator."
      ::= { isIdent 4 }

-- ===========================================================================
--
-- isConfig
--      Provides the overall information and configuration of ispro device.
--      .1.3.6.1.4.1.2468.1.3.2.1.2
--
-- ===========================================================================
	
isConfigMibVersion OBJECT-TYPE
        SYNTAX DisplayString (SIZE(0..31))
        ACCESS read-only
        STATUS mandatory
        DESCRIPTION
                "The version of MIB spec."
        ::= { isConfig 1}

--
-- isConfigNetwork Group
--

isConfigNetwork   OBJECT IDENTIFIER ::= { isConfig 2 }

isConfigIpAddress OBJECT-TYPE
        SYNTAX IpAddress
        ACCESS read-write
        STATUS mandatory
        DESCRIPTION
                " The ip address that NMS can identify the managed
                device"
        ::= { isConfigNetwork 1 }

isConfigGateway OBJECT-TYPE
        SYNTAX IpAddress
        ACCESS read-write
        STATUS mandatory
        DESCRIPTION
                " The default gateway that allow device managed
                through routers "
        ::= { isConfigNetwork 2 }

isConfigSubnetMask OBJECT-TYPE
        SYNTAX IpAddress
        ACCESS read-write
        STATUS mandatory
        DESCRIPTION
                " Internet address subnet mask"
        ::= { isConfigNetwork 3 }

--
-- end of isConfigNetwork Group
--

--
-- isConfigDateTime Group
--

isConfigDateTime   OBJECT IDENTIFIER ::= { isConfig 3 }

isConfigDate OBJECT-TYPE
        SYNTAX DisplayString (SIZE(0..10))
        ACCESS read-write
        STATUS mandatory
        DESCRIPTION
                "The date in ispro, format ask the Date Format of references "
        ::= { isConfigDateTime 1}

isConfigTime OBJECT-TYPE
        SYNTAX DisplayString(SIZE (0..8))
        ACCESS read-write
        STATUS mandatory
        DESCRIPTION
                "The time of ispro, format is (hh:mm:ss)"
        ::= { isConfigDateTime 2}

isConfigTimeFromNtp OBJECT-TYPE
        SYNTAX IsproEnuEnable
        ACCESS read-write
        STATUS mandatory
        DESCRIPTION
                "Enable/disable update date/time from NTP server."
        ::= { isConfigDateTime 3}

isConfigNtpIpAddress OBJECT-TYPE
	      SYNTAX DisplayString (SIZE(0..63))
        ACCESS read-write
        STATUS mandatory
        DESCRIPTION
                "NTP IP address."
        ::= { isConfigDateTime 4}

isConfigNtpTimeZone OBJECT-TYPE
        SYNTAX IsproEnuTimeZone
        ACCESS read-write
        STATUS mandatory
        DESCRIPTION
                "Configure the time zone of ispro to access NTP server."
        ::= { isConfigDateTime 5}

isConfigDayLightSaving OBJECT-TYPE
        SYNTAX IsproEnuEnable
        ACCESS read-write
        STATUS mandatory
        DESCRIPTION
                "Enable/disable daylight saving for NTP time, if enabled, the time get from NTP will be set
		 set one hour in advance to reflect daylight saving status."
        ::= { isConfigDateTime 6}

--
-- end of isConfigDateTime Group
--

--
-- isConfigLog Group
--

isConfigLog   OBJECT IDENTIFIER ::= { isConfig 4 }

isConfigHistoryLogFrequency OBJECT-TYPE
        SYNTAX INTEGER (5..3600) -- in seconds
        ACCESS read-write
        STATUS mandatory
        DESCRIPTION
                "The frequency of the history log updates. The value
                 is in seconds"
        ::= { isConfigLog 1}

isConfigExtHistoryLogFrequency      OBJECT-TYPE
        SYNTAX INTEGER (1..720) -- in minutes
        ACCESS read-write
        STATUS mandatory
        DESCRIPTION
                "The frequency of the extended history log updates.
                 The value is in seconds"
        ::= { isConfigLog 2}

isConfigConfigurationLog OBJECT-TYPE
        SYNTAX IsproEnuEnable
        ACCESS read-write
        STATUS mandatory
        DESCRIPTION
                " Enable/disable ispro to log parameters change."
        ::= { isConfigLog 3}
        
isConfigLogType OBJECT-TYPE
        SYNTAX IsproLogType
        ACCESS read-only
        STATUS mandatory
        DESCRIPTION
                "The type of log in agent"
        ::= { isConfigLog 4}
        
--
-- end of isConfigLog Group
--

isConfigDhcpState OBJECT-TYPE
        SYNTAX  IsproEnuEnable
        ACCESS read-write
        STATUS mandatory
        DESCRIPTION
                "Enable or disable DHCP/BootP capability"
        ::= { isConfig 5}

isConfigPingState OBJECT-TYPE
        SYNTAX  IsproEnuEnable
        ACCESS read-write
        STATUS mandatory
        DESCRIPTION
                "Enable or disable Ping Echo capability"
        ::= { isConfig 6}

isConfigTftpState OBJECT-TYPE
        SYNTAX  IsproEnuEnable
        ACCESS read-write
        STATUS mandatory
        DESCRIPTION
                "Enable or disable TFTP network upgrade capability"
        ::= { isConfig 7}

--
-- isConfigTelnet Group
--

isConfigTelnet   OBJECT IDENTIFIER ::= { isConfig 8 }

isConfigTelnetState OBJECT-TYPE
        SYNTAX  IsproEnuEnable
        ACCESS read-write
        STATUS mandatory
        DESCRIPTION
                "Enable or disable telnet access"
        ::= { isConfigTelnet 1}

isConfigTelnetPortNumber            OBJECT-TYPE
        SYNTAX INTEGER (1..65535)
        ACCESS read-write
        STATUS mandatory
        DESCRIPTION
                 "Setting the server port of telnet."
        ::= { isConfigTelnet 2}
--
-- end of isConfigTelnet Group
--

--
-- isConfigHttp Group
--

isConfigHttp   OBJECT IDENTIFIER ::= { isConfig 9 }

isConfigHttpState OBJECT-TYPE
        SYNTAX  IsproEnuEnable
        ACCESS read-write
        STATUS mandatory
        DESCRIPTION
                "Enable or disable HTTP access"
        ::= { isConfigHttp 1}

isConfigHttpPortNumber            OBJECT-TYPE
        SYNTAX INTEGER (1..65535)
        ACCESS read-write
        STATUS mandatory
        DESCRIPTION
                 "Setting the server port of HTTP."
        ::= { isConfigHttp 2}

isConfigHttpSecurity OBJECT-TYPE
        SYNTAX  IsproEnuEnable
        ACCESS read-write
        STATUS mandatory
        DESCRIPTION
                "Enable/disable HTTP access for read-only users"
        ::= { isConfigHttp 3}
--
-- end of isConfigHttp Group
--

--
-- isConfigSnmp Group
--

isConfigSnmp   OBJECT IDENTIFIER ::= { isConfig 10 }

isConfigSnmpState OBJECT-TYPE
        SYNTAX IsproEnuEnable
        ACCESS read-write
        STATUS mandatory
        DESCRIPTION
                "Enable or disable SNMP access"
        ::= { isConfigSnmp 1}

isConfigSnmpPortNumber            OBJECT-TYPE
        SYNTAX INTEGER (1..65535)
        ACCESS read-write
        STATUS mandatory
        DESCRIPTION
                 "Setting the server port of SNMP."
        ::= { isConfigSnmp 2}
--
-- end of isConfigSnmp Group
--

--
-- isConfigControl Group
--

isConfigControl   OBJECT IDENTIFIER ::= { isConfig 11 }
isConfigResetToDefault OBJECT-TYPE
        SYNTAX IsproEnuReset
        ACCESS read-write
        STATUS mandatory
        DESCRIPTION
                "Reset all parameters of ispro to default value"
        ::= { isConfigControl 1}

isConfigRestart OBJECT-TYPE
        SYNTAX IsproEnuRestart
        ACCESS read-write
        STATUS mandatory
        DESCRIPTION
                "Restart ispro"
        ::= { isConfigControl 2}
--
-- end of isConfigControl Group
--

--
-- isConfigTrap Group
--

isConfigTrap   OBJECT IDENTIFIER ::= { isConfig 12 }

isConfigTrapRetryCount OBJECT-TYPE
        SYNTAX INTEGER (0..65535)
        ACCESS read-write
        STATUS mandatory
        DESCRIPTION
                "The count of repeat traps to send to NMS before trap
                 acknowledge received."
        ::= { isConfigTrap 1}

isConfigTrapRetryTime OBJECT-TYPE
        SYNTAX INTEGER (0..65535)
        ACCESS read-write
        STATUS mandatory
        DESCRIPTION
                "The time between retry traps send to NMS."
        ::= { isConfigTrap 2}

isConfigTrapAckSignature OBJECT-TYPE
        SYNTAX INTEGER (0..65535)
        ACCESS read-write
        STATUS mandatory
        DESCRIPTION
                "The signature of trap acknowledge."
        ::= { isConfigTrap 3}
--
-- end of isConfigTrap Group
--

isConfigRefreshRate OBJECT-TYPE
        SYNTAX INTEGER (1..60)
        ACCESS read-write
        STATUS mandatory
        DESCRIPTION
                " The frequency that ispro refresh web page from agent
                (unit : second)."
        ::= { isConfig 13}

--
-- isConfigTrapReceiverTable
--

isConfigTrapReceiverTable OBJECT-TYPE
        SYNTAX SEQUENCE OF IsproReceiverEntry
        ACCESS not-accessible
        STATUS mandatory
        DESCRIPTION
                "A list of managers to send traps to.  The number of
                 entries is given by the value of isConfigNumTrapReceivers"
        ::= { isConfig 14 }

isConfigTrapReceiverEntry OBJECT-TYPE
        SYNTAX IsproReceiverEntry
        ACCESS not-accessible
        STATUS mandatory
        DESCRIPTION
                "The managers to send traps to."
        INDEX  { isReceiverIndex}
        ::= { isConfigTrapReceiverTable 1 }

IsproReceiverEntry ::=
        SEQUENCE {
                isReceiverIndex
                        INTEGER,
                isReceiverAddr
                        IpAddress,
                isReceiverCommunityString
                        DisplayString,
                isReceiverSeverityLevel
                        INTEGER,
                isReceiverDescription
                        DisplayString
        }

isReceiverIndex OBJECT-TYPE
        SYNTAX INTEGER (1..8)
        ACCESS read-only
        STATUS mandatory
        DESCRIPTION
                "The index to a trap receiver entry."
        ::= { isConfigTrapReceiverEntry 1 }

isReceiverAddr OBJECT-TYPE
        SYNTAX IpAddress
        ACCESS read-write
        STATUS mandatory
        DESCRIPTION
                "The IP address of the manager to send a trap to."
        ::= { isConfigTrapReceiverEntry 2 }

isReceiverCommunityString OBJECT-TYPE
        SYNTAX DisplayString (SIZE(0..19))
        ACCESS read-write
        STATUS mandatory
        DESCRIPTION
                "The community name to use in the trap when
                 sent to the manager."
        ::= { isConfigTrapReceiverEntry 3 }

isReceiverSeverityLevel OBJECT-TYPE
        SYNTAX IsproEnuSeverity
        ACCESS read-write
        STATUS mandatory
        DESCRIPTION
                "The severity level of traps to be received by this manager."
        ::= { isConfigTrapReceiverEntry 4 }

isReceiverDescription OBJECT-TYPE
        SYNTAX DisplayString (SIZE(0..24))
        ACCESS read-write
        STATUS mandatory
        DESCRIPTION
                "Description of trap receivers"
        ::= { isConfigTrapReceiverEntry 5 }
--
-- end of isConfigTrapReceiverTable
--

--
-- isConfigAccessControlTable
--

isConfigAccessControlTable OBJECT-TYPE
        SYNTAX SEQUENCE OF IsproAccessEntry
        ACCESS not-accessible
        STATUS mandatory
        DESCRIPTION
                "A list of managers which can access ispro with private
                community string."
        ::= { isConfig 15}

isConfigAccessControlEntry OBJECT-TYPE
        SYNTAX IsproAccessEntry
        ACCESS not-accessible
        STATUS mandatory
        DESCRIPTION
                "The managers."
        INDEX  { isAccessIndex}
        ::= { isConfigAccessControlTable 1 }

IsproAccessEntry ::=
        SEQUENCE {
                isAccessIndex
                        INTEGER,
                isAccessControlAddr
                        IpAddress,
                isAccessCommunityString
                        DisplayString,
                isAccessControlMode
                        INTEGER,
                isAccessAccount
                        DisplayString
        }

isAccessIndex OBJECT-TYPE
        SYNTAX INTEGER (1..8)
        ACCESS read-only
        STATUS mandatory
        DESCRIPTION
                "The index to an access control entry."
        ::= { isConfigAccessControlEntry 1 }

isAccessControlAddr OBJECT-TYPE
        SYNTAX IpAddress
        ACCESS read-write
        STATUS mandatory
        DESCRIPTION
                "The IP address of the manager to access ispro"
        ::= { isConfigAccessControlEntry 2 }

isAccessCommunityString OBJECT-TYPE
        SYNTAX DisplayString (SIZE(0..15))
        ACCESS read-write
        STATUS mandatory
        DESCRIPTION
                "The community name to use in the manager when
                 access ispro"
        ::= { isConfigAccessControlEntry 3 }

isAccessControlMode OBJECT-TYPE
        SYNTAX IsproEnuAccess
        ACCESS read-write
        STATUS mandatory
        DESCRIPTION
                "Access type, only read/Write access type can change parameter
                 of ispro"
        ::= { isConfigAccessControlEntry 4 }
        
isAccessAccount OBJECT-TYPE
        SYNTAX DisplayString (SIZE(0..31))
        ACCESS read-write
        STATUS mandatory
        DESCRIPTION
                "Access account, the account for web login to
                 access ispro"
        ::= { isConfigAccessControlEntry 5 }
        
--
-- end of isConfigAccessControlTable
--

isConfigTemperatureUnit OBJECT-TYPE
        SYNTAX IsproEnuTempUnit
        ACCESS read-write
        STATUS mandatory
        DESCRIPTION
                "The temperature unit of the system, can be Celsius or Fahrenheit"
        ::= { isConfig 16}

isConfigDateFormat OBJECT-TYPE
        SYNTAX IsproEnuDateFormat
        ACCESS read-write
        STATUS mandatory
        DESCRIPTION
                "The date format of the system, can be dd/mm/yyyy or mm/dd/yyyy"
        ::= { isConfig 17}

-- ===========================================================================
--
-- isDevice
--      Monitor and Configure the sensors of ispro device.
--      1.3.6.1.4.1.2468.1.3.2.1.3
--
-- ===========================================================================

-- Monitor
--   1.3.6.1.4.1.2468.1.3.2.1.3.1
--    Temperature

isDeviceMonitorTemperatureTable OBJECT-TYPE
        SYNTAX SEQUENCE OF IsproDeviceMonitorTemperatureEntry
        ACCESS not-accessible
        STATUS mandatory
        DESCRIPTION
                "The temperature monitoring table, to provides
        overall status of temperature."
        ::= { isDeviceMonitor 1}

isDeviceMonitorTemperatureEntry OBJECT-TYPE
        SYNTAX IsproDeviceMonitorTemperatureEntry
        ACCESS not-accessible
        STATUS mandatory
        DESCRIPTION
                "The temperature monitoring table, to provides
        overall status of temperature."
        INDEX  { isDeviceMonitorTemperatureIndex}
        ::= { isDeviceMonitorTemperatureTable 1 }

IsproDeviceMonitorTemperatureEntry ::=
        SEQUENCE {
                isDeviceMonitorTemperatureIndex
                        INTEGER,
                isDeviceMonitorTemperatureName
                        DisplayString,
                isDeviceMonitorTemperature
                        INTEGER,
                isDeviceMonitorTemperatureAlarm
                        INTEGER
        }

isDeviceMonitorTemperatureIndex OBJECT-TYPE
        SYNTAX INTEGER (1..24)
        ACCESS read-only
        STATUS mandatory
        DESCRIPTION
                "The index to a temperature entry."
        ::= { isDeviceMonitorTemperatureEntry 1 }

isDeviceMonitorTemperatureName OBJECT-TYPE
        SYNTAX DisplayString (SIZE (0..15))
        ACCESS read-only
        STATUS mandatory
        DESCRIPTION
                "The temperature sensor name."
        ::= { isDeviceMonitorTemperatureEntry 2 }

isDeviceMonitorTemperature OBJECT-TYPE
        SYNTAX INTEGER
        ACCESS read-only
        STATUS mandatory
        DESCRIPTION
                "The temperature of sensor on device Ispro, the unit is 0.01 degree."
        ::= { isDeviceMonitorTemperatureEntry 3 }

isDeviceMonitorTemperatureAlarm OBJECT-TYPE
        SYNTAX IsproEnuThresholdStatus
        ACCESS read-only
        STATUS mandatory
        DESCRIPTION
                "The status of temperature sensor in Ispro."
        ::= { isDeviceMonitorTemperatureEntry 4 }

--    Humidity

isDeviceMonitorHumidityTable OBJECT-TYPE
        SYNTAX SEQUENCE OF IsproDeviceMonitorHumidityEntry
        ACCESS not-accessible
        STATUS mandatory
        DESCRIPTION
                "The humidity monitoring table, to provides
        overall status of humidity."
        ::= { isDeviceMonitor 2 }

isDeviceMonitorHumidityEntry OBJECT-TYPE
        SYNTAX IsproDeviceMonitorHumidityEntry
        ACCESS not-accessible
        STATUS mandatory
        DESCRIPTION
                "The humidity monitoring table, to provides
        overall status of humidity."
        INDEX  { isDeviceMonitorHumidityIndex}
        ::= { isDeviceMonitorHumidityTable 1 }

IsproDeviceMonitorHumidityEntry ::=
        SEQUENCE {
                isDeviceMonitorHumidityIndex
                        INTEGER,
                isDeviceMonitorHumidityName
                        DisplayString,
                isDeviceMonitorHumidity
                        INTEGER,
                isDeviceMonitorHumidityAlarm
                        INTEGER
        }

isDeviceMonitorHumidityIndex OBJECT-TYPE
        SYNTAX INTEGER (1..24)
        ACCESS read-only
        STATUS mandatory
        DESCRIPTION
                "The index to a humidity entry."
        ::= { isDeviceMonitorHumidityEntry 1 }

isDeviceMonitorHumidityName OBJECT-TYPE
        SYNTAX DisplayString (SIZE (0..15))
        ACCESS read-only
        STATUS mandatory
        DESCRIPTION
                "The humidity sensor name."
        ::= { isDeviceMonitorHumidityEntry 2 }

isDeviceMonitorHumidity OBJECT-TYPE
        SYNTAX INTEGER
        ACCESS read-only
        STATUS mandatory
        DESCRIPTION
                "The humidity of sensor on device Ispro, the unit is 0.01 %."
        ::= { isDeviceMonitorHumidityEntry 3 }

isDeviceMonitorHumidityAlarm OBJECT-TYPE
        SYNTAX IsproEnuThresholdStatus
        ACCESS read-only
        STATUS mandatory
        DESCRIPTION
                "The status of humidity sensor in Ispro."
        ::= { isDeviceMonitorHumidityEntry 4 }

--    Digital Input

isDeviceMonitorDigitalInTable OBJECT-TYPE
        SYNTAX SEQUENCE OF IsproDeviceMonitorDigitalInEntry
        ACCESS not-accessible
        STATUS mandatory
        DESCRIPTION
                "The digital input monitoring table, to provides
        overall status of digital input."
        ::= { isDeviceMonitor 3}

isDeviceMonitorDigitalInEntry OBJECT-TYPE
        SYNTAX IsproDeviceMonitorDigitalInEntry
        ACCESS not-accessible
        STATUS mandatory
        DESCRIPTION
                "The digital input monitoring table, to provides
        overall status of digital input."
        INDEX  { isDeviceMonitorDigitalInIndex}
        ::= { isDeviceMonitorDigitalInTable 1 }

IsproDeviceMonitorDigitalInEntry ::=
        SEQUENCE {
                isDeviceMonitorDigitalInIndex
                        INTEGER,
                isDeviceMonitorDigitalInName
                        DisplayString,
                isDeviceMonitorDigitalIn
                        INTEGER,
                isDeviceMonitorDigitalInAlarm
                        INTEGER
        }
isDeviceMonitorDigitalInIndex OBJECT-TYPE
        SYNTAX INTEGER (1..48)
        ACCESS read-only
        STATUS mandatory
        DESCRIPTION
                "The index to a digital input entry."
        ::= { isDeviceMonitorDigitalInEntry 1 }

isDeviceMonitorDigitalInName OBJECT-TYPE
        SYNTAX DisplayString (SIZE (0..15))
        ACCESS read-only
        STATUS mandatory
        DESCRIPTION
                "The digital input sensor name."
        ::= { isDeviceMonitorDigitalInEntry 2 }

isDeviceMonitorDigitalIn OBJECT-TYPE
        SYNTAX INTEGER
        ACCESS read-only
        STATUS mandatory
        DESCRIPTION
                "The digital input of sensor on device Ispro."
        ::= { isDeviceMonitorDigitalInEntry 3 }

isDeviceMonitorDigitalInAlarm OBJECT-TYPE
        SYNTAX IsproEnuDigitalStatus
        ACCESS read-only
        STATUS mandatory
        DESCRIPTION
                "The status of digital alarm sensor."
        ::= { isDeviceMonitorDigitalInEntry 4 }

-- Device Configuration
--   1.3.6.1.4.1.2468.1.3.2.1.3.2

isDeviceConfigTable OBJECT-TYPE
        SYNTAX SEQUENCE OF IsproDeviceConfigEntry
        ACCESS not-accessible
        STATUS mandatory
        DESCRIPTION
                "The device configuration table."
        ::= { isDeviceConfig 1}

isDeviceConfigEntry OBJECT-TYPE
        SYNTAX IsproDeviceConfigEntry
        ACCESS not-accessible
        STATUS mandatory
        DESCRIPTION
                "The device configuration table."
        INDEX  { isDeviceConfigIndex }
        ::= { isDeviceConfigTable 1 }

IsproDeviceConfigEntry ::=
        SEQUENCE {
                isDeviceConfigIndex
                        INTEGER,
                isDeviceConfigName
                        DisplayString,
                isDeviceConfigState
                        INTEGER,
                isDeviceConfigDisplay
                        INTEGER
        }

isDeviceConfigIndex OBJECT-TYPE
        SYNTAX INTEGER (1..24)
        ACCESS read-only
        STATUS mandatory
        DESCRIPTION
                "The index to a sensor entry."
        ::= { isDeviceConfigEntry 1 }

isDeviceConfigName OBJECT-TYPE
        SYNTAX DisplayString (SIZE (0..15))
        ACCESS read-write
        STATUS mandatory
        DESCRIPTION
                "The name of sensor device."
        ::= { isDeviceConfigEntry 2}

isDeviceConfigState OBJECT-TYPE
        SYNTAX IsproEnuSensorState
        ACCESS read-write
        STATUS mandatory
        DESCRIPTION
                "The setup of device type."
        ::= { isDeviceConfigEntry 3 }
        
isDeviceConfigDisplay OBJECT-TYPE
        SYNTAX IsproEnuEnable
        ACCESS read-write
        STATUS mandatory
        DESCRIPTION
                "Enable or disable of displaying this sensor in Comprehensive
        webpage."
        ::= { isDeviceConfigEntry 4 }

-- Temperature

isDeviceConfigTemperatureTable OBJECT-TYPE
        SYNTAX SEQUENCE OF IsproDeviceConfigTemperatureEntry
        ACCESS not-accessible
        STATUS mandatory
        DESCRIPTION
                "The temperature configuration table of Device."
        ::= { isDeviceConfig 2}

isDeviceConfigTemperatureEntry OBJECT-TYPE
        SYNTAX IsproDeviceConfigTemperatureEntry
        ACCESS not-accessible
        STATUS mandatory
        DESCRIPTION
                "The sensor configuration table of Device."
        INDEX  { isDeviceConfigTemperatureIndex}
        ::= { isDeviceConfigTemperatureTable 1 }

IsproDeviceConfigTemperatureEntry ::=
        SEQUENCE {
                isDeviceConfigTemperatureIndex
                        INTEGER,
                isDeviceConfigTemperatureName
                        DisplayString,
                isDeviceConfigTemperatureLowWarning
                        INTEGER,
                isDeviceConfigTemperatureLowCritical
                        INTEGER,
                isDeviceConfigTemperatureHighWarning
                        INTEGER,
                isDeviceConfigTemperatureHighCritical
                        INTEGER,
                isDeviceConfigTemperatureHysteresis
                        INTEGER,
                isDeviceConfigTemperatureCalibration
                        INTEGER,
                isDeviceConfigTemperatureLowWarningState
                        INTEGER,
                isDeviceConfigTemperatureLowCriticalState
                        INTEGER,
                isDeviceConfigTemperatureHighWarningState
                        INTEGER,
                isDeviceConfigTemperatureHighCriticalState
                        INTEGER,
                isDeviceConfigTemperatureEventDO
                        INTEGER
        }

isDeviceConfigTemperatureIndex OBJECT-TYPE
        SYNTAX INTEGER (1..24)
        ACCESS read-only
        STATUS mandatory
        DESCRIPTION
                "The index to a temperature device entry."
        ::= { isDeviceConfigTemperatureEntry 1 }

isDeviceConfigTemperatureName OBJECT-TYPE
        SYNTAX DisplayString (SIZE (0..15))
        ACCESS read-write
        STATUS mandatory
        DESCRIPTION
                "The temperature sensor name."
        ::= { isDeviceConfigTemperatureEntry 2 }

isDeviceConfigTemperatureLowWarning OBJECT-TYPE
        SYNTAX INTEGER (-1500..6500)
        ACCESS read-write
        STATUS mandatory
        DESCRIPTION
                "The set point to trigger low warning alarm. the unit is 0.01 degree."
        ::= { isDeviceConfigTemperatureEntry 3 }


isDeviceConfigTemperatureLowCritical OBJECT-TYPE
        SYNTAX INTEGER  (-1500..6500)
        ACCESS read-write
        STATUS mandatory
        DESCRIPTION
                "The threshold to trigger low critical alarm. the unit is 0.01 degree."

        ::= { isDeviceConfigTemperatureEntry 4 }

isDeviceConfigTemperatureHighWarning OBJECT-TYPE
        SYNTAX INTEGER (-1500..6500)
        ACCESS read-write
        STATUS mandatory
        DESCRIPTION
                "The threshold to trigger high warning alarm. the unit is 0.01 degree."
        ::= { isDeviceConfigTemperatureEntry 5 }

isDeviceConfigTemperatureHighCritical OBJECT-TYPE
        SYNTAX INTEGER (-1500..6500)
        ACCESS read-write
        STATUS mandatory
        DESCRIPTION
                "The threshold to trigger high critical alarm. the unit is 0.01 degree."
        ::= { isDeviceConfigTemperatureEntry 6 }

isDeviceConfigTemperatureHysteresis OBJECT-TYPE
        SYNTAX INTEGER
        ACCESS read-write
        STATUS mandatory
        DESCRIPTION
                "The set value to prevent too many alarms when temperature is hovering around the
                 set threshold. The unit is 0.01"
        ::= { isDeviceConfigTemperatureEntry 7 }

isDeviceConfigTemperatureCalibration OBJECT-TYPE
        SYNTAX IsproEnuTempCalibration
        ACCESS read-write
        STATUS mandatory
        DESCRIPTION
                "The set value to get the correct temperature according to your reference temperature."
        ::= { isDeviceConfigTemperatureEntry 8 }

isDeviceConfigTemperatureLowWarningState OBJECT-TYPE
        SYNTAX IsproEnuEnable
        ACCESS read-write
        STATUS mandatory
        DESCRIPTION
                "Enable/disable the set point to trigger low warning alarm."
        ::= { isDeviceConfigTemperatureEntry 9 }

isDeviceConfigTemperatureLowCriticalState OBJECT-TYPE
        SYNTAX IsproEnuEnable
        ACCESS read-write
        STATUS mandatory
        DESCRIPTION
                "Enable/disable the set point to trigger low critical alarm."
        ::= { isDeviceConfigTemperatureEntry 10 }

isDeviceConfigTemperatureHighWarningState OBJECT-TYPE
        SYNTAX IsproEnuEnable
        ACCESS read-write
        STATUS mandatory
        DESCRIPTION
                "Enable/disable the set point to trigger high warning alarm."
        ::= { isDeviceConfigTemperatureEntry 11 }

isDeviceConfigTemperatureHighCriticalState OBJECT-TYPE
        SYNTAX IsproEnuEnable
        ACCESS read-write
        STATUS mandatory
        DESCRIPTION
                "Enable/disable the set point to trigger high critical alarm."
        ::= { isDeviceConfigTemperatureEntry 12 }

isDeviceConfigTemperatureEventDO OBJECT-TYPE
        SYNTAX IsproEnuDO
        ACCESS read-write
        STATUS mandatory
        DESCRIPTION
                "Set the trigger action of temperature events. If event asserted, 
        this will invert the digital output #1 or #2."
        ::= { isDeviceConfigTemperatureEntry 13 }

-- Humidity

isDeviceConfigHumidityTable OBJECT-TYPE
        SYNTAX SEQUENCE OF IsproDeviceConfigHumidityEntry
        ACCESS not-accessible
        STATUS mandatory
        DESCRIPTION
                "The humidity configuration table of Device."
        ::= { isDeviceConfig 3}

isDeviceConfigHumidityEntry OBJECT-TYPE
        SYNTAX IsproDeviceConfigHumidityEntry
        ACCESS not-accessible
        STATUS mandatory
        DESCRIPTION
                "The humidity configuration table of Device."
        INDEX  { isDeviceConfigHumidityIndex}
        ::= { isDeviceConfigHumidityTable 1 }

IsproDeviceConfigHumidityEntry ::=
        SEQUENCE {
                isDeviceConfigHumidityIndex
                        INTEGER,
                isDeviceConfigHumidityName
                        DisplayString,
                isDeviceConfigHumidityLowWarning
                        INTEGER,
                isDeviceConfigHumidityLowCritical
                        INTEGER,
                isDeviceConfigHumidityHighWarning
                        INTEGER,
                isDeviceConfigHumidityHighCritical
                        INTEGER,
                isDeviceConfigHumidityHysteresis
                        INTEGER,
                isDeviceConfigHumidityCalibration
                        INTEGER,
                isDeviceConfigHumidityLowWarningState
                        INTEGER,
                isDeviceConfigHumidityLowCriticalState
                        INTEGER,
                isDeviceConfigHumidityHighWarningState
                        INTEGER,
                isDeviceConfigHumidityHighCriticalState
                        INTEGER,
                isDeviceConfigHumidityEventDO
                        INTEGER
        }

isDeviceConfigHumidityIndex OBJECT-TYPE
        SYNTAX INTEGER (1..24)
        ACCESS read-only
        STATUS mandatory
        DESCRIPTION
                "The index to a humidity device entry."
        ::= { isDeviceConfigHumidityEntry 1 }

isDeviceConfigHumidityName OBJECT-TYPE
        SYNTAX DisplayString (SIZE (0..15))
        ACCESS read-write
        STATUS mandatory
        DESCRIPTION
                "The humidity sensor name."
        ::= { isDeviceConfigHumidityEntry 2 }

isDeviceConfigHumidityLowWarning OBJECT-TYPE
        SYNTAX INTEGER (500..9500)
        ACCESS read-write
        STATUS mandatory
        DESCRIPTION
                "The set point to trigger low warning alarm. the unit is 0.01 %."
        ::= { isDeviceConfigHumidityEntry 3 }


isDeviceConfigHumidityLowCritical OBJECT-TYPE
        SYNTAX INTEGER (500..9500)
        ACCESS read-write
        STATUS mandatory
        DESCRIPTION
                "The threshold to trigger low critical alarm. the unit is 0.01 %."
        ::= { isDeviceConfigHumidityEntry 4 }

isDeviceConfigHumidityHighWarning OBJECT-TYPE
        SYNTAX INTEGER (500..9500)
        ACCESS read-write
        STATUS mandatory
        DESCRIPTION
                "The threshold to trigger high warning alarm. the unit is 0.01 %."
        ::= { isDeviceConfigHumidityEntry 5 }

isDeviceConfigHumidityHighCritical OBJECT-TYPE
        SYNTAX INTEGER (500..9500)
        ACCESS read-write
        STATUS mandatory
        DESCRIPTION
                "The threshold to trigger high critical alarm. the unit is 0.01 %."
        ::= { isDeviceConfigHumidityEntry 6 }

isDeviceConfigHumidityHysteresis OBJECT-TYPE
        SYNTAX INTEGER
        ACCESS read-write
        STATUS mandatory
        DESCRIPTION
                "The set value to prevent too many alarms when Humidity 
        is hovering around the set threshold. The unit is 0.01"
        ::= { isDeviceConfigHumidityEntry 7 }

isDeviceConfigHumidityCalibration OBJECT-TYPE
        SYNTAX IsproEnuHumidityCalibration
        ACCESS read-write
        STATUS mandatory
        DESCRIPTION
                "The set value to get the correct temperature according 
        to your reference temperature."
        ::= { isDeviceConfigHumidityEntry 8 }

isDeviceConfigHumidityLowWarningState OBJECT-TYPE
        SYNTAX IsproEnuEnable
        ACCESS read-write
        STATUS mandatory
        DESCRIPTION
                "Enable/disable the set point to trigger low warning alarm."
        ::= { isDeviceConfigHumidityEntry 9 }

isDeviceConfigHumidityLowCriticalState OBJECT-TYPE
        SYNTAX IsproEnuEnable
        ACCESS read-write
        STATUS mandatory
        DESCRIPTION
                "Enable/disable the set point to trigger low critical alarm."
        ::= { isDeviceConfigHumidityEntry 10 }

isDeviceConfigHumidityHighWarningState OBJECT-TYPE
        SYNTAX IsproEnuEnable
        ACCESS read-write
        STATUS mandatory
        DESCRIPTION
                "Enable/disable the set point to trigger high warning alarm."
        ::= { isDeviceConfigHumidityEntry 11 }

isDeviceConfigHumidityHighCriticalState OBJECT-TYPE
        SYNTAX IsproEnuEnable
        ACCESS read-write
        STATUS mandatory
        DESCRIPTION
                "Enable/disable the set point to trigger high critical alarm."
        ::= { isDeviceConfigHumidityEntry 12 }

isDeviceConfigHumidityEventDO OBJECT-TYPE
        SYNTAX IsproEnuDO
        ACCESS read-write
        STATUS mandatory
        DESCRIPTION
                "Set the trigger action of humidity events. If event asserted, 
        this will invert the digital output #1 or #2."
        ::= { isDeviceConfigHumidityEntry 13 }

-- Digital Input

isDeviceConfigDigitalInTable OBJECT-TYPE
        SYNTAX SEQUENCE OF IsproDeviceConfigDigitalInEntry
        ACCESS not-accessible
        STATUS mandatory
        DESCRIPTION
                "The digital input configuration table of Device."
        ::= { isDeviceConfig 4}

isDeviceConfigDigitalInEntry OBJECT-TYPE
        SYNTAX IsproDeviceConfigDigitalInEntry
        ACCESS not-accessible
        STATUS mandatory
        DESCRIPTION
                "The digital input configuration table of Device."
        INDEX  { isDeviceConfigDigitalInIndex}
        ::= { isDeviceConfigDigitalInTable 1 }

IsproDeviceConfigDigitalInEntry ::=
        SEQUENCE {
                isDeviceConfigDigitalInIndex
                        INTEGER,
                isDeviceConfigDigitalInName
                        DisplayString,
                isDeviceConfigDigitalInState
                        INTEGER,
                isDeviceConfigDigitalInHysteresis
                        INTEGER,
                isDeviceConfigDigitalInEventDO
                        INTEGER
        }

isDeviceConfigDigitalInIndex OBJECT-TYPE
        SYNTAX INTEGER (1..48)
        ACCESS read-only
        STATUS mandatory
        DESCRIPTION
                "The index to a digital input device entry."
        ::= { isDeviceConfigDigitalInEntry 1 }

isDeviceConfigDigitalInName OBJECT-TYPE
        SYNTAX DisplayString (SIZE (0..15))
        ACCESS read-write
        STATUS mandatory
        DESCRIPTION
                "The name of digital input."
        ::= { isDeviceConfigDigitalInEntry 2 }

isDeviceConfigDigitalInState OBJECT-TYPE
        SYNTAX IsproEnuAlarmState
        ACCESS read-write
        STATUS mandatory
        DESCRIPTION
                "Setup the signal type to trigger alarm."
        ::= { isDeviceConfigDigitalInEntry 3 }

isDeviceConfigDigitalInHysteresis OBJECT-TYPE
        SYNTAX INTEGER
        ACCESS read-write
        STATUS mandatory
        DESCRIPTION
                "The set value to delay the alarm triggered when event occurs."
        ::= { isDeviceConfigDigitalInEntry 4 }

isDeviceConfigDigitalInEventDO OBJECT-TYPE
        SYNTAX IsproEnuDO
        ACCESS read-write
        STATUS mandatory
        DESCRIPTION
                "Set the trigger action of digital alarm #1 events. If event asserted, 
        this will invert the digital output #1 or #2."
        ::= { isDeviceConfigDigitalInEntry 5 }

-- Digital Output

isDeviceDigitalOutTable OBJECT-TYPE
        SYNTAX SEQUENCE OF IsproDeviceDigitalOutEntry
        ACCESS not-accessible
        STATUS mandatory
        DESCRIPTION
                "The configuration table of Device digital output."
        ::= { isDeviceConfig 5}
        
isDeviceID OBJECT-TYPE
        SYNTAX INTEGER (1..3)
        ACCESS read-only
        STATUS mandatory
        DESCRIPTION
                "The device board id."
        ::= { isDevice 3}
        
isDeviceDigitalOutEntry OBJECT-TYPE
        SYNTAX IsproDeviceDigitalOutEntry
        ACCESS not-accessible
        STATUS mandatory
        DESCRIPTION
                "The configuration table of Device digital output."
        INDEX  { isDeviceDigitalOutIndex }
        ::= { isDeviceDigitalOutTable 1 }

IsproDeviceDigitalOutEntry ::=
        SEQUENCE {
                isDeviceDigitalOutIndex
                        INTEGER,
                isDeviceDigitalOutStartState
                        INTEGER,
                isDeviceDigitalOutEventAction
                        INTEGER,
                isDeviceDigitalOutManualControl
                        INTEGER
        }

isDeviceDigitalOutIndex OBJECT-TYPE
        SYNTAX INTEGER (1..24)
        ACCESS read-only
        STATUS mandatory
        DESCRIPTION
                "The index is 1 and 2, it maps to digital output 1 and 2."
        ::= { isDeviceDigitalOutEntry 1 }

isDeviceDigitalOutStartState OBJECT-TYPE
        SYNTAX IsproEnuOnOff
        ACCESS read-write
        STATUS mandatory
        DESCRIPTION
                "Turn power on/off specific digital output when system
        start up."
        ::= { isDeviceDigitalOutEntry 2 }

isDeviceDigitalOutEventAction OBJECT-TYPE
        SYNTAX IsproEnuEnable
        ACCESS read-write
        STATUS mandatory
        DESCRIPTION
                "If select yes, it will invert the current status of
        specific digital output when Ispro event occurred."
        ::= { isDeviceDigitalOutEntry 3 }

isDeviceDigitalOutManualControl OBJECT-TYPE
        SYNTAX IsproEnuTurnOnOff
        ACCESS read-write
        STATUS mandatory
        DESCRIPTION
                "Invert current status of specific digital output manually."
        ::= { isDeviceDigitalOutEntry 4 }

-- ===========================================================================
--
-- isTraps
--      Grouping all ispro traps here.
-- 
-- ===========================================================================

isTrapsDescription OBJECT-TYPE
        SYNTAX DisplayString (SIZE (0..255))
        ACCESS read-only
        STATUS mandatory
        DESCRIPTION
                "The description of current trap"
        ::= { isTraps 1 }

--isCommunicationRestored TRAP-TYPE
--        ENTERPRISE isTraps
--        VARIABLES {
--            isTrapsDescription,
--            isDeviceConfigIndex,
--            isDeviceConfigName
--        }
--        DESCRIPTION
--                "INFORMATION: Communication between ispro and sensor had
--                 established."
--        ::= 1
--
--isCommunicationLost TRAP-TYPE
--        ENTERPRISE isTraps
--        VARIABLES {
--            isTrapsDescription,
--            isDeviceConfigIndex,
--            isDeviceConfigName
--        }
--        DESCRIPTION
--                "WARNING: Communication between ispro and sensor had
--                 lost."
--        ::= 2
--
--isDigitalAlarmInactive TRAP-TYPE
--        ENTERPRISE isTraps
--        VARIABLES {
--            isTrapsDescription,
--            isDeviceMonitorDigitalInIndex,
--            isDeviceMonitorDigitalInName
--        }
--        DESCRIPTION
--                "INFORMATION: Digital input of sensor had return from active state."
--        ::= 3
--
--isDigitalAlarmActive TRAP-TYPE
--        ENTERPRISE isTraps
--        VARIABLES {
--            isTrapsDescription,
--            isDeviceMonitorDigitalInIndex,
--            isDeviceMonitorDigitalInName
--        }
--        DESCRIPTION
--                "WARNING: Digital input had become active."
--        ::= 4
--
--isTemperatureNotHighWarning TRAP-TYPE
--        ENTERPRISE isTraps
--        VARIABLES {
--            isTrapsDescription,
--            isDeviceMonitorTemperatureIndex,
--            isDeviceMonitorTemperatureName,
--            isDeviceMonitorTemperature,
--            isDeviceConfigTemperatureHighWarning
--        }
--        DESCRIPTION
--                "INFORMATION: The temperature of sensor had return from High warning to normal."
--        ::= 5
--
--isTemperatureHighWarning TRAP-TYPE
--        ENTERPRISE isTraps
--        VARIABLES {
--            isTrapsDescription,
--            isDeviceMonitorTemperatureIndex,
--            isDeviceMonitorTemperatureName,
--            isDeviceMonitorTemperature,
--            isDeviceConfigTemperatureHighWarning
--        }
--        DESCRIPTION
--                "WARNING: The temperature of sensor was higher than High warning set point."
--        ::= 6
--
--isTemperatureNotLowWarning TRAP-TYPE
--        ENTERPRISE isTraps
--        VARIABLES {
--            isTrapsDescription,
--            isDeviceMonitorTemperatureIndex,
--            isDeviceMonitorTemperatureName,
--            isDeviceMonitorTemperature,
--            isDeviceConfigTemperatureLowWarning
--        }
--        DESCRIPTION
--                "INFORMATION: The temperature of sensor had return from low warning to normal."
--        ::= 7
--
--isTemperatureLowWarning TRAP-TYPE
--        ENTERPRISE isTraps
--        VARIABLES {
--            isTrapsDescription,
--            isDeviceMonitorTemperatureIndex,
--            isDeviceMonitorTemperatureName,
--            isDeviceMonitorTemperature,
--            isDeviceConfigTemperatureLowWarning
--        }
--        DESCRIPTION
--                "WARNING: The temperature of sensor was lower than low warning set point."
--        ::= 8
--
--isTemperatureNotHighCritical TRAP-TYPE
--        ENTERPRISE isTraps
--        VARIABLES {
--            isTrapsDescription,
--            isDeviceMonitorTemperatureIndex,
--            isDeviceMonitorTemperatureName,
--            isDeviceMonitorTemperature,
--            isDeviceConfigTemperatureHighCritical
--        }
--        DESCRIPTION
--                "INFORMATION: The temperature of sensor lower than high critical set point."
--        ::= 9
--
--isTemperatureHighCritical TRAP-TYPE
--        ENTERPRISE isTraps
--        VARIABLES {
--            isTrapsDescription,
--            isDeviceMonitorTemperatureIndex,
--            isDeviceMonitorTemperatureName,
--            isDeviceMonitorTemperature,
--            isDeviceConfigTemperatureHighCritical
--        }
--        DESCRIPTION
--                "CRITICAL: The temperature of sensor was higher than high critical set point."
--        ::= 10
--
--isTemperatureNotLowCritical TRAP-TYPE
--        ENTERPRISE isTraps
--        VARIABLES {
--            isTrapsDescription,
--            isDeviceMonitorTemperatureIndex,
--            isDeviceMonitorTemperatureName,
--            isDeviceMonitorTemperature,
--            isDeviceConfigTemperatureLowCritical
--        }
--        DESCRIPTION
--                "INFORMATION: The temperature of sensor was higher than low critical set point."
--        ::= 11
--
--isTemperatureLowCritical TRAP-TYPE
--        ENTERPRISE isTraps
--        VARIABLES {
--            isTrapsDescription,
--            isDeviceMonitorTemperatureIndex,
--            isDeviceMonitorTemperatureName,
--            isDeviceMonitorTemperature,
--            isDeviceConfigTemperatureLowCritical
--        }
--        DESCRIPTION
--                "CRITICAL: The temperature of sensor was lower than low critical set point."
--        ::= 12
--isHumidityNotHighWarning TRAP-TYPE
--        ENTERPRISE isTraps
--        VARIABLES {
--            isTrapsDescription,
--            isDeviceMonitorHumidityIndex,
--            isDeviceMonitorHumidityName,
--            isDeviceMonitorHumidity,
--            isDeviceConfigHumidityHighWarning
--        }
--        DESCRIPTION
--                "INFORMATION: The humidity of sensor had return from High warning to normal."
--        ::= 13
--
--isHumidityHighWarning TRAP-TYPE
--        ENTERPRISE isTraps
--        VARIABLES {
--            isTrapsDescription,
--            isDeviceMonitorHumidityIndex,
--            isDeviceMonitorHumidityName,
--            isDeviceMonitorHumidity,
--            isDeviceConfigHumidityHighWarning
--        }
--        DESCRIPTION
--                "WARNING: The humidity of sensor was higher than High warning set point."
--        ::= 14
--
--isHumidityNotLowWarning TRAP-TYPE
--        ENTERPRISE isTraps
--        VARIABLES {
--            isTrapsDescription,
--            isDeviceMonitorHumidityIndex,
--            isDeviceMonitorHumidityName,
--            isDeviceMonitorHumidity,
--            isDeviceConfigHumidityLowWarning
--        }
--        DESCRIPTION
--                "INFORMATION: The humidity of sensor had return from low warning to normal."
--        ::= 15
--
--isHumidityLowWarning TRAP-TYPE
--        ENTERPRISE isTraps
--        VARIABLES {
--            isTrapsDescription,
--            isDeviceMonitorHumidityIndex,
--            isDeviceMonitorHumidityName,
--            isDeviceMonitorHumidity,
--            isDeviceConfigHumidityLowWarning
--        }
--        DESCRIPTION
--                "WARNING: The humidity of sensor was lower than low warning set point."
--        ::= 16
--
--isHumidityNotHighCritical TRAP-TYPE
--        ENTERPRISE isTraps
--        VARIABLES {
--            isTrapsDescription,
--            isDeviceMonitorHumidityIndex,
--            isDeviceMonitorHumidityName,
--            isDeviceMonitorHumidity,
--            isDeviceConfigHumidityHighCritical
--        }
--        DESCRIPTION
--                "INFORMATION: The humidity of sensor lower than high critical set point."
--        ::= 17
--
--isHumidityHighCritical TRAP-TYPE
--        ENTERPRISE isTraps
--        VARIABLES {
--            isTrapsDescription,
--            isDeviceMonitorHumidityIndex,
--            isDeviceMonitorHumidityName,
--            isDeviceMonitorHumidity,
--            isDeviceConfigHumidityHighCritical
--        }
--        DESCRIPTION
--                "CRITICAL: The humidity of sensor was higher than high critical set point."
--        ::= 18
--
--isHumidityNotLowCritical TRAP-TYPE
--        ENTERPRISE isTraps
--        VARIABLES {
--            isTrapsDescription,
--            isDeviceMonitorHumidityIndex,
--            isDeviceMonitorHumidityName,
--            isDeviceMonitorHumidity,
--            isDeviceConfigHumidityLowCritical
--        }
--        DESCRIPTION
--                "INFORMATION: The humidity of sensor was higher than low critical set point."
--        ::= 19
--
--isHumidityLowCritical TRAP-TYPE
--        ENTERPRISE isTraps
--        VARIABLES {
--            isTrapsDescription,
--            isDeviceMonitorHumidityIndex,
--            isDeviceMonitorHumidityName,
--            isDeviceMonitorHumidity,
--            isDeviceConfigHumidityLowCritical
--        }
--        DESCRIPTION
--                "CRITICAL: The humidity of sensor was lower than low critical set point."
--      ::= 20

END
