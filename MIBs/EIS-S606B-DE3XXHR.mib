RFC1213-MIB DEFINITIONS ::= BEGIN

          IMPORTS
                  mgmt, Counter,
                          TimeTicks
                      FROM RFC1155-SMI
					  
                  OBJECT-TYPE
                          FROM RFC-1212;

          --  This MIB module uses the extended OBJECT-TYPE macro as
          --  defined in [14];


          --  MIB-II (same prefix as MIB-I)

          mib-2      OBJECT IDENTIFIER ::= { mgmt 1 }

          -- textual conventions

          DisplayString ::=
              OCTET STRING
          -- This data type is used to model textual information taken
          -- from the NVT ASCII character set.  By convention, objects
          -- with this syntax are declared as having






          --
          --      SIZE (0..255)

          PhysAddress ::=
              OCTET STRING
          -- This data type is used to model media addresses.  For many
          -- types of media, this will be in a binary representation.
          -- For example, an ethernet address would be represented as
          -- a string of 6 octets.


          -- groups in MIB-II

          system       OBJECT IDENTIFIER ::= { mib-2 1 }

          


          -- the System group

          -- Implementation of the System group is mandatory for all
          -- systems.  If an agent is not configured to have a value
          -- for any of these variables, a string of length 0 is
          -- returned.

          sysDescr OBJECT-TYPE
              SYNTAX  DisplayString (SIZE (0..255))
              ACCESS  read-only
              STATUS  mandatory





              DESCRIPTION
                      "A textual description of the entity.  This value
                      should include the full name and version
                      identification of the system's hardware type,
                      software operating-system, and networking
                      software.  It is mandatory that this only contain
                      printable ASCII characters."
              ::= { system 1 }

          sysObjectID OBJECT-TYPE
              SYNTAX  OBJECT IDENTIFIER
              ACCESS  read-only
              STATUS  mandatory
              DESCRIPTION
                      "The vendor's authoritative identification of the
                      network management subsystem contained in the
                      entity.  This value is allocated within the SMI
                      enterprises subtree (1.3.6.1.4.1) and provides an
                      easy and unambiguous means for determining `what
                      kind of box' is being managed.  For example, if
                      vendor `Flintstones, Inc.' was assigned the
                      subtree 1.3.6.1.4.1.4242, it could assign the
                      identifier 1.3.6.1.4.1.4242.1.1 to its `Fred
                      Router'."
              ::= { system 2 }

          sysUpTime OBJECT-TYPE
              SYNTAX  TimeTicks
              ACCESS  read-only
              STATUS  mandatory
              DESCRIPTION
                      "The time (in hundredths of a second) since the
                      network management portion of the system was last
                      re-initialized."
              ::= { system 3 }

          sysContact OBJECT-TYPE
              SYNTAX  DisplayString (SIZE (0..255))
              ACCESS  read-write
              STATUS  mandatory
              DESCRIPTION
                      "The textual identification of the contact person
                      for this managed node, together with information
                      on how to contact this person."
              ::= { system 4 }

          sysName OBJECT-TYPE
              SYNTAX  DisplayString (SIZE (0..255))





              ACCESS  read-write
              STATUS  mandatory
              DESCRIPTION
                      "An administratively-assigned name for this
                      managed node.  By convention, this is the node's
                      fully-qualified domain name."
              ::= { system 5 }

          sysLocation OBJECT-TYPE
              SYNTAX  DisplayString (SIZE (0..255))
              ACCESS  read-write
              STATUS  mandatory
              DESCRIPTION
                      "The physical location of this node (e.g.,
                      `telephone closet, 3rd floor')."
              ::= { system 6 }

          sysServices OBJECT-TYPE
              SYNTAX  INTEGER (0..127)
              ACCESS  read-only
              STATUS  mandatory
              DESCRIPTION
                      "A value which indicates the set of services that
                      this entity primarily offers.

                      The value is a sum.  This sum initially takes the
                      value zero, Then, for each layer, L, in the range
                      1 through 7, that this node performs transactions
                      for, 2 raised to (L - 1) is added to the sum.  For
                      example, a node which performs primarily routing
                      functions would have a value of 4 (2^(3-1)).  In
                      contrast, a node which is a host offering
                      application services would have a value of 72
                      (2^(4-1) + 2^(7-1)).  Note that in the context of
                      the Internet suite of protocols, values should be
                      calculated accordingly:

                           layer  functionality
                               1  physical (e.g., repeaters)
                               2  datalink/subnetwork (e.g., bridges)
                               3  internet (e.g., IP gateways)
                               4  end-to-end  (e.g., IP hosts)
                               7  applications (e.g., mail relays)

                      For systems including OSI protocols, layers 5 and
                      6 may also be counted."
              ::= { system 7 }


END


-- ElcomNet-MIB { iso org(3) dod(6) internet(1) private(4)
--    enterprises(1) elcom(40367) }

ElcomNet-MIB DEFINITIONS ::= BEGIN

IMPORTS
	enterprises, Gauge, TimeTicks,MODULE-IDENTITY       FROM RFC1155-SMI
	DisplayString                                       FROM RFC1213-MIB
	OBJECT-TYPE                                         FROM RFC-1212
	TRAP-TYPE                                           FROM RFC-1215 ;
											
	
	
elcom OBJECT IDENTIFIER ::=  { enterprises 40367 }

ed    	MODULE-IDENTITY
        
		LAST-UPDATED    "201611240000Z"
        ORGANIZATION    "Elcom International"
        CONTACT-INFO    "postal : Elcom House kolhapur
                                  
                         e-mail : Technical Support
                                  pdusupport@elcom-in.com"
        DESCRIPTION        
        "This module defines the Elcom iPDU extensions to ed-iPDU products."
         

        REVISION        "201611240000Z"
        DESCRIPTION     "Adding Power Management OIDs.
                        Fixed SYNTAX of some OIDs.
                        Updating OIDs DESCRIPTION to include not applicable values."  

::= {elcom 12 }

edProducts     		OBJECT IDENTIFIER ::= { ed 1 }
edManagement   		OBJECT IDENTIFIER ::= { ed 2 }

--
 

--
cP207YA     		OBJECT IDENTIFIER ::= { edProducts 1 } 


edAppliance   	 	OBJECT IDENTIFIER ::= { edManagement 1  }
edPowerMgmt     	OBJECT IDENTIFIER ::= { edManagement 2  }
edTrapObject   		OBJECT IDENTIFIER ::= { edManagement 3 	} 




edHostName OBJECT-TYPE
        SYNTAX             	DisplayString ( SIZE (0..32) )
        ACCESS         		read-only
        STATUS             	mandatory
        DESCRIPTION
        "The appliance name"
::= { edAppliance 1 }

edProductModel OBJECT-TYPE
        SYNTAX             DisplayString ( SIZE (0..50) )
        ACCESS         		read-only
        STATUS             mandatory
        DESCRIPTION
        "The appliance product model"
::= { edAppliance 2 }

edPartNumber OBJECT-TYPE
        SYNTAX             DisplayString ( SIZE (0..32) )
        ACCESS         read-only
        STATUS             mandatory
        DESCRIPTION
        "The part number of this appliance as shown on the label
         attached or imprinted on the appliance."
::= { edAppliance 3 }

edSerialNumber OBJECT-TYPE
        SYNTAX             DisplayString ( SIZE (0..32) )
        ACCESS         read-only
        STATUS             mandatory
        DESCRIPTION
        "The serial number of this appliance as shown on the label
         attached or imprinted on the appliance."
::= { edAppliance 4 }

edBootcodeVersion OBJECT-TYPE
        SYNTAX             DisplayString ( SIZE (0..32) )
        ACCESS         read-only
        STATUS             mandatory
        DESCRIPTION 
        "The version of the bootcode of this appliance."
::= { edAppliance 5 }

edFirmwareVersion OBJECT-TYPE
        SYNTAX             DisplayString ( SIZE (0..32) )
        ACCESS         read-only
        STATUS             mandatory
        DESCRIPTION 
        "The version of the firmware of this appliance."
::= { edAppliance 6 }





edPowerMgmtPDUTable OBJECT IDENTIFIER::= { edPowerMgmt 1 }
 
edPowerMgmtPDUTableData OBJECT IDENTIFIER::= { edPowerMgmtPDUTable 1 }
edPowerMgmtPDUTableFirmwareVersion       OBJECT-TYPE
        SYNTAX             DisplayString
        ACCESS         read-only
        STATUS             mandatory
        DESCRIPTION
        "Version of the PDU firmware.
         Returns N/A if not applicable."
::= { edPowerMgmtPDUTableData 2 }



edPowerMgmtPDUTableNumberOfOutlets OBJECT-TYPE
        SYNTAX             Integer32
        ACCESS         read-only
        STATUS             mandatory
        DESCRIPTION
        "Number of outlets of the PDU."
::= { edPowerMgmtPDUTableData 3 }

edPowerMgmtPDUTableNumberOfPhases OBJECT-TYPE
        SYNTAX             Integer32
        ACCESS         read-only
        STATUS             mandatory
        DESCRIPTION
        "Number of phases of the PDU."
::= { edPowerMgmtPDUTableData 4 }


edPowerMgmtPDUTableNumberOfSensors OBJECT-TYPE
        SYNTAX             Integer32
        ACCESS         read-only
        STATUS             mandatory
        DESCRIPTION
        "Number of sensors in the PDU."
::= { edPowerMgmtPDUTableData 5 }



edPowerMgmtPDUTableVendor   OBJECT-TYPE
        SYNTAX             DisplayString
        ACCESS         	  read-only
        STATUS             mandatory
        DESCRIPTION
        "Vendor of the PDU.
         Returns N/A if not applicable."
::= { edPowerMgmtPDUTableData 6 }


edPowerMgmtTotalNumberOfPhases OBJECT-TYPE
        SYNTAX             Integer32
        ACCESS         read-only
        STATUS             mandatory
        DESCRIPTION
        "Number of Phases managed by the appliance."
::= { edPowerMgmt 4 }

edPowerMgmtPhasesTable OBJECT IDENTIFIER::= { edPowerMgmt 5 }

edPowerMgmtPhasesData OBJECT IDENTIFIER::= { edPowerMgmtPhasesTable 1 }

edPowerMgmtPhasesTableVoltageValue OBJECT IDENTIFIER::= { edPowerMgmtPhasesData 2 }
edPowerMgmtPhasesTablecurrentValue OBJECT IDENTIFIER::= { edPowerMgmtPhasesData 3 }
edPowerMgmtPhasesTableApearentEnergyValue OBJECT IDENTIFIER::= { edPowerMgmtPhasesData 4 }
edPowerMgmtPhasesTableReactiveEnergyValue OBJECT IDENTIFIER::= { edPowerMgmtPhasesData 5 }
edPowerMgmtPhasesTableActiveEnergyValue OBJECT IDENTIFIER::= { edPowerMgmtPhasesData 6 }
edPowerMgmtPhasesTableInstantaneousPowerValue OBJECT IDENTIFIER::= { edPowerMgmtPhasesData 7 }
edPowerMgmtPhasesTablePowerFactorValue OBJECT IDENTIFIER::= { edPowerMgmtPhasesData 8 }


edPowerMgmtPhasesTableVoltageValuePhase1 OBJECT-TYPE
        SYNTAX             Integer32
        ACCESS         read-only
        STATUS             mandatory
        DESCRIPTION
        "Actual value of Voltage of the phase.
         Returns 0 if not supported or available"
::= { edPowerMgmtPhasesTableVoltageValue 1 }

edPowerMgmtPhasesTableVoltageValuePhase2 OBJECT-TYPE
        SYNTAX             Integer32
        ACCESS         read-only
        STATUS             mandatory
        DESCRIPTION
        "Actual value of Voltage of the phase.
         Returns 0 if not supported or available"
::= { edPowerMgmtPhasesTableVoltageValue 2 }

edPowerMgmtPhasesTableVoltageValuePhase3 OBJECT-TYPE
        SYNTAX             Integer32
        ACCESS         read-only
        STATUS             mandatory
        DESCRIPTION
        "Actual value of Voltage of the phase.
         Returns 0 if not supported or available"
::= { edPowerMgmtPhasesTableVoltageValue 3 }


edPowerMgmtPhasesTablecurrentPhase1 OBJECT-TYPE
        SYNTAX             Integer32
        ACCESS         read-only
        STATUS             mandatory
        DESCRIPTION
        "Actual value of current of Phase(amp).
         Returns 0 if not supported or available"
::= { edPowerMgmtPhasesTablecurrentValue 1 }


edPowerMgmtPhasesTablecurrentPhase2 OBJECT-TYPE
        SYNTAX             Integer32
        ACCESS         read-only
        STATUS             mandatory
        DESCRIPTION
        "Actual value of current of Phase(amp).
         Returns 0 if not supported or available"
::= { edPowerMgmtPhasesTablecurrentValue 2 }



edPowerMgmtPhasesTablecurrentPhase3 OBJECT-TYPE
        SYNTAX             Integer32
        ACCESS         read-only
        STATUS             mandatory
        DESCRIPTION
        "Actual value of current of Phase(amp).
         Returns 0 if not supported or available"
::= { edPowerMgmtPhasesTablecurrentValue 3 }



edPowerMgmtPhasesTableApearentEnergyPhase1 OBJECT-TYPE
        SYNTAX             Integer32
        ACCESS         read-only
        STATUS             mandatory
        DESCRIPTION
        "Actual value of KVaHr of Phase .
        Returns 0 if not supported or available"
::= { edPowerMgmtPhasesTableApearentEnergyValue 1 }


edPowerMgmtPhasesTableApearentEnergyPhase2 OBJECT-TYPE
        SYNTAX             Integer32
        ACCESS         read-only
        STATUS             mandatory
        DESCRIPTION
        "Actual value of KVaHr of Phase .
        Returns 0 if not supported or available"
::= { edPowerMgmtPhasesTableApearentEnergyValue 2 }

edPowerMgmtPhasesTableApearentEnergyPhase3 OBJECT-TYPE
        SYNTAX             Integer32
        ACCESS         read-only
        STATUS             mandatory
        DESCRIPTION
        "Actual value of KVaHr of Phase .
        Returns 0 if not supported or available"
::= { edPowerMgmtPhasesTableApearentEnergyValue 3 }


edPowerMgmtPhasesTableReactiveEnergyPhase1 OBJECT-TYPE
        SYNTAX             Integer32
        ACCESS         read-only
        STATUS             mandatory
        DESCRIPTION
        "Actual value of KVarHr of the phase .
         Returns 0 if not supported or available."
::= { edPowerMgmtPhasesTableReactiveEnergyValue 1 }



edPowerMgmtPhasesTableReactiveEnergyPhase2 OBJECT-TYPE
        SYNTAX             Integer32
        ACCESS         read-only
        STATUS             mandatory
        DESCRIPTION
        "Actual value of KVarHr of the phase .
         Returns 0 if not supported or available."
::= { edPowerMgmtPhasesTableReactiveEnergyValue 2 }



edPowerMgmtPhasesTableReactiveEnergyPhase3 OBJECT-TYPE
        SYNTAX             Integer32
        ACCESS         read-only
        STATUS             mandatory
        DESCRIPTION
        "Actual value of KVarHr of the phase .
         Returns 0 if not supported or available."
::= { edPowerMgmtPhasesTableReactiveEnergyValue 3 }

edPowerMgmtPhasesTableActiveEnergyPhase1 OBJECT-TYPE
        SYNTAX             Integer32
        ACCESS         read-only
        STATUS             mandatory
        DESCRIPTION
        "Actual value of kWattHr of the phase .
         Returns 0 if not supported."
::= { edPowerMgmtPhasesTableActiveEnergyValue 1 }

edPowerMgmtPhasesTableActiveEnergyPhase2 OBJECT-TYPE
        SYNTAX             Integer32
        ACCESS         read-only
        STATUS             mandatory
        DESCRIPTION
        "Actual value of kWattHr of the phase .
         Returns 0 if not supported."
::= { edPowerMgmtPhasesTableActiveEnergyValue 2 }

edPowerMgmtPhasesTableActiveEnergyPhase3 OBJECT-TYPE
        SYNTAX             Integer32
        ACCESS         read-only
        STATUS             mandatory
        DESCRIPTION
        "Actual value of kWattHr of the phase .
         Returns 0 if not supported."
::= { edPowerMgmtPhasesTableActiveEnergyValue 3 }


edPowerMgmtPhasesTableInstantaneousPowerPhase1 OBJECT-TYPE
        SYNTAX             Integer32
        ACCESS         read-only
        STATUS             mandatory
        DESCRIPTION
        "Actual value of KWatt of the Phase.
         Returns 0 if not supported."
::= { edPowerMgmtPhasesTableInstantaneousPowerValue 1 }


edPowerMgmtPhasesTableInstantaneousPowerPhase2 OBJECT-TYPE
        SYNTAX             Integer32
        ACCESS         read-only
        STATUS             mandatory
        DESCRIPTION
        "Actual value of KWatt of the Phase.
         Returns 0 if not supported."
::= { edPowerMgmtPhasesTableInstantaneousPowerValue 2 }


edPowerMgmtPhasesTableInstantaneousPowerPhase3 OBJECT-TYPE
        SYNTAX             Integer32
        ACCESS         read-only
        STATUS             mandatory
        DESCRIPTION
        "Actual value of KWatt of the Phase.
         Returns 0 if not supported."
::= { edPowerMgmtPhasesTableInstantaneousPowerValue 3 }


edPowerMgmtPhasesTablePowerFactorPhase1 OBJECT-TYPE
        SYNTAX             Integer32
        ACCESS         read-only
        STATUS             mandatory
        DESCRIPTION
        "Actual value of Power Factor of the Phase.
         Returns 0 if not supported."
::= { edPowerMgmtPhasesTablePowerFactorValue 1 }

edPowerMgmtPhasesTablePowerFactorPhase2 OBJECT-TYPE
        SYNTAX             Integer32
        ACCESS         read-only
        STATUS             mandatory
        DESCRIPTION
        "Actual value of Power Factor of the Phase.
         Returns 0 if not supported."
::= { edPowerMgmtPhasesTablePowerFactorValue 2 }

edPowerMgmtPhasesTablePowerFactorPhase3 OBJECT-TYPE
        SYNTAX             Integer32
        ACCESS         read-only
        STATUS             mandatory
        DESCRIPTION
        "Actual value of Power Factor of the Phase.
         Returns 0 if not supported."
::= { edPowerMgmtPhasesTablePowerFactorValue 3 }


edPowerMgmtTotalNumberOfSensor OBJECT-TYPE
        SYNTAX             Integer32
        ACCESS         read-only
        STATUS             mandatory
        DESCRIPTION
        "Number of Sensors managed by the appliance."
::= { edPowerMgmt 6 }


edPowerMgmtSensorsTable OBJECT IDENTIFIER ::= { edPowerMgmt 7 }

edPowerMgmtSensorsData OBJECT IDENTIFIER ::= { edPowerMgmtSensorsTable 1 }

edPowerMgmtSensorsTableNumber OBJECT IDENTIFIER ::= { edPowerMgmtSensorsData 1 }
edPowerMgmtSensorsTableSensorType OBJECT IDENTIFIER ::= { edPowerMgmtSensorsData 2 }
edPowerMgmtSensorsTableSensorValue OBJECT IDENTIFIER::= { edPowerMgmtSensorsData 3 }

edPowerMgmtSensorsTableSensor1 OBJECT-TYPE
        SYNTAX             INTEGER
        ACCESS         read-only
        STATUS             mandatory
        DESCRIPTION
        "Number of the sensor in the PDU."
::= { edPowerMgmtSensorsTableNumber 1 }


edPowerMgmtSensorsTableSensor2 OBJECT-TYPE
        SYNTAX             INTEGER
        ACCESS         read-only
        STATUS             mandatory
        DESCRIPTION
        "Number of the sensor in the PDU."
::= { edPowerMgmtSensorsTableNumber 2 }


edPowerMgmtSensorsTableSensor3 OBJECT-TYPE
        SYNTAX             INTEGER
        ACCESS         read-only
        STATUS             mandatory
        DESCRIPTION
        "Number of the sensor in the PDU."
::= { edPowerMgmtSensorsTableNumber 3 }

edPowerMgmtSensorsTableSensor4 OBJECT-TYPE
        SYNTAX             INTEGER
        ACCESS         read-only
        STATUS             mandatory
        DESCRIPTION
        "Number of the sensor in the PDU."
::= { edPowerMgmtSensorsTableNumber 4 }

edPowerMgmtSensorsTableSensorType1 OBJECT-TYPE
        SYNTAX             DisplayString
        ACCESS         read-only
        STATUS             mandatory
        DESCRIPTION
        "returns string displaying type of Sensor."
::= { edPowerMgmtSensorsTableSensorType 1 }

edPowerMgmtSensorsTableSensorType2 OBJECT-TYPE
        SYNTAX             DisplayString
        ACCESS         read-only
        STATUS             mandatory
        DESCRIPTION
        "returns string displaying type of Sensor."
::= { edPowerMgmtSensorsTableSensorType 2 }

edPowerMgmtSensorsTableSensorType3 OBJECT-TYPE
        SYNTAX             DisplayString
        ACCESS         read-only
        STATUS             mandatory
        DESCRIPTION
        "returns string displaying type of Sensor."
::= { edPowerMgmtSensorsTableSensorType 3 }


edPowerMgmtSensorsTableSensorType4 OBJECT-TYPE
        SYNTAX             DisplayString
        ACCESS         read-only
        STATUS             mandatory
        DESCRIPTION
        "returns string displaying type of Sensor."
::= { edPowerMgmtSensorsTableSensorType 4 }



edPowerMgmtSensorsTableSensorValueSensor1 OBJECT-TYPE
        SYNTAX             Integer32
        ACCESS         read-only
        STATUS             mandatory
        DESCRIPTION
        "returns value of Sensor
         Returns 0 if not supported."
::= { edPowerMgmtSensorsTableSensorValue 1 }

edPowerMgmtSensorsTableSensorValueSensor2 OBJECT-TYPE
        SYNTAX             Integer32
        ACCESS         read-only
        STATUS             mandatory
        DESCRIPTION
        "returns value of Sensor
         Returns 0 if not supported."
::= { edPowerMgmtSensorsTableSensorValue 2 }

edPowerMgmtSensorsTableSensorValueSensor3 OBJECT-TYPE
        SYNTAX             Integer32
        ACCESS         read-only
        STATUS             mandatory
        DESCRIPTION
        "returns value of Sensor
         Returns 0 if not supported."
::= { edPowerMgmtSensorsTableSensorValue 3 }

edPowerMgmtSensorsTableSensorValueSensor4 OBJECT-TYPE
        SYNTAX             Integer32
        ACCESS         read-only
        STATUS             mandatory
        DESCRIPTION
        "returns value of Sensor
         Returns 0 if not supported."
::= { edPowerMgmtSensorsTableSensorValue 4 }

--



-- Traps
-- Annotations are provided for Novell's NMS product
--
-- Each trap has at least one variable (mtrapargsString) which always appears
-- as the last variable in the list. This variable contains either a static
-- or dynamically-constructed string which provides an enhanced description of
-- the trap's purpose and any pertinent information about the trap.



lowLoadR TRAP-TYPE
   ENTERPRISE elcom
   VARIABLES {edPowerMgmtPhasesTablecurrentPhase1}
   DESCRIPTION
      "WARNING: A Rack PDU has violated the low load threshold."
       --#SEVERITY SEVERE
   ::= 1


nearOverloadR TRAP-TYPE
   ENTERPRISE elcom
   VARIABLES {edPowerMgmtPhasesTablecurrentPhase1  }
   DESCRIPTION
      "WARNING: A Rack PDU is near an overload condition."
   ::= 2

overloadR TRAP-TYPE
   ENTERPRISE elcom
   VARIABLES { edPowerMgmtPhasesTablecurrentPhase1  }
   DESCRIPTION
      "SEVERE: A Rack PDU is in an overload condition."
   ::= 3

lowLoadY TRAP-TYPE
   ENTERPRISE elcom
   VARIABLES {edPowerMgmtPhasesTablecurrentPhase2 }
   DESCRIPTION
      "WARNING: A Rack PDU has violated the low load threshold."
   ::= 4


nearOverloadY TRAP-TYPE
   ENTERPRISE elcom
   VARIABLES {edPowerMgmtPhasesTablecurrentPhase2  }
   DESCRIPTION
      "WARNING: A Rack PDU is near an overload condition."
   ::= 5

overloadY TRAP-TYPE
   ENTERPRISE elcom
   VARIABLES { edPowerMgmtPhasesTablecurrentPhase2  }
   DESCRIPTION
      "SEVERE: A Rack PDU is in an overload condition."
   ::= 6

lowLoadB TRAP-TYPE
   ENTERPRISE elcom
   VARIABLES {edPowerMgmtPhasesTablecurrentPhase3  }
   DESCRIPTION
      "WARNING: A Rack PDU has violated the low load threshold."
   ::= 7


nearOverloadB TRAP-TYPE
   ENTERPRISE elcom
   VARIABLES {edPowerMgmtPhasesTablecurrentPhase3  }
   DESCRIPTION
      "WARNING: A Rack PDU is near an overload condition."
 
   ::= 8

overloadB TRAP-TYPE
   ENTERPRISE elcom
   VARIABLES { edPowerMgmtPhasesTablecurrentPhase3 }
   DESCRIPTION
      "SEVERE: A Rack PDU is in an overload condition."

   ::= 9
   
lowLoad TRAP-TYPE
   ENTERPRISE elcom
   VARIABLES {edPowerMgmtPhasesTablecurrentPhase1 }
   DESCRIPTION
      "WARNING: A Rack PDU has violated the low load threshold."
   ::= 10
   
nearOverload TRAP-TYPE
   ENTERPRISE elcom
   VARIABLES {edPowerMgmtPhasesTablecurrentPhase1  }
   DESCRIPTION
      "WARNING: A Rack PDU is near an overload condition."
   ::= 11

overload TRAP-TYPE
   ENTERPRISE elcom
   VARIABLES { edPowerMgmtPhasesTablecurrentPhase1  }
   DESCRIPTION
      "SEVERE: A Rack PDU is in an overload condition."
   ::= 12





humLowCutoff TRAP-TYPE
   ENTERPRISE elcom
   VARIABLES { edPowerMgmtSensorsTableSensorValueSensor1}
   DESCRIPTION
      "SEVERE: The Humidity of the PDU is below  the lower thershold value ."
   ::= 13

humHighCutoff TRAP-TYPE
   ENTERPRISE elcom
   VARIABLES { edPowerMgmtSensorsTableSensorValueSensor1}
   DESCRIPTION
      "SEVERE: The Humidity of the PDU has exceeded the higher thershold value ."
   ::= 14
   
tempLowCutoff TRAP-TYPE
   ENTERPRISE elcom
   VARIABLES { edPowerMgmtSensorsTableSensorValueSensor2 }
   DESCRIPTION
      "SEVERE: The temperature of the PDU has gone below the lower thershold value ."
   ::= 15

tempHighCutoff TRAP-TYPE
   ENTERPRISE elcom
   VARIABLES { edPowerMgmtSensorsTableSensorValueSensor2 }
   DESCRIPTION
      "SEVERE: The temperature of the PDU has exceeded the higher thershold value ."
   ::= 16


   
   
waterSensorMoistureDetect TRAP-TYPE
   ENTERPRISE elcom
   VARIABLES { edPowerMgmtSensorsTableSensorValueSensor3}
   DESCRIPTION
      "SEVERE: The water sensor has detected Moisture along the length of Sensing cable ."
  
   ::= 17


waterSensorLeakDetect TRAP-TYPE
   ENTERPRISE elcom
   VARIABLES { edPowerMgmtSensorsTableSensorValueSensor3}
   DESCRIPTION
      "SEVERE: The Water sensor has detected a leackage along the length of Sensing cable ."
 
   ::= 18

-- Misc. Traps






-- MasterSwitch Vm Traps


-- MasterSwitch plus (MSP) Traps















-- Switched and Metered Rack PDU Traps


-- xPDU Traps (part 1)







   



-- xPDU Traps (part 2)








END
