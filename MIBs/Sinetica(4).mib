-- ----------------------------------------------------------------------
--
-- sinetica.mib
--
-- ----------------------------------------------------------------------

SINETICA-MIB DEFINITIONS ::= BEGIN



-- {{{ Imports

IMPORTS
	OBJECT-TYPE
		FROM SNMPv2-SMI
        TRAP-TYPE
                FROM RFC-1215
        DisplayString
                FROM RFC1213-MIB
        enterprises 
                FROM RFC1155-SMI
	MODULE-COMPLIANCE, OBJECT-GROUP
		FROM SNMPv2-CONF
	TEXTUAL-CONVENTION
		FROM SNMPv2-TC
	;

-- }}}



sinetica   OBJECT IDENTIFIER ::= { enterprises 3711 }



mea        OBJECT IDENTIFIER ::= { sinetica 1 }
mea1       OBJECT IDENTIFIER ::= { mea 1 }
meaObjects OBJECT IDENTIFIER ::= { mea1 1 }
meaTraps   OBJECT IDENTIFIER ::= { mea1 2 }
meaTH      OBJECT IDENTIFIER ::= { mea1 3 }

-- {{{ meaObjects  

meaIdent         OBJECT IDENTIFIER ::= { meaObjects 1  }
meaEnvironment   OBJECT IDENTIFIER ::= { meaObjects 2  }
meaDigitalInput  OBJECT IDENTIFIER ::= { meaObjects 3  }
meaDigitalOutput OBJECT IDENTIFIER ::= { meaObjects 4  }
meaAnalogInput   OBJECT IDENTIFIER ::= { meaObjects 5  }
meaAnalogOutput  OBJECT IDENTIFIER ::= { meaObjects 6  }
meaContact       OBJECT IDENTIFIER ::= { meaObjects 7  }
meaAlarm         OBJECT IDENTIFIER ::= { meaObjects 8  }
meaTest          OBJECT IDENTIFIER ::= { meaObjects 9  }
meaControl       OBJECT IDENTIFIER ::= { meaObjects 10 }
meaConfig        OBJECT IDENTIFIER ::= { meaObjects 11 }

-- {{{ meaIdent group          

manufacturer OBJECT-TYPE
    SYNTAX    DisplayString  
    ACCESS    read-only
    STATUS    mandatory
    DESCRIPTION
        "Name of aux product mfr "
    ::= { meaIdent 1 }

model OBJECT-TYPE
 SYNTAX    DisplayString  
    ACCESS    read-only
    STATUS    mandatory
    DESCRIPTION
        "Auxiliary product Model "
    ::= { meaIdent 2 }

softwareVersion OBJECT-TYPE
    SYNTAX    DisplayString  
    ACCESS    read-only
    STATUS    mandatory
    DESCRIPTION
        "Firmware/software version. "
    ::= { meaIdent 3 }

identification OBJECT-TYPE
    SYNTAX    DisplayString  
    ACCESS    read-only
    STATUS    mandatory
    DESCRIPTION
        "String identifying the Device. "
    ::= { meaIdent 4 }

unitNumber OBJECT-TYPE
    SYNTAX    INTEGER (  0..16  )
    ACCESS    read-only
    STATUS    mandatory
    DESCRIPTION
        "Unit Number "
    ::= { meaIdent 5 }

numberOfWrites OBJECT-TYPE
    SYNTAX    INTEGER (  0..99999  )
    ACCESS    read-only
    STATUS    mandatory
    DESCRIPTION
        "Number of times EEPROM written.  Implementation is vendor specific."
    ::= { meaIdent 6 }

configuration1 OBJECT-TYPE
    SYNTAX    INTEGER (  0..9999  )
    ACCESS    read-only
    STATUS    mandatory
    DESCRIPTION
        "Vendor Specific Flags "
    ::= { meaIdent 7 }

configuration2 OBJECT-TYPE
    SYNTAX    INTEGER (  0..9999  )
    ACCESS    read-only
    STATUS    mandatory
    DESCRIPTION
        "Vendor Specific Flags "
    ::= { meaIdent 8 }

configuration3 OBJECT-TYPE
    SYNTAX    INTEGER (  0..9999  )
    ACCESS    read-only
    STATUS    mandatory
    DESCRIPTION
        "Vendor Specific Flags "
    ::= { meaIdent 9 }

configuration4 OBJECT-TYPE
    SYNTAX    INTEGER (  0..9999  )
    ACCESS    read-only
    STATUS    mandatory
    DESCRIPTION
        "Vendor Specific Flags "
    ::= { meaIdent 10 }

userConfiguration1 OBJECT-TYPE
    SYNTAX    INTEGER (  0..9999  )
    ACCESS    read-write
    STATUS    mandatory
    DESCRIPTION
        "Vendor Specific Flags "
    ::= { meaIdent 11 }

userConfiguration2 OBJECT-TYPE
    SYNTAX    INTEGER (  0..9999  )
    ACCESS    read-write
    STATUS    mandatory
    DESCRIPTION
        "Vendor Specific Flags "
    ::= { meaIdent 12 }

userConfiguration3 OBJECT-TYPE
    SYNTAX    INTEGER (  0..9999  )
    ACCESS    read-write
    STATUS    mandatory
    DESCRIPTION
        "Vendor Specific Flags "
    ::= { meaIdent 13 }

userConfiguration4 OBJECT-TYPE
    SYNTAX    INTEGER (  0..9999  )
    ACCESS    read-write
    STATUS    mandatory
    DESCRIPTION
        "Vendor Specific Flags "
    ::= { meaIdent 14 }

-- }}}
-- {{{ meaEnvironment group    

meaEnvHumidityTable     OBJECT IDENTIFIER ::= { meaEnvironment 1 }
meaEnvTemperatureTable  OBJECT IDENTIFIER ::= { meaEnvironment 2 }

-- {{{ meaEnvHumidityTable    

meaEnvHumidityEntry1  OBJECT IDENTIFIER ::= { meaEnvHumidityTable 1  }
meaEnvHumidityEntry2  OBJECT IDENTIFIER ::= { meaEnvHumidityTable 2  }
meaEnvHumidityEntry3  OBJECT IDENTIFIER ::= { meaEnvHumidityTable 3  }
meaEnvHumidityEntry4  OBJECT IDENTIFIER ::= { meaEnvHumidityTable 4  }
meaEnvHumidityEntry5  OBJECT IDENTIFIER ::= { meaEnvHumidityTable 5  }
meaEnvHumidityEntry6  OBJECT IDENTIFIER ::= { meaEnvHumidityTable 6  }
meaEnvHumidityEntry7  OBJECT IDENTIFIER ::= { meaEnvHumidityTable 7  }
meaEnvHumidityEntry8  OBJECT IDENTIFIER ::= { meaEnvHumidityTable 8  }
meaEnvHumidityEntry9  OBJECT IDENTIFIER ::= { meaEnvHumidityTable 9  }
meaEnvHumidityEntry10 OBJECT IDENTIFIER ::= { meaEnvHumidityTable 10 }
meaEnvHumidityEntry11 OBJECT IDENTIFIER ::= { meaEnvHumidityTable 11 }
meaEnvHumidityEntry12 OBJECT IDENTIFIER ::= { meaEnvHumidityTable 12 }
meaEnvHumidityEntry13 OBJECT IDENTIFIER ::= { meaEnvHumidityTable 13 }
meaEnvHumidityEntry14 OBJECT IDENTIFIER ::= { meaEnvHumidityTable 14 }
meaEnvHumidityEntry15 OBJECT IDENTIFIER ::= { meaEnvHumidityTable 15 }
meaEnvHumidityEntry16 OBJECT IDENTIFIER ::= { meaEnvHumidityTable 16 }

-- meaEnvHumidityEntries
-- {{{ Entry 1

meaEnvHumidityInputName1 OBJECT-TYPE
    SYNTAX    DisplayString
    ACCESS    read-write
    STATUS    mandatory
    DESCRIPTION
        "Name of Humidity Input"
    ::= { meaEnvHumidityEntry1 1 }

meaEnvHumidityInputValue1  OBJECT-TYPE
    SYNTAX    INTEGER (0..100)
    ACCESS    read-only
    STATUS    mandatory
    DESCRIPTION
        "Humidity value in percentage - 0 to 100%"
    ::= { meaEnvHumidityEntry1 2 }

meaEnvHumidityInputUpperThreshold1  OBJECT-TYPE
    SYNTAX    INTEGER (0..100)
    ACCESS    read-write
    STATUS    mandatory
    DESCRIPTION
        "Humidity Upper Threshold in percentage - 0 to 100%"
    ::= { meaEnvHumidityEntry1 3 }

meaEnvHumidityInputLowerThreshold1  OBJECT-TYPE
    SYNTAX    INTEGER (0..100)
    ACCESS    read-write
    STATUS    mandatory
    DESCRIPTION
        "Humidity Lower Threshold in Percentage - 0 to 100%"
    ::= { meaEnvHumidityEntry1 4 }

-- }}}
-- {{{ Entry 2

meaEnvHumidityInputName2 OBJECT-TYPE
    SYNTAX    DisplayString
    ACCESS    read-write
    STATUS    mandatory
    DESCRIPTION
        "Name of Humidity Input"
    ::= { meaEnvHumidityEntry2 1 }

meaEnvHumidityInputValue2  OBJECT-TYPE
    SYNTAX    INTEGER (0..100)
    ACCESS    read-only
    STATUS    mandatory
    DESCRIPTION
        "Humidity value in percentage - 0 to 100%"
    ::= { meaEnvHumidityEntry2 2 }

meaEnvHumidityInputUpperThreshold2  OBJECT-TYPE
    SYNTAX    INTEGER (0..100)
    ACCESS    read-write
    STATUS    mandatory
    DESCRIPTION
        "Humidity Upper Threshold in percentage - 0 to 100%"
    ::= { meaEnvHumidityEntry2 3 }

meaEnvHumidityInputLowerThreshold2  OBJECT-TYPE
    SYNTAX    INTEGER (0..100)
    ACCESS    read-write
    STATUS    mandatory
    DESCRIPTION
        "Humidity Lower Threshold in Percentage - 0 to 100%"
    ::= { meaEnvHumidityEntry2 4 }

-- }}}
-- {{{ Entry 3

meaEnvHumidityInputName3 OBJECT-TYPE
    SYNTAX    DisplayString
    ACCESS    read-write
    STATUS    mandatory
    DESCRIPTION
        "Name of Humidity Input"
    ::= { meaEnvHumidityEntry3 1 }

meaEnvHumidityInputValue3  OBJECT-TYPE
    SYNTAX    INTEGER (0..100)
    ACCESS    read-only
    STATUS    mandatory
    DESCRIPTION
        "Humidity value in percentage - 0 to 100%"
    ::= { meaEnvHumidityEntry3 2 }

meaEnvHumidityInputUpperThreshold3  OBJECT-TYPE
    SYNTAX    INTEGER (0..100)
    ACCESS    read-write
    STATUS    mandatory
    DESCRIPTION
        "Humidity Upper Threshold in percentage - 0 to 100%"
    ::= { meaEnvHumidityEntry3 3 }

meaEnvHumidityInputLowerThreshold3  OBJECT-TYPE
    SYNTAX    INTEGER (0..100)
    ACCESS    read-write
    STATUS    mandatory
    DESCRIPTION
        "Humidity Lower Threshold in Percentage - 0 to 100%"
    ::= { meaEnvHumidityEntry3 4 }

-- }}}
-- {{{ Entry 4

meaEnvHumidityInputName4 OBJECT-TYPE
    SYNTAX    DisplayString
    ACCESS    read-write
    STATUS    mandatory
    DESCRIPTION
        "Name of Humidity Input"
    ::= { meaEnvHumidityEntry4 1 }

meaEnvHumidityInputValue4  OBJECT-TYPE
    SYNTAX    INTEGER (0..100)
    ACCESS    read-only
    STATUS    mandatory
    DESCRIPTION
        "Humidity value in percentage - 0 to 100%"
    ::= { meaEnvHumidityEntry4 2 }

meaEnvHumidityInputUpperThreshold4  OBJECT-TYPE
    SYNTAX    INTEGER (0..100)
    ACCESS    read-write
    STATUS    mandatory
    DESCRIPTION
        "Humidity Upper Threshold in percentage - 0 to 100%"
    ::= { meaEnvHumidityEntry4 3 }

meaEnvHumidityInputLowerThreshold4  OBJECT-TYPE
    SYNTAX    INTEGER (0..100)
    ACCESS    read-write
    STATUS    mandatory
    DESCRIPTION
        "Humidity Lower Threshold in Percentage - 0 to 100%"
    ::= { meaEnvHumidityEntry4 4 }

-- }}}
-- {{{ Entry 5

meaEnvHumidityInputName5 OBJECT-TYPE
    SYNTAX    DisplayString
    ACCESS    read-write
    STATUS    mandatory
    DESCRIPTION
        "Name of Humidity Input"
    ::= { meaEnvHumidityEntry5 1 }

meaEnvHumidityInputValue5  OBJECT-TYPE
    SYNTAX    INTEGER (0..100)
    ACCESS    read-only
    STATUS    mandatory
    DESCRIPTION
        "Humidity value in percentage - 0 to 100%"
    ::= { meaEnvHumidityEntry5 2 }

meaEnvHumidityInputUpperThreshold5  OBJECT-TYPE
    SYNTAX    INTEGER (0..100)
    ACCESS    read-write
    STATUS    mandatory
    DESCRIPTION
        "Humidity Upper Threshold in percentage - 0 to 100%"
    ::= { meaEnvHumidityEntry5 3 }

meaEnvHumidityInputLowerThreshold5  OBJECT-TYPE
    SYNTAX    INTEGER (0..100)
    ACCESS    read-write
    STATUS    mandatory
    DESCRIPTION
        "Humidity Lower Threshold in Percentage - 0 to 100%"
    ::= { meaEnvHumidityEntry5 4 }

-- }}}
-- {{{ Entry 6

meaEnvHumidityInputName6 OBJECT-TYPE
    SYNTAX    DisplayString
    ACCESS    read-write
    STATUS    mandatory
    DESCRIPTION
        "Name of Humidity Input"
    ::= { meaEnvHumidityEntry6 1 }

meaEnvHumidityInputValue6  OBJECT-TYPE
    SYNTAX    INTEGER (0..100)
    ACCESS    read-only
    STATUS    mandatory
    DESCRIPTION
        "Humidity value in percentage - 0 to 100%"
    ::= { meaEnvHumidityEntry6 2 }

meaEnvHumidityInputUpperThreshold6  OBJECT-TYPE
    SYNTAX    INTEGER (0..100)
    ACCESS    read-write
    STATUS    mandatory
    DESCRIPTION
        "Humidity Upper Threshold in percentage - 0 to 100%"
    ::= { meaEnvHumidityEntry6 3 }

meaEnvHumidityInputLowerThreshold6  OBJECT-TYPE
    SYNTAX    INTEGER (0..100)
    ACCESS    read-write
    STATUS    mandatory
    DESCRIPTION
        "Humidity Lower Threshold in Percentage - 0 to 100%"
    ::= { meaEnvHumidityEntry6 4 }

-- }}}
-- {{{ Entry 7

meaEnvHumidityInputName7 OBJECT-TYPE
    SYNTAX    DisplayString
    ACCESS    read-write
    STATUS    mandatory
    DESCRIPTION
        "Name of Humidity Input"
    ::= { meaEnvHumidityEntry7 1 }

meaEnvHumidityInputValue7  OBJECT-TYPE
    SYNTAX    INTEGER (0..100)
    ACCESS    read-only
    STATUS    mandatory
    DESCRIPTION
        "Humidity value in percentage - 0 to 100%"
    ::= { meaEnvHumidityEntry7 2 }

meaEnvHumidityInputUpperThreshold7  OBJECT-TYPE
    SYNTAX    INTEGER (0..100)
    ACCESS    read-write
    STATUS    mandatory
    DESCRIPTION
        "Humidity Upper Threshold in percentage - 0 to 100%"
    ::= { meaEnvHumidityEntry7 3 }

meaEnvHumidityInputLowerThreshold7  OBJECT-TYPE
    SYNTAX    INTEGER (0..100)
    ACCESS    read-write
    STATUS    mandatory
    DESCRIPTION
        "Humidity Lower Threshold in Percentage - 0 to 100%"
    ::= { meaEnvHumidityEntry7 4 }

-- }}}
-- {{{ Entry 8

meaEnvHumidityInputName8 OBJECT-TYPE
    SYNTAX    DisplayString
    ACCESS    read-write
    STATUS    mandatory
    DESCRIPTION
        "Name of Humidity Input"
    ::= { meaEnvHumidityEntry8 1 }

meaEnvHumidityInputValue8  OBJECT-TYPE
    SYNTAX    INTEGER (0..100)
    ACCESS    read-only
    STATUS    mandatory
    DESCRIPTION
        "Humidity value in percentage - 0 to 100%"
    ::= { meaEnvHumidityEntry8 2 }

meaEnvHumidityInputUpperThreshold8  OBJECT-TYPE
    SYNTAX    INTEGER (0..100)
    ACCESS    read-write
    STATUS    mandatory
    DESCRIPTION
        "Humidity Upper Threshold in percentage - 0 to 100%"
    ::= { meaEnvHumidityEntry8 3 }

meaEnvHumidityInputLowerThreshold8  OBJECT-TYPE
    SYNTAX    INTEGER (0..100)
    ACCESS    read-write
    STATUS    mandatory
    DESCRIPTION
        "Humidity Lower Threshold in Percentage - 0 to 100%"
    ::= { meaEnvHumidityEntry8 4 }

-- }}}
-- {{{ Entry 9

meaEnvHumidityInputName9 OBJECT-TYPE
    SYNTAX    DisplayString
    ACCESS    read-write
    STATUS    mandatory
    DESCRIPTION
        "Name of Humidity Input"
    ::= { meaEnvHumidityEntry9 1 }

meaEnvHumidityInputValue9  OBJECT-TYPE
    SYNTAX    INTEGER (0..100)
    ACCESS    read-only
    STATUS    mandatory
    DESCRIPTION
        "Humidity value in percentage - 0 to 100%"
    ::= { meaEnvHumidityEntry9 2 }

meaEnvHumidityInputUpperThreshold9  OBJECT-TYPE
    SYNTAX    INTEGER (0..100)
    ACCESS    read-write
    STATUS    mandatory
    DESCRIPTION
        "Humidity Upper Threshold in percentage - 0 to 100%"
    ::= { meaEnvHumidityEntry9 3 }

meaEnvHumidityInputLowerThreshold9  OBJECT-TYPE
    SYNTAX    INTEGER (0..100)
    ACCESS    read-write
    STATUS    mandatory
    DESCRIPTION
        "Humidity Lower Threshold in Percentage - 0 to 100%"
    ::= { meaEnvHumidityEntry9 4 }

-- }}}
-- {{{ Entry 10

meaEnvHumidityInputName10 OBJECT-TYPE
    SYNTAX    DisplayString
    ACCESS    read-write
    STATUS    mandatory
    DESCRIPTION
        "Name of Humidity Input"
    ::= { meaEnvHumidityEntry10 1 }

meaEnvHumidityInputValue10  OBJECT-TYPE
    SYNTAX    INTEGER (0..100)
    ACCESS    read-only
    STATUS    mandatory
    DESCRIPTION
        "Humidity value in percentage - 0 to 100%"
    ::= { meaEnvHumidityEntry10 2 }

meaEnvHumidityInputUpperThreshold10  OBJECT-TYPE
    SYNTAX    INTEGER (0..100)
    ACCESS    read-write
    STATUS    mandatory
    DESCRIPTION
        "Humidity Upper Threshold in percentage - 0 to 100%"
    ::= { meaEnvHumidityEntry10 3 }

meaEnvHumidityInputLowerThreshold10  OBJECT-TYPE
    SYNTAX    INTEGER (0..100)
    ACCESS    read-write
    STATUS    mandatory
    DESCRIPTION
        "Humidity Lower Threshold in Percentage - 0 to 100%"
    ::= { meaEnvHumidityEntry10 4 }

-- }}}
-- {{{ Entry 11

meaEnvHumidityInputName11 OBJECT-TYPE
    SYNTAX    DisplayString
    ACCESS    read-write
    STATUS    mandatory
    DESCRIPTION
        "Name of Humidity Input"
    ::= { meaEnvHumidityEntry11 1 }

meaEnvHumidityInputValue11  OBJECT-TYPE
    SYNTAX    INTEGER (0..100)
    ACCESS    read-only
    STATUS    mandatory
    DESCRIPTION
        "Humidity value in percentage - 0 to 100%"
    ::= { meaEnvHumidityEntry11 2 }

meaEnvHumidityInputUpperThreshold11  OBJECT-TYPE
    SYNTAX    INTEGER (0..100)
    ACCESS    read-write
    STATUS    mandatory
    DESCRIPTION
        "Humidity Upper Threshold in percentage - 0 to 100%"
    ::= { meaEnvHumidityEntry11 3 }

meaEnvHumidityInputLowerThreshold11  OBJECT-TYPE
    SYNTAX    INTEGER (0..100)
    ACCESS    read-write
    STATUS    mandatory
    DESCRIPTION
        "Humidity Lower Threshold in Percentage - 0 to 100%"
    ::= { meaEnvHumidityEntry11 4 }

-- }}}
-- {{{ Entry 12

meaEnvHumidityInputName12 OBJECT-TYPE
    SYNTAX    DisplayString
    ACCESS    read-write
    STATUS    mandatory
    DESCRIPTION
        "Name of Humidity Input"
    ::= { meaEnvHumidityEntry12 1 }

meaEnvHumidityInputValue12  OBJECT-TYPE
    SYNTAX    INTEGER (0..100)
    ACCESS    read-only
    STATUS    mandatory
    DESCRIPTION
        "Humidity value in percentage - 0 to 100%"
    ::= { meaEnvHumidityEntry12 2 }

meaEnvHumidityInputUpperThreshold12  OBJECT-TYPE
    SYNTAX    INTEGER (0..100)
    ACCESS    read-write
    STATUS    mandatory
    DESCRIPTION
        "Humidity Upper Threshold in percentage - 0 to 100%"
    ::= { meaEnvHumidityEntry12 3 }

meaEnvHumidityInputLowerThreshold12  OBJECT-TYPE
    SYNTAX    INTEGER (0..100)
    ACCESS    read-write
    STATUS    mandatory
    DESCRIPTION
        "Humidity Lower Threshold in Percentage - 0 to 100%"
    ::= { meaEnvHumidityEntry12 4 }

-- }}}
-- {{{ Entry 13

meaEnvHumidityInputName13 OBJECT-TYPE
    SYNTAX    DisplayString
    ACCESS    read-write
    STATUS    mandatory
    DESCRIPTION
        "Name of Humidity Input"
    ::= { meaEnvHumidityEntry13 1 }

meaEnvHumidityInputValue13  OBJECT-TYPE
    SYNTAX    INTEGER (0..100)
    ACCESS    read-only
    STATUS    mandatory
    DESCRIPTION
        "Humidity value in percentage - 0 to 100%"
    ::= { meaEnvHumidityEntry13 2 }

meaEnvHumidityInputUpperThreshold13  OBJECT-TYPE
    SYNTAX    INTEGER (0..100)
    ACCESS    read-write
    STATUS    mandatory
    DESCRIPTION
        "Humidity Upper Threshold in percentage - 0 to 100%"
    ::= { meaEnvHumidityEntry13 3 }

meaEnvHumidityInputLowerThreshold13  OBJECT-TYPE
    SYNTAX    INTEGER (0..100)
    ACCESS    read-write
    STATUS    mandatory
    DESCRIPTION
        "Humidity Lower Threshold in Percentage - 0 to 100%"
    ::= { meaEnvHumidityEntry13 4 }

-- }}}
-- {{{ Entry 14

meaEnvHumidityInputName14 OBJECT-TYPE
    SYNTAX    DisplayString
    ACCESS    read-write
    STATUS    mandatory
    DESCRIPTION
        "Name of Humidity Input"
    ::= { meaEnvHumidityEntry14 1 }

meaEnvHumidityInputValue14  OBJECT-TYPE
    SYNTAX    INTEGER (0..100)
    ACCESS    read-only
    STATUS    mandatory
    DESCRIPTION
        "Humidity value in percentage - 0 to 100%"
    ::= { meaEnvHumidityEntry14 2 }

meaEnvHumidityInputUpperThreshold14  OBJECT-TYPE
    SYNTAX    INTEGER (0..100)
    ACCESS    read-write
    STATUS    mandatory
    DESCRIPTION
        "Humidity Upper Threshold in percentage - 0 to 100%"
    ::= { meaEnvHumidityEntry14 3 }

meaEnvHumidityInputLowerThreshold14  OBJECT-TYPE
    SYNTAX    INTEGER (0..100)
    ACCESS    read-write
    STATUS    mandatory
    DESCRIPTION
        "Humidity Lower Threshold in Percentage - 0 to 100%"
    ::= { meaEnvHumidityEntry14 4 }

-- }}}
-- {{{ Entry 15

meaEnvHumidityInputName15 OBJECT-TYPE
    SYNTAX    DisplayString
    ACCESS    read-write
    STATUS    mandatory
    DESCRIPTION
        "Name of Humidity Input"
    ::= { meaEnvHumidityEntry15 1 }

meaEnvHumidityInputValue15  OBJECT-TYPE
    SYNTAX    INTEGER (0..100)
    ACCESS    read-only
    STATUS    mandatory
    DESCRIPTION
        "Humidity value in percentage - 0 to 100%"
    ::= { meaEnvHumidityEntry15 2 }

meaEnvHumidityInputUpperThreshold15  OBJECT-TYPE
    SYNTAX    INTEGER (0..100)
    ACCESS    read-write
    STATUS    mandatory
    DESCRIPTION
        "Humidity Upper Threshold in percentage - 0 to 100%"
    ::= { meaEnvHumidityEntry15 3 }

meaEnvHumidityInputLowerThreshold15  OBJECT-TYPE
    SYNTAX    INTEGER (0..100)
    ACCESS    read-write
    STATUS    mandatory
    DESCRIPTION
        "Humidity Lower Threshold in Percentage - 0 to 100%"
    ::= { meaEnvHumidityEntry15 4 }

-- }}}
-- {{{ Entry 16

meaEnvHumidityInputName16 OBJECT-TYPE
    SYNTAX    DisplayString
    ACCESS    read-write
    STATUS    mandatory
    DESCRIPTION
        "Name of Humidity Input"
    ::= { meaEnvHumidityEntry16 1 }

meaEnvHumidityInputValue16  OBJECT-TYPE
    SYNTAX    INTEGER (0..100)
    ACCESS    read-only
    STATUS    mandatory
    DESCRIPTION
        "Humidity value in percentage - 0 to 100%"
    ::= { meaEnvHumidityEntry16 2 }

meaEnvHumidityInputUpperThreshold16  OBJECT-TYPE
    SYNTAX    INTEGER (0..100)
    ACCESS    read-write
    STATUS    mandatory
    DESCRIPTION
        "Humidity Upper Threshold in percentage - 0 to 100%"
    ::= { meaEnvHumidityEntry16 3 }

meaEnvHumidityInputLowerThreshold16  OBJECT-TYPE
    SYNTAX    INTEGER (0..100)
    ACCESS    read-write
    STATUS    mandatory
    DESCRIPTION
        "Humidity Lower Threshold in Percentage - 0 to 100%"
    ::= { meaEnvHumidityEntry16 4 }

-- }}}

-- }}}
-- {{{ meaEnvTemperatureTable 

meaEnvTemperatureEntry1  OBJECT IDENTIFIER ::= { meaEnvTemperatureTable 1  }
meaEnvTemperatureEntry2  OBJECT IDENTIFIER ::= { meaEnvTemperatureTable 2  }
meaEnvTemperatureEntry3  OBJECT IDENTIFIER ::= { meaEnvTemperatureTable 3  }
meaEnvTemperatureEntry4  OBJECT IDENTIFIER ::= { meaEnvTemperatureTable 4  }
meaEnvTemperatureEntry5  OBJECT IDENTIFIER ::= { meaEnvTemperatureTable 5  }
meaEnvTemperatureEntry6  OBJECT IDENTIFIER ::= { meaEnvTemperatureTable 6  }
meaEnvTemperatureEntry7  OBJECT IDENTIFIER ::= { meaEnvTemperatureTable 7  }
meaEnvTemperatureEntry8  OBJECT IDENTIFIER ::= { meaEnvTemperatureTable 8  }
meaEnvTemperatureEntry9  OBJECT IDENTIFIER ::= { meaEnvTemperatureTable 9  }
meaEnvTemperatureEntry10 OBJECT IDENTIFIER ::= { meaEnvTemperatureTable 10 }
meaEnvTemperatureEntry11 OBJECT IDENTIFIER ::= { meaEnvTemperatureTable 11 }
meaEnvTemperatureEntry12 OBJECT IDENTIFIER ::= { meaEnvTemperatureTable 12 }
meaEnvTemperatureEntry13 OBJECT IDENTIFIER ::= { meaEnvTemperatureTable 13 }
meaEnvTemperatureEntry14 OBJECT IDENTIFIER ::= { meaEnvTemperatureTable 14 }
meaEnvTemperatureEntry15 OBJECT IDENTIFIER ::= { meaEnvTemperatureTable 15 }
meaEnvTemperatureEntry16 OBJECT IDENTIFIER ::= { meaEnvTemperatureTable 16 }

-- meaTemperatureEntries

-- {{{ Entry 1

meaEnvTemperatureInputName1 OBJECT-TYPE
    SYNTAX    DisplayString
    ACCESS    read-write
    STATUS    mandatory
    DESCRIPTION
        "Name of Temperature Input"
    ::= { meaEnvTemperatureEntry1 1 }

meaEnvTemperatureInputValue1  OBJECT-TYPE
    SYNTAX    INTEGER (-40..200)
    ACCESS    read-only
    STATUS    mandatory
    DESCRIPTION
        "Temperature value in deg C -20 to 100"
    ::= { meaEnvTemperatureEntry1 2 }

meaEnvTemperatureInputUpperThreshold1  OBJECT-TYPE
    SYNTAX    INTEGER (-40..200)
    ACCESS    read-write
    STATUS    mandatory
    DESCRIPTION
        "Temperature Upper Threshold in deg C -20 to 100"
    ::= { meaEnvTemperatureEntry1 3 }

meaEnvTemperatureInputLowerThreshold1  OBJECT-TYPE
    SYNTAX    INTEGER (-40..200)
    ACCESS    read-write
    STATUS    mandatory
    DESCRIPTION
        "Temperature Lower Threshold in deg C -20 to 100"
    ::= { meaEnvTemperatureEntry1 4 }

-- }}}
-- {{{ Entry 2

meaEnvTemperatureInputName2 OBJECT-TYPE
    SYNTAX    DisplayString
    ACCESS    read-write
    STATUS    mandatory
    DESCRIPTION
        "Name of Temperature Input"
    ::= { meaEnvTemperatureEntry2 1 }

meaEnvTemperatureInputValue2  OBJECT-TYPE
    SYNTAX    INTEGER (-40..200)
    ACCESS    read-only
    STATUS    mandatory
    DESCRIPTION
        "Temperature value in deg C -20 to 100"
    ::= { meaEnvTemperatureEntry2 2 }

meaEnvTemperatureInputUpperThreshold2  OBJECT-TYPE
    SYNTAX    INTEGER (-40..200)
    ACCESS    read-write
    STATUS    mandatory
    DESCRIPTION
        "Temperature Upper Threshold in deg C -20 to 100"
    ::= { meaEnvTemperatureEntry2 3 }

meaEnvTemperatureInputLowerThreshold2  OBJECT-TYPE
    SYNTAX    INTEGER (-40..200)
    ACCESS    read-write
    STATUS    mandatory
    DESCRIPTION
        "Temperature Lower Threshold in deg C -20 to 100"
    ::= { meaEnvTemperatureEntry2 4 }

-- }}}
-- {{{ Entry 3 

meaEnvTemperatureInputName3 OBJECT-TYPE
    SYNTAX    DisplayString
    ACCESS    read-write
    STATUS    mandatory
    DESCRIPTION
        "Name of Temperature Input"
    ::= { meaEnvTemperatureEntry3 1 }

meaEnvTemperatureInputValue3  OBJECT-TYPE
    SYNTAX    INTEGER (-40..200)
    ACCESS    read-only
    STATUS    mandatory
    DESCRIPTION
        "Temperature value in deg C -20 to 100"
    ::= { meaEnvTemperatureEntry3 2 }

meaEnvTemperatureInputUpperThreshold3  OBJECT-TYPE
    SYNTAX    INTEGER (-40..200)
    ACCESS    read-write
    STATUS    mandatory
    DESCRIPTION
        "Temperature Upper Threshold in deg C -20 to 100"
    ::= { meaEnvTemperatureEntry3 3 }

meaEnvTemperatureInputLowerThreshold3  OBJECT-TYPE
    SYNTAX    INTEGER (-40..200)
    ACCESS    read-write
    STATUS    mandatory
    DESCRIPTION
        "Temperature Lower Threshold in deg C -20 to 100"
    ::= { meaEnvTemperatureEntry3 4 }

-- }}}
-- {{{ Entry 4 

meaEnvTemperatureInputName4 OBJECT-TYPE
    SYNTAX    DisplayString
    ACCESS    read-write
    STATUS    mandatory
    DESCRIPTION
        "Name of Temperature Input"
    ::= { meaEnvTemperatureEntry4 1 }

meaEnvTemperatureInputValue4  OBJECT-TYPE
    SYNTAX    INTEGER (-40..200)
    ACCESS    read-only
    STATUS    mandatory
    DESCRIPTION
        "Temperature value in deg C -20 to 100"
    ::= { meaEnvTemperatureEntry4 2 }

meaEnvTemperatureInputUpperThreshold4  OBJECT-TYPE
    SYNTAX    INTEGER (-40..200)
    ACCESS    read-write
    STATUS    mandatory
    DESCRIPTION
        "Temperature Upper Threshold in deg C -20 to 100"
    ::= { meaEnvTemperatureEntry4 3 }

meaEnvTemperatureInputLowerThreshold4  OBJECT-TYPE
    SYNTAX    INTEGER (-40..200)
    ACCESS    read-write
    STATUS    mandatory
    DESCRIPTION
        "Temperature Lower Threshold in deg C -20 to 100"
    ::= { meaEnvTemperatureEntry4 4 }

-- }}}
-- {{{ Entry 5 

meaEnvTemperatureInputName5 OBJECT-TYPE
    SYNTAX    DisplayString
    ACCESS    read-write
    STATUS    mandatory
    DESCRIPTION
        "Name of Temperature Input"
    ::= { meaEnvTemperatureEntry5 1 }

meaEnvTemperatureInputValue5  OBJECT-TYPE
    SYNTAX    INTEGER (-40..200)
    ACCESS    read-only
    STATUS    mandatory
    DESCRIPTION
        "Temperature value in deg C -20 to 100"
    ::= { meaEnvTemperatureEntry5 2 }

meaEnvTemperatureInputUpperThreshold5  OBJECT-TYPE
    SYNTAX    INTEGER (-40..200)
    ACCESS    read-write
    STATUS    mandatory
    DESCRIPTION
        "Temperature Upper Threshold in deg C -20 to 100"
    ::= { meaEnvTemperatureEntry5 3 }

meaEnvTemperatureInputLowerThreshold5  OBJECT-TYPE
    SYNTAX    INTEGER (-40..200)
    ACCESS    read-write
    STATUS    mandatory
    DESCRIPTION
        "Temperature Lower Threshold in deg C -20 to 100"
    ::= { meaEnvTemperatureEntry5 4 }

-- }}}
-- {{{ Entry 6 

meaEnvTemperatureInputName6 OBJECT-TYPE
    SYNTAX    DisplayString
    ACCESS    read-write
    STATUS    mandatory
    DESCRIPTION
        "Name of Temperature Input"
    ::= { meaEnvTemperatureEntry6 1 }

meaEnvTemperatureInputValue6  OBJECT-TYPE
    SYNTAX    INTEGER (-40..200)
    ACCESS    read-only
    STATUS    mandatory
    DESCRIPTION
        "Temperature value in deg C -20 to 100"
    ::= { meaEnvTemperatureEntry6 2 }

meaEnvTemperatureInputUpperThreshold6  OBJECT-TYPE
    SYNTAX    INTEGER (-40..200)
    ACCESS    read-write
    STATUS    mandatory
    DESCRIPTION
        "Temperature Upper Threshold in deg C -20 to 100"
    ::= { meaEnvTemperatureEntry6 3 }

meaEnvTemperatureInputLowerThreshold6  OBJECT-TYPE
    SYNTAX    INTEGER (-40..200)
    ACCESS    read-write
    STATUS    mandatory
    DESCRIPTION
        "Temperature Lower Threshold in deg C -20 to 100"
    ::= { meaEnvTemperatureEntry6 4 }

-- }}}
-- {{{ Entry 7 

meaEnvTemperatureInputName7 OBJECT-TYPE
    SYNTAX    DisplayString
    ACCESS    read-write
    STATUS    mandatory
    DESCRIPTION
        "Name of Temperature Input"
    ::= { meaEnvTemperatureEntry7 1 }

meaEnvTemperatureInputValue7  OBJECT-TYPE
    SYNTAX    INTEGER (-40..200)
    ACCESS    read-only
    STATUS    mandatory
    DESCRIPTION
        "Temperature value in deg C -20 to 100"
    ::= { meaEnvTemperatureEntry7 2 }

meaEnvTemperatureInputUpperThreshold7  OBJECT-TYPE
    SYNTAX    INTEGER (-40..200)
    ACCESS    read-write
    STATUS    mandatory
    DESCRIPTION
        "Temperature Upper Threshold in deg C -20 to 100"
    ::= { meaEnvTemperatureEntry7 3 }

meaEnvTemperatureInputLowerThreshold7  OBJECT-TYPE
    SYNTAX    INTEGER (-40..200)
    ACCESS    read-write
    STATUS    mandatory
    DESCRIPTION
        "Temperature Lower Threshold in deg C -20 to 100"
    ::= { meaEnvTemperatureEntry7 4 }

-- }}}
-- {{{ Entry 8 

meaEnvTemperatureInputName8 OBJECT-TYPE
    SYNTAX    DisplayString
    ACCESS    read-write
    STATUS    mandatory
    DESCRIPTION
        "Name of Temperature Input"
    ::= { meaEnvTemperatureEntry8 1 }

meaEnvTemperatureInputValue8  OBJECT-TYPE
    SYNTAX    INTEGER (-40..200)
    ACCESS    read-only
    STATUS    mandatory
    DESCRIPTION
        "Temperature value in deg C -20 to 100"
    ::= { meaEnvTemperatureEntry8 2 }

meaEnvTemperatureInputUpperThreshold8  OBJECT-TYPE
    SYNTAX    INTEGER (-40..200)
    ACCESS    read-write
    STATUS    mandatory
    DESCRIPTION
        "Temperature Upper Threshold in deg C -20 to 100"
    ::= { meaEnvTemperatureEntry8 3 }

meaEnvTemperatureInputLowerThreshold8  OBJECT-TYPE
    SYNTAX    INTEGER (-40..200)
    ACCESS    read-write
    STATUS    mandatory
    DESCRIPTION
        "Temperature Lower Threshold in deg C -20 to 100"
    ::= { meaEnvTemperatureEntry8 4 }


-- }}}
-- {{{ Entry 9 

meaEnvTemperatureInputName9 OBJECT-TYPE
    SYNTAX    DisplayString
    ACCESS    read-write
    STATUS    mandatory
    DESCRIPTION
        "Name of Temperature Input"
    ::= { meaEnvTemperatureEntry9 1 }

meaEnvTemperatureInputValue9  OBJECT-TYPE
    SYNTAX    INTEGER (-40..200)
    ACCESS    read-only
    STATUS    mandatory
    DESCRIPTION
        "Temperature value in deg C -20 to 100"
    ::= { meaEnvTemperatureEntry9 2 }

meaEnvTemperatureInputUpperThreshold9  OBJECT-TYPE
    SYNTAX    INTEGER (-40..200)
    ACCESS    read-write
    STATUS    mandatory
    DESCRIPTION
        "Temperature Upper Threshold in deg C -20 to 100"
    ::= { meaEnvTemperatureEntry9 3 }

meaEnvTemperatureInputLowerThreshold9  OBJECT-TYPE
    SYNTAX    INTEGER (-40..200)
    ACCESS    read-write
    STATUS    mandatory
    DESCRIPTION
        "Temperature Lower Threshold in deg C -20 to 100"
    ::= { meaEnvTemperatureEntry9 4 }

-- }}}
-- {{{ Entry 10

meaEnvTemperatureInputName10 OBJECT-TYPE
    SYNTAX    DisplayString
    ACCESS    read-write
    STATUS    mandatory
    DESCRIPTION
        "Name of Temperature Input"
    ::= { meaEnvTemperatureEntry10 1 }

meaEnvTemperatureInputValue10  OBJECT-TYPE
    SYNTAX    INTEGER (-40..200)
    ACCESS    read-only
    STATUS    mandatory
    DESCRIPTION
        "Temperature value in deg C -20 to 100"
    ::= { meaEnvTemperatureEntry10 2 }

meaEnvTemperatureInputUpperThreshold10  OBJECT-TYPE
    SYNTAX    INTEGER (-40..200)
    ACCESS    read-write
    STATUS    mandatory
    DESCRIPTION
        "Temperature Upper Threshold in deg C -20 to 100"
    ::= { meaEnvTemperatureEntry10 3 }

meaEnvTemperatureInputLowerThreshold10  OBJECT-TYPE
    SYNTAX    INTEGER (-40..200)
    ACCESS    read-write
    STATUS    mandatory
    DESCRIPTION
        "Temperature Lower Threshold in deg C -20 to 100"
    ::= { meaEnvTemperatureEntry10 4 }

-- }}}
-- {{{ Entry 11

meaEnvTemperatureInputName11 OBJECT-TYPE
    SYNTAX    DisplayString
    ACCESS    read-write
    STATUS    mandatory
    DESCRIPTION
        "Name of Temperature Input"
    ::= { meaEnvTemperatureEntry11 1 }

meaEnvTemperatureInputValue11  OBJECT-TYPE
    SYNTAX    INTEGER (-40..200)
    ACCESS    read-only
    STATUS    mandatory
    DESCRIPTION
        "Temperature value in deg C -20 to 100"
    ::= { meaEnvTemperatureEntry11 2 }

meaEnvTemperatureInputUpperThreshold11  OBJECT-TYPE
    SYNTAX    INTEGER (-40..200)
    ACCESS    read-write
    STATUS    mandatory
    DESCRIPTION
        "Temperature Upper Threshold in deg C -20 to 100"
    ::= { meaEnvTemperatureEntry11 3 }

meaEnvTemperatureInputLowerThreshold11  OBJECT-TYPE
    SYNTAX    INTEGER (-40..200)
    ACCESS    read-write
    STATUS    mandatory
    DESCRIPTION
        "Temperature Lower Threshold in deg C -20 to 100"
    ::= { meaEnvTemperatureEntry11 4 }

-- }}}
-- {{{ Entry 12

meaEnvTemperatureInputName12 OBJECT-TYPE
    SYNTAX    DisplayString
    ACCESS    read-write
    STATUS    mandatory
    DESCRIPTION
        "Name of Temperature Input"
    ::= { meaEnvTemperatureEntry12 1 }

meaEnvTemperatureInputValue12  OBJECT-TYPE
    SYNTAX    INTEGER (-40..200)
    ACCESS    read-only
    STATUS    mandatory
    DESCRIPTION
        "Temperature value in deg C -20 to 100"
    ::= { meaEnvTemperatureEntry12 2 }

meaEnvTemperatureInputUpperThreshold12  OBJECT-TYPE
    SYNTAX    INTEGER (-40..200)
    ACCESS    read-write
    STATUS    mandatory
    DESCRIPTION
        "Temperature Upper Threshold in deg C -20 to 100"
    ::= { meaEnvTemperatureEntry12 3 }

meaEnvTemperatureInputLowerThreshold12  OBJECT-TYPE
    SYNTAX    INTEGER (-40..200)
    ACCESS    read-write
    STATUS    mandatory
    DESCRIPTION
        "Temperature Lower Threshold in deg C -20 to 100"
    ::= { meaEnvTemperatureEntry12 4 }

-- }}}
-- {{{ Entry 13

meaEnvTemperatureInputName13 OBJECT-TYPE
    SYNTAX    DisplayString
    ACCESS    read-write
    STATUS    mandatory
    DESCRIPTION
        "Name of Temperature Input"
    ::= { meaEnvTemperatureEntry13 1 }

meaEnvTemperatureInputValue13  OBJECT-TYPE
    SYNTAX    INTEGER (-40..200)
    ACCESS    read-only
    STATUS    mandatory
    DESCRIPTION
        "Temperature value in deg C -20 to 100"
    ::= { meaEnvTemperatureEntry13 2 }

meaEnvTemperatureInputUpperThreshold13  OBJECT-TYPE
    SYNTAX    INTEGER (-40..200)
    ACCESS    read-write
    STATUS    mandatory
    DESCRIPTION
        "Temperature Upper Threshold in deg C -20 to 100"
    ::= { meaEnvTemperatureEntry13 3 }

meaEnvTemperatureInputLowerThreshold13  OBJECT-TYPE
    SYNTAX    INTEGER (-40..200)
    ACCESS    read-write
    STATUS    mandatory
    DESCRIPTION
        "Temperature Lower Threshold in deg C -20 to 100"
    ::= { meaEnvTemperatureEntry13 4 }

-- }}}
-- {{{ Entry 14

meaEnvTemperatureInputName14 OBJECT-TYPE
    SYNTAX    DisplayString
    ACCESS    read-write
    STATUS    mandatory
    DESCRIPTION
        "Name of Temperature Input"
    ::= { meaEnvTemperatureEntry14 1 }

meaEnvTemperatureInputValue14  OBJECT-TYPE
    SYNTAX    INTEGER (-40..200)
    ACCESS    read-only
    STATUS    mandatory
    DESCRIPTION
        "Temperature value in deg C -20 to 100"
    ::= { meaEnvTemperatureEntry14 2 }

meaEnvTemperatureInputUpperThreshold14  OBJECT-TYPE
    SYNTAX    INTEGER (-40..200)
    ACCESS    read-write
    STATUS    mandatory
    DESCRIPTION
        "Temperature Upper Threshold in deg C -20 to 100"
    ::= { meaEnvTemperatureEntry14 3 }

meaEnvTemperatureInputLowerThreshold14  OBJECT-TYPE
    SYNTAX    INTEGER (-40..200)
    ACCESS    read-write
    STATUS    mandatory
    DESCRIPTION
        "Temperature Lower Threshold in deg C -20 to 100"
    ::= { meaEnvTemperatureEntry14 4 }

-- }}}
-- {{{ Entry 15

meaEnvTemperatureInputName15 OBJECT-TYPE
    SYNTAX    DisplayString
    ACCESS    read-write
    STATUS    mandatory
    DESCRIPTION
        "Name of Temperature Input"
    ::= { meaEnvTemperatureEntry15 1 }

meaEnvTemperatureInputValue15  OBJECT-TYPE
    SYNTAX    INTEGER (-40..200)
    ACCESS    read-only
    STATUS    mandatory
    DESCRIPTION
        "Temperature value in deg C -20 to 100"
    ::= { meaEnvTemperatureEntry15 2 }

meaEnvTemperatureInputUpperThreshold15  OBJECT-TYPE
    SYNTAX    INTEGER (-40..200)
    ACCESS    read-write
    STATUS    mandatory
    DESCRIPTION
        "Temperature Upper Threshold in deg C -20 to 100"
    ::= { meaEnvTemperatureEntry15 3 }

meaEnvTemperatureInputLowerThreshold15  OBJECT-TYPE
    SYNTAX    INTEGER (-40..200)
    ACCESS    read-write
    STATUS    mandatory
    DESCRIPTION
        "Temperature Lower Threshold in deg C -20 to 100"
    ::= { meaEnvTemperatureEntry15 4 }

-- }}}
-- {{{ Entry 16

meaEnvTemperatureInputName16 OBJECT-TYPE
    SYNTAX    DisplayString
    ACCESS    read-write
    STATUS    mandatory
    DESCRIPTION
        "Name of Temperature Input"
    ::= { meaEnvTemperatureEntry16 1 }

meaEnvTemperatureInputValue16  OBJECT-TYPE
    SYNTAX    INTEGER (-40..200)
    ACCESS    read-only
    STATUS    mandatory
    DESCRIPTION
        "Temperature value in deg C -20 to 100"
    ::= { meaEnvTemperatureEntry16 2 }

meaEnvTemperatureInputUpperThreshold16  OBJECT-TYPE
    SYNTAX    INTEGER (-40..200)
    ACCESS    read-write
    STATUS    mandatory
    DESCRIPTION
        "Temperature Upper Threshold in deg C -20 to 100"
    ::= { meaEnvTemperatureEntry16 3 }

meaEnvTemperatureInputLowerThreshold16  OBJECT-TYPE
    SYNTAX    INTEGER (-40..200)
    ACCESS    read-write
    STATUS    mandatory
    DESCRIPTION
        "Temperature Lower Threshold in deg C -20 to 100"
    ::= { meaEnvTemperatureEntry16 4 }

-- }}}

-- }}}

-- }}} 
-- {{{ meaDigitalInput group   

meaDigitalInputTable  OBJECT IDENTIFIER ::= { meaDigitalInput 1 }

-- {{{ meaDigitalInputTable  

meaDigitalInputEntry1  OBJECT IDENTIFIER ::= { meaDigitalInputTable 1  }
meaDigitalInputEntry2  OBJECT IDENTIFIER ::= { meaDigitalInputTable 2  }
meaDigitalInputEntry3  OBJECT IDENTIFIER ::= { meaDigitalInputTable 3  }
meaDigitalInputEntry4  OBJECT IDENTIFIER ::= { meaDigitalInputTable 4  }
meaDigitalInputEntry5  OBJECT IDENTIFIER ::= { meaDigitalInputTable 5  }
meaDigitalInputEntry6  OBJECT IDENTIFIER ::= { meaDigitalInputTable 6  }
meaDigitalInputEntry7  OBJECT IDENTIFIER ::= { meaDigitalInputTable 7  }
meaDigitalInputEntry8  OBJECT IDENTIFIER ::= { meaDigitalInputTable 8  }
meaDigitalInputEntry9  OBJECT IDENTIFIER ::= { meaDigitalInputTable 9  }
meaDigitalInputEntry10 OBJECT IDENTIFIER ::= { meaDigitalInputTable 10 }
meaDigitalInputEntry11 OBJECT IDENTIFIER ::= { meaDigitalInputTable 11 }
meaDigitalInputEntry12 OBJECT IDENTIFIER ::= { meaDigitalInputTable 12 }
meaDigitalInputEntry13 OBJECT IDENTIFIER ::= { meaDigitalInputTable 13 }
meaDigitalInputEntry14 OBJECT IDENTIFIER ::= { meaDigitalInputTable 14 }
meaDigitalInputEntry15 OBJECT IDENTIFIER ::= { meaDigitalInputTable 15 }
meaDigitalInputEntry16 OBJECT IDENTIFIER ::= { meaDigitalInputTable 16 }
meaDigitalInputEntry17 OBJECT IDENTIFIER ::= { meaDigitalInputTable 17 }
meaDigitalInputEntry18 OBJECT IDENTIFIER ::= { meaDigitalInputTable 18 }
meaDigitalInputEntry19 OBJECT IDENTIFIER ::= { meaDigitalInputTable 19 }
meaDigitalInputEntry20 OBJECT IDENTIFIER ::= { meaDigitalInputTable 20 }
meaDigitalInputEntry21 OBJECT IDENTIFIER ::= { meaDigitalInputTable 21 }
meaDigitalInputEntry22 OBJECT IDENTIFIER ::= { meaDigitalInputTable 22 }
meaDigitalInputEntry23 OBJECT IDENTIFIER ::= { meaDigitalInputTable 23 }
meaDigitalInputEntry24 OBJECT IDENTIFIER ::= { meaDigitalInputTable 24 }
meaDigitalInputEntry25 OBJECT IDENTIFIER ::= { meaDigitalInputTable 25 }
meaDigitalInputEntry26 OBJECT IDENTIFIER ::= { meaDigitalInputTable 26 }
meaDigitalInputEntry27 OBJECT IDENTIFIER ::= { meaDigitalInputTable 27 }
meaDigitalInputEntry28 OBJECT IDENTIFIER ::= { meaDigitalInputTable 28 }
meaDigitalInputEntry29 OBJECT IDENTIFIER ::= { meaDigitalInputTable 29 }
meaDigitalInputEntry30 OBJECT IDENTIFIER ::= { meaDigitalInputTable 30 }
meaDigitalInputEntry31 OBJECT IDENTIFIER ::= { meaDigitalInputTable 31 }
meaDigitalInputEntry32 OBJECT IDENTIFIER ::= { meaDigitalInputTable 32 }

-- meaDigitalInputEntries
-- {{{ Entry 1

meaDigitalInputName1 OBJECT-TYPE
    SYNTAX    DisplayString
    ACCESS    read-write
    STATUS    mandatory
    DESCRIPTION
        "Name of Digital Input number 1"
    ::= { meaDigitalInputEntry1 1 }

meaDigitalInputState1 OBJECT-TYPE
    SYNTAX    INTEGER (0..1)
    ACCESS    read-only
    STATUS    mandatory
    DESCRIPTION
        "State of the digital input (0=Closed 1=Open)"
    ::= { meaDigitalInputEntry1 2 }

meaDigitalInputActiveState1 OBJECT-TYPE
    SYNTAX    INTEGER (0..1)
    ACCESS    read-write
    STATUS    mandatory
    DESCRIPTION
        "The active state of the Digital Input (0=Normal 1=Invert)"
    ::= { meaDigitalInputEntry1 3 }

-- }}}
-- {{{ Entry 2

meaDigitalInputName2 OBJECT-TYPE
    SYNTAX    DisplayString
    ACCESS    read-write
    STATUS    mandatory
    DESCRIPTION
        "Name of digital input number 2"
    ::= { meaDigitalInputEntry2 1 }

meaDigitalInputState2 OBJECT-TYPE
    SYNTAX    INTEGER (0..1)
    ACCESS    read-only
    STATUS    mandatory
    DESCRIPTION
        "State of the digital input (0=Closed 1=Open)"
    ::= { meaDigitalInputEntry2 2 }

meaDigitalInputActiveState2 OBJECT-TYPE
    SYNTAX    INTEGER (0..1)
    ACCESS    read-write
    STATUS    mandatory
    DESCRIPTION
        "The active state of the Digital Input (0=Normal 1=Invert)"
    ::= { meaDigitalInputEntry2 3 }

-- }}}
-- {{{ Entry 3

meaDigitalInputName3 OBJECT-TYPE
    SYNTAX    DisplayString
    ACCESS    read-write
    STATUS    mandatory
    DESCRIPTION
        "Name of digital input number 3"
    ::= { meaDigitalInputEntry3 1 }

meaDigitalInputState3 OBJECT-TYPE
    SYNTAX    INTEGER (0..1)
    ACCESS    read-only
    STATUS    mandatory
    DESCRIPTION
        "State of the digital input (0=Closed 1=Open)"
    ::= { meaDigitalInputEntry3 2 }

meaDigitalInputActiveState3 OBJECT-TYPE
    SYNTAX    INTEGER (0..1)
    ACCESS    read-write
    STATUS    mandatory
    DESCRIPTION
        "The active state of the Digital Input (0=Normal 1=Invert)"
    ::= { meaDigitalInputEntry3 3 }

-- }}}
-- {{{ Entry 4

meaDigitalInputName4 OBJECT-TYPE
    SYNTAX    DisplayString
    ACCESS    read-write
    STATUS    mandatory
    DESCRIPTION
        "Name of digital input number 4"
    ::= { meaDigitalInputEntry4 1 }

meaDigitalInputState4 OBJECT-TYPE
    SYNTAX    INTEGER (0..1)
    ACCESS    read-only
    STATUS    mandatory
    DESCRIPTION
        "State of the digital input (0=Closed 1=Open)"
    ::= { meaDigitalInputEntry4 2 }

meaDigitalInputActiveState4 OBJECT-TYPE
    SYNTAX    INTEGER (0..1)
    ACCESS    read-write
    STATUS    mandatory
    DESCRIPTION
        "The active state of the Digital Input (0=Normal 1=Invert)"
    ::= { meaDigitalInputEntry4 3 }

-- }}}
-- {{{ Entry 5

meaDigitalInputName5 OBJECT-TYPE
    SYNTAX    DisplayString
    ACCESS    read-write
    STATUS    mandatory
    DESCRIPTION
        "Name of digital input number 5"
    ::= { meaDigitalInputEntry5 1 }

meaDigitalInputState5 OBJECT-TYPE
    SYNTAX    INTEGER (0..1)
    ACCESS    read-only
    STATUS    mandatory
    DESCRIPTION
        "State of the digital input (0=Closed 1=Open)"
    ::= { meaDigitalInputEntry5 2 }

meaDigitalInputActiveState5 OBJECT-TYPE
    SYNTAX    INTEGER (0..1)
    ACCESS    read-write
    STATUS    mandatory
    DESCRIPTION
        "The active state of the Digital Input (0=Normal 1=Invert)"
    ::= { meaDigitalInputEntry5 3 }

-- }}}
-- {{{ Entry 6

meaDigitalInputName6 OBJECT-TYPE
    SYNTAX    DisplayString
    ACCESS    read-write
    STATUS    mandatory
    DESCRIPTION
        "Name of digital input number 6"
    ::= { meaDigitalInputEntry6 1 }

meaDigitalInputState6 OBJECT-TYPE
    SYNTAX    INTEGER (0..1)
    ACCESS    read-only
    STATUS    mandatory
    DESCRIPTION
        "State of the digital input (0=Closed 1=Open)"
    ::= { meaDigitalInputEntry6 2 }

meaDigitalInputActiveState6 OBJECT-TYPE
    SYNTAX    INTEGER (0..1)
    ACCESS    read-write
    STATUS    mandatory
    DESCRIPTION
        "The active state of the Digital Input (0=Normal 1=Invert)"
    ::= { meaDigitalInputEntry6 3 }

-- }}}
-- {{{ Entry 7

meaDigitalInputName7 OBJECT-TYPE
    SYNTAX    DisplayString
    ACCESS    read-write
    STATUS    mandatory
    DESCRIPTION
        "Name of digital input number 7"
    ::= { meaDigitalInputEntry7 1 }

meaDigitalInputState7 OBJECT-TYPE
    SYNTAX    INTEGER (0..1)
    ACCESS    read-only
    STATUS    mandatory
    DESCRIPTION
        "State of the digital input (0=Closed 1=Open)"
    ::= { meaDigitalInputEntry7 2 }

meaDigitalInputActiveState7 OBJECT-TYPE
    SYNTAX    INTEGER (0..1)
    ACCESS    read-write
    STATUS    mandatory
    DESCRIPTION
        "The active state of the Digital Input (0=Normal 1=Invert)"
    ::= { meaDigitalInputEntry7 3 }

-- }}}
-- {{{ Entry 8

meaDigitalInputName8 OBJECT-TYPE
    SYNTAX    DisplayString
    ACCESS    read-write
    STATUS    mandatory
    DESCRIPTION
        "Name of digital input number 8"
    ::= { meaDigitalInputEntry8 1 }

meaDigitalInputState8 OBJECT-TYPE
    SYNTAX    INTEGER (0..1)
    ACCESS    read-only
    STATUS    mandatory
    DESCRIPTION
        "State of the digital input (0=Closed 1=Open)"
    ::= { meaDigitalInputEntry8 2 }

meaDigitalInputActiveState8 OBJECT-TYPE
    SYNTAX    INTEGER (0..1)
    ACCESS    read-write
    STATUS    mandatory
    DESCRIPTION
        "The active state of the Digital Input (0=Normal 1=Invert)"
    ::= { meaDigitalInputEntry8 3 }

-- }}}
-- {{{ Entry 9

meaDigitalInputName9 OBJECT-TYPE
    SYNTAX    DisplayString
    ACCESS    read-write
    STATUS    mandatory
    DESCRIPTION
        "Name of digital input number 9"
    ::= { meaDigitalInputEntry9 1 }

meaDigitalInputState9 OBJECT-TYPE
    SYNTAX    INTEGER (0..1)
    ACCESS    read-only
    STATUS    mandatory
    DESCRIPTION
        "State of the digital input (0=Closed 1=Open)"
    ::= { meaDigitalInputEntry9 2 }

meaDigitalInputActiveState9 OBJECT-TYPE
    SYNTAX    INTEGER (0..1)
    ACCESS    read-write
    STATUS    mandatory
    DESCRIPTION
        "The active state of the Digital Input (0=Normal 1=Invert)"
    ::= { meaDigitalInputEntry9 3 }

-- }}}
-- {{{ Entry 10

meaDigitalInputName10 OBJECT-TYPE
    SYNTAX    DisplayString
    ACCESS    read-write
    STATUS    mandatory
    DESCRIPTION
        "Name of Digital Input number 10"
    ::= { meaDigitalInputEntry10 1 }

meaDigitalInputState10 OBJECT-TYPE
    SYNTAX    INTEGER (0..1)
    ACCESS    read-only
    STATUS    mandatory
    DESCRIPTION
        "State of the digital input (0=Closed 1=Open)"
    ::= { meaDigitalInputEntry10 2 }

meaDigitalInputActiveState10 OBJECT-TYPE
    SYNTAX    INTEGER (0..1)
    ACCESS    read-write
    STATUS    mandatory
    DESCRIPTION
        "The active state of the Digital Input (0=Normal 1=Invert)"
    ::= { meaDigitalInputEntry10 3 }

-- }}}
-- {{{ Entry 11

meaDigitalInputName11 OBJECT-TYPE
    SYNTAX    DisplayString
    ACCESS    read-write
    STATUS    mandatory
    DESCRIPTION
        "Name of Digital Input number 11"
    ::= { meaDigitalInputEntry11 1 }

meaDigitalInputState11 OBJECT-TYPE
    SYNTAX    INTEGER (0..1)
    ACCESS    read-only
    STATUS    mandatory
    DESCRIPTION
        "State of the digital input (0=Closed 1=Open)"
    ::= { meaDigitalInputEntry11 2 }

meaDigitalInputActiveState11 OBJECT-TYPE
    SYNTAX    INTEGER (0..1)
    ACCESS    read-write
    STATUS    mandatory
    DESCRIPTION
        "The active state of the Digital Input (0=Normal 1=Invert)"
    ::= { meaDigitalInputEntry11 3 }

-- }}}
-- {{{ Entry 12

meaDigitalInputName12 OBJECT-TYPE
    SYNTAX    DisplayString
    ACCESS    read-write
    STATUS    mandatory
    DESCRIPTION
        "Name of Digital Input number 12"
    ::= { meaDigitalInputEntry12 1 }

meaDigitalInputState12 OBJECT-TYPE
    SYNTAX    INTEGER (0..1)
    ACCESS    read-only
    STATUS    mandatory
    DESCRIPTION
        "State of the digital input (0=Closed 1=Open)"
    ::= { meaDigitalInputEntry12 2 }

meaDigitalInputActiveState12 OBJECT-TYPE
    SYNTAX    INTEGER (0..1)
    ACCESS    read-write
    STATUS    mandatory
    DESCRIPTION
        "The active state of the Digital Input (0=Normal 1=Invert)"
    ::= { meaDigitalInputEntry12 3 }

-- }}}
-- {{{ Entry 13

meaDigitalInputName13 OBJECT-TYPE
    SYNTAX    DisplayString
    ACCESS    read-write
    STATUS    mandatory
    DESCRIPTION
        "Name of Digital Input number 13"
    ::= { meaDigitalInputEntry13 1 }

meaDigitalInputState13 OBJECT-TYPE
    SYNTAX    INTEGER (0..1)
    ACCESS    read-only
    STATUS    mandatory
    DESCRIPTION
        "State of the digital input (0=Closed 1=Open)"
    ::= { meaDigitalInputEntry13 2 }

meaDigitalInputActiveState13 OBJECT-TYPE
    SYNTAX    INTEGER (0..1)
    ACCESS    read-write
    STATUS    mandatory
    DESCRIPTION
        "The active state of the Digital Input (0=Normal 1=Invert)"
    ::= { meaDigitalInputEntry13 3 }

-- }}}
-- {{{ Entry 14

meaDigitalInputName14 OBJECT-TYPE
    SYNTAX    DisplayString
    ACCESS    read-write
    STATUS    mandatory
    DESCRIPTION
        "Name of Digital Input number 14"
    ::= { meaDigitalInputEntry14 1 }

meaDigitalInputState14 OBJECT-TYPE
    SYNTAX    INTEGER (0..1)
    ACCESS    read-only
    STATUS    mandatory
    DESCRIPTION
        "State of the digital input (0=Closed 1=Open)"
    ::= { meaDigitalInputEntry14 2 }

meaDigitalInputActiveState14 OBJECT-TYPE
    SYNTAX    INTEGER (0..1)
    ACCESS    read-write
    STATUS    mandatory
    DESCRIPTION
        "The active state of the Digital Input (0=Normal 1=Invert)"
    ::= { meaDigitalInputEntry14 3 }

-- }}}
-- {{{ Entry 15

meaDigitalInputName15 OBJECT-TYPE
    SYNTAX    DisplayString
    ACCESS    read-write
    STATUS    mandatory
    DESCRIPTION
        "Name of Digital Input number 15"
    ::= { meaDigitalInputEntry15 1 }

meaDigitalInputState15 OBJECT-TYPE
    SYNTAX    INTEGER (0..1)
    ACCESS    read-only
    STATUS    mandatory
    DESCRIPTION
        "State of the digital input (0=Closed 1=Open)"
    ::= { meaDigitalInputEntry15 2 }

meaDigitalInputActiveState15 OBJECT-TYPE
    SYNTAX    INTEGER (0..1)
    ACCESS    read-write
    STATUS    mandatory
    DESCRIPTION
        "The active state of the Digital Input (0=Normal 1=Invert)"
    ::= { meaDigitalInputEntry15 3 }

-- }}}
-- {{{ Entry 16

meaDigitalInputName16 OBJECT-TYPE
    SYNTAX    DisplayString
    ACCESS    read-write
    STATUS    mandatory
    DESCRIPTION
        "Name of Digital Input number 16"
    ::= { meaDigitalInputEntry16 1 }

meaDigitalInputState16 OBJECT-TYPE
    SYNTAX    INTEGER (0..1)
    ACCESS    read-only
    STATUS    mandatory
    DESCRIPTION
        "State of the digital input (0=Closed 1=Open)"
    ::= { meaDigitalInputEntry16 2 }

meaDigitalInputActiveState16 OBJECT-TYPE
    SYNTAX    INTEGER (0..1)
    ACCESS    read-write
    STATUS    mandatory
    DESCRIPTION
        "The active state of the Digital Input (0=Normal 1=Invert)"
    ::= { meaDigitalInputEntry16 3 }

-- }}}
-- {{{ Entry 17

meaDigitalInputName17 OBJECT-TYPE
    SYNTAX    DisplayString
    ACCESS    read-write
    STATUS    mandatory
    DESCRIPTION
        "Name of Digital Input number 17"
    ::= { meaDigitalInputEntry17 1 }

meaDigitalInputState17 OBJECT-TYPE
    SYNTAX    INTEGER (0..1)
    ACCESS    read-only
    STATUS    mandatory
    DESCRIPTION
        "State of the digital input (0=Closed 1=Open)"
    ::= { meaDigitalInputEntry17 2 }

meaDigitalInputActiveState17 OBJECT-TYPE
    SYNTAX    INTEGER (0..1)
    ACCESS    read-write
    STATUS    mandatory
    DESCRIPTION
        "The active state of the Digital Input (0=Normal 1=Invert)"
    ::= { meaDigitalInputEntry17 3 }

-- }}}
-- {{{ Entry 18

meaDigitalInputName18 OBJECT-TYPE
    SYNTAX    DisplayString
    ACCESS    read-write
    STATUS    mandatory
    DESCRIPTION
        "Name of Digital Input number 18"
    ::= { meaDigitalInputEntry18 1 }

meaDigitalInputState18 OBJECT-TYPE
    SYNTAX    INTEGER (0..1)
    ACCESS    read-only
    STATUS    mandatory
    DESCRIPTION
        "State of the digital input (0=Closed 1=Open)"
    ::= { meaDigitalInputEntry18 2 }

meaDigitalInputActiveState18 OBJECT-TYPE
    SYNTAX    INTEGER (0..1)
    ACCESS    read-write
    STATUS    mandatory
    DESCRIPTION
        "The active state of the Digital Input (0=Normal 1=Invert)"
    ::= { meaDigitalInputEntry18 3 }

-- }}}
-- {{{ Entry 19

meaDigitalInputName19 OBJECT-TYPE
    SYNTAX    DisplayString
    ACCESS    read-write
    STATUS    mandatory
    DESCRIPTION
        "Name of Digital Input number 19"
    ::= { meaDigitalInputEntry19 1 }

meaDigitalInputState19 OBJECT-TYPE
    SYNTAX    INTEGER (0..1)
    ACCESS    read-only
    STATUS    mandatory
    DESCRIPTION
        "State of the digital input (0=Closed 1=Open)"
    ::= { meaDigitalInputEntry19 2 }

meaDigitalInputActiveState19 OBJECT-TYPE
    SYNTAX    INTEGER (0..1)
    ACCESS    read-write
    STATUS    mandatory
    DESCRIPTION
        "The active state of the Digital Input (0=Normal 1=Invert)"
    ::= { meaDigitalInputEntry19 3 }

-- }}}
-- {{{ Entry 20

meaDigitalInputName20 OBJECT-TYPE
    SYNTAX    DisplayString
    ACCESS    read-write
    STATUS    mandatory
    DESCRIPTION
        "Name of digital input number 20"
    ::= { meaDigitalInputEntry20 1 }

meaDigitalInputState20 OBJECT-TYPE
    SYNTAX    INTEGER (0..1)
    ACCESS    read-only
    STATUS    mandatory
    DESCRIPTION
        "State of the digital input (0=Closed 1=Open)"
    ::= { meaDigitalInputEntry20 2 }

meaDigitalInputActiveState20 OBJECT-TYPE
    SYNTAX    INTEGER (0..1)
    ACCESS    read-write
    STATUS    mandatory
    DESCRIPTION
        "The active state of the Digital Input (0=Normal 1=Invert)"
    ::= { meaDigitalInputEntry20 3 }

-- }}}
-- {{{ Entry 21

meaDigitalInputName21 OBJECT-TYPE
    SYNTAX    DisplayString
    ACCESS    read-write
    STATUS    mandatory
    DESCRIPTION
        "Name of digital input number 21"
    ::= { meaDigitalInputEntry21 1 }

meaDigitalInputState21 OBJECT-TYPE
    SYNTAX    INTEGER (0..1)
    ACCESS    read-only
    STATUS    mandatory
    DESCRIPTION
        "State of the digital input (0=Closed 1=Open)"
    ::= { meaDigitalInputEntry21 2 }

meaDigitalInputActiveState21 OBJECT-TYPE
    SYNTAX    INTEGER (0..1)
    ACCESS    read-write
    STATUS    mandatory
    DESCRIPTION
        "The active state of the Digital Input (0=Normal 1=Invert)"
    ::= { meaDigitalInputEntry21 3 }

-- }}}
-- {{{ Entry 22

meaDigitalInputName22 OBJECT-TYPE
    SYNTAX    DisplayString
    ACCESS    read-write
    STATUS    mandatory
    DESCRIPTION
        "Name of digital input number 22"
    ::= { meaDigitalInputEntry22 1 }

meaDigitalInputState22 OBJECT-TYPE
    SYNTAX    INTEGER (0..1)
    ACCESS    read-only
    STATUS    mandatory
    DESCRIPTION
        "State of the digital input (0=Closed 1=Open)"
    ::= { meaDigitalInputEntry22 2 }

meaDigitalInputActiveState22 OBJECT-TYPE
    SYNTAX    INTEGER (0..1)
    ACCESS    read-write
    STATUS    mandatory
    DESCRIPTION
        "The active state of the Digital Input (0=Normal 1=Invert)"
    ::= { meaDigitalInputEntry22 3 }

-- }}}
-- {{{ Entry 23

meaDigitalInputName23 OBJECT-TYPE
    SYNTAX    DisplayString
    ACCESS    read-write
    STATUS    mandatory
    DESCRIPTION
        "Name of digital input number 23"
    ::= { meaDigitalInputEntry23 1 }

meaDigitalInputState23 OBJECT-TYPE
    SYNTAX    INTEGER (0..1)
    ACCESS    read-only
    STATUS    mandatory
    DESCRIPTION
        "State of the digital input (0=Closed 1=Open)"
    ::= { meaDigitalInputEntry23 2 }

meaDigitalInputActiveState23 OBJECT-TYPE
    SYNTAX    INTEGER (0..1)
    ACCESS    read-write
    STATUS    mandatory
    DESCRIPTION
        "The active state of the Digital Input (0=Normal 1=Invert)"
    ::= { meaDigitalInputEntry23 3 }

-- }}}
-- {{{ Entry 24

meaDigitalInputName24 OBJECT-TYPE
    SYNTAX    DisplayString
    ACCESS    read-write
    STATUS    mandatory
    DESCRIPTION
        "Name of digital input number 24"
    ::= { meaDigitalInputEntry24 1 }

meaDigitalInputState24 OBJECT-TYPE
    SYNTAX    INTEGER (0..1)
    ACCESS    read-only
    STATUS    mandatory
    DESCRIPTION
        "State of the digital input (0=Closed 1=Open)"
    ::= { meaDigitalInputEntry24 2 }

meaDigitalInputActiveState24 OBJECT-TYPE
    SYNTAX    INTEGER (0..1)
    ACCESS    read-write
    STATUS    mandatory
    DESCRIPTION
        "The active state of the Digital Input (0=Normal 1=Invert)"
    ::= { meaDigitalInputEntry24 3 }

-- }}}
-- {{{ Entry 25

meaDigitalInputName25 OBJECT-TYPE
    SYNTAX    DisplayString
    ACCESS    read-write
    STATUS    mandatory
    DESCRIPTION
        "Name of digital input number 25"
    ::= { meaDigitalInputEntry25 1 }

meaDigitalInputState25 OBJECT-TYPE
    SYNTAX    INTEGER (0..1)
    ACCESS    read-only
    STATUS    mandatory
    DESCRIPTION
        "State of the digital input (0=Closed 1=Open)"
    ::= { meaDigitalInputEntry25 2 }

meaDigitalInputActiveState25 OBJECT-TYPE
    SYNTAX    INTEGER (0..1)
    ACCESS    read-write
    STATUS    mandatory
    DESCRIPTION
        "The active state of the Digital Input (0=Normal 1=Invert)"
    ::= { meaDigitalInputEntry25 3 }

-- }}}
-- {{{ Entry 26

meaDigitalInputName26 OBJECT-TYPE
    SYNTAX    DisplayString
    ACCESS    read-write
    STATUS    mandatory
    DESCRIPTION
        "Name of digital input number 26"
    ::= { meaDigitalInputEntry26 1 }

meaDigitalInputState26 OBJECT-TYPE
    SYNTAX    INTEGER (0..1)
    ACCESS    read-only
    STATUS    mandatory
    DESCRIPTION
        "State of the digital input (0=Closed 1=Open)"
    ::= { meaDigitalInputEntry26 2 }

meaDigitalInputActiveState26 OBJECT-TYPE
    SYNTAX    INTEGER (0..1)
    ACCESS    read-write
    STATUS    mandatory
    DESCRIPTION
        "The active state of the Digital Input (0=Normal 1=Invert)"
    ::= { meaDigitalInputEntry26 3 }

-- }}}
-- {{{ Entry 27

meaDigitalInputName27 OBJECT-TYPE
    SYNTAX    DisplayString
    ACCESS    read-write
    STATUS    mandatory
    DESCRIPTION
        "Name of digital input number 27"
    ::= { meaDigitalInputEntry27 1 }

meaDigitalInputState27 OBJECT-TYPE
    SYNTAX    INTEGER (0..1)
    ACCESS    read-only
    STATUS    mandatory
    DESCRIPTION
        "State of the digital input (0=Closed 1=Open)"
    ::= { meaDigitalInputEntry27 2 }

meaDigitalInputActiveState27 OBJECT-TYPE
    SYNTAX    INTEGER (0..1)
    ACCESS    read-write
    STATUS    mandatory
    DESCRIPTION
        "The active state of the Digital Input (0=Normal 1=Invert)"
    ::= { meaDigitalInputEntry27 3 }

-- }}}
-- {{{ Entry 28

meaDigitalInputName28 OBJECT-TYPE
    SYNTAX    DisplayString
    ACCESS    read-write
    STATUS    mandatory
    DESCRIPTION
        "Name of digital input number 28"
    ::= { meaDigitalInputEntry28 1 }

meaDigitalInputState28 OBJECT-TYPE
    SYNTAX    INTEGER (0..1)
    ACCESS    read-only
    STATUS    mandatory
    DESCRIPTION
        "State of the digital input (0=Closed 1=Open)"
    ::= { meaDigitalInputEntry28 2 }

meaDigitalInputActiveState28 OBJECT-TYPE
    SYNTAX    INTEGER (0..1)
    ACCESS    read-write
    STATUS    mandatory
    DESCRIPTION
        "The active state of the Digital Input (0=Normal 1=Invert)"
    ::= { meaDigitalInputEntry28 3 }

-- }}}
-- {{{ Entry 29

meaDigitalInputName29 OBJECT-TYPE
    SYNTAX    DisplayString
    ACCESS    read-write
    STATUS    mandatory
    DESCRIPTION
        "Name of digital input number 29"
    ::= { meaDigitalInputEntry29 1 }

meaDigitalInputState29 OBJECT-TYPE
    SYNTAX    INTEGER (0..1)
    ACCESS    read-only
    STATUS    mandatory
    DESCRIPTION
        "State of the digital input (0=Closed 1=Open)"
    ::= { meaDigitalInputEntry29 2 }

meaDigitalInputActiveState29 OBJECT-TYPE
    SYNTAX    INTEGER (0..1)
    ACCESS    read-write
    STATUS    mandatory
    DESCRIPTION
        "The active state of the Digital Input (0=Normal 1=Invert)"
    ::= { meaDigitalInputEntry29 3 }

-- }}}
-- {{{ Entry 30

meaDigitalInputName30 OBJECT-TYPE
    SYNTAX    DisplayString
    ACCESS    read-write
    STATUS    mandatory
    DESCRIPTION
        "Name of digital input number 30"
    ::= { meaDigitalInputEntry30 1 }

meaDigitalInputState30 OBJECT-TYPE
    SYNTAX    INTEGER (0..1)
    ACCESS    read-only
    STATUS    mandatory
    DESCRIPTION
        "State of the digital input (0=Closed 1=Open)"
    ::= { meaDigitalInputEntry30 2 }

meaDigitalInputActiveState30 OBJECT-TYPE
    SYNTAX    INTEGER (0..1)
    ACCESS    read-write
    STATUS    mandatory
    DESCRIPTION
        "The active state of the Digital Input (0=Normal 1=Invert)"
    ::= { meaDigitalInputEntry30 3 }

-- }}}
-- {{{ Entry 31

meaDigitalInputName31 OBJECT-TYPE
    SYNTAX    DisplayString
    ACCESS    read-write
    STATUS    mandatory
    DESCRIPTION
        "Name of digital input number 31"
    ::= { meaDigitalInputEntry31 1 }

meaDigitalInputState31 OBJECT-TYPE
    SYNTAX    INTEGER (0..1)
    ACCESS    read-only
    STATUS    mandatory
    DESCRIPTION
        "State of the digital input (0=Closed 1=Open)"
    ::= { meaDigitalInputEntry31 2 }

meaDigitalInputActiveState31 OBJECT-TYPE
    SYNTAX    INTEGER (0..1)
    ACCESS    read-write
    STATUS    mandatory
    DESCRIPTION
        "The active state of the Digital Input (0=Normal 1=Invert)"
    ::= { meaDigitalInputEntry31 3 }

-- }}}
-- {{{ Entry 32

meaDigitalInputName32 OBJECT-TYPE
    SYNTAX    DisplayString
    ACCESS    read-write
    STATUS    mandatory
    DESCRIPTION
        "Name of digital input number 32"
    ::= { meaDigitalInputEntry32 1 }

meaDigitalInputState32 OBJECT-TYPE
    SYNTAX    INTEGER (0..1)
    ACCESS    read-only
    STATUS    mandatory
    DESCRIPTION
        "State of the digital input (0=Closed 1=Open)"
    ::= { meaDigitalInputEntry32 2 }

meaDigitalInputActiveState32 OBJECT-TYPE
    SYNTAX    INTEGER (0..1)
    ACCESS    read-write
    STATUS    mandatory
    DESCRIPTION
        "The active state of the Digital Input (0=Normal 1=Invert)"
    ::= { meaDigitalInputEntry32 3 }

-- }}}


-- }}}

-- }}}
-- {{{ meaDigitalOutput group  

meaDigitalOutputConfigTable  OBJECT IDENTIFIER ::= { meaDigitalOutput 1 }
meaDigitalOutputControlTable OBJECT IDENTIFIER ::= { meaDigitalOutput 2 }
meaDigitalOutputStatusTable  OBJECT IDENTIFIER ::= { meaDigitalOutput 3 }

-- {{{ meaDigitalOutputConfigTable 

meaDigitalOutputConfigEntry1  OBJECT IDENTIFIER ::= { meaDigitalOutputConfigTable 1  }
meaDigitalOutputConfigEntry2  OBJECT IDENTIFIER ::= { meaDigitalOutputConfigTable 2  }
meaDigitalOutputConfigEntry3  OBJECT IDENTIFIER ::= { meaDigitalOutputConfigTable 3  }
meaDigitalOutputConfigEntry4  OBJECT IDENTIFIER ::= { meaDigitalOutputConfigTable 4  }
meaDigitalOutputConfigEntry5  OBJECT IDENTIFIER ::= { meaDigitalOutputConfigTable 5  }
meaDigitalOutputConfigEntry6  OBJECT IDENTIFIER ::= { meaDigitalOutputConfigTable 6  }
meaDigitalOutputConfigEntry7  OBJECT IDENTIFIER ::= { meaDigitalOutputConfigTable 7  }
meaDigitalOutputConfigEntry8  OBJECT IDENTIFIER ::= { meaDigitalOutputConfigTable 8  }
meaDigitalOutputConfigEntry9  OBJECT IDENTIFIER ::= { meaDigitalOutputConfigTable 9  }
meaDigitalOutputConfigEntry10 OBJECT IDENTIFIER ::= { meaDigitalOutputConfigTable 10 }
meaDigitalOutputConfigEntry11 OBJECT IDENTIFIER ::= { meaDigitalOutputConfigTable 11 }
meaDigitalOutputConfigEntry12 OBJECT IDENTIFIER ::= { meaDigitalOutputConfigTable 12 }
meaDigitalOutputConfigEntry13 OBJECT IDENTIFIER ::= { meaDigitalOutputConfigTable 13 }
meaDigitalOutputConfigEntry14 OBJECT IDENTIFIER ::= { meaDigitalOutputConfigTable 14 }
meaDigitalOutputConfigEntry15 OBJECT IDENTIFIER ::= { meaDigitalOutputConfigTable 15 }
meaDigitalOutputConfigEntry16 OBJECT IDENTIFIER ::= { meaDigitalOutputConfigTable 16 }
meaDigitalOutputConfigEntry17 OBJECT IDENTIFIER ::= { meaDigitalOutputConfigTable 17 }
meaDigitalOutputConfigEntry18 OBJECT IDENTIFIER ::= { meaDigitalOutputConfigTable 18 }
meaDigitalOutputConfigEntry19 OBJECT IDENTIFIER ::= { meaDigitalOutputConfigTable 19 }
meaDigitalOutputConfigEntry20 OBJECT IDENTIFIER ::= { meaDigitalOutputConfigTable 20 }
meaDigitalOutputConfigEntry21 OBJECT IDENTIFIER ::= { meaDigitalOutputConfigTable 21 }
meaDigitalOutputConfigEntry22 OBJECT IDENTIFIER ::= { meaDigitalOutputConfigTable 22 }
meaDigitalOutputConfigEntry23 OBJECT IDENTIFIER ::= { meaDigitalOutputConfigTable 23 }
meaDigitalOutputConfigEntry24 OBJECT IDENTIFIER ::= { meaDigitalOutputConfigTable 24 }
meaDigitalOutputConfigEntry25 OBJECT IDENTIFIER ::= { meaDigitalOutputConfigTable 25 }
meaDigitalOutputConfigEntry26 OBJECT IDENTIFIER ::= { meaDigitalOutputConfigTable 26 }
meaDigitalOutputConfigEntry27 OBJECT IDENTIFIER ::= { meaDigitalOutputConfigTable 27 }
meaDigitalOutputConfigEntry28 OBJECT IDENTIFIER ::= { meaDigitalOutputConfigTable 28 }
meaDigitalOutputConfigEntry29 OBJECT IDENTIFIER ::= { meaDigitalOutputConfigTable 29 }
meaDigitalOutputConfigEntry30 OBJECT IDENTIFIER ::= { meaDigitalOutputConfigTable 30 }
meaDigitalOutputConfigEntry31 OBJECT IDENTIFIER ::= { meaDigitalOutputConfigTable 31 }
meaDigitalOutputConfigEntry32 OBJECT IDENTIFIER ::= { meaDigitalOutputConfigTable 32 }

-- meaDigitalOutputConfigEntries
-- {{{ Entry 1

meaDigitalOutputName1 OBJECT-TYPE
    SYNTAX    DisplayString
    ACCESS    read-write
    STATUS    mandatory
    DESCRIPTION
        "Name of Digital Output number 1"
    ::= { meaDigitalOutputConfigEntry1 1 }

meaDigitalOutputUpTimer1 OBJECT-TYPE
    SYNTAX    INTEGER ( 0..999999 )
    ACCESS    read-write
    STATUS    mandatory
    DESCRIPTION
        "<0=Stay Off 0=immediate >0=Time in seconds"
    ::= { meaDigitalOutputConfigEntry1 2 }

meaDigitalOutputDownTimer1 OBJECT-TYPE
    SYNTAX    INTEGER ( 0..999999 )
    ACCESS    read-write
    STATUS    mandatory
    DESCRIPTION
        "<0=Stay Off 0=immediate >0=Time in seconds"
    ::= { meaDigitalOutputConfigEntry1 3 }

meaDigitalOutputCommandedState1 OBJECT-TYPE
    SYNTAX    INTEGER ( 0..1 )
    ACCESS    read-write
    STATUS    mandatory
    DESCRIPTION
        "<0=0=Low 1=High"
    ::= { meaDigitalOutputConfigEntry1 4 }

-- }}}
-- {{{ Entry 2

meaDigitalOutputName2 OBJECT-TYPE
    SYNTAX    DisplayString
    ACCESS    read-write
    STATUS    mandatory
    DESCRIPTION
        "Name of Digital Output number 2"
    ::= { meaDigitalOutputConfigEntry2 1 }

meaDigitalOutputUpTimer2 OBJECT-TYPE
    SYNTAX    INTEGER ( 0..999999 )
    ACCESS    read-write
    STATUS    mandatory
    DESCRIPTION
        "<0=Stay Off 0=immediate >0=Time in seconds"
    ::= { meaDigitalOutputConfigEntry2 2 }

meaDigitalOutputDownTimer2 OBJECT-TYPE
    SYNTAX    INTEGER ( 0..999999 )
    ACCESS    read-write
    STATUS    mandatory
    DESCRIPTION
        "<0=Stay Off 0=immediate >0=Time in seconds"
    ::= { meaDigitalOutputConfigEntry2 3 }

meaDigitalOutputCommandedState2 OBJECT-TYPE
    SYNTAX    INTEGER ( 0..1 )
    ACCESS    read-write
    STATUS    mandatory
    DESCRIPTION
        "<0=0=Low 1=High"
    ::= { meaDigitalOutputConfigEntry2 4 }

-- }}}
-- {{{ Entry 3

meaDigitalOutputName3 OBJECT-TYPE
    SYNTAX    DisplayString
    ACCESS    read-write
    STATUS    mandatory
    DESCRIPTION
        "Name of Digital Output number 3"
    ::= { meaDigitalOutputConfigEntry3 1 }

meaDigitalOutputUpTimer3 OBJECT-TYPE
    SYNTAX    INTEGER ( 0..999999 )
    ACCESS    read-write
    STATUS    mandatory
    DESCRIPTION
        "<0=Stay Off 0=immediate >0=Time in seconds"
    ::= { meaDigitalOutputConfigEntry3 2 }

meaDigitalOutputDownTimer3 OBJECT-TYPE
    SYNTAX    INTEGER ( 0..999999 )
    ACCESS    read-write
    STATUS    mandatory
    DESCRIPTION
        "<0=Stay Off 0=immediate >0=Time in seconds"
    ::= { meaDigitalOutputConfigEntry3 3 }

meaDigitalOutputCommandedState3 OBJECT-TYPE
    SYNTAX    INTEGER ( 0..1 )
    ACCESS    read-write
    STATUS    mandatory
    DESCRIPTION
        "<0=0=Low 1=High"
    ::= { meaDigitalOutputConfigEntry3 4 }

-- }}}
-- {{{ Entry 4

meaDigitalOutputName4 OBJECT-TYPE
    SYNTAX    DisplayString
    ACCESS    read-write
    STATUS    mandatory
    DESCRIPTION
        "Name of Digital Output number 4"
    ::= { meaDigitalOutputConfigEntry4 1 }

meaDigitalOutputUpTimer4 OBJECT-TYPE
    SYNTAX    INTEGER ( 0..999999 )
    ACCESS    read-write
    STATUS    mandatory
    DESCRIPTION
        "<0=Stay Off 0=immediate >0=Time in seconds"
    ::= { meaDigitalOutputConfigEntry4 2 }

meaDigitalOutputDownTimer4 OBJECT-TYPE
    SYNTAX    INTEGER ( 0..999999 )
    ACCESS    read-write
    STATUS    mandatory
    DESCRIPTION
        "<0=Stay Off 0=immediate >0=Time in seconds"
    ::= { meaDigitalOutputConfigEntry4 3 }

meaDigitalOutputCommandedState4 OBJECT-TYPE
    SYNTAX    INTEGER ( 0..1 )
    ACCESS    read-write
    STATUS    mandatory
    DESCRIPTION
        "<0=0=Low 1=High"
    ::= { meaDigitalOutputConfigEntry4 4 }

-- }}}
-- {{{ Entry 5

meaDigitalOutputName5 OBJECT-TYPE
    SYNTAX    DisplayString
    ACCESS    read-write
    STATUS    mandatory
    DESCRIPTION
        "Name of Digital Output number 5"
    ::= { meaDigitalOutputConfigEntry5 1 }

meaDigitalOutputUpTimer5 OBJECT-TYPE
    SYNTAX    INTEGER ( 0..999999 )
    ACCESS    read-write
    STATUS    mandatory
    DESCRIPTION
        "<0=Stay Off 0=immediate >0=Time in seconds"
    ::= { meaDigitalOutputConfigEntry5 2 }

meaDigitalOutputDownTimer5 OBJECT-TYPE
    SYNTAX    INTEGER ( 0..999999 )
    ACCESS    read-write
    STATUS    mandatory
    DESCRIPTION
        "<0=Stay Off 0=immediate >0=Time in seconds"
    ::= { meaDigitalOutputConfigEntry5 3 }

meaDigitalOutputCommandedState5 OBJECT-TYPE
    SYNTAX    INTEGER ( 0..1 )
    ACCESS    read-write
    STATUS    mandatory
    DESCRIPTION
        "<0=0=Low 1=High"
    ::= { meaDigitalOutputConfigEntry5 4 }

-- }}}
-- {{{ Entry 6

meaDigitalOutputName6 OBJECT-TYPE
    SYNTAX    DisplayString
    ACCESS    read-write
    STATUS    mandatory
    DESCRIPTION
        "Name of Digital Output number 6"
    ::= { meaDigitalOutputConfigEntry6 1 }

meaDigitalOutputUpTimer6 OBJECT-TYPE
    SYNTAX    INTEGER ( 0..999999 )
    ACCESS    read-write
    STATUS    mandatory
    DESCRIPTION
        "<0=Stay Off 0=immediate >0=Time in seconds"
    ::= { meaDigitalOutputConfigEntry6 2 }

meaDigitalOutputDownTimer6 OBJECT-TYPE
    SYNTAX    INTEGER ( 0..999999 )
    ACCESS    read-write
    STATUS    mandatory
    DESCRIPTION
        "<0=Stay Off 0=immediate >0=Time in seconds"
    ::= { meaDigitalOutputConfigEntry6 3 }

meaDigitalOutputCommandedState6 OBJECT-TYPE
    SYNTAX    INTEGER ( 0..1 )
    ACCESS    read-write
    STATUS    mandatory
    DESCRIPTION
        "<0=0=Low 1=High"
    ::= { meaDigitalOutputConfigEntry6 4 }

-- }}}
-- {{{ Entry 7

meaDigitalOutputName7 OBJECT-TYPE
    SYNTAX    DisplayString
    ACCESS    read-write
    STATUS    mandatory
    DESCRIPTION
        "Name of Digital Output number 7"
    ::= { meaDigitalOutputConfigEntry7 1 }

meaDigitalOutputUpTimer7 OBJECT-TYPE
    SYNTAX    INTEGER ( 0..999999 )
    ACCESS    read-write
    STATUS    mandatory
    DESCRIPTION
        "<0=Stay Off 0=immediate >0=Time in seconds"
    ::= { meaDigitalOutputConfigEntry7 2 }

meaDigitalOutputDownTimer7 OBJECT-TYPE
    SYNTAX    INTEGER ( 0..999999 )
    ACCESS    read-write
    STATUS    mandatory
    DESCRIPTION
        "<0=Stay Off 0=immediate >0=Time in seconds"
    ::= { meaDigitalOutputConfigEntry7 3 }

meaDigitalOutputCommandedState7 OBJECT-TYPE
    SYNTAX    INTEGER ( 0..1 )
    ACCESS    read-write
    STATUS    mandatory
    DESCRIPTION
        "<0=0=Low 1=High"
    ::= { meaDigitalOutputConfigEntry7 4 }

-- }}}
-- {{{ Entry 8

meaDigitalOutputName8 OBJECT-TYPE
    SYNTAX    DisplayString
    ACCESS    read-write
    STATUS    mandatory
    DESCRIPTION
        "Name of Digital Output number 8"
    ::= { meaDigitalOutputConfigEntry8 1 }

meaDigitalOutputUpTimer8 OBJECT-TYPE
    SYNTAX    INTEGER ( 0..999999 )
    ACCESS    read-write
    STATUS    mandatory
    DESCRIPTION
        "<0=Stay Off 0=immediate >0=Time in seconds"
    ::= { meaDigitalOutputConfigEntry8 2 }

meaDigitalOutputDownTimer8 OBJECT-TYPE
    SYNTAX    INTEGER ( 0..999999 )
    ACCESS    read-write
    STATUS    mandatory
    DESCRIPTION
        "<0=Stay Off 0=immediate >0=Time in seconds"
    ::= { meaDigitalOutputConfigEntry8 3 }

meaDigitalOutputCommandedState8 OBJECT-TYPE
    SYNTAX    INTEGER ( 0..1 )
    ACCESS    read-write
    STATUS    mandatory
    DESCRIPTION
        "<0=0=Low 1=High"
    ::= { meaDigitalOutputConfigEntry8 4 }

-- }}}
-- {{{ Entry 9

meaDigitalOutputName9 OBJECT-TYPE
    SYNTAX    DisplayString
    ACCESS    read-write
    STATUS    mandatory
    DESCRIPTION
        "Name of Digital Output number 9"
    ::= { meaDigitalOutputConfigEntry9 1 }

meaDigitalOutputUpTimer9 OBJECT-TYPE
    SYNTAX    INTEGER ( 0..999999 )
    ACCESS    read-write
    STATUS    mandatory
    DESCRIPTION
        "<0=Stay Off 0=immediate >0=Time in seconds"
    ::= { meaDigitalOutputConfigEntry9 2 }

meaDigitalOutputDownTimer9 OBJECT-TYPE
    SYNTAX    INTEGER ( 0..999999 )
    ACCESS    read-write
    STATUS    mandatory
    DESCRIPTION
        "<0=Stay Off 0=immediate >0=Time in seconds"
    ::= { meaDigitalOutputConfigEntry9 3 }

meaDigitalOutputCommandedState9 OBJECT-TYPE
    SYNTAX    INTEGER ( 0..1 )
    ACCESS    read-write
    STATUS    mandatory
    DESCRIPTION
        "<0=0=Low 1=High"
    ::= { meaDigitalOutputConfigEntry9 4 }

-- }}}
-- {{{ Entry 10

meaDigitalOutputName10 OBJECT-TYPE
    SYNTAX    DisplayString
    ACCESS    read-write
    STATUS    mandatory
    DESCRIPTION
        "Name of Digital Output number 10"
    ::= { meaDigitalOutputConfigEntry10 1 }

meaDigitalOutputUpTimer10 OBJECT-TYPE
    SYNTAX    INTEGER ( 0..999999 )
    ACCESS    read-write
    STATUS    mandatory
    DESCRIPTION
        "<0=Stay Off 0=immediate >0=Time in seconds"
    ::= { meaDigitalOutputConfigEntry10 2 }

meaDigitalOutputDownTimer10 OBJECT-TYPE
    SYNTAX    INTEGER ( 0..999999 )
    ACCESS    read-write
    STATUS    mandatory
    DESCRIPTION
        "<0=Stay Off 0=immediate >0=Time in seconds"
    ::= { meaDigitalOutputConfigEntry10 3 }

meaDigitalOutputCommandedState10 OBJECT-TYPE
    SYNTAX    INTEGER ( 0..1 )
    ACCESS    read-write
    STATUS    mandatory
    DESCRIPTION
        "<0=0=Low 1=High"
    ::= { meaDigitalOutputConfigEntry10 4 }

-- }}}
-- {{{ Entry 11

meaDigitalOutputName11 OBJECT-TYPE
    SYNTAX    DisplayString
    ACCESS    read-write
    STATUS    mandatory
    DESCRIPTION
        "Name of Digital Output number 11"
    ::= { meaDigitalOutputConfigEntry11 1 }

meaDigitalOutputUpTimer11 OBJECT-TYPE
    SYNTAX    INTEGER ( 0..999999 )
    ACCESS    read-write
    STATUS    mandatory
    DESCRIPTION
        "<0=Stay Off 0=immediate >0=Time in seconds"
    ::= { meaDigitalOutputConfigEntry11 2 }

meaDigitalOutputDownTimer11 OBJECT-TYPE
    SYNTAX    INTEGER ( 0..999999 )
    ACCESS    read-write
    STATUS    mandatory
    DESCRIPTION
        "<0=Stay Off 0=immediate >0=Time in seconds"
    ::= { meaDigitalOutputConfigEntry11 3 }

meaDigitalOutputCommandedState11 OBJECT-TYPE
    SYNTAX    INTEGER ( 0..1 )
    ACCESS    read-write
    STATUS    mandatory
    DESCRIPTION
        "<0=0=Low 1=High"
    ::= { meaDigitalOutputConfigEntry11 4 }

-- }}}
-- {{{ Entry 12

meaDigitalOutputName12 OBJECT-TYPE
    SYNTAX    DisplayString
    ACCESS    read-write
    STATUS    mandatory
    DESCRIPTION
        "Name of Digital Output number 12"
    ::= { meaDigitalOutputConfigEntry12 1 }

meaDigitalOutputUpTimer12 OBJECT-TYPE
    SYNTAX    INTEGER ( 0..999999 )
    ACCESS    read-write
    STATUS    mandatory
    DESCRIPTION
        "<0=Stay Off 0=immediate >0=Time in seconds"
    ::= { meaDigitalOutputConfigEntry12 2 }

meaDigitalOutputDownTimer12 OBJECT-TYPE
    SYNTAX    INTEGER ( 0..999999 )
    ACCESS    read-write
    STATUS    mandatory
    DESCRIPTION
        "<0=Stay Off 0=immediate >0=Time in seconds"
    ::= { meaDigitalOutputConfigEntry12 3 }

meaDigitalOutputCommandedState12 OBJECT-TYPE
    SYNTAX    INTEGER ( 0..1 )
    ACCESS    read-write
    STATUS    mandatory
    DESCRIPTION
        "<0=0=Low 1=High"
    ::= { meaDigitalOutputConfigEntry12 4 }

-- }}}
-- {{{ Entry 13

meaDigitalOutputName13 OBJECT-TYPE
    SYNTAX    DisplayString
    ACCESS    read-write
    STATUS    mandatory
    DESCRIPTION
        "Name of Digital Output number 13"
    ::= { meaDigitalOutputConfigEntry13 1 }

meaDigitalOutputUpTimer13 OBJECT-TYPE
    SYNTAX    INTEGER ( 0..999999 )
    ACCESS    read-write
    STATUS    mandatory
    DESCRIPTION
        "<0=Stay Off 0=immediate >0=Time in seconds"
    ::= { meaDigitalOutputConfigEntry13 2 }

meaDigitalOutputDownTimer13 OBJECT-TYPE
    SYNTAX    INTEGER ( 0..999999 )
    ACCESS    read-write
    STATUS    mandatory
    DESCRIPTION
        "<0=Stay Off 0=immediate >0=Time in seconds"
    ::= { meaDigitalOutputConfigEntry13 3 }

meaDigitalOutputCommandedState13 OBJECT-TYPE
    SYNTAX    INTEGER ( 0..1 )
    ACCESS    read-write
    STATUS    mandatory
    DESCRIPTION
        "<0=0=Low 1=High"
    ::= { meaDigitalOutputConfigEntry13 4 }

-- }}}
-- {{{ Entry 14

meaDigitalOutputName14 OBJECT-TYPE
    SYNTAX    DisplayString
    ACCESS    read-write
    STATUS    mandatory
    DESCRIPTION
        "Name of Digital Output number 14"
    ::= { meaDigitalOutputConfigEntry14 1 }

meaDigitalOutputUpTimer14 OBJECT-TYPE
    SYNTAX    INTEGER ( 0..999999 )
    ACCESS    read-write
    STATUS    mandatory
    DESCRIPTION
        "<0=Stay Off 0=immediate >0=Time in seconds"
    ::= { meaDigitalOutputConfigEntry14 2 }

meaDigitalOutputDownTimer14 OBJECT-TYPE
    SYNTAX    INTEGER ( 0..999999 )
    ACCESS    read-write
    STATUS    mandatory
    DESCRIPTION
        "<0=Stay Off 0=immediate >0=Time in seconds"
    ::= { meaDigitalOutputConfigEntry14 3 }

meaDigitalOutputCommandedState14 OBJECT-TYPE
    SYNTAX    INTEGER ( 0..1 )
    ACCESS    read-write
    STATUS    mandatory
    DESCRIPTION
        "<0=0=Low 1=High"
    ::= { meaDigitalOutputConfigEntry14 4 }

-- }}}
-- {{{ Entry 15

meaDigitalOutputName15 OBJECT-TYPE
    SYNTAX    DisplayString
    ACCESS    read-write
    STATUS    mandatory
    DESCRIPTION
        "Name of Digital Output number 15"
    ::= { meaDigitalOutputConfigEntry15 1 }

meaDigitalOutputUpTimer15 OBJECT-TYPE
    SYNTAX    INTEGER ( 0..999999 )
    ACCESS    read-write
    STATUS    mandatory
    DESCRIPTION
        "<0=Stay Off 0=immediate >0=Time in seconds"
    ::= { meaDigitalOutputConfigEntry15 2 }

meaDigitalOutputDownTimer15 OBJECT-TYPE
    SYNTAX    INTEGER ( 0..999999 )
    ACCESS    read-write
    STATUS    mandatory
    DESCRIPTION
        "<0=Stay Off 0=immediate >0=Time in seconds"
    ::= { meaDigitalOutputConfigEntry15 3 }

meaDigitalOutputCommandedState15 OBJECT-TYPE
    SYNTAX    INTEGER ( 0..1 )
    ACCESS    read-write
    STATUS    mandatory
    DESCRIPTION
        "<0=0=Low 1=High"
    ::= { meaDigitalOutputConfigEntry15 4 }

-- }}}
-- {{{ Entry 16

meaDigitalOutputName16 OBJECT-TYPE
    SYNTAX    DisplayString
    ACCESS    read-write
    STATUS    mandatory
    DESCRIPTION
        "Name of Digital Output number 16"
    ::= { meaDigitalOutputConfigEntry16 1 }

meaDigitalOutputUpTimer16 OBJECT-TYPE
    SYNTAX    INTEGER ( 0..999999 )
    ACCESS    read-write
    STATUS    mandatory
    DESCRIPTION
        "<0=Stay Off 0=immediate >0=Time in seconds"
    ::= { meaDigitalOutputConfigEntry16 2 }

meaDigitalOutputDownTimer16 OBJECT-TYPE
    SYNTAX    INTEGER ( 0..999999 )
    ACCESS    read-write
    STATUS    mandatory
    DESCRIPTION
        "<0=Stay Off 0=immediate >0=Time in seconds"
    ::= { meaDigitalOutputConfigEntry16 3 }

meaDigitalOutputCommandedState16 OBJECT-TYPE
    SYNTAX    INTEGER ( 0..1 )
    ACCESS    read-write
    STATUS    mandatory
    DESCRIPTION
        "<0=0=Low 1=High"
    ::= { meaDigitalOutputConfigEntry16 4 }

-- }}}
-- {{{ Entry 17

meaDigitalOutputName17 OBJECT-TYPE
    SYNTAX    DisplayString
    ACCESS    read-write
    STATUS    mandatory
    DESCRIPTION
        "Name of Digital Output number 17"
    ::= { meaDigitalOutputConfigEntry17 1 }

meaDigitalOutputUpTimer17 OBJECT-TYPE
    SYNTAX    INTEGER ( 0..999999 )
    ACCESS    read-write
    STATUS    mandatory
    DESCRIPTION
        "<0=Stay Off 0=immediate >0=Time in seconds"
    ::= { meaDigitalOutputConfigEntry17 2 }

meaDigitalOutputDownTimer17 OBJECT-TYPE
    SYNTAX    INTEGER ( 0..999999 )
    ACCESS    read-write
    STATUS    mandatory
    DESCRIPTION
        "<0=Stay Off 0=immediate >0=Time in seconds"
    ::= { meaDigitalOutputConfigEntry17 3 }

meaDigitalOutputCommandedState17 OBJECT-TYPE
    SYNTAX    INTEGER ( 0..1 )
    ACCESS    read-write
    STATUS    mandatory
    DESCRIPTION
        "<0=0=Low 1=High"
    ::= { meaDigitalOutputConfigEntry17 4 }

-- }}}
-- {{{ Entry 18

meaDigitalOutputName18 OBJECT-TYPE
    SYNTAX    DisplayString
    ACCESS    read-write
    STATUS    mandatory
    DESCRIPTION
        "Name of Digital Output number 18"
    ::= { meaDigitalOutputConfigEntry18 1 }

meaDigitalOutputUpTimer18 OBJECT-TYPE
    SYNTAX    INTEGER ( 0..999999 )
    ACCESS    read-write
    STATUS    mandatory
    DESCRIPTION
        "<0=Stay Off 0=immediate >0=Time in seconds"
    ::= { meaDigitalOutputConfigEntry18 2 }

meaDigitalOutputDownTimer18 OBJECT-TYPE
    SYNTAX    INTEGER ( 0..999999 )
    ACCESS    read-write
    STATUS    mandatory
    DESCRIPTION
        "<0=Stay Off 0=immediate >0=Time in seconds"
    ::= { meaDigitalOutputConfigEntry18 3 }

meaDigitalOutputCommandedState18 OBJECT-TYPE
    SYNTAX    INTEGER ( 0..1 )
    ACCESS    read-write
    STATUS    mandatory
    DESCRIPTION
        "<0=0=Low 1=High"
    ::= { meaDigitalOutputConfigEntry18 4 }

-- }}}
-- {{{ Entry 19

meaDigitalOutputName19 OBJECT-TYPE
    SYNTAX    DisplayString
    ACCESS    read-write
    STATUS    mandatory
    DESCRIPTION
        "Name of Digital Output number 19"
    ::= { meaDigitalOutputConfigEntry19 1 }

meaDigitalOutputUpTimer19 OBJECT-TYPE
    SYNTAX    INTEGER ( 0..999999 )
    ACCESS    read-write
    STATUS    mandatory
    DESCRIPTION
        "<0=Stay Off 0=immediate >0=Time in seconds"
    ::= { meaDigitalOutputConfigEntry19 2 }

meaDigitalOutputDownTimer19 OBJECT-TYPE
    SYNTAX    INTEGER ( 0..999999 )
    ACCESS    read-write
    STATUS    mandatory
    DESCRIPTION
        "<0=Stay Off 0=immediate >0=Time in seconds"
    ::= { meaDigitalOutputConfigEntry19 3 }

meaDigitalOutputCommandedState19 OBJECT-TYPE
    SYNTAX    INTEGER ( 0..1 )
    ACCESS    read-write
    STATUS    mandatory
    DESCRIPTION
        "<0=0=Low 1=High"
    ::= { meaDigitalOutputConfigEntry19 4 }

-- }}}
-- {{{ Entry 20

meaDigitalOutputName20 OBJECT-TYPE
    SYNTAX    DisplayString
    ACCESS    read-write
    STATUS    mandatory
    DESCRIPTION
        "Name of Digital Output number 20"
    ::= { meaDigitalOutputConfigEntry20 1 }

meaDigitalOutputUpTimer20 OBJECT-TYPE
    SYNTAX    INTEGER ( 0..999999 )
    ACCESS    read-write
    STATUS    mandatory
    DESCRIPTION
        "<0=Stay Off 0=immediate >0=Time in seconds"
    ::= { meaDigitalOutputConfigEntry20 2 }

meaDigitalOutputDownTimer20 OBJECT-TYPE
    SYNTAX    INTEGER ( 0..999999 )
    ACCESS    read-write
    STATUS    mandatory
    DESCRIPTION
        "<0=Stay Off 0=immediate >0=Time in seconds"
    ::= { meaDigitalOutputConfigEntry20 3 }

meaDigitalOutputCommandedState20 OBJECT-TYPE
    SYNTAX    INTEGER ( 0..1 )
    ACCESS    read-write
    STATUS    mandatory
    DESCRIPTION
        "<0=0=Low 1=High"
    ::= { meaDigitalOutputConfigEntry20 4 }

-- }}}
-- {{{ Entry 21

meaDigitalOutputName21 OBJECT-TYPE
    SYNTAX    DisplayString
    ACCESS    read-write
    STATUS    mandatory
    DESCRIPTION
        "Name of Digital Output number 21"
    ::= { meaDigitalOutputConfigEntry21 1 }

meaDigitalOutputUpTimer21 OBJECT-TYPE
    SYNTAX    INTEGER ( 0..999999 )
    ACCESS    read-write
    STATUS    mandatory
    DESCRIPTION
        "<0=Stay Off 0=immediate >0=Time in seconds"
    ::= { meaDigitalOutputConfigEntry21 2 }

meaDigitalOutputDownTimer21 OBJECT-TYPE
    SYNTAX    INTEGER ( 0..999999 )
    ACCESS    read-write
    STATUS    mandatory
    DESCRIPTION
        "<0=Stay Off 0=immediate >0=Time in seconds"
    ::= { meaDigitalOutputConfigEntry21 3 }

meaDigitalOutputCommandedState21 OBJECT-TYPE
    SYNTAX    INTEGER ( 0..1 )
    ACCESS    read-write
    STATUS    mandatory
    DESCRIPTION
        "<0=0=Low 1=High"
    ::= { meaDigitalOutputConfigEntry21 4 }

-- }}}
-- {{{ Entry 22

meaDigitalOutputName22 OBJECT-TYPE
    SYNTAX    DisplayString
    ACCESS    read-write
    STATUS    mandatory
    DESCRIPTION
        "Name of Digital Output number 22"
    ::= { meaDigitalOutputConfigEntry22 1 }

meaDigitalOutputUpTimer22 OBJECT-TYPE
    SYNTAX    INTEGER ( 0..999999 )
    ACCESS    read-write
    STATUS    mandatory
    DESCRIPTION
        "<0=Stay Off 0=immediate >0=Time in seconds"
    ::= { meaDigitalOutputConfigEntry22 2 }

meaDigitalOutputDownTimer22 OBJECT-TYPE
    SYNTAX    INTEGER ( 0..999999 )
    ACCESS    read-write
    STATUS    mandatory
    DESCRIPTION
        "<0=Stay Off 0=immediate >0=Time in seconds"
    ::= { meaDigitalOutputConfigEntry22 3 }

meaDigitalOutputCommandedState22 OBJECT-TYPE
    SYNTAX    INTEGER ( 0..1 )
    ACCESS    read-write
    STATUS    mandatory
    DESCRIPTION
        "<0=0=Low 1=High"
    ::= { meaDigitalOutputConfigEntry22 4 }

-- }}}
-- {{{ Entry 23

meaDigitalOutputName23 OBJECT-TYPE
    SYNTAX    DisplayString
    ACCESS    read-write
    STATUS    mandatory
    DESCRIPTION
        "Name of Digital Output number 23"
    ::= { meaDigitalOutputConfigEntry23 1 }

meaDigitalOutputUpTimer23 OBJECT-TYPE
    SYNTAX    INTEGER ( 0..999999 )
    ACCESS    read-write
    STATUS    mandatory
    DESCRIPTION
        "<0=Stay Off 0=immediate >0=Time in seconds"
    ::= { meaDigitalOutputConfigEntry23 2 }

meaDigitalOutputDownTimer23 OBJECT-TYPE
    SYNTAX    INTEGER ( 0..999999 )
    ACCESS    read-write
    STATUS    mandatory
    DESCRIPTION
        "<0=Stay Off 0=immediate >0=Time in seconds"
    ::= { meaDigitalOutputConfigEntry23 3 }

meaDigitalOutputCommandedState23 OBJECT-TYPE
    SYNTAX    INTEGER ( 0..1 )
    ACCESS    read-write
    STATUS    mandatory
    DESCRIPTION
        "<0=0=Low 1=High"
    ::= { meaDigitalOutputConfigEntry23 4 }

-- }}}
-- {{{ Entry 24

meaDigitalOutputName24 OBJECT-TYPE
    SYNTAX    DisplayString
    ACCESS    read-write
    STATUS    mandatory
    DESCRIPTION
        "Name of Digital Output number 24"
    ::= { meaDigitalOutputConfigEntry24 1 }

meaDigitalOutputUpTimer24 OBJECT-TYPE
    SYNTAX    INTEGER ( 0..999999 )
    ACCESS    read-write
    STATUS    mandatory
    DESCRIPTION
        "<0=Stay Off 0=immediate >0=Time in seconds"
    ::= { meaDigitalOutputConfigEntry24 2 }

meaDigitalOutputDownTimer24 OBJECT-TYPE
    SYNTAX    INTEGER ( 0..999999 )
    ACCESS    read-write
    STATUS    mandatory
    DESCRIPTION
        "<0=Stay Off 0=immediate >0=Time in seconds"
    ::= { meaDigitalOutputConfigEntry24 3 }

meaDigitalOutputCommandedState24 OBJECT-TYPE
    SYNTAX    INTEGER ( 0..1 )
    ACCESS    read-write
    STATUS    mandatory
    DESCRIPTION
        "<0=0=Low 1=High"
    ::= { meaDigitalOutputConfigEntry24 4 }

-- }}}
-- {{{ Entry 25

meaDigitalOutputName25 OBJECT-TYPE
    SYNTAX    DisplayString
    ACCESS    read-write
    STATUS    mandatory
    DESCRIPTION
        "Name of Digital Output number 25"
    ::= { meaDigitalOutputConfigEntry25 1 }

meaDigitalOutputUpTimer25 OBJECT-TYPE
    SYNTAX    INTEGER ( 0..999999 )
    ACCESS    read-write
    STATUS    mandatory
    DESCRIPTION
        "<0=Stay Off 0=immediate >0=Time in seconds"
    ::= { meaDigitalOutputConfigEntry25 2 }

meaDigitalOutputDownTimer25 OBJECT-TYPE
    SYNTAX    INTEGER ( 0..999999 )
    ACCESS    read-write
    STATUS    mandatory
    DESCRIPTION
        "<0=Stay Off 0=immediate >0=Time in seconds"
    ::= { meaDigitalOutputConfigEntry25 3 }

meaDigitalOutputCommandedState25 OBJECT-TYPE
    SYNTAX    INTEGER ( 0..1 )
    ACCESS    read-write
    STATUS    mandatory
    DESCRIPTION
        "<0=0=Low 1=High"
    ::= { meaDigitalOutputConfigEntry25 4 }

-- }}}
-- {{{ Entry 26

meaDigitalOutputName26 OBJECT-TYPE
    SYNTAX    DisplayString
    ACCESS    read-write
    STATUS    mandatory
    DESCRIPTION
        "Name of Digital Output number 26"
    ::= { meaDigitalOutputConfigEntry26 1 }

meaDigitalOutputUpTimer26 OBJECT-TYPE
    SYNTAX    INTEGER ( 0..999999 )
    ACCESS    read-write
    STATUS    mandatory
    DESCRIPTION
        "<0=Stay Off 0=immediate >0=Time in seconds"
    ::= { meaDigitalOutputConfigEntry26 2 }

meaDigitalOutputDownTimer26 OBJECT-TYPE
    SYNTAX    INTEGER ( 0..999999 )
    ACCESS    read-write
    STATUS    mandatory
    DESCRIPTION
        "<0=Stay Off 0=immediate >0=Time in seconds"
    ::= { meaDigitalOutputConfigEntry26 3 }

meaDigitalOutputCommandedState26 OBJECT-TYPE
    SYNTAX    INTEGER ( 0..1 )
    ACCESS    read-write
    STATUS    mandatory
    DESCRIPTION
        "<0=0=Low 1=High"
    ::= { meaDigitalOutputConfigEntry26 4 }

-- }}}
-- {{{ Entry 27

meaDigitalOutputName27 OBJECT-TYPE
    SYNTAX    DisplayString
    ACCESS    read-write
    STATUS    mandatory
    DESCRIPTION
        "Name of Digital Output number 27"
    ::= { meaDigitalOutputConfigEntry27 1 }

meaDigitalOutputUpTimer27 OBJECT-TYPE
    SYNTAX    INTEGER ( 0..999999 )
    ACCESS    read-write
    STATUS    mandatory
    DESCRIPTION
        "<0=Stay Off 0=immediate >0=Time in seconds"
    ::= { meaDigitalOutputConfigEntry27 2 }

meaDigitalOutputDownTimer27 OBJECT-TYPE
    SYNTAX    INTEGER ( 0..999999 )
    ACCESS    read-write
    STATUS    mandatory
    DESCRIPTION
        "<0=Stay Off 0=immediate >0=Time in seconds"
    ::= { meaDigitalOutputConfigEntry27 3 }

meaDigitalOutputCommandedState27 OBJECT-TYPE
    SYNTAX    INTEGER ( 0..1 )
    ACCESS    read-write
    STATUS    mandatory
    DESCRIPTION
        "<0=0=Low 1=High"
    ::= { meaDigitalOutputConfigEntry27 4 }

-- }}}
-- {{{ Entry 28

meaDigitalOutputName28 OBJECT-TYPE
    SYNTAX    DisplayString
    ACCESS    read-write
    STATUS    mandatory
    DESCRIPTION
        "Name of Digital Output number 28"
    ::= { meaDigitalOutputConfigEntry28 1 }

meaDigitalOutputUpTimer28 OBJECT-TYPE
    SYNTAX    INTEGER ( 0..999999 )
    ACCESS    read-write
    STATUS    mandatory
    DESCRIPTION
        "<0=Stay Off 0=immediate >0=Time in seconds"
    ::= { meaDigitalOutputConfigEntry28 2 }

meaDigitalOutputDownTimer28 OBJECT-TYPE
    SYNTAX    INTEGER ( 0..999999 )
    ACCESS    read-write
    STATUS    mandatory
    DESCRIPTION
        "<0=Stay Off 0=immediate >0=Time in seconds"
    ::= { meaDigitalOutputConfigEntry28 3 }

meaDigitalOutputCommandedState28 OBJECT-TYPE
    SYNTAX    INTEGER ( 0..1 )
    ACCESS    read-write
    STATUS    mandatory
    DESCRIPTION
        "<0=0=Low 1=High"
    ::= { meaDigitalOutputConfigEntry28 4 }

-- }}}
-- {{{ Entry 29

meaDigitalOutputName29 OBJECT-TYPE
    SYNTAX    DisplayString
    ACCESS    read-write
    STATUS    mandatory
    DESCRIPTION
        "Name of Digital Output number 29"
    ::= { meaDigitalOutputConfigEntry29 1 }

meaDigitalOutputUpTimer29 OBJECT-TYPE
    SYNTAX    INTEGER ( 0..999999 )
    ACCESS    read-write
    STATUS    mandatory
    DESCRIPTION
        "<0=Stay Off 0=immediate >0=Time in seconds"
    ::= { meaDigitalOutputConfigEntry29 2 }

meaDigitalOutputDownTimer29 OBJECT-TYPE
    SYNTAX    INTEGER ( 0..999999 )
    ACCESS    read-write
    STATUS    mandatory
    DESCRIPTION
        "<0=Stay Off 0=immediate >0=Time in seconds"
    ::= { meaDigitalOutputConfigEntry29 3 }

meaDigitalOutputCommandedState29 OBJECT-TYPE
    SYNTAX    INTEGER ( 0..1 )
    ACCESS    read-write
    STATUS    mandatory
    DESCRIPTION
        "<0=0=Low 1=High"
    ::= { meaDigitalOutputConfigEntry29 4 }

-- }}}
-- {{{ Entry 30

meaDigitalOutputName30 OBJECT-TYPE
    SYNTAX    DisplayString
    ACCESS    read-write
    STATUS    mandatory
    DESCRIPTION
        "Name of Digital Output number 30"
    ::= { meaDigitalOutputConfigEntry30 1 }

meaDigitalOutputUpTimer30 OBJECT-TYPE
    SYNTAX    INTEGER ( 0..999999 )
    ACCESS    read-write
    STATUS    mandatory
    DESCRIPTION
        "<0=Stay Off 0=immediate >0=Time in seconds"
    ::= { meaDigitalOutputConfigEntry30 2 }

meaDigitalOutputDownTimer30 OBJECT-TYPE
    SYNTAX    INTEGER ( 0..999999 )
    ACCESS    read-write
    STATUS    mandatory
    DESCRIPTION
        "<0=Stay Off 0=immediate >0=Time in seconds"
    ::= { meaDigitalOutputConfigEntry30 3 }

meaDigitalOutputCommandedState30 OBJECT-TYPE
    SYNTAX    INTEGER ( 0..1 )
    ACCESS    read-write
    STATUS    mandatory
    DESCRIPTION
        "<0=0=Low 1=High"
    ::= { meaDigitalOutputConfigEntry30 4 }

-- }}}
-- {{{ Entry 31

meaDigitalOutputName31 OBJECT-TYPE
    SYNTAX    DisplayString
    ACCESS    read-write
    STATUS    mandatory
    DESCRIPTION
        "Name of Digital Output number 31"
    ::= { meaDigitalOutputConfigEntry31 1 }

meaDigitalOutputUpTimer31 OBJECT-TYPE
    SYNTAX    INTEGER ( 0..999999 )
    ACCESS    read-write
    STATUS    mandatory
    DESCRIPTION
        "<0=Stay Off 0=immediate >0=Time in seconds"
    ::= { meaDigitalOutputConfigEntry31 2 }

meaDigitalOutputDownTimer31 OBJECT-TYPE
    SYNTAX    INTEGER ( 0..999999 )
    ACCESS    read-write
    STATUS    mandatory
    DESCRIPTION
        "<0=Stay Off 0=immediate >0=Time in seconds"
    ::= { meaDigitalOutputConfigEntry31 3 }

meaDigitalOutputCommandedState31 OBJECT-TYPE
    SYNTAX    INTEGER ( 0..1 )
    ACCESS    read-write
    STATUS    mandatory
    DESCRIPTION
        "<0=0=Low 1=High"
    ::= { meaDigitalOutputConfigEntry31 4 }

-- }}}
-- {{{ Entry 32

meaDigitalOutputName32 OBJECT-TYPE
    SYNTAX    DisplayString
    ACCESS    read-write
    STATUS    mandatory
    DESCRIPTION
        "Name of Digital Output number 32"
    ::= { meaDigitalOutputConfigEntry32 1 }

meaDigitalOutputUpTimer32 OBJECT-TYPE
    SYNTAX    INTEGER ( 0..999999 )
    ACCESS    read-write
    STATUS    mandatory
    DESCRIPTION
        "<0=Stay Off 0=immediate >0=Time in seconds"
    ::= { meaDigitalOutputConfigEntry32 2 }

meaDigitalOutputDownTimer32 OBJECT-TYPE
    SYNTAX    INTEGER ( 0..999999 )
    ACCESS    read-write
    STATUS    mandatory
    DESCRIPTION
        "<0=Stay Off 0=immediate >0=Time in seconds"
    ::= { meaDigitalOutputConfigEntry32 3 }

meaDigitalOutputCommandedState32 OBJECT-TYPE
    SYNTAX    INTEGER ( 0..1 )
    ACCESS    read-write
    STATUS    mandatory
    DESCRIPTION
        "<0=0=Low 1=High"
    ::= { meaDigitalOutputConfigEntry32 4 }

-- }}}

-- }}}
-- {{{ meaDigitalOutputControlTable

meaDigitalOutputControlEntry1  OBJECT IDENTIFIER ::= { meaDigitalOutputControlTable 1  }
meaDigitalOutputControlEntry2  OBJECT IDENTIFIER ::= { meaDigitalOutputControlTable 2  }
meaDigitalOutputControlEntry3  OBJECT IDENTIFIER ::= { meaDigitalOutputControlTable 3  }
meaDigitalOutputControlEntry4  OBJECT IDENTIFIER ::= { meaDigitalOutputControlTable 4  }
meaDigitalOutputControlEntry5  OBJECT IDENTIFIER ::= { meaDigitalOutputControlTable 5  }
meaDigitalOutputControlEntry6  OBJECT IDENTIFIER ::= { meaDigitalOutputControlTable 6  }
meaDigitalOutputControlEntry7  OBJECT IDENTIFIER ::= { meaDigitalOutputControlTable 7  }
meaDigitalOutputControlEntry8  OBJECT IDENTIFIER ::= { meaDigitalOutputControlTable 8  }
meaDigitalOutputControlEntry9  OBJECT IDENTIFIER ::= { meaDigitalOutputControlTable 9  }
meaDigitalOutputControlEntry10 OBJECT IDENTIFIER ::= { meaDigitalOutputControlTable 10 }
meaDigitalOutputControlEntry11 OBJECT IDENTIFIER ::= { meaDigitalOutputControlTable 11 }
meaDigitalOutputControlEntry12 OBJECT IDENTIFIER ::= { meaDigitalOutputControlTable 12 }
meaDigitalOutputControlEntry13 OBJECT IDENTIFIER ::= { meaDigitalOutputControlTable 13 }
meaDigitalOutputControlEntry14 OBJECT IDENTIFIER ::= { meaDigitalOutputControlTable 14 }
meaDigitalOutputControlEntry15 OBJECT IDENTIFIER ::= { meaDigitalOutputControlTable 15 }
meaDigitalOutputControlEntry16 OBJECT IDENTIFIER ::= { meaDigitalOutputControlTable 16 }
meaDigitalOutputControlEntry17 OBJECT IDENTIFIER ::= { meaDigitalOutputControlTable 17 }
meaDigitalOutputControlEntry18 OBJECT IDENTIFIER ::= { meaDigitalOutputControlTable 18 }
meaDigitalOutputControlEntry19 OBJECT IDENTIFIER ::= { meaDigitalOutputControlTable 19 }
meaDigitalOutputControlEntry20 OBJECT IDENTIFIER ::= { meaDigitalOutputControlTable 20 }
meaDigitalOutputControlEntry21 OBJECT IDENTIFIER ::= { meaDigitalOutputControlTable 21 }
meaDigitalOutputControlEntry22 OBJECT IDENTIFIER ::= { meaDigitalOutputControlTable 22 }
meaDigitalOutputControlEntry23 OBJECT IDENTIFIER ::= { meaDigitalOutputControlTable 23 }
meaDigitalOutputControlEntry24 OBJECT IDENTIFIER ::= { meaDigitalOutputControlTable 24 }
meaDigitalOutputControlEntry25 OBJECT IDENTIFIER ::= { meaDigitalOutputControlTable 25 }
meaDigitalOutputControlEntry26 OBJECT IDENTIFIER ::= { meaDigitalOutputControlTable 26 }
meaDigitalOutputControlEntry27 OBJECT IDENTIFIER ::= { meaDigitalOutputControlTable 27 }
meaDigitalOutputControlEntry28 OBJECT IDENTIFIER ::= { meaDigitalOutputControlTable 28 }
meaDigitalOutputControlEntry29 OBJECT IDENTIFIER ::= { meaDigitalOutputControlTable 29 }
meaDigitalOutputControlEntry30 OBJECT IDENTIFIER ::= { meaDigitalOutputControlTable 30 }
meaDigitalOutputControlEntry31 OBJECT IDENTIFIER ::= { meaDigitalOutputControlTable 31 }
meaDigitalOutputControlEntry32 OBJECT IDENTIFIER ::= { meaDigitalOutputControlTable 32 }

-- special case
meaDigitalOutputUnitsAction OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlTable 33 }

-- meaDigitalOutputControlEntries
-- {{{ Entry 1

meaDigitalOutputAction1 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry1 1 }

-- }}}
-- {{{ Entry 2

meaDigitalOutputAction2 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry2 1 }

-- }}}
-- {{{ Entry 3

meaDigitalOutputAction3 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry3 1 }

-- }}}
-- {{{ Entry 4

meaDigitalOutputAction4 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry4 1 }

-- }}}
-- {{{ Entry 5

meaDigitalOutputAction5 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry5 1 }

-- }}}
-- {{{ Entry 6

meaDigitalOutputAction6 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry6 1 }

-- }}}
-- {{{ Entry 7

meaDigitalOutputAction7 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry7 1 }

-- }}}
-- {{{ Entry 8

meaDigitalOutputAction8 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry8 1 }

-- }}}
-- {{{ Entry 9

meaDigitalOutputAction9 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry9 1 }

-- }}}
-- {{{ Entry 10

meaDigitalOutputAction10 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry10 1 }

-- }}}
-- {{{ Entry 11

meaDigitalOutputAction11 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry11 1 }

-- }}}
-- {{{ Entry 12

meaDigitalOutputAction12 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry12 1 }

-- }}}
-- {{{ Entry 13

meaDigitalOutputAction13 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry13 1 }

-- }}}
-- {{{ Entry 14

meaDigitalOutputAction14 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry14 1 }

-- }}}
-- {{{ Entry 15

meaDigitalOutputAction15 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry15 1 }

-- }}}
-- {{{ Entry 16

meaDigitalOutputAction16 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry16 1 }

-- }}}
-- {{{ Entry 17

meaDigitalOutputAction17 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry17 1 }

-- }}}
-- {{{ Entry 18

meaDigitalOutputAction18 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry18 1 }

-- }}}
-- {{{ Entry 19

meaDigitalOutputAction19 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry19 1 }

-- }}}
-- {{{ Entry 20

meaDigitalOutputAction20 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry20 1 }

-- }}}
-- {{{ Entry 21

meaDigitalOutputAction21 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry21 1 }

-- }}}
-- {{{ Entry 22

meaDigitalOutputAction22 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry22 1 }

-- }}}
-- {{{ Entry 23

meaDigitalOutputAction23 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry23 1 }

-- }}}
-- {{{ Entry 24

meaDigitalOutputAction24 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry24 1 }

-- }}}
-- {{{ Entry 25

meaDigitalOutputAction25 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry25 1 }

-- }}}
-- {{{ Entry 26

meaDigitalOutputAction26 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry26 1 }

-- }}}
-- {{{ Entry 27

meaDigitalOutputAction27 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry27 1 }

-- }}}
-- {{{ Entry 28

meaDigitalOutputAction28 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry28 1 }

-- }}}
-- {{{ Entry 29

meaDigitalOutputAction29 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry29 1 }

-- }}}
-- {{{ Entry 30

meaDigitalOutputAction30 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry30 1 }

-- }}}
-- {{{ Entry 31

meaDigitalOutputAction31 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry31 1 }

-- }}}
-- {{{ Entry 32

meaDigitalOutputAction32 OBJECT-TYPE
    SYNTAX    INTEGER (0..4)
    ACCESS    read-write
    STATUS    mandatory
    DESCRIPTION
        "0=Cancel 1=On Immed 2=On with time on(power on default) 3=Off with time off 4=Cycle immediate"
    ::= { meaDigitalOutputControlEntry32 1 }

-- }}}

-- }}}
-- {{{ meaDigitalOutputStatusTable 

meaDigitalOutputStatusEntry1  OBJECT IDENTIFIER ::= { meaDigitalOutputStatusTable 1  }
meaDigitalOutputStatusEntry2  OBJECT IDENTIFIER ::= { meaDigitalOutputStatusTable 2  }
meaDigitalOutputStatusEntry3  OBJECT IDENTIFIER ::= { meaDigitalOutputStatusTable 3  }
meaDigitalOutputStatusEntry4  OBJECT IDENTIFIER ::= { meaDigitalOutputStatusTable 4  }
meaDigitalOutputStatusEntry5  OBJECT IDENTIFIER ::= { meaDigitalOutputStatusTable 5  }
meaDigitalOutputStatusEntry6  OBJECT IDENTIFIER ::= { meaDigitalOutputStatusTable 6  }
meaDigitalOutputStatusEntry7  OBJECT IDENTIFIER ::= { meaDigitalOutputStatusTable 7  }
meaDigitalOutputStatusEntry8  OBJECT IDENTIFIER ::= { meaDigitalOutputStatusTable 8  }
meaDigitalOutputStatusEntry9  OBJECT IDENTIFIER ::= { meaDigitalOutputStatusTable 9  }
meaDigitalOutputStatusEntry10 OBJECT IDENTIFIER ::= { meaDigitalOutputStatusTable 10 }
meaDigitalOutputStatusEntry11 OBJECT IDENTIFIER ::= { meaDigitalOutputStatusTable 11 }
meaDigitalOutputStatusEntry12 OBJECT IDENTIFIER ::= { meaDigitalOutputStatusTable 12 }
meaDigitalOutputStatusEntry13 OBJECT IDENTIFIER ::= { meaDigitalOutputStatusTable 13 }
meaDigitalOutputStatusEntry14 OBJECT IDENTIFIER ::= { meaDigitalOutputStatusTable 14 }
meaDigitalOutputStatusEntry15 OBJECT IDENTIFIER ::= { meaDigitalOutputStatusTable 15 }
meaDigitalOutputStatusEntry16 OBJECT IDENTIFIER ::= { meaDigitalOutputStatusTable 16 }
meaDigitalOutputStatusEntry17 OBJECT IDENTIFIER ::= { meaDigitalOutputStatusTable 17 }
meaDigitalOutputStatusEntry18 OBJECT IDENTIFIER ::= { meaDigitalOutputStatusTable 18 }
meaDigitalOutputStatusEntry19 OBJECT IDENTIFIER ::= { meaDigitalOutputStatusTable 19 }
meaDigitalOutputStatusEntry20 OBJECT IDENTIFIER ::= { meaDigitalOutputStatusTable 20 }
meaDigitalOutputStatusEntry21 OBJECT IDENTIFIER ::= { meaDigitalOutputStatusTable 21 }
meaDigitalOutputStatusEntry22 OBJECT IDENTIFIER ::= { meaDigitalOutputStatusTable 22 }
meaDigitalOutputStatusEntry23 OBJECT IDENTIFIER ::= { meaDigitalOutputStatusTable 23 }
meaDigitalOutputStatusEntry24 OBJECT IDENTIFIER ::= { meaDigitalOutputStatusTable 24 }
meaDigitalOutputStatusEntry25 OBJECT IDENTIFIER ::= { meaDigitalOutputStatusTable 25 }
meaDigitalOutputStatusEntry26 OBJECT IDENTIFIER ::= { meaDigitalOutputStatusTable 26 }
meaDigitalOutputStatusEntry27 OBJECT IDENTIFIER ::= { meaDigitalOutputStatusTable 27 }
meaDigitalOutputStatusEntry28 OBJECT IDENTIFIER ::= { meaDigitalOutputStatusTable 28 }
meaDigitalOutputStatusEntry29 OBJECT IDENTIFIER ::= { meaDigitalOutputStatusTable 29 }
meaDigitalOutputStatusEntry30 OBJECT IDENTIFIER ::= { meaDigitalOutputStatusTable 30 }
meaDigitalOutputStatusEntry31 OBJECT IDENTIFIER ::= { meaDigitalOutputStatusTable 31 }
meaDigitalOutputStatusEntry32 OBJECT IDENTIFIER ::= { meaDigitalOutputStatusTable 32 }

-- special case
meaDigitalOutputUnitsStatus OBJECT-TYPE
    SYNTAX    INTEGER (0..2)
    ACCESS    read-only
    STATUS    mandatory
    DESCRIPTION
        "0=All outputs on 1=Some outputs off, 2=All outputs off"
    ::= { meaDigitalOutputStatusTable 33 }

-- meaDigitalOutputStatusEntries
-- {{{ Entry 1

meaDigitalOutputStatus1 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry1 1 }

meaDigitalOutputTimeToGo1 OBJECT-TYPE
    SYNTAX    INTEGER (0..999999)
    ACCESS    read-only
    STATUS    mandatory
    DESCRIPTION
        "Time to go in seconds"
    ::= { meaDigitalOutputStatusEntry1 2 }

-- }}}
-- {{{ Entry 2

meaDigitalOutputStatus2 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry2 1 }

meaDigitalOutputTimeToGo2 OBJECT-TYPE
    SYNTAX    INTEGER (0..999999)
    ACCESS    read-only
    STATUS    mandatory
    DESCRIPTION
        "Time to go in seconds"
    ::= { meaDigitalOutputStatusEntry2 2 }

-- }}}
-- {{{ Entry 3

meaDigitalOutputStatus3 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry3 1 }

meaDigitalOutputTimeToGo3 OBJECT-TYPE
    SYNTAX    INTEGER (0..999999)
    ACCESS    read-only
    STATUS    mandatory
    DESCRIPTION
        "Time to go in seconds"
    ::= { meaDigitalOutputStatusEntry3 2 }

-- }}}
-- {{{ Entry 4

meaDigitalOutputStatus4 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry4 1 }

meaDigitalOutputTimeToGo4 OBJECT-TYPE
    SYNTAX    INTEGER (0..999999)
    ACCESS    read-only
    STATUS    mandatory
    DESCRIPTION
        "Time to go in seconds"
    ::= { meaDigitalOutputStatusEntry4 2 }

-- }}}
-- {{{ Entry 5

meaDigitalOutputStatus5 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry5 1 }

meaDigitalOutputTimeToGo5 OBJECT-TYPE
    SYNTAX    INTEGER (0..999999)
    ACCESS    read-only
    STATUS    mandatory
    DESCRIPTION
        "Time to go in seconds"
    ::= { meaDigitalOutputStatusEntry5 2 }

-- }}}
-- {{{ Entry 6

meaDigitalOutputStatus6 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry6 1 }

meaDigitalOutputTimeToGo6 OBJECT-TYPE
    SYNTAX    INTEGER (0..999999)
    ACCESS    read-only
    STATUS    mandatory
    DESCRIPTION
        "Time to go in seconds"
    ::= { meaDigitalOutputStatusEntry6 2 }

-- }}}
-- {{{ Entry 7

meaDigitalOutputStatus7 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry7 1 }

meaDigitalOutputTimeToGo7 OBJECT-TYPE
    SYNTAX    INTEGER (0..999999)
    ACCESS    read-only
    STATUS    mandatory
    DESCRIPTION
        "Time to go in seconds"
    ::= { meaDigitalOutputStatusEntry7 2 }

-- }}}
-- {{{ Entry 8

meaDigitalOutputStatus8 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry8 1 }

meaDigitalOutputTimeToGo8 OBJECT-TYPE
    SYNTAX    INTEGER (0..999999)
    ACCESS    read-only
    STATUS    mandatory
    DESCRIPTION
        "Time to go in seconds"
    ::= { meaDigitalOutputStatusEntry8 2 }

-- }}}
-- {{{ Entry 9

meaDigitalOutputStatus9 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry9 1 }

meaDigitalOutputTimeToGo9 OBJECT-TYPE
    SYNTAX    INTEGER (0..999999)
    ACCESS    read-only
    STATUS    mandatory
    DESCRIPTION
        "Time to go in seconds"
    ::= { meaDigitalOutputStatusEntry9 2 }

-- }}}
-- {{{ Entry 10

meaDigitalOutputStatus10 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry10 1 }

meaDigitalOutputTimeToGo10 OBJECT-TYPE
    SYNTAX    INTEGER (0..999999)
    ACCESS    read-only
    STATUS    mandatory
    DESCRIPTION
        "Time to go in seconds"
    ::= { meaDigitalOutputStatusEntry10 2 }

-- }}}
-- {{{ Entry 11

meaDigitalOutputStatus11 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry11 1 }

meaDigitalOutputTimeToGo11 OBJECT-TYPE
    SYNTAX    INTEGER (0..999999)
    ACCESS    read-only
    STATUS    mandatory
    DESCRIPTION
        "Time to go in seconds"
    ::= { meaDigitalOutputStatusEntry11 2 }

-- }}}
-- {{{ Entry 12

meaDigitalOutputStatus12 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry12 1 }

meaDigitalOutputTimeToGo12 OBJECT-TYPE
    SYNTAX    INTEGER (0..999999)
    ACCESS    read-only
    STATUS    mandatory
    DESCRIPTION
        "Time to go in seconds"
    ::= { meaDigitalOutputStatusEntry12 2 }

-- }}}
-- {{{ Entry 13

meaDigitalOutputStatus13 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry13 1 }

meaDigitalOutputTimeToGo13 OBJECT-TYPE
    SYNTAX    INTEGER (0..999999)
    ACCESS    read-only
    STATUS    mandatory
    DESCRIPTION
        "Time to go in seconds"
    ::= { meaDigitalOutputStatusEntry13 2 }

-- }}}
-- {{{ Entry 14

meaDigitalOutputStatus14 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry14 1 }

meaDigitalOutputTimeToGo14 OBJECT-TYPE
    SYNTAX    INTEGER (0..999999)
    ACCESS    read-only
    STATUS    mandatory
    DESCRIPTION
        "Time to go in seconds"
    ::= { meaDigitalOutputStatusEntry14 2 }

-- }}}
-- {{{ Entry 15

meaDigitalOutputStatus15 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry15 1 }

meaDigitalOutputTimeToGo15 OBJECT-TYPE
    SYNTAX    INTEGER (0..999999)
    ACCESS    read-only
    STATUS    mandatory
    DESCRIPTION
        "Time to go in seconds"
    ::= { meaDigitalOutputStatusEntry15 2 }

-- }}}
-- {{{ Entry 16

meaDigitalOutputStatus16 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry16 1 }

meaDigitalOutputTimeToGo16 OBJECT-TYPE
    SYNTAX    INTEGER (0..999999)
    ACCESS    read-only
    STATUS    mandatory
    DESCRIPTION
        "Time to go in seconds"
    ::= { meaDigitalOutputStatusEntry16 2 }

-- }}}
-- {{{ Entry 17

meaDigitalOutputStatus17 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry17 1 }

meaDigitalOutputTimeToGo17 OBJECT-TYPE
    SYNTAX    INTEGER (0..999999)
    ACCESS    read-only
    STATUS    mandatory
    DESCRIPTION
        "Time to go in seconds"
    ::= { meaDigitalOutputStatusEntry17 2 }

-- }}}
-- {{{ Entry 18

meaDigitalOutputStatus18 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry18 1 }

meaDigitalOutputTimeToGo18 OBJECT-TYPE
    SYNTAX    INTEGER (0..999999)
    ACCESS    read-only
    STATUS    mandatory
    DESCRIPTION
        "Time to go in seconds"
    ::= { meaDigitalOutputStatusEntry18 2 }

-- }}}
-- {{{ Entry 19

meaDigitalOutputStatus19 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry19 1 }

meaDigitalOutputTimeToGo19 OBJECT-TYPE
    SYNTAX    INTEGER (0..999999)
    ACCESS    read-only
    STATUS    mandatory
    DESCRIPTION
        "Time to go in seconds"
    ::= { meaDigitalOutputStatusEntry19 2 }

-- }}}
-- {{{ Entry 20

meaDigitalOutputStatus20 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry20 1 }

meaDigitalOutputTimeToGo20 OBJECT-TYPE
    SYNTAX    INTEGER (0..999999)
    ACCESS    read-only
    STATUS    mandatory
    DESCRIPTION
        "Time to go in seconds"
    ::= { meaDigitalOutputStatusEntry20 2 }

-- }}}
-- {{{ Entry 21

meaDigitalOutputStatus21 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry21 1 }

meaDigitalOutputTimeToGo21 OBJECT-TYPE
    SYNTAX    INTEGER (0..999999)
    ACCESS    read-only
    STATUS    mandatory
    DESCRIPTION
        "Time to go in seconds"
    ::= { meaDigitalOutputStatusEntry21 2 }

-- }}}
-- {{{ Entry 22

meaDigitalOutputStatus22 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry22 1 }

meaDigitalOutputTimeToGo22 OBJECT-TYPE
    SYNTAX    INTEGER (0..999999)
    ACCESS    read-only
    STATUS    mandatory
    DESCRIPTION
        "Time to go in seconds"
    ::= { meaDigitalOutputStatusEntry22 2 }

-- }}}
-- {{{ Entry 23

meaDigitalOutputStatus23 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry23 1 }

meaDigitalOutputTimeToGo23 OBJECT-TYPE
    SYNTAX    INTEGER (0..999999)
    ACCESS    read-only
    STATUS    mandatory
    DESCRIPTION
        "Time to go in seconds"
    ::= { meaDigitalOutputStatusEntry23 2 }

-- }}}
-- {{{ Entry 24

meaDigitalOutputStatus24 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry24 1 }

meaDigitalOutputTimeToGo24 OBJECT-TYPE
    SYNTAX    INTEGER (0..999999)
    ACCESS    read-only
    STATUS    mandatory
    DESCRIPTION
        "Time to go in seconds"
    ::= { meaDigitalOutputStatusEntry24 2 }

-- }}}
-- {{{ Entry 25

meaDigitalOutputStatus25 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry25 1 }

meaDigitalOutputTimeToGo25 OBJECT-TYPE
    SYNTAX    INTEGER (0..999999)
    ACCESS    read-only
    STATUS    mandatory
    DESCRIPTION
        "Time to go in seconds"
    ::= { meaDigitalOutputStatusEntry25 2 }

-- }}}
-- {{{ Entry 26

meaDigitalOutputStatus26 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry26 1 }

meaDigitalOutputTimeToGo26 OBJECT-TYPE
    SYNTAX    INTEGER (0..999999)
    ACCESS    read-only
    STATUS    mandatory
    DESCRIPTION
        "Time to go in seconds"
    ::= { meaDigitalOutputStatusEntry26 2 }

-- }}}
-- {{{ Entry 27

meaDigitalOutputStatus27 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry27 1 }

meaDigitalOutputTimeToGo27 OBJECT-TYPE
    SYNTAX    INTEGER (0..999999)
    ACCESS    read-only
    STATUS    mandatory
    DESCRIPTION
        "Time to go in seconds"
    ::= { meaDigitalOutputStatusEntry27 2 }

-- }}}
-- {{{ Entry 28

meaDigitalOutputStatus28 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry28 1 }

meaDigitalOutputTimeToGo28 OBJECT-TYPE
    SYNTAX    INTEGER (0..999999)
    ACCESS    read-only
    STATUS    mandatory
    DESCRIPTION
        "Time to go in seconds"
    ::= { meaDigitalOutputStatusEntry28 2 }

-- }}}
-- {{{ Entry 29

meaDigitalOutputStatus29 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry29 1 }

meaDigitalOutputTimeToGo29 OBJECT-TYPE
    SYNTAX    INTEGER (0..999999)
    ACCESS    read-only
    STATUS    mandatory
    DESCRIPTION
        "Time to go in seconds"
    ::= { meaDigitalOutputStatusEntry29 2 }

-- }}}
-- {{{ Entry 30

meaDigitalOutputStatus30 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry30 1 }

meaDigitalOutputTimeToGo30 OBJECT-TYPE
    SYNTAX    INTEGER (0..999999)
    ACCESS    read-only
    STATUS    mandatory
    DESCRIPTION
        "Time to go in seconds"
    ::= { meaDigitalOutputStatusEntry30 2 }

-- }}}
-- {{{ Entry 31

meaDigitalOutputStatus31 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry31 1 }

meaDigitalOutputTimeToGo31 OBJECT-TYPE
    SYNTAX    INTEGER (0..999999)
    ACCESS    read-only
    STATUS    mandatory
    DESCRIPTION
        "Time to go in seconds"
    ::= { meaDigitalOutputStatusEntry31 2 }

-- }}}
-- {{{ Entry 32

meaDigitalOutputStatus32 OBJECT-TYPE
    SYNTAX    INTEGER (0..4)
    ACCESS    read-only
    STATUS    mandatory
    DESCRIPTION
        "0=On 1=Off 2=On Transitioning to Off 3=Off Transitioning to On 4=Cycle scheduled"
    ::= { meaDigitalOutputStatusEntry32 1 }

meaDigitalOutputTimeToGo32 OBJECT-TYPE
    SYNTAX    INTEGER (0..999999)
    ACCESS    read-only
    STATUS    mandatory
    DESCRIPTION
        "Time to go in seconds"
    ::= { meaDigitalOutputStatusEntry32 2 }

-- }}}




-- }}}
-- }}}
-- {{{ meaAnalogInput group    

meaAnalogInputTable  OBJECT IDENTIFIER ::= { meaAnalogInput 1 }

-- {{{ meaAnalogInputTable   

meaAnalogInputEntry1  OBJECT IDENTIFIER ::= { meaAnalogInputTable 1  }
meaAnalogInputEntry2  OBJECT IDENTIFIER ::= { meaAnalogInputTable 2  }
meaAnalogInputEntry3  OBJECT IDENTIFIER ::= { meaAnalogInputTable 3  }
meaAnalogInputEntry4  OBJECT IDENTIFIER ::= { meaAnalogInputTable 4  }
meaAnalogInputEntry5  OBJECT IDENTIFIER ::= { meaAnalogInputTable 5  }
meaAnalogInputEntry6  OBJECT IDENTIFIER ::= { meaAnalogInputTable 6  }
meaAnalogInputEntry7  OBJECT IDENTIFIER ::= { meaAnalogInputTable 7  }
meaAnalogInputEntry8  OBJECT IDENTIFIER ::= { meaAnalogInputTable 8  }
meaAnalogInputEntry9  OBJECT IDENTIFIER ::= { meaAnalogInputTable 9  }
meaAnalogInputEntry10 OBJECT IDENTIFIER ::= { meaAnalogInputTable 10 }
meaAnalogInputEntry11 OBJECT IDENTIFIER ::= { meaAnalogInputTable 11 }
meaAnalogInputEntry12 OBJECT IDENTIFIER ::= { meaAnalogInputTable 12 }
meaAnalogInputEntry13 OBJECT IDENTIFIER ::= { meaAnalogInputTable 13 }
meaAnalogInputEntry14 OBJECT IDENTIFIER ::= { meaAnalogInputTable 14 }
meaAnalogInputEntry15 OBJECT IDENTIFIER ::= { meaAnalogInputTable 15 }
meaAnalogInputEntry16 OBJECT IDENTIFIER ::= { meaAnalogInputTable 16 }

-- meaAnalogInput entries
-- {{{ Entry 1

meaAnalogueInputName1 OBJECT-TYPE
    SYNTAX    DisplayString
    ACCESS    read-write
    STATUS    mandatory
    DESCRIPTION
        "Name of AnalogueInput"
    ::= { meaAnalogInputEntry1 1 }

meaAnalogueInputOffset1 OBJECT-TYPE
    SYNTAX    INTEGER ( 0..1000 )
    ACCESS    read-write
    STATUS    mandatory
    DESCRIPTION
        "Input Offset Value in .1%"
    ::= { meaAnalogInputEntry1 2 }

meaAnalogueInputValue1 OBJECT-TYPE
    SYNTAX    INTEGER ( 0..1000 )
    ACCESS    read-only
    STATUS    mandatory
    DESCRIPTION
        "Input Value in .1%"
    ::= { meaAnalogInputEntry1 3 }

meaAnalogueInputUpperThreshold1 OBJECT-TYPE
    SYNTAX    INTEGER ( 0..1000 )
    ACCESS    read-write
    STATUS    mandatory
    DESCRIPTION
        "Upper Threshold Value in .1%"
    ::= { meaAnalogInputEntry1 4 }

meaAnalogueInputLowerThreshold1 OBJECT-TYPE
    SYNTAX    INTEGER ( 0..1000 )
    ACCESS    read-write
    STATUS    mandatory
    DESCRIPTION
        "Lower Threshold Value in .1%"
    ::= { meaAnalogInputEntry1 5 }

-- }}}
-- {{{ Entry 2

meaAnalogueInputName2 OBJECT-TYPE
    SYNTAX    DisplayString
    ACCESS    read-write
    STATUS    mandatory
    DESCRIPTION
        "Name of AnalogueInput"
    ::= { meaAnalogInputEntry2 1 }

meaAnalogueInputOffset2 OBJECT-TYPE
    SYNTAX    INTEGER ( 0..1000 )
    ACCESS    read-write
    STATUS    mandatory
    DESCRIPTION
        "Input Offset Value in .1%"
    ::= { meaAnalogInputEntry2 2 }

meaAnalogueInputValue2 OBJECT-TYPE
    SYNTAX    INTEGER ( 0..1000 )
    ACCESS    read-only
    STATUS    mandatory
    DESCRIPTION
        "Input Value in .1%"
    ::= { meaAnalogInputEntry2 3 }

meaAnalogueInputUpperThreshold2 OBJECT-TYPE
    SYNTAX    INTEGER ( 0..1000 )
    ACCESS    read-write
    STATUS    mandatory
    DESCRIPTION
        "Upper Threshold Value in .1%"
    ::= { meaAnalogInputEntry2 4 }

meaAnalogueInputLowerThreshold2 OBJECT-TYPE
    SYNTAX    INTEGER ( 0..1000 )
    ACCESS    read-write
    STATUS    mandatory
    DESCRIPTION
        "Lower Threshold Value in .1%"
    ::= { meaAnalogInputEntry2 5 }

-- }}}
-- {{{ Entry 3

meaAnalogueInputName3 OBJECT-TYPE
    SYNTAX    DisplayString
    ACCESS    read-write
    STATUS    mandatory
    DESCRIPTION
        "Name of AnalogueInput"
    ::= { meaAnalogInputEntry3 1 }

meaAnalogueInputOffset3 OBJECT-TYPE
    SYNTAX    INTEGER ( 0..1000 )
    ACCESS    read-write
    STATUS    mandatory
    DESCRIPTION
        "Input Offset Value in .1%"
    ::= { meaAnalogInputEntry3 2 }

meaAnalogueInputValue3 OBJECT-TYPE
    SYNTAX    INTEGER ( 0..1000 )
    ACCESS    read-only
    STATUS    mandatory
    DESCRIPTION
        "Input Value in .1%"
    ::= { meaAnalogInputEntry3 3 }

meaAnalogueInputUpperThreshold3 OBJECT-TYPE
    SYNTAX    INTEGER ( 0..1000 )
    ACCESS    read-write
    STATUS    mandatory
    DESCRIPTION
        "Upper Threshold Value in .1%"
    ::= { meaAnalogInputEntry3 4 }

meaAnalogueInputLowerThreshold3 OBJECT-TYPE
    SYNTAX    INTEGER ( 0..1000 )
    ACCESS    read-write
    STATUS    mandatory
    DESCRIPTION
        "Lower Threshold Value in .1%"
    ::= { meaAnalogInputEntry3 5 }

-- }}}
-- {{{ Entry 4

meaAnalogueInputName4 OBJECT-TYPE
    SYNTAX    DisplayString
    ACCESS    read-write
    STATUS    mandatory
    DESCRIPTION
        "Name of AnalogueInput"
    ::= { meaAnalogInputEntry4 1 }

meaAnalogueInputOffset4 OBJECT-TYPE
    SYNTAX    INTEGER ( 0..1000 )
    ACCESS    read-write
    STATUS    mandatory
    DESCRIPTION
        "Input Offset Value in .1%"
    ::= { meaAnalogInputEntry4 2 }

meaAnalogueInputValue4 OBJECT-TYPE
    SYNTAX    INTEGER ( 0..1000 )
    ACCESS    read-only
    STATUS    mandatory
    DESCRIPTION
        "Input Value in .1%"
    ::= { meaAnalogInputEntry4 3 }

meaAnalogueInputUpperThreshold4 OBJECT-TYPE
    SYNTAX    INTEGER ( 0..1000 )
    ACCESS    read-write
    STATUS    mandatory
    DESCRIPTION
        "Upper Threshold Value in .1%"
    ::= { meaAnalogInputEntry4 4 }

meaAnalogueInputLowerThreshold4 OBJECT-TYPE
    SYNTAX    INTEGER ( 0..1000 )
    ACCESS    read-write
    STATUS    mandatory
    DESCRIPTION
        "Lower Threshold Value in .1%"
    ::= { meaAnalogInputEntry4 5 }

-- }}}
-- {{{ Entry 5

meaAnalogueInputName5 OBJECT-TYPE
    SYNTAX    DisplayString
    ACCESS    read-write
    STATUS    mandatory
    DESCRIPTION
        "Name of AnalogueInput"
    ::= { meaAnalogInputEntry5 1 }

meaAnalogueInputOffset5 OBJECT-TYPE
    SYNTAX    INTEGER ( 0..1000 )
    ACCESS    read-write
    STATUS    mandatory
    DESCRIPTION
        "Input Offset Value in .1%"
    ::= { meaAnalogInputEntry5 2 }

meaAnalogueInputValue5 OBJECT-TYPE
    SYNTAX    INTEGER ( 0..1000 )
    ACCESS    read-only
    STATUS    mandatory
    DESCRIPTION
        "Input Value in .1%"
    ::= { meaAnalogInputEntry5 3 }

meaAnalogueInputUpperThreshold5 OBJECT-TYPE
    SYNTAX    INTEGER ( 0..1000 )
    ACCESS    read-write
    STATUS    mandatory
    DESCRIPTION
        "Upper Threshold Value in .1%"
    ::= { meaAnalogInputEntry5 4 }

meaAnalogueInputLowerThreshold5 OBJECT-TYPE
    SYNTAX    INTEGER ( 0..1000 )
    ACCESS    read-write
    STATUS    mandatory
    DESCRIPTION
        "Lower Threshold Value in .1%"
    ::= { meaAnalogInputEntry5 5 }

-- }}}
-- {{{ Entry 6

meaAnalogueInputName6 OBJECT-TYPE
    SYNTAX    DisplayString
    ACCESS    read-write
    STATUS    mandatory
    DESCRIPTION
        "Name of AnalogueInput"
    ::= { meaAnalogInputEntry6 1 }

meaAnalogueInputOffset6 OBJECT-TYPE
    SYNTAX    INTEGER ( 0..1000 )
    ACCESS    read-write
    STATUS    mandatory
    DESCRIPTION
        "Input Offset Value in .1%"
    ::= { meaAnalogInputEntry6 2 }

meaAnalogueInputValue6 OBJECT-TYPE
    SYNTAX    INTEGER ( 0..1000 )
    ACCESS    read-only
    STATUS    mandatory
    DESCRIPTION
        "Input Value in .1%"
    ::= { meaAnalogInputEntry6 3 }

meaAnalogueInputUpperThreshold6 OBJECT-TYPE
    SYNTAX    INTEGER ( 0..1000 )
    ACCESS    read-write
    STATUS    mandatory
    DESCRIPTION
        "Upper Threshold Value in .1%"
    ::= { meaAnalogInputEntry6 4 }

meaAnalogueInputLowerThreshold6 OBJECT-TYPE
    SYNTAX    INTEGER ( 0..1000 )
    ACCESS    read-write
    STATUS    mandatory
    DESCRIPTION
        "Lower Threshold Value in .1%"
    ::= { meaAnalogInputEntry6 5 }

-- }}}
-- {{{ Entry 7

meaAnalogueInputName7 OBJECT-TYPE
    SYNTAX    DisplayString
    ACCESS    read-write
    STATUS    mandatory
    DESCRIPTION
        "Name of AnalogueInput"
    ::= { meaAnalogInputEntry7 1 }

meaAnalogueInputOffset7 OBJECT-TYPE
    SYNTAX    INTEGER ( 0..1000 )
    ACCESS    read-write
    STATUS    mandatory
    DESCRIPTION
        "Input Offset Value in .1%"
    ::= { meaAnalogInputEntry7 2 }

meaAnalogueInputValue7 OBJECT-TYPE
    SYNTAX    INTEGER ( 0..1000 )
    ACCESS    read-only
    STATUS    mandatory
    DESCRIPTION
        "Input Value in .1%"
    ::= { meaAnalogInputEntry7 3 }

meaAnalogueInputUpperThreshold7 OBJECT-TYPE
    SYNTAX    INTEGER ( 0..1000 )
    ACCESS    read-write
    STATUS    mandatory
    DESCRIPTION
        "Upper Threshold Value in .1%"
    ::= { meaAnalogInputEntry7 4 }

meaAnalogueInputLowerThreshold7 OBJECT-TYPE
    SYNTAX    INTEGER ( 0..1000 )
    ACCESS    read-write
    STATUS    mandatory
    DESCRIPTION
        "Lower Threshold Value in .1%"
    ::= { meaAnalogInputEntry7 5 }

-- }}}
-- {{{ Entry 8

meaAnalogueInputName8 OBJECT-TYPE
    SYNTAX    DisplayString
    ACCESS    read-write
    STATUS    mandatory
    DESCRIPTION
        "Name of AnalogueInput"
    ::= { meaAnalogInputEntry8 1 }

meaAnalogueInputOffset8 OBJECT-TYPE
    SYNTAX    INTEGER ( 0..1000 )
    ACCESS    read-write
    STATUS    mandatory
    DESCRIPTION
        "Input Offset Value in .1%"
    ::= { meaAnalogInputEntry8 2 }

meaAnalogueInputValue8 OBJECT-TYPE
    SYNTAX    INTEGER ( 0..1000 )
    ACCESS    read-only
    STATUS    mandatory
    DESCRIPTION
        "Input Value in .1%"
    ::= { meaAnalogInputEntry8 3 }

meaAnalogueInputUpperThreshold8 OBJECT-TYPE
    SYNTAX    INTEGER ( 0..1000 )
    ACCESS    read-write
    STATUS    mandatory
    DESCRIPTION
        "Upper Threshold Value in .1%"
    ::= { meaAnalogInputEntry8 4 }

meaAnalogueInputLowerThreshold8 OBJECT-TYPE
    SYNTAX    INTEGER ( 0..1000 )
    ACCESS    read-write
    STATUS    mandatory
    DESCRIPTION
        "Lower Threshold Value in .1%"
    ::= { meaAnalogInputEntry8 5 }

-- }}}
-- {{{ Entry 9

meaAnalogueInputName9 OBJECT-TYPE
    SYNTAX    DisplayString
    ACCESS    read-write
    STATUS    mandatory
    DESCRIPTION
        "Name of AnalogueInput"
    ::= { meaAnalogInputEntry9 1 }

meaAnalogueInputOffset9 OBJECT-TYPE
    SYNTAX    INTEGER ( 0..1000 )
    ACCESS    read-write
    STATUS    mandatory
    DESCRIPTION
        "Input Offset Value in .1%"
    ::= { meaAnalogInputEntry9 2 }

meaAnalogueInputValue9 OBJECT-TYPE
    SYNTAX    INTEGER ( 0..1000 )
    ACCESS    read-only
    STATUS    mandatory
    DESCRIPTION
        "Input Value in .1%"
    ::= { meaAnalogInputEntry9 3 }

meaAnalogueInputUpperThreshold9 OBJECT-TYPE
    SYNTAX    INTEGER ( 0..1000 )
    ACCESS    read-write
    STATUS    mandatory
    DESCRIPTION
        "Upper Threshold Value in .1%"
    ::= { meaAnalogInputEntry9 4 }

meaAnalogueInputLowerThreshold9 OBJECT-TYPE
    SYNTAX    INTEGER ( 0..1000 )
    ACCESS    read-write
    STATUS    mandatory
    DESCRIPTION
        "Lower Threshold Value in .1%"
    ::= { meaAnalogInputEntry9 5 }

-- }}}
-- {{{ Entry 10

meaAnalogueInputName10 OBJECT-TYPE
    SYNTAX    DisplayString
    ACCESS    read-write
    STATUS    mandatory
    DESCRIPTION
        "Name of AnalogueInput"
    ::= { meaAnalogInputEntry10 1 }

meaAnalogueInputOffset10 OBJECT-TYPE
    SYNTAX    INTEGER ( 0..1000 )
    ACCESS    read-write
    STATUS    mandatory
    DESCRIPTION
        "Input Offset Value in .1%"
    ::= { meaAnalogInputEntry10 2 }

meaAnalogueInputValue10 OBJECT-TYPE
    SYNTAX    INTEGER ( 0..1000 )
    ACCESS    read-only
    STATUS    mandatory
    DESCRIPTION
        "Input Value in .1%"
    ::= { meaAnalogInputEntry10 3 }

meaAnalogueInputUpperThreshold10 OBJECT-TYPE
    SYNTAX    INTEGER ( 0..1000 )
    ACCESS    read-write
    STATUS    mandatory
    DESCRIPTION
        "Upper Threshold Value in .1%"
    ::= { meaAnalogInputEntry10 4 }

meaAnalogueInputLowerThreshold10 OBJECT-TYPE
    SYNTAX    INTEGER ( 0..1000 )
    ACCESS    read-write
    STATUS    mandatory
    DESCRIPTION
        "Lower Threshold Value in .1%"
    ::= { meaAnalogInputEntry10 5 }

-- }}}
-- {{{ Entry 11

meaAnalogueInputName11 OBJECT-TYPE
    SYNTAX    DisplayString
    ACCESS    read-write
    STATUS    mandatory
    DESCRIPTION
        "Name of AnalogueInput"
    ::= { meaAnalogInputEntry11 1 }

meaAnalogueInputOffset11 OBJECT-TYPE
    SYNTAX    INTEGER ( 0..1000 )
    ACCESS    read-write
    STATUS    mandatory
    DESCRIPTION
        "Input Offset Value in .1%"
    ::= { meaAnalogInputEntry11 2 }

meaAnalogueInputValue11 OBJECT-TYPE
    SYNTAX    INTEGER ( 0..1000 )
    ACCESS    read-only
    STATUS    mandatory
    DESCRIPTION
        "Input Value in .1%"
    ::= { meaAnalogInputEntry11 3 }

meaAnalogueInputUpperThreshold11 OBJECT-TYPE
    SYNTAX    INTEGER ( 0..1000 )
    ACCESS    read-write
    STATUS    mandatory
    DESCRIPTION
        "Upper Threshold Value in .1%"
    ::= { meaAnalogInputEntry11 4 }

meaAnalogueInputLowerThreshold11 OBJECT-TYPE
    SYNTAX    INTEGER ( 0..1000 )
    ACCESS    read-write
    STATUS    mandatory
    DESCRIPTION
        "Lower Threshold Value in .1%"
    ::= { meaAnalogInputEntry11 5 }

-- }}}
-- {{{ Entry 12

meaAnalogueInputName12 OBJECT-TYPE
    SYNTAX    DisplayString
    ACCESS    read-write
    STATUS    mandatory
    DESCRIPTION
        "Name of AnalogueInput"
    ::= { meaAnalogInputEntry12 1 }

meaAnalogueInputOffset12 OBJECT-TYPE
    SYNTAX    INTEGER ( 0..1000 )
    ACCESS    read-write
    STATUS    mandatory
    DESCRIPTION
        "Input Offset Value in .1%"
    ::= { meaAnalogInputEntry12 2 }

meaAnalogueInputValue12 OBJECT-TYPE
    SYNTAX    INTEGER ( 0..1000 )
    ACCESS    read-only
    STATUS    mandatory
    DESCRIPTION
        "Input Value in .1%"
    ::= { meaAnalogInputEntry12 3 }

meaAnalogueInputUpperThreshold12 OBJECT-TYPE
    SYNTAX    INTEGER ( 0..1000 )
    ACCESS    read-write
    STATUS    mandatory
    DESCRIPTION
        "Upper Threshold Value in .1%"
    ::= { meaAnalogInputEntry12 4 }

meaAnalogueInputLowerThreshold12 OBJECT-TYPE
    SYNTAX    INTEGER ( 0..1000 )
    ACCESS    read-write
    STATUS    mandatory
    DESCRIPTION
        "Lower Threshold Value in .1%"
    ::= { meaAnalogInputEntry12 5 }

-- }}}
-- {{{ Entry 13

meaAnalogueInputName13 OBJECT-TYPE
    SYNTAX    DisplayString
    ACCESS    read-write
    STATUS    mandatory
    DESCRIPTION
        "Name of AnalogueInput"
    ::= { meaAnalogInputEntry13 1 }

meaAnalogueInputOffset13 OBJECT-TYPE
    SYNTAX    INTEGER ( 0..1000 )
    ACCESS    read-write
    STATUS    mandatory
    DESCRIPTION
        "Input Offset Value in .1%"
    ::= { meaAnalogInputEntry13 2 }

meaAnalogueInputValue13 OBJECT-TYPE
    SYNTAX    INTEGER ( 0..1000 )
    ACCESS    read-only
    STATUS    mandatory
    DESCRIPTION
        "Input Value in .1%"
    ::= { meaAnalogInputEntry13 3 }

meaAnalogueInputUpperThreshold13 OBJECT-TYPE
    SYNTAX    INTEGER ( 0..1000 )
    ACCESS    read-write
    STATUS    mandatory
    DESCRIPTION
        "Upper Threshold Value in .1%"
    ::= { meaAnalogInputEntry13 4 }

meaAnalogueInputLowerThreshold13 OBJECT-TYPE
    SYNTAX    INTEGER ( 0..1000 )
    ACCESS    read-write
    STATUS    mandatory
    DESCRIPTION
        "Lower Threshold Value in .1%"
    ::= { meaAnalogInputEntry13 5 }

-- }}}
-- {{{ Entry 14

meaAnalogueInputName14 OBJECT-TYPE
    SYNTAX    DisplayString
    ACCESS    read-write
    STATUS    mandatory
    DESCRIPTION
        "Name of AnalogueInput"
    ::= { meaAnalogInputEntry14 1 }

meaAnalogueInputOffset14 OBJECT-TYPE
    SYNTAX    INTEGER ( 0..1000 )
    ACCESS    read-write
    STATUS    mandatory
    DESCRIPTION
        "Input Offset Value in .1%"
    ::= { meaAnalogInputEntry14 2 }

meaAnalogueInputValue14 OBJECT-TYPE
    SYNTAX    INTEGER ( 0..1000 )
    ACCESS    read-only
    STATUS    mandatory
    DESCRIPTION
        "Input Value in .1%"
    ::= { meaAnalogInputEntry14 3 }

meaAnalogueInputUpperThreshold14 OBJECT-TYPE
    SYNTAX    INTEGER ( 0..1000 )
    ACCESS    read-write
    STATUS    mandatory
    DESCRIPTION
        "Upper Threshold Value in .1%"
    ::= { meaAnalogInputEntry14 4 }

meaAnalogueInputLowerThreshold14 OBJECT-TYPE
    SYNTAX    INTEGER ( 0..1000 )
    ACCESS    read-write
    STATUS    mandatory
    DESCRIPTION
        "Lower Threshold Value in .1%"
    ::= { meaAnalogInputEntry14 5 }

-- }}}
-- {{{ Entry 15

meaAnalogueInputName15 OBJECT-TYPE
    SYNTAX    DisplayString
    ACCESS    read-write
    STATUS    mandatory
    DESCRIPTION
        "Name of AnalogueInput"
    ::= { meaAnalogInputEntry15 1 }

meaAnalogueInputOffset15 OBJECT-TYPE
    SYNTAX    INTEGER ( 0..1000 )
    ACCESS    read-write
    STATUS    mandatory
    DESCRIPTION
        "Input Offset Value in .1%"
    ::= { meaAnalogInputEntry15 2 }

meaAnalogueInputValue15 OBJECT-TYPE
    SYNTAX    INTEGER ( 0..1000 )
    ACCESS    read-only
    STATUS    mandatory
    DESCRIPTION
        "Input Value in .1%"
    ::= { meaAnalogInputEntry15 3 }

meaAnalogueInputUpperThreshold15 OBJECT-TYPE
    SYNTAX    INTEGER ( 0..1000 )
    ACCESS    read-write
    STATUS    mandatory
    DESCRIPTION
        "Upper Threshold Value in .1%"
    ::= { meaAnalogInputEntry15 4 }

meaAnalogueInputLowerThreshold15 OBJECT-TYPE
    SYNTAX    INTEGER ( 0..1000 )
    ACCESS    read-write
    STATUS    mandatory
    DESCRIPTION
        "Lower Threshold Value in .1%"
    ::= { meaAnalogInputEntry15 5 }

-- }}}
-- {{{ Entry 16

meaAnalogueInputName16 OBJECT-TYPE
    SYNTAX    DisplayString
    ACCESS    read-write
    STATUS    mandatory
    DESCRIPTION
        "Name of AnalogueInput"
    ::= { meaAnalogInputEntry16 1 }

meaAnalogueInputOffset16 OBJECT-TYPE
    SYNTAX    INTEGER ( 0..1000 )
    ACCESS    read-write
    STATUS    mandatory
    DESCRIPTION
        "Input Offset Value in .1%"
    ::= { meaAnalogInputEntry16 2 }

meaAnalogueInputValue16 OBJECT-TYPE
    SYNTAX    INTEGER ( 0..1000 )
    ACCESS    read-only
    STATUS    mandatory
    DESCRIPTION
        "Input Value in .1%"
    ::= { meaAnalogInputEntry16 3 }

meaAnalogueInputUpperThreshold16 OBJECT-TYPE
    SYNTAX    INTEGER ( 0..1000 )
    ACCESS    read-write
    STATUS    mandatory
    DESCRIPTION
        "Upper Threshold Value in .1%"
    ::= { meaAnalogInputEntry16 4 }

meaAnalogueInputLowerThreshold16 OBJECT-TYPE
    SYNTAX    INTEGER ( 0..1000 )
    ACCESS    read-write
    STATUS    mandatory
    DESCRIPTION
        "Lower Threshold Value in .1%"
    ::= { meaAnalogInputEntry16 5 }

-- }}}

-- }}}

-- }}}
-- {{{ meaAnalogOutput group   

meaAnalogOutputTable OBJECT IDENTIFIER ::= { meaAnalogOutput 1 }

-- {{{ meaAnalogOutputTable  

meaAnalogOutputEntry1  OBJECT IDENTIFIER ::= { meaAnalogOutputTable 1  }
meaAnalogOutputEntry2  OBJECT IDENTIFIER ::= { meaAnalogOutputTable 2  }
meaAnalogOutputEntry3  OBJECT IDENTIFIER ::= { meaAnalogOutputTable 3  }
meaAnalogOutputEntry4  OBJECT IDENTIFIER ::= { meaAnalogOutputTable 4  }
meaAnalogOutputEntry5  OBJECT IDENTIFIER ::= { meaAnalogOutputTable 5  }
meaAnalogOutputEntry6  OBJECT IDENTIFIER ::= { meaAnalogOutputTable 6  }
meaAnalogOutputEntry7  OBJECT IDENTIFIER ::= { meaAnalogOutputTable 7  }
meaAnalogOutputEntry8  OBJECT IDENTIFIER ::= { meaAnalogOutputTable 8  }
meaAnalogOutputEntry9  OBJECT IDENTIFIER ::= { meaAnalogOutputTable 9  }
meaAnalogOutputEntry10 OBJECT IDENTIFIER ::= { meaAnalogOutputTable 10 }
meaAnalogOutputEntry11 OBJECT IDENTIFIER ::= { meaAnalogOutputTable 11 }
meaAnalogOutputEntry12 OBJECT IDENTIFIER ::= { meaAnalogOutputTable 12 }
meaAnalogOutputEntry13 OBJECT IDENTIFIER ::= { meaAnalogOutputTable 13 }
meaAnalogOutputEntry14 OBJECT IDENTIFIER ::= { meaAnalogOutputTable 14 }
meaAnalogOutputEntry15 OBJECT IDENTIFIER ::= { meaAnalogOutputTable 15 }
meaAnalogOutputEntry16 OBJECT IDENTIFIER ::= { meaAnalogOutputTable 16 }

-- meaAnalogOutputEntries
-- {{{ Entry 1

meaAnalogueOutputName1 OBJECT-TYPE
    SYNTAX    DisplayString
    ACCESS    read-write
    STATUS    mandatory
    DESCRIPTION
        "Name of Analogue Output 1"
    ::= { meaAnalogOutputEntry1 1 }

meaAnalogueOutputVoltage1 OBJECT-TYPE
    SYNTAX    INTEGER ( 0..1000 )
    ACCESS    read-write
    STATUS    mandatory
    DESCRIPTION
        "Actual analog output value in 0.1 percent of full scale"
    ::= { meaAnalogOutputEntry1 2 }

-- }}}
-- {{{ Entry 2

meaAnalogueOutputName2 OBJECT-TYPE
    SYNTAX    DisplayString
    ACCESS    read-write
    STATUS    mandatory
    DESCRIPTION
        "Name of Analogue Output 2"
    ::= { meaAnalogOutputEntry2 1 }

meaAnalogueOutputVoltage2 OBJECT-TYPE
    SYNTAX    INTEGER ( 0..1000 )
    ACCESS    read-write
    STATUS    mandatory
    DESCRIPTION
        "Actual analog output value in 0.1 percent of full scale"
    ::= { meaAnalogOutputEntry2 2 }

-- }}}
-- {{{ Entry 3

meaAnalogueOutputName3 OBJECT-TYPE
    SYNTAX    DisplayString
    ACCESS    read-write
    STATUS    mandatory
    DESCRIPTION
        "Name of Analogue Output 3"
    ::= { meaAnalogOutputEntry3 1 }

meaAnalogueOutputVoltage3 OBJECT-TYPE
    SYNTAX    INTEGER ( 0..1000 )
    ACCESS    read-write
    STATUS    mandatory
    DESCRIPTION
        "Actual analog output value in 0.1 percent of full scale"
    ::= { meaAnalogOutputEntry3 2 }

-- }}}
-- {{{ Entry 4

meaAnalogueOutputName4 OBJECT-TYPE
    SYNTAX    DisplayString
    ACCESS    read-write
    STATUS    mandatory
    DESCRIPTION
        "Name of Analogue Output 4"
    ::= { meaAnalogOutputEntry4 1 }

meaAnalogueOutputVoltage4 OBJECT-TYPE
    SYNTAX    INTEGER ( 0..1000 )
    ACCESS    read-write
    STATUS    mandatory
    DESCRIPTION
        "Actual analog output value in 0.1 percent of full scale"
    ::= { meaAnalogOutputEntry4 2 }

-- }}}
-- {{{ Entry 5

meaAnalogueOutputName5 OBJECT-TYPE
    SYNTAX    DisplayString
    ACCESS    read-write
    STATUS    mandatory
    DESCRIPTION
        "Name of Analogue Output 5"
    ::= { meaAnalogOutputEntry5 1 }

meaAnalogueOutputVoltage5 OBJECT-TYPE
    SYNTAX    INTEGER ( 0..1000 )
    ACCESS    read-write
    STATUS    mandatory
    DESCRIPTION
        "Actual analog output value in 0.1 percent of full scale"
    ::= { meaAnalogOutputEntry5 2 }

-- }}}
-- {{{ Entry 6

meaAnalogueOutputName6 OBJECT-TYPE
    SYNTAX    DisplayString
    ACCESS    read-write
    STATUS    mandatory
    DESCRIPTION
        "Name of Analogue Output 6"
    ::= { meaAnalogOutputEntry6 1 }

meaAnalogueOutputVoltage6 OBJECT-TYPE
    SYNTAX    INTEGER ( 0..1000 )
    ACCESS    read-write
    STATUS    mandatory
    DESCRIPTION
        "Actual analog output value in 0.1 percent of full scale"
    ::= { meaAnalogOutputEntry6 2 }

-- }}}
-- {{{ Entry 7

meaAnalogueOutputName7 OBJECT-TYPE
    SYNTAX    DisplayString
    ACCESS    read-write
    STATUS    mandatory
    DESCRIPTION
        "Name of Analogue Output 7"
    ::= { meaAnalogOutputEntry7 1 }

meaAnalogueOutputVoltage7 OBJECT-TYPE
    SYNTAX    INTEGER ( 0..1000 )
    ACCESS    read-write
    STATUS    mandatory
    DESCRIPTION
        "Actual analog output value in 0.1 percent of full scale"
    ::= { meaAnalogOutputEntry7 2 }

-- }}}
-- {{{ Entry 8

meaAnalogueOutputName8 OBJECT-TYPE
    SYNTAX    DisplayString
    ACCESS    read-write
    STATUS    mandatory
    DESCRIPTION
        "Name of Analogue Output 8"
    ::= { meaAnalogOutputEntry8 1 }

meaAnalogueOutputVoltage8 OBJECT-TYPE
    SYNTAX    INTEGER ( 0..1000 )
    ACCESS    read-write
    STATUS    mandatory
    DESCRIPTION
        "Actual analog output value in 0.1 percent of full scale"
    ::= { meaAnalogOutputEntry8 2 }

-- }}}
-- {{{ Entry 9

meaAnalogueOutputName9 OBJECT-TYPE
    SYNTAX    DisplayString
    ACCESS    read-write
    STATUS    mandatory
    DESCRIPTION
        "Name of Analogue Output 9"
    ::= { meaAnalogOutputEntry9 1 }

meaAnalogueOutputVoltage9 OBJECT-TYPE
    SYNTAX    INTEGER ( 0..1000 )
    ACCESS    read-write
    STATUS    mandatory
    DESCRIPTION
        "Actual analog output value in 0.1 percent of full scale"
    ::= { meaAnalogOutputEntry9 2 }

-- }}}
-- {{{ Entry 10

meaAnalogueOutputName10 OBJECT-TYPE
    SYNTAX    DisplayString
    ACCESS    read-write
    STATUS    mandatory
    DESCRIPTION
        "Name of Analogue Output 10"
    ::= { meaAnalogOutputEntry10 1 }

meaAnalogueOutputVoltage10 OBJECT-TYPE
    SYNTAX    INTEGER ( 0..1000 )
    ACCESS    read-write
    STATUS    mandatory
    DESCRIPTION
        "Actual analog output value in 0.1 percent of full scale"
    ::= { meaAnalogOutputEntry10 2 }

-- }}}
-- {{{ Entry 11

meaAnalogueOutputName11 OBJECT-TYPE
    SYNTAX    DisplayString
    ACCESS    read-write
    STATUS    mandatory
    DESCRIPTION
        "Name of Analogue Output 11"
    ::= { meaAnalogOutputEntry11 1 }

meaAnalogueOutputVoltage11 OBJECT-TYPE
    SYNTAX    INTEGER ( 0..1000 )
    ACCESS    read-write
    STATUS    mandatory
    DESCRIPTION
        "Actual analog output value in 0.1 percent of full scale"
    ::= { meaAnalogOutputEntry11 2 }

-- }}}
-- {{{ Entry 12

meaAnalogueOutputName12 OBJECT-TYPE
    SYNTAX    DisplayString
    ACCESS    read-write
    STATUS    mandatory
    DESCRIPTION
        "Name of Analogue Output 12"
    ::= { meaAnalogOutputEntry12 1 }

meaAnalogueOutputVoltage12 OBJECT-TYPE
    SYNTAX    INTEGER ( 0..1000 )
    ACCESS    read-write
    STATUS    mandatory
    DESCRIPTION
        "Actual analog output value in 0.1 percent of full scale"
    ::= { meaAnalogOutputEntry12 2 }

-- }}}
-- {{{ Entry 13

meaAnalogueOutputName13 OBJECT-TYPE
    SYNTAX    DisplayString
    ACCESS    read-write
    STATUS    mandatory
    DESCRIPTION
        "Name of Analogue Output 13"
    ::= { meaAnalogOutputEntry13 1 }

meaAnalogueOutputVoltage13 OBJECT-TYPE
    SYNTAX    INTEGER ( 0..1000 )
    ACCESS    read-write
    STATUS    mandatory
    DESCRIPTION
        "Actual analog output value in 0.1 percent of full scale"
    ::= { meaAnalogOutputEntry13 2 }

-- }}}
-- {{{ Entry 14

meaAnalogueOutputName14 OBJECT-TYPE
    SYNTAX    DisplayString
    ACCESS    read-write
    STATUS    mandatory
    DESCRIPTION
        "Name of Analogue Output 14"
    ::= { meaAnalogOutputEntry14 1 }

meaAnalogueOutputVoltage14 OBJECT-TYPE
    SYNTAX    INTEGER ( 0..1000 )
    ACCESS    read-write
    STATUS    mandatory
    DESCRIPTION
        "Actual analog output value in 0.1 percent of full scale"
    ::= { meaAnalogOutputEntry14 2 }

-- }}}
-- {{{ Entry 15

meaAnalogueOutputName15 OBJECT-TYPE
    SYNTAX    DisplayString
    ACCESS    read-write
    STATUS    mandatory
    DESCRIPTION
        "Name of Analogue Output 15"
    ::= { meaAnalogOutputEntry15 1 }

meaAnalogueOutputVoltage15 OBJECT-TYPE
    SYNTAX    INTEGER ( 0..1000 )
    ACCESS    read-write
    STATUS    mandatory
    DESCRIPTION
        "Actual analog output value in 0.1 percent of full scale"
    ::= { meaAnalogOutputEntry15 2 }

-- }}}
-- {{{ Entry 16

meaAnalogueOutputName16 OBJECT-TYPE
    SYNTAX    DisplayString
    ACCESS    read-write
    STATUS    mandatory
    DESCRIPTION
        "Name of Analogue Output 16"
    ::= { meaAnalogOutputEntry16 1 }

meaAnalogueOutputVoltage16 OBJECT-TYPE
    SYNTAX    INTEGER ( 0..1000 )
    ACCESS    read-write
    STATUS    mandatory
    DESCRIPTION
        "Actual analog output value in 0.1 percent of full scale"
    ::= { meaAnalogOutputEntry16 2 }

-- }}}

-- }}}

-- }}}
-- {{{ meaContact              

-- }}}
-- {{{ meaAlarm                

meaDigitalInputAlarmTable   OBJECT IDENTIFIER ::= { meaAlarm 1 }
meaAnalogInputAlarmTable    OBJECT IDENTIFIER ::= { meaAlarm 2 }
meaDigitalOutputAlarmTable  OBJECT IDENTIFIER ::= { meaAlarm 3 }

-- {{{ meaDigitalInputAlarmTable  

meaDigitalInputAlarmEntry1  OBJECT IDENTIFIER ::= { meaDigitalInputAlarmTable 1  }
meaDigitalInputAlarmEntry2  OBJECT IDENTIFIER ::= { meaDigitalInputAlarmTable 2  }
meaDigitalInputAlarmEntry3  OBJECT IDENTIFIER ::= { meaDigitalInputAlarmTable 3  }
meaDigitalInputAlarmEntry4  OBJECT IDENTIFIER ::= { meaDigitalInputAlarmTable 4  }
meaDigitalInputAlarmEntry5  OBJECT IDENTIFIER ::= { meaDigitalInputAlarmTable 5  }
meaDigitalInputAlarmEntry6  OBJECT IDENTIFIER ::= { meaDigitalInputAlarmTable 6  }
meaDigitalInputAlarmEntry7  OBJECT IDENTIFIER ::= { meaDigitalInputAlarmTable 7  }
meaDigitalInputAlarmEntry8  OBJECT IDENTIFIER ::= { meaDigitalInputAlarmTable 8  }
meaDigitalInputAlarmEntry9  OBJECT IDENTIFIER ::= { meaDigitalInputAlarmTable 9  }
meaDigitalInputAlarmEntry10 OBJECT IDENTIFIER ::= { meaDigitalInputAlarmTable 10 }
meaDigitalInputAlarmEntry11 OBJECT IDENTIFIER ::= { meaDigitalInputAlarmTable 11 }
meaDigitalInputAlarmEntry12 OBJECT IDENTIFIER ::= { meaDigitalInputAlarmTable 12 }
meaDigitalInputAlarmEntry13 OBJECT IDENTIFIER ::= { meaDigitalInputAlarmTable 13 }
meaDigitalInputAlarmEntry14 OBJECT IDENTIFIER ::= { meaDigitalInputAlarmTable 14 }
meaDigitalInputAlarmEntry15 OBJECT IDENTIFIER ::= { meaDigitalInputAlarmTable 15 }
meaDigitalInputAlarmEntry16 OBJECT IDENTIFIER ::= { meaDigitalInputAlarmTable 16 }
meaDigitalInputAlarmEntry17 OBJECT IDENTIFIER ::= { meaDigitalInputAlarmTable 17 }
meaDigitalInputAlarmEntry18 OBJECT IDENTIFIER ::= { meaDigitalInputAlarmTable 18 }
meaDigitalInputAlarmEntry19 OBJECT IDENTIFIER ::= { meaDigitalInputAlarmTable 19 }
meaDigitalInputAlarmEntry20 OBJECT IDENTIFIER ::= { meaDigitalInputAlarmTable 20 }
meaDigitalInputAlarmEntry21 OBJECT IDENTIFIER ::= { meaDigitalInputAlarmTable 21 }
meaDigitalInputAlarmEntry22 OBJECT IDENTIFIER ::= { meaDigitalInputAlarmTable 22 }
meaDigitalInputAlarmEntry23 OBJECT IDENTIFIER ::= { meaDigitalInputAlarmTable 23 }
meaDigitalInputAlarmEntry24 OBJECT IDENTIFIER ::= { meaDigitalInputAlarmTable 24 }
meaDigitalInputAlarmEntry25 OBJECT IDENTIFIER ::= { meaDigitalInputAlarmTable 25 }
meaDigitalInputAlarmEntry26 OBJECT IDENTIFIER ::= { meaDigitalInputAlarmTable 26 }
meaDigitalInputAlarmEntry27 OBJECT IDENTIFIER ::= { meaDigitalInputAlarmTable 27 }
meaDigitalInputAlarmEntry28 OBJECT IDENTIFIER ::= { meaDigitalInputAlarmTable 28 }
meaDigitalInputAlarmEntry29 OBJECT IDENTIFIER ::= { meaDigitalInputAlarmTable 29 }
meaDigitalInputAlarmEntry30 OBJECT IDENTIFIER ::= { meaDigitalInputAlarmTable 30 }
meaDigitalInputAlarmEntry31 OBJECT IDENTIFIER ::= { meaDigitalInputAlarmTable 31 }
meaDigitalInputAlarmEntry32 OBJECT IDENTIFIER ::= { meaDigitalInputAlarmTable 32 }

-- meaDigitalInputAlarmEntries
-- {{{ Entry 1

meaDigitalInputAlarmEnable1 OBJECT-TYPE
    SYNTAX    INTEGER (0..1)
    ACCESS    read-write
    STATUS    mandatory
    DESCRIPTION
        "0=Disable Alarm 1=Enable Alarm"
    ::= { meaDigitalInputAlarmEntry1 1 }

meaDigitalInputAlarmStatus1 OBJECT-TYPE
    SYNTAX    INTEGER (0..1)
    ACCESS    read-only
    STATUS    mandatory
    DESCRIPTION
        "0=No Alarm 1=Alarm"
    ::= { meaDigitalInputAlarmEntry1 2 }

-- }}}
-- {{{ Entry 2

meaDigitalInputAlarmEnable2 OBJECT-TYPE
    SYNTAX    INTEGER (0..1)
    ACCESS    read-write
    STATUS    mandatory
    DESCRIPTION
        "0=Disable Alarm 1=Enable Alarm"
    ::= { meaDigitalInputAlarmEntry2 1 }

meaDigitalInputAlarmStatus2 OBJECT-TYPE
    SYNTAX    INTEGER (0..1)
    ACCESS    read-only
    STATUS    mandatory
    DESCRIPTION
        "0=No Alarm 1=Alarm"
    ::= { meaDigitalInputAlarmEntry2 2 }

-- }}}
-- {{{ Entry 3

meaDigitalInputAlarmEnable3 OBJECT-TYPE
    SYNTAX    INTEGER (0..1)
    ACCESS    read-write
    STATUS    mandatory
    DESCRIPTION
        "0=Disable Alarm 1=Enable Alarm"
    ::= { meaDigitalInputAlarmEntry3 1 }

meaDigitalInputAlarmStatus3 OBJECT-TYPE
    SYNTAX    INTEGER (0..1)
    ACCESS    read-only
    STATUS    mandatory
    DESCRIPTION
        "0=No Alarm 1=Alarm"
    ::= { meaDigitalInputAlarmEntry3 2 }

-- }}}
-- {{{ Entry 4

meaDigitalInputAlarmEnable4 OBJECT-TYPE
    SYNTAX    INTEGER (0..1)
    ACCESS    read-write
    STATUS    mandatory
    DESCRIPTION
        "0=Disable Alarm 1=Enable Alarm"
    ::= { meaDigitalInputAlarmEntry4 1 }

meaDigitalInputAlarmStatus4 OBJECT-TYPE
    SYNTAX    INTEGER (0..1)
    ACCESS    read-only
    STATUS    mandatory
    DESCRIPTION
        "0=No Alarm 1=Alarm"
    ::= { meaDigitalInputAlarmEntry4 2 }

-- }}}
-- {{{ Entry 5

meaDigitalInputAlarmEnable5 OBJECT-TYPE
    SYNTAX    INTEGER (0..1)
    ACCESS    read-write
    STATUS    mandatory
    DESCRIPTION
        "0=Disable Alarm 1=Enable Alarm"
    ::= { meaDigitalInputAlarmEntry5 1 }

meaDigitalInputAlarmStatus5 OBJECT-TYPE
    SYNTAX    INTEGER (0..1)
    ACCESS    read-only
    STATUS    mandatory
    DESCRIPTION
        "0=No Alarm 1=Alarm"
    ::= { meaDigitalInputAlarmEntry5 2 }

-- }}}
-- {{{ Entry 6

meaDigitalInputAlarmEnable6 OBJECT-TYPE
    SYNTAX    INTEGER (0..1)
    ACCESS    read-write
    STATUS    mandatory
    DESCRIPTION
        "0=Disable Alarm 1=Enable Alarm"
    ::= { meaDigitalInputAlarmEntry6 1 }

meaDigitalInputAlarmStatus6 OBJECT-TYPE
    SYNTAX    INTEGER (0..1)
    ACCESS    read-only
    STATUS    mandatory
    DESCRIPTION
        "0=No Alarm 1=Alarm"
    ::= { meaDigitalInputAlarmEntry6 2 }

-- }}}
-- {{{ Entry 7

meaDigitalInputAlarmEnable7 OBJECT-TYPE
    SYNTAX    INTEGER (0..1)
    ACCESS    read-write
    STATUS    mandatory
    DESCRIPTION
        "0=Disable Alarm 1=Enable Alarm"
    ::= { meaDigitalInputAlarmEntry7 1 }

meaDigitalInputAlarmStatus7 OBJECT-TYPE
    SYNTAX    INTEGER (0..1)
    ACCESS    read-only
    STATUS    mandatory
    DESCRIPTION
        "0=No Alarm 1=Alarm"
    ::= { meaDigitalInputAlarmEntry7 2 }

-- }}}
-- {{{ Entry 8

meaDigitalInputAlarmEnable8 OBJECT-TYPE
    SYNTAX    INTEGER (0..1)
    ACCESS    read-write
    STATUS    mandatory
    DESCRIPTION
        "0=Disable Alarm 1=Enable Alarm"
    ::= { meaDigitalInputAlarmEntry8 1 }

meaDigitalInputAlarmStatus8 OBJECT-TYPE
    SYNTAX    INTEGER (0..1)
    ACCESS    read-only
    STATUS    mandatory
    DESCRIPTION
        "0=No Alarm 1=Alarm"
    ::= { meaDigitalInputAlarmEntry8 2 }

-- }}}
-- {{{ Entry 9

meaDigitalInputAlarmEnable9 OBJECT-TYPE
    SYNTAX    INTEGER (0..1)
    ACCESS    read-write
    STATUS    mandatory
    DESCRIPTION
        "0=Disable Alarm 1=Enable Alarm"
    ::= { meaDigitalInputAlarmEntry9 1 }

meaDigitalInputAlarmStatus9 OBJECT-TYPE
    SYNTAX    INTEGER (0..1)
    ACCESS    read-only
    STATUS    mandatory
    DESCRIPTION
        "0=No Alarm 1=Alarm"
    ::= { meaDigitalInputAlarmEntry9 2 }

-- }}}
-- {{{ Entry 10

meaDigitalInputAlarmEnable10 OBJECT-TYPE
    SYNTAX    INTEGER (0..1)
    ACCESS    read-write
    STATUS    mandatory
    DESCRIPTION
        "0=Disable Alarm 1=Enable Alarm"
    ::= { meaDigitalInputAlarmEntry10 1 }

meaDigitalInputAlarmStatus10 OBJECT-TYPE
    SYNTAX    INTEGER (0..1)
    ACCESS    read-only
    STATUS    mandatory
    DESCRIPTION
        "0=No Alarm 1=Alarm"
    ::= { meaDigitalInputAlarmEntry10 2 }

-- }}}
-- {{{ Entry 11

meaDigitalInputAlarmEnable11 OBJECT-TYPE
    SYNTAX    INTEGER (0..1)
    ACCESS    read-write
    STATUS    mandatory
    DESCRIPTION
        "0=Disable Alarm 1=Enable Alarm"
    ::= { meaDigitalInputAlarmEntry11 1 }

meaDigitalInputAlarmStatus11 OBJECT-TYPE
    SYNTAX    INTEGER (0..1)
    ACCESS    read-only
    STATUS    mandatory
    DESCRIPTION
        "0=No Alarm 1=Alarm"
    ::= { meaDigitalInputAlarmEntry11 2 }

-- }}}
-- {{{ Entry 12

meaDigitalInputAlarmEnable12 OBJECT-TYPE
    SYNTAX    INTEGER (0..1)
    ACCESS    read-write
    STATUS    mandatory
    DESCRIPTION
        "0=Disable Alarm 1=Enable Alarm"
    ::= { meaDigitalInputAlarmEntry12 1 }

meaDigitalInputAlarmStatus12 OBJECT-TYPE
    SYNTAX    INTEGER (0..1)
    ACCESS    read-only
    STATUS    mandatory
    DESCRIPTION
        "0=No Alarm 1=Alarm"
    ::= { meaDigitalInputAlarmEntry12 2 }

-- }}}
-- {{{ Entry 13

meaDigitalInputAlarmEnable13 OBJECT-TYPE
    SYNTAX    INTEGER (0..1)
    ACCESS    read-write
    STATUS    mandatory
    DESCRIPTION
        "0=Disable Alarm 1=Enable Alarm"
    ::= { meaDigitalInputAlarmEntry13 1 }

meaDigitalInputAlarmStatus13 OBJECT-TYPE
    SYNTAX    INTEGER (0..1)
    ACCESS    read-only
    STATUS    mandatory
    DESCRIPTION
        "0=No Alarm 1=Alarm"
    ::= { meaDigitalInputAlarmEntry13 2 }

-- }}}
-- {{{ Entry 14

meaDigitalInputAlarmEnable14 OBJECT-TYPE
    SYNTAX    INTEGER (0..1)
    ACCESS    read-write
    STATUS    mandatory
    DESCRIPTION
        "0=Disable Alarm 1=Enable Alarm"
    ::= { meaDigitalInputAlarmEntry14 1 }

meaDigitalInputAlarmStatus14 OBJECT-TYPE
    SYNTAX    INTEGER (0..1)
    ACCESS    read-only
    STATUS    mandatory
    DESCRIPTION
        "0=No Alarm 1=Alarm"
    ::= { meaDigitalInputAlarmEntry14 2 }

-- }}}
-- {{{ Entry 15

meaDigitalInputAlarmEnable15 OBJECT-TYPE
    SYNTAX    INTEGER (0..1)
    ACCESS    read-write
    STATUS    mandatory
    DESCRIPTION
        "0=Disable Alarm 1=Enable Alarm"
    ::= { meaDigitalInputAlarmEntry15 1 }

meaDigitalInputAlarmStatus15 OBJECT-TYPE
    SYNTAX    INTEGER (0..1)
    ACCESS    read-only
    STATUS    mandatory
    DESCRIPTION
        "0=No Alarm 1=Alarm"
    ::= { meaDigitalInputAlarmEntry15 2 }

-- }}}
-- {{{ Entry 16

meaDigitalInputAlarmEnable16 OBJECT-TYPE
    SYNTAX    INTEGER (0..1)
    ACCESS    read-write
    STATUS    mandatory
    DESCRIPTION
        "0=Disable Alarm 1=Enable Alarm"
    ::= { meaDigitalInputAlarmEntry16 1 }

meaDigitalInputAlarmStatus16 OBJECT-TYPE
    SYNTAX    INTEGER (0..1)
    ACCESS    read-only
    STATUS    mandatory
    DESCRIPTION
        "0=No Alarm 1=Alarm"
    ::= { meaDigitalInputAlarmEntry16 2 }

-- }}}
-- {{{ Entry 17

meaDigitalInputAlarmEnable17 OBJECT-TYPE
    SYNTAX    INTEGER (0..1)
    ACCESS    read-write
    STATUS    mandatory
    DESCRIPTION
        "0=Disable Alarm 1=Enable Alarm"
    ::= { meaDigitalInputAlarmEntry17 1 }

meaDigitalInputAlarmStatus17 OBJECT-TYPE
    SYNTAX    INTEGER (0..1)
    ACCESS    read-only
    STATUS    mandatory
    DESCRIPTION
        "0=No Alarm 1=Alarm"
    ::= { meaDigitalInputAlarmEntry17 2 }

-- }}}
-- {{{ Entry 18

meaDigitalInputAlarmEnable18 OBJECT-TYPE
    SYNTAX    INTEGER (0..1)
    ACCESS    read-write
    STATUS    mandatory
    DESCRIPTION
        "0=Disable Alarm 1=Enable Alarm"
    ::= { meaDigitalInputAlarmEntry18 1 }

meaDigitalInputAlarmStatus18 OBJECT-TYPE
    SYNTAX    INTEGER (0..1)
    ACCESS    read-only
    STATUS    mandatory
    DESCRIPTION
        "0=No Alarm 1=Alarm"
    ::= { meaDigitalInputAlarmEntry18 2 }

-- }}}
-- {{{ Entry 19

meaDigitalInputAlarmEnable19 OBJECT-TYPE
    SYNTAX    INTEGER (0..1)
    ACCESS    read-write
    STATUS    mandatory
    DESCRIPTION
        "0=Disable Alarm 1=Enable Alarm"
    ::= { meaDigitalInputAlarmEntry19 1 }

meaDigitalInputAlarmStatus19 OBJECT-TYPE
    SYNTAX    INTEGER (0..1)
    ACCESS    read-only
    STATUS    mandatory
    DESCRIPTION
        "0=No Alarm 1=Alarm"
    ::= { meaDigitalInputAlarmEntry19 2 }

-- }}}
-- {{{ Entry 20

meaDigitalInputAlarmEnable20 OBJECT-TYPE
    SYNTAX    INTEGER (0..1)
    ACCESS    read-write
    STATUS    mandatory
    DESCRIPTION
        "0=Disable Alarm 1=Enable Alarm"
    ::= { meaDigitalInputAlarmEntry20 1 }

meaDigitalInputAlarmStatus20 OBJECT-TYPE
    SYNTAX    INTEGER (0..1)
    ACCESS    read-only
    STATUS    mandatory
    DESCRIPTION
        "0=No Alarm 1=Alarm"
    ::= { meaDigitalInputAlarmEntry20 2 }

-- }}}
-- {{{ Entry 21

meaDigitalInputAlarmEnable21 OBJECT-TYPE
    SYNTAX    INTEGER (0..1)
    ACCESS    read-write
    STATUS    mandatory
    DESCRIPTION
        "0=Disable Alarm 1=Enable Alarm"
    ::= { meaDigitalInputAlarmEntry21 1 }

meaDigitalInputAlarmStatus21 OBJECT-TYPE
    SYNTAX    INTEGER (0..1)
    ACCESS    read-only
    STATUS    mandatory
    DESCRIPTION
        "0=No Alarm 1=Alarm"
    ::= { meaDigitalInputAlarmEntry21 2 }

-- }}}
-- {{{ Entry 22

meaDigitalInputAlarmEnable22 OBJECT-TYPE
    SYNTAX    INTEGER (0..1)
    ACCESS    read-write
    STATUS    mandatory
    DESCRIPTION
        "0=Disable Alarm 1=Enable Alarm"
    ::= { meaDigitalInputAlarmEntry22 1 }

meaDigitalInputAlarmStatus22 OBJECT-TYPE
    SYNTAX    INTEGER (0..1)
    ACCESS    read-only
    STATUS    mandatory
    DESCRIPTION
        "0=No Alarm 1=Alarm"
    ::= { meaDigitalInputAlarmEntry22 2 }

-- }}}
-- {{{ Entry 23

meaDigitalInputAlarmEnable23 OBJECT-TYPE
    SYNTAX    INTEGER (0..1)
    ACCESS    read-write
    STATUS    mandatory
    DESCRIPTION
        "0=Disable Alarm 1=Enable Alarm"
    ::= { meaDigitalInputAlarmEntry23 1 }

meaDigitalInputAlarmStatus23 OBJECT-TYPE
    SYNTAX    INTEGER (0..1)
    ACCESS    read-only
    STATUS    mandatory
    DESCRIPTION
        "0=No Alarm 1=Alarm"
    ::= { meaDigitalInputAlarmEntry23 2 }

-- }}}
-- {{{ Entry 24

meaDigitalInputAlarmEnable24 OBJECT-TYPE
    SYNTAX    INTEGER (0..1)
    ACCESS    read-write
    STATUS    mandatory
    DESCRIPTION
        "0=Disable Alarm 1=Enable Alarm"
    ::= { meaDigitalInputAlarmEntry24 1 }

meaDigitalInputAlarmStatus24 OBJECT-TYPE
    SYNTAX    INTEGER (0..1)
    ACCESS    read-only
    STATUS    mandatory
    DESCRIPTION
        "0=No Alarm 1=Alarm"
    ::= { meaDigitalInputAlarmEntry24 2 }

-- }}}
-- {{{ Entry 25

meaDigitalInputAlarmEnable25 OBJECT-TYPE
    SYNTAX    INTEGER (0..1)
    ACCESS    read-write
    STATUS    mandatory
    DESCRIPTION
        "0=Disable Alarm 1=Enable Alarm"
    ::= { meaDigitalInputAlarmEntry25 1 }

meaDigitalInputAlarmStatus25 OBJECT-TYPE
    SYNTAX    INTEGER (0..1)
    ACCESS    read-only
    STATUS    mandatory
    DESCRIPTION
        "0=No Alarm 1=Alarm"
    ::= { meaDigitalInputAlarmEntry25 2 }

-- }}}
-- {{{ Entry 26

meaDigitalInputAlarmEnable26 OBJECT-TYPE
    SYNTAX    INTEGER (0..1)
    ACCESS    read-write
    STATUS    mandatory
    DESCRIPTION
        "0=Disable Alarm 1=Enable Alarm"
    ::= { meaDigitalInputAlarmEntry26 1 }

meaDigitalInputAlarmStatus26 OBJECT-TYPE
    SYNTAX    INTEGER (0..1)
    ACCESS    read-only
    STATUS    mandatory
    DESCRIPTION
        "0=No Alarm 1=Alarm"
    ::= { meaDigitalInputAlarmEntry26 2 }

-- }}}
-- {{{ Entry 27

meaDigitalInputAlarmEnable27 OBJECT-TYPE
    SYNTAX    INTEGER (0..1)
    ACCESS    read-write
    STATUS    mandatory
    DESCRIPTION
        "0=Disable Alarm 1=Enable Alarm"
    ::= { meaDigitalInputAlarmEntry27 1 }

meaDigitalInputAlarmStatus27 OBJECT-TYPE
    SYNTAX    INTEGER (0..1)
    ACCESS    read-only
    STATUS    mandatory
    DESCRIPTION
        "0=No Alarm 1=Alarm"
    ::= { meaDigitalInputAlarmEntry27 2 }

-- }}}
-- {{{ Entry 28

meaDigitalInputAlarmEnable28 OBJECT-TYPE
    SYNTAX    INTEGER (0..1)
    ACCESS    read-write
    STATUS    mandatory
    DESCRIPTION
        "0=Disable Alarm 1=Enable Alarm"
    ::= { meaDigitalInputAlarmEntry28 1 }

meaDigitalInputAlarmStatus28 OBJECT-TYPE
    SYNTAX    INTEGER (0..1)
    ACCESS    read-only
    STATUS    mandatory
    DESCRIPTION
        "0=No Alarm 1=Alarm"
    ::= { meaDigitalInputAlarmEntry28 2 }

-- }}}
-- {{{ Entry 29

meaDigitalInputAlarmEnable29 OBJECT-TYPE
    SYNTAX    INTEGER (0..1)
    ACCESS    read-write
    STATUS    mandatory
    DESCRIPTION
        "0=Disable Alarm 1=Enable Alarm"
    ::= { meaDigitalInputAlarmEntry29 1 }

meaDigitalInputAlarmStatus29 OBJECT-TYPE
    SYNTAX    INTEGER (0..1)
    ACCESS    read-only
    STATUS    mandatory
    DESCRIPTION
        "0=No Alarm 1=Alarm"
    ::= { meaDigitalInputAlarmEntry29 2 }

-- }}}
-- {{{ Entry 30

meaDigitalInputAlarmEnable30 OBJECT-TYPE
    SYNTAX    INTEGER (0..1)
    ACCESS    read-write
    STATUS    mandatory
    DESCRIPTION
        "0=Disable Alarm 1=Enable Alarm"
    ::= { meaDigitalInputAlarmEntry30 1 }

meaDigitalInputAlarmStatus30 OBJECT-TYPE
    SYNTAX    INTEGER (0..1)
    ACCESS    read-only
    STATUS    mandatory
    DESCRIPTION
        "0=No Alarm 1=Alarm"
    ::= { meaDigitalInputAlarmEntry30 2 }

-- }}}
-- {{{ Entry 31

meaDigitalInputAlarmEnable31 OBJECT-TYPE
    SYNTAX    INTEGER (0..1)
    ACCESS    read-write
    STATUS    mandatory
    DESCRIPTION
        "0=Disable Alarm 1=Enable Alarm"
    ::= { meaDigitalInputAlarmEntry31 1 }

meaDigitalInputAlarmStatus31 OBJECT-TYPE
    SYNTAX    INTEGER (0..1)
    ACCESS    read-only
    STATUS    mandatory
    DESCRIPTION
        "0=No Alarm 1=Alarm"
    ::= { meaDigitalInputAlarmEntry31 2 }

-- }}}
-- {{{ Entry 32

meaDigitalInputAlarmEnable32 OBJECT-TYPE
    SYNTAX    INTEGER (0..1)
    ACCESS    read-write
    STATUS    mandatory
    DESCRIPTION
        "0=Disable Alarm 1=Enable Alarm"
    ::= { meaDigitalInputAlarmEntry32 1 }

meaDigitalInputAlarmStatus32 OBJECT-TYPE
    SYNTAX    INTEGER (0..1)
    ACCESS    read-only
    STATUS    mandatory
    DESCRIPTION
        "0=No Alarm 1=Alarm"
    ::= { meaDigitalInputAlarmEntry32 2 }

-- }}}


-- }}}
-- {{{ meaAnalogInputAlarmTable   

meaAnalogInputAlarmEntry1  OBJECT IDENTIFIER ::= { meaAnalogInputAlarmTable 1  }
meaAnalogInputAlarmEntry2  OBJECT IDENTIFIER ::= { meaAnalogInputAlarmTable 2  }
meaAnalogInputAlarmEntry3  OBJECT IDENTIFIER ::= { meaAnalogInputAlarmTable 3  }
meaAnalogInputAlarmEntry4  OBJECT IDENTIFIER ::= { meaAnalogInputAlarmTable 4  }
meaAnalogInputAlarmEntry5  OBJECT IDENTIFIER ::= { meaAnalogInputAlarmTable 5  }
meaAnalogInputAlarmEntry6  OBJECT IDENTIFIER ::= { meaAnalogInputAlarmTable 6  }
meaAnalogInputAlarmEntry7  OBJECT IDENTIFIER ::= { meaAnalogInputAlarmTable 7  }
meaAnalogInputAlarmEntry8  OBJECT IDENTIFIER ::= { meaAnalogInputAlarmTable 8  }
meaAnalogInputAlarmEntry9  OBJECT IDENTIFIER ::= { meaAnalogInputAlarmTable 9  }
meaAnalogInputAlarmEntry10 OBJECT IDENTIFIER ::= { meaAnalogInputAlarmTable 10 }
meaAnalogInputAlarmEntry11 OBJECT IDENTIFIER ::= { meaAnalogInputAlarmTable 11 }
meaAnalogInputAlarmEntry12 OBJECT IDENTIFIER ::= { meaAnalogInputAlarmTable 12 }
meaAnalogInputAlarmEntry13 OBJECT IDENTIFIER ::= { meaAnalogInputAlarmTable 13 }
meaAnalogInputAlarmEntry14 OBJECT IDENTIFIER ::= { meaAnalogInputAlarmTable 14 }
meaAnalogInputAlarmEntry15 OBJECT IDENTIFIER ::= { meaAnalogInputAlarmTable 15 }
meaAnalogInputAlarmEntry16 OBJECT IDENTIFIER ::= { meaAnalogInputAlarmTable 16 }

-- meaAnalogInputAlarmEntries
-- {{{ Entry 1

meaAnalogInputAlarmStatus1 OBJECT-TYPE
    SYNTAX    INTEGER (0..1)
    ACCESS    read-only
    STATUS    mandatory
    DESCRIPTION
        "0=No Alarm 1=Alarm"
    ::= { meaAnalogInputAlarmEntry1 1 }

-- }}}
-- {{{ Entry 2

meaAnalogInputAlarmStatus2 OBJECT-TYPE
    SYNTAX    INTEGER (0..1)
    ACCESS    read-only
    STATUS    mandatory
    DESCRIPTION
        "0=No Alarm 1=Alarm"
    ::= { meaAnalogInputAlarmEntry2 1 }

-- }}}
-- {{{ Entry 3

meaAnalogInputAlarmStatus3 OBJECT-TYPE
    SYNTAX    INTEGER (0..1)
    ACCESS    read-only
    STATUS    mandatory
    DESCRIPTION
        "0=No Alarm 1=Alarm"
    ::= { meaAnalogInputAlarmEntry3 1 }

-- }}}
-- {{{ Entry 4

meaAnalogInputAlarmStatus4 OBJECT-TYPE
    SYNTAX    INTEGER (0..1)
    ACCESS    read-only
    STATUS    mandatory
    DESCRIPTION
        "0=No Alarm 1=Alarm"
    ::= { meaAnalogInputAlarmEntry4 1 }

-- }}}
-- {{{ Entry 5

meaAnalogInputAlarmStatus5 OBJECT-TYPE
    SYNTAX    INTEGER (0..1)
    ACCESS    read-only
    STATUS    mandatory
    DESCRIPTION
        "0=No Alarm 1=Alarm"
    ::= { meaAnalogInputAlarmEntry5 1 }

-- }}}
-- {{{ Entry 6

meaAnalogInputAlarmStatus6 OBJECT-TYPE
    SYNTAX    INTEGER (0..1)
    ACCESS    read-only
    STATUS    mandatory
    DESCRIPTION
        "0=No Alarm 1=Alarm"
    ::= { meaAnalogInputAlarmEntry6 1 }

-- }}}
-- {{{ Entry 7

meaAnalogInputAlarmStatus7 OBJECT-TYPE
    SYNTAX    INTEGER (0..1)
    ACCESS    read-only
    STATUS    mandatory
    DESCRIPTION
        "0=No Alarm 1=Alarm"
    ::= { meaAnalogInputAlarmEntry7 1 }

-- }}}
-- {{{ Entry 8

meaAnalogInputAlarmStatus8 OBJECT-TYPE
    SYNTAX    INTEGER (0..1)
    ACCESS    read-only
    STATUS    mandatory
    DESCRIPTION
        "0=No Alarm 1=Alarm"
    ::= { meaAnalogInputAlarmEntry8 1 }

-- }}}
-- {{{ Entry 9

meaAnalogInputAlarmStatus9 OBJECT-TYPE
    SYNTAX    INTEGER (0..1)
    ACCESS    read-only
    STATUS    mandatory
    DESCRIPTION
        "0=No Alarm 1=Alarm"
    ::= { meaAnalogInputAlarmEntry9 1 }

-- }}}
-- {{{ Entry 10

meaAnalogInputAlarmStatus10 OBJECT-TYPE
    SYNTAX    INTEGER (0..1)
    ACCESS    read-only
    STATUS    mandatory
    DESCRIPTION
        "0=No Alarm 1=Alarm"
    ::= { meaAnalogInputAlarmEntry10 1 }

-- }}}
-- {{{ Entry 11

meaAnalogInputAlarmStatus11 OBJECT-TYPE
    SYNTAX    INTEGER (0..1)
    ACCESS    read-only
    STATUS    mandatory
    DESCRIPTION
        "0=No Alarm 1=Alarm"
    ::= { meaAnalogInputAlarmEntry11 1 }

-- }}}
-- {{{ Entry 12

meaAnalogInputAlarmStatus12 OBJECT-TYPE
    SYNTAX    INTEGER (0..1)
    ACCESS    read-only
    STATUS    mandatory
    DESCRIPTION
        "0=No Alarm 1=Alarm"
    ::= { meaAnalogInputAlarmEntry12 1 }

-- }}}
-- {{{ Entry 13

meaAnalogInputAlarmStatus13 OBJECT-TYPE
    SYNTAX    INTEGER (0..1)
    ACCESS    read-only
    STATUS    mandatory
    DESCRIPTION
        "0=No Alarm 1=Alarm"
    ::= { meaAnalogInputAlarmEntry13 1 }

-- }}}
-- {{{ Entry 14

meaAnalogInputAlarmStatus14 OBJECT-TYPE
    SYNTAX    INTEGER (0..1)
    ACCESS    read-only
    STATUS    mandatory
    DESCRIPTION
        "0=No Alarm 1=Alarm"
    ::= { meaAnalogInputAlarmEntry14 1 }

-- }}}
-- {{{ Entry 15

meaAnalogInputAlarmStatus15 OBJECT-TYPE
    SYNTAX    INTEGER (0..1)
    ACCESS    read-only
    STATUS    mandatory
    DESCRIPTION
        "0=No Alarm 1=Alarm"
    ::= { meaAnalogInputAlarmEntry15 1 }

-- }}}
-- {{{ Entry 16

meaAnalogInputAlarmStatus16 OBJECT-TYPE
    SYNTAX    INTEGER (0..1)
    ACCESS    read-only
    STATUS    mandatory
    DESCRIPTION
        "0=No Alarm 1=Alarm"
    ::= { meaAnalogInputAlarmEntry16 1 }

-- }}}


-- }}}
-- {{{ meaDigitalOutputAlarmTable 

meaDigitalOutputAlarmEntry1  OBJECT IDENTIFIER ::= { meaDigitalOutputAlarmTable 1  }
meaDigitalOutputAlarmEntry2  OBJECT IDENTIFIER ::= { meaDigitalOutputAlarmTable 2  }
meaDigitalOutputAlarmEntry3  OBJECT IDENTIFIER ::= { meaDigitalOutputAlarmTable 3  }
meaDigitalOutputAlarmEntry4  OBJECT IDENTIFIER ::= { meaDigitalOutputAlarmTable 4  }
meaDigitalOutputAlarmEntry5  OBJECT IDENTIFIER ::= { meaDigitalOutputAlarmTable 5  }
meaDigitalOutputAlarmEntry6  OBJECT IDENTIFIER ::= { meaDigitalOutputAlarmTable 6  }
meaDigitalOutputAlarmEntry7  OBJECT IDENTIFIER ::= { meaDigitalOutputAlarmTable 7  }
meaDigitalOutputAlarmEntry8  OBJECT IDENTIFIER ::= { meaDigitalOutputAlarmTable 8  }
meaDigitalOutputAlarmEntry9  OBJECT IDENTIFIER ::= { meaDigitalOutputAlarmTable 9  }
meaDigitalOutputAlarmEntry10 OBJECT IDENTIFIER ::= { meaDigitalOutputAlarmTable 10 }
meaDigitalOutputAlarmEntry11 OBJECT IDENTIFIER ::= { meaDigitalOutputAlarmTable 11 }
meaDigitalOutputAlarmEntry12 OBJECT IDENTIFIER ::= { meaDigitalOutputAlarmTable 12 }
meaDigitalOutputAlarmEntry13 OBJECT IDENTIFIER ::= { meaDigitalOutputAlarmTable 13 }
meaDigitalOutputAlarmEntry14 OBJECT IDENTIFIER ::= { meaDigitalOutputAlarmTable 14 }
meaDigitalOutputAlarmEntry15 OBJECT IDENTIFIER ::= { meaDigitalOutputAlarmTable 15 }
meaDigitalOutputAlarmEntry16 OBJECT IDENTIFIER ::= { meaDigitalOutputAlarmTable 16 }
meaDigitalOutputAlarmEntry17 OBJECT IDENTIFIER ::= { meaDigitalOutputAlarmTable 17 }
meaDigitalOutputAlarmEntry18 OBJECT IDENTIFIER ::= { meaDigitalOutputAlarmTable 18 }
meaDigitalOutputAlarmEntry19 OBJECT IDENTIFIER ::= { meaDigitalOutputAlarmTable 19 }
meaDigitalOutputAlarmEntry20 OBJECT IDENTIFIER ::= { meaDigitalOutputAlarmTable 20 }
meaDigitalOutputAlarmEntry21 OBJECT IDENTIFIER ::= { meaDigitalOutputAlarmTable 21 }
meaDigitalOutputAlarmEntry22 OBJECT IDENTIFIER ::= { meaDigitalOutputAlarmTable 22 }
meaDigitalOutputAlarmEntry23 OBJECT IDENTIFIER ::= { meaDigitalOutputAlarmTable 23 }
meaDigitalOutputAlarmEntry24 OBJECT IDENTIFIER ::= { meaDigitalOutputAlarmTable 24 }
meaDigitalOutputAlarmEntry25 OBJECT IDENTIFIER ::= { meaDigitalOutputAlarmTable 25 }
meaDigitalOutputAlarmEntry26 OBJECT IDENTIFIER ::= { meaDigitalOutputAlarmTable 26 }
meaDigitalOutputAlarmEntry27 OBJECT IDENTIFIER ::= { meaDigitalOutputAlarmTable 27 }
meaDigitalOutputAlarmEntry28 OBJECT IDENTIFIER ::= { meaDigitalOutputAlarmTable 28 }
meaDigitalOutputAlarmEntry29 OBJECT IDENTIFIER ::= { meaDigitalOutputAlarmTable 29 }
meaDigitalOutputAlarmEntry30 OBJECT IDENTIFIER ::= { meaDigitalOutputAlarmTable 30 }
meaDigitalOutputAlarmEntry31 OBJECT IDENTIFIER ::= { meaDigitalOutputAlarmTable 31 }
meaDigitalOutputAlarmEntry32 OBJECT IDENTIFIER ::= { meaDigitalOutputAlarmTable 32 }

-- meaDigitalOutputAlarmEntries
-- {{{ Entry 1

meaDigitalOutputAlarmEnable1 OBJECT-TYPE
    SYNTAX    INTEGER (0..1)
    ACCESS    read-write
    STATUS    mandatory
    DESCRIPTION
        "0=no alarm enable 1=alarm enable"
    ::= { meaDigitalOutputAlarmEntry1 1 }

meaDigitalOutputAlarmStatus1 OBJECT-TYPE
    SYNTAX    INTEGER (0..1)
    ACCESS    read-only
    STATUS    mandatory
    DESCRIPTION
        "0=No Alarm 1=Alarm"
    ::= { meaDigitalOutputAlarmEntry1 2 }

-- }}}
-- {{{ Entry 2

meaDigitalOutputAlarmEnable2 OBJECT-TYPE
    SYNTAX    INTEGER (0..1)
    ACCESS    read-write
    STATUS    mandatory
    DESCRIPTION
        "0=no alarm enable 1=alarm enable"
    ::= { meaDigitalOutputAlarmEntry2 1 }

meaDigitalOutputAlarmStatus2 OBJECT-TYPE
    SYNTAX    INTEGER (0..1)
    ACCESS    read-only
    STATUS    mandatory
    DESCRIPTION
        "0=No Alarm 1=Alarm"
    ::= { meaDigitalOutputAlarmEntry2 2 }

-- }}}
-- {{{ Entry 3

meaDigitalOutputAlarmEnable3 OBJECT-TYPE
    SYNTAX    INTEGER (0..1)
    ACCESS    read-write
    STATUS    mandatory
    DESCRIPTION
        "0=no alarm enable 1=alarm enable"
    ::= { meaDigitalOutputAlarmEntry3 1 }

meaDigitalOutputAlarmStatus3 OBJECT-TYPE
    SYNTAX    INTEGER (0..1)
    ACCESS    read-only
    STATUS    mandatory
    DESCRIPTION
        "0=No Alarm 1=Alarm"
    ::= { meaDigitalOutputAlarmEntry3 2 }

-- }}}
-- {{{ Entry 4

meaDigitalOutputAlarmEnable4 OBJECT-TYPE
    SYNTAX    INTEGER (0..1)
    ACCESS    read-write
    STATUS    mandatory
    DESCRIPTION
        "0=no alarm enable 1=alarm enable"
    ::= { meaDigitalOutputAlarmEntry4 1 }

meaDigitalOutputAlarmStatus4 OBJECT-TYPE
    SYNTAX    INTEGER (0..1)
    ACCESS    read-only
    STATUS    mandatory
    DESCRIPTION
        "0=No Alarm 1=Alarm"
    ::= { meaDigitalOutputAlarmEntry4 2 }

-- }}}
-- {{{ Entry 5

meaDigitalOutputAlarmEnable5 OBJECT-TYPE
    SYNTAX    INTEGER (0..1)
    ACCESS    read-write
    STATUS    mandatory
    DESCRIPTION
        "0=no alarm enable 1=alarm enable"
    ::= { meaDigitalOutputAlarmEntry5 1 }

meaDigitalOutputAlarmStatus5 OBJECT-TYPE
    SYNTAX    INTEGER (0..1)
    ACCESS    read-only
    STATUS    mandatory
    DESCRIPTION
        "0=No Alarm 1=Alarm"
    ::= { meaDigitalOutputAlarmEntry5 2 }

-- }}}
-- {{{ Entry 6

meaDigitalOutputAlarmEnable6 OBJECT-TYPE
    SYNTAX    INTEGER (0..1)
    ACCESS    read-write
    STATUS    mandatory
    DESCRIPTION
        "0=no alarm enable 1=alarm enable"
    ::= { meaDigitalOutputAlarmEntry6 1 }

meaDigitalOutputAlarmStatus6 OBJECT-TYPE
    SYNTAX    INTEGER (0..1)
    ACCESS    read-only
    STATUS    mandatory
    DESCRIPTION
        "0=No Alarm 1=Alarm"
    ::= { meaDigitalOutputAlarmEntry6 2 }

-- }}}
-- {{{ Entry 7

meaDigitalOutputAlarmEnable7 OBJECT-TYPE
    SYNTAX    INTEGER (0..1)
    ACCESS    read-write
    STATUS    mandatory
    DESCRIPTION
        "0=no alarm enable 1=alarm enable"
    ::= { meaDigitalOutputAlarmEntry7 1 }

meaDigitalOutputAlarmStatus7 OBJECT-TYPE
    SYNTAX    INTEGER (0..1)
    ACCESS    read-only
    STATUS    mandatory
    DESCRIPTION
        "0=No Alarm 1=Alarm"
    ::= { meaDigitalOutputAlarmEntry7 2 }

-- }}}
-- {{{ Entry 8

meaDigitalOutputAlarmEnable8 OBJECT-TYPE
    SYNTAX    INTEGER (0..1)
    ACCESS    read-write
    STATUS    mandatory
    DESCRIPTION
        "0=no alarm enable 1=alarm enable"
    ::= { meaDigitalOutputAlarmEntry8 1 }

meaDigitalOutputAlarmStatus8 OBJECT-TYPE
    SYNTAX    INTEGER (0..1)
    ACCESS    read-only
    STATUS    mandatory
    DESCRIPTION
        "0=No Alarm 1=Alarm"
    ::= { meaDigitalOutputAlarmEntry8 2 }

-- }}}
-- {{{ Entry 9

meaDigitalOutputAlarmEnable9 OBJECT-TYPE
    SYNTAX    INTEGER (0..1)
    ACCESS    read-write
    STATUS    mandatory
    DESCRIPTION
        "0=no alarm enable 1=alarm enable"
    ::= { meaDigitalOutputAlarmEntry9 1 }

meaDigitalOutputAlarmStatus9 OBJECT-TYPE
    SYNTAX    INTEGER (0..1)
    ACCESS    read-only
    STATUS    mandatory
    DESCRIPTION
        "0=No Alarm 1=Alarm"
    ::= { meaDigitalOutputAlarmEntry9 2 }

-- }}}
-- {{{ Entry 10

meaDigitalOutputAlarmEnable10 OBJECT-TYPE
    SYNTAX    INTEGER (0..1)
    ACCESS    read-write
    STATUS    mandatory
    DESCRIPTION
        "0=no alarm enable 1=alarm enable"
    ::= { meaDigitalOutputAlarmEntry10 1 }

meaDigitalOutputAlarmStatus10 OBJECT-TYPE
    SYNTAX    INTEGER (0..1)
    ACCESS    read-only
    STATUS    mandatory
    DESCRIPTION
        "0=No Alarm 1=Alarm"
    ::= { meaDigitalOutputAlarmEntry10 2 }

-- }}}
-- {{{ Entry 11

meaDigitalOutputAlarmEnable11 OBJECT-TYPE
    SYNTAX    INTEGER (0..1)
    ACCESS    read-write
    STATUS    mandatory
    DESCRIPTION
        "0=no alarm enable 1=alarm enable"
    ::= { meaDigitalOutputAlarmEntry11 1 }

meaDigitalOutputAlarmStatus11 OBJECT-TYPE
    SYNTAX    INTEGER (0..1)
    ACCESS    read-only
    STATUS    mandatory
    DESCRIPTION
        "0=No Alarm 1=Alarm"
    ::= { meaDigitalOutputAlarmEntry11 2 }

-- }}}
-- {{{ Entry 12

meaDigitalOutputAlarmEnable12 OBJECT-TYPE
    SYNTAX    INTEGER (0..1)
    ACCESS    read-write
    STATUS    mandatory
    DESCRIPTION
        "0=no alarm enable 1=alarm enable"
    ::= { meaDigitalOutputAlarmEntry12 1 }

meaDigitalOutputAlarmStatus12 OBJECT-TYPE
    SYNTAX    INTEGER (0..1)
    ACCESS    read-only
    STATUS    mandatory
    DESCRIPTION
        "0=No Alarm 1=Alarm"
    ::= { meaDigitalOutputAlarmEntry12 2 }

-- }}}
-- {{{ Entry 13

meaDigitalOutputAlarmEnable13 OBJECT-TYPE
    SYNTAX    INTEGER (0..1)
    ACCESS    read-write
    STATUS    mandatory
    DESCRIPTION
        "0=no alarm enable 1=alarm enable"
    ::= { meaDigitalOutputAlarmEntry13 1 }

meaDigitalOutputAlarmStatus13 OBJECT-TYPE
    SYNTAX    INTEGER (0..1)
    ACCESS    read-only
    STATUS    mandatory
    DESCRIPTION
        "0=No Alarm 1=Alarm"
    ::= { meaDigitalOutputAlarmEntry13 2 }

-- }}}
-- {{{ Entry 14

meaDigitalOutputAlarmEnable14 OBJECT-TYPE
    SYNTAX    INTEGER (0..1)
    ACCESS    read-write
    STATUS    mandatory
    DESCRIPTION
        "0=no alarm enable 1=alarm enable"
    ::= { meaDigitalOutputAlarmEntry14 1 }

meaDigitalOutputAlarmStatus14 OBJECT-TYPE
    SYNTAX    INTEGER (0..1)
    ACCESS    read-only
    STATUS    mandatory
    DESCRIPTION
        "0=No Alarm 1=Alarm"
    ::= { meaDigitalOutputAlarmEntry14 2 }

-- }}}
-- {{{ Entry 15

meaDigitalOutputAlarmEnable15 OBJECT-TYPE
    SYNTAX    INTEGER (0..1)
    ACCESS    read-write
    STATUS    mandatory
    DESCRIPTION
        "0=no alarm enable 1=alarm enable"
    ::= { meaDigitalOutputAlarmEntry15 1 }

meaDigitalOutputAlarmStatus15 OBJECT-TYPE
    SYNTAX    INTEGER (0..1)
    ACCESS    read-only
    STATUS    mandatory
    DESCRIPTION
        "0=No Alarm 1=Alarm"
    ::= { meaDigitalOutputAlarmEntry15 2 }

-- }}}
-- {{{ Entry 16

meaDigitalOutputAlarmEnable16 OBJECT-TYPE
    SYNTAX    INTEGER (0..1)
    ACCESS    read-write
    STATUS    mandatory
    DESCRIPTION
        "0=no alarm enable 1=alarm enable"
    ::= { meaDigitalOutputAlarmEntry16 1 }

meaDigitalOutputAlarmStatus16 OBJECT-TYPE
    SYNTAX    INTEGER (0..1)
    ACCESS    read-only
    STATUS    mandatory
    DESCRIPTION
        "0=No Alarm 1=Alarm"
    ::= { meaDigitalOutputAlarmEntry16 2 }

-- }}}
-- {{{ Entry 17

meaDigitalOutputAlarmEnable17 OBJECT-TYPE
    SYNTAX    INTEGER (0..1)
    ACCESS    read-write
    STATUS    mandatory
    DESCRIPTION
        "0=no alarm enable 1=alarm enable"
    ::= { meaDigitalOutputAlarmEntry17 1 }

meaDigitalOutputAlarmStatus17 OBJECT-TYPE
    SYNTAX    INTEGER (0..1)
    ACCESS    read-only
    STATUS    mandatory
    DESCRIPTION
        "0=No Alarm 1=Alarm"
    ::= { meaDigitalOutputAlarmEntry17 2 }

-- }}}
-- {{{ Entry 18

meaDigitalOutputAlarmEnable18 OBJECT-TYPE
    SYNTAX    INTEGER (0..1)
    ACCESS    read-write
    STATUS    mandatory
    DESCRIPTION
        "0=no alarm enable 1=alarm enable"
    ::= { meaDigitalOutputAlarmEntry18 1 }

meaDigitalOutputAlarmStatus18 OBJECT-TYPE
    SYNTAX    INTEGER (0..1)
    ACCESS    read-only
    STATUS    mandatory
    DESCRIPTION
        "0=No Alarm 1=Alarm"
    ::= { meaDigitalOutputAlarmEntry18 2 }

-- }}}
-- {{{ Entry 19

meaDigitalOutputAlarmEnable19 OBJECT-TYPE
    SYNTAX    INTEGER (0..1)
    ACCESS    read-write
    STATUS    mandatory
    DESCRIPTION
        "0=no alarm enable 1=alarm enable"
    ::= { meaDigitalOutputAlarmEntry19 1 }

meaDigitalOutputAlarmStatus19 OBJECT-TYPE
    SYNTAX    INTEGER (0..1)
    ACCESS    read-only
    STATUS    mandatory
    DESCRIPTION
        "0=No Alarm 1=Alarm"
    ::= { meaDigitalOutputAlarmEntry19 2 }

-- }}}
-- {{{ Entry 20

meaDigitalOutputAlarmEnable20 OBJECT-TYPE
    SYNTAX    INTEGER (0..1)
    ACCESS    read-write
    STATUS    mandatory
    DESCRIPTION
        "0=no alarm enable 1=alarm enable"
    ::= { meaDigitalOutputAlarmEntry20 1 }

meaDigitalOutputAlarmStatus20 OBJECT-TYPE
    SYNTAX    INTEGER (0..1)
    ACCESS    read-only
    STATUS    mandatory
    DESCRIPTION
        "0=No Alarm 1=Alarm"
    ::= { meaDigitalOutputAlarmEntry20 2 }

-- }}}
-- {{{ Entry 21

meaDigitalOutputAlarmEnable21 OBJECT-TYPE
    SYNTAX    INTEGER (0..1)
    ACCESS    read-write
    STATUS    mandatory
    DESCRIPTION
        "0=no alarm enable 1=alarm enable"
    ::= { meaDigitalOutputAlarmEntry21 1 }

meaDigitalOutputAlarmStatus21 OBJECT-TYPE
    SYNTAX    INTEGER (0..1)
    ACCESS    read-only
    STATUS    mandatory
    DESCRIPTION
        "0=No Alarm 1=Alarm"
    ::= { meaDigitalOutputAlarmEntry21 2 }

-- }}}
-- {{{ Entry 22

meaDigitalOutputAlarmEnable22 OBJECT-TYPE
    SYNTAX    INTEGER (0..1)
    ACCESS    read-write
    STATUS    mandatory
    DESCRIPTION
        "0=no alarm enable 1=alarm enable"
    ::= { meaDigitalOutputAlarmEntry22 1 }

meaDigitalOutputAlarmStatus22 OBJECT-TYPE
    SYNTAX    INTEGER (0..1)
    ACCESS    read-only
    STATUS    mandatory
    DESCRIPTION
        "0=No Alarm 1=Alarm"
    ::= { meaDigitalOutputAlarmEntry22 2 }

-- }}}
-- {{{ Entry 23

meaDigitalOutputAlarmEnable23 OBJECT-TYPE
    SYNTAX    INTEGER (0..1)
    ACCESS    read-write
    STATUS    mandatory
    DESCRIPTION
        "0=no alarm enable 1=alarm enable"
    ::= { meaDigitalOutputAlarmEntry23 1 }

meaDigitalOutputAlarmStatus23 OBJECT-TYPE
    SYNTAX    INTEGER (0..1)
    ACCESS    read-only
    STATUS    mandatory
    DESCRIPTION
        "0=No Alarm 1=Alarm"
    ::= { meaDigitalOutputAlarmEntry23 2 }

-- }}}
-- {{{ Entry 24

meaDigitalOutputAlarmEnable24 OBJECT-TYPE
    SYNTAX    INTEGER (0..1)
    ACCESS    read-write
    STATUS    mandatory
    DESCRIPTION
        "0=no alarm enable 1=alarm enable"
    ::= { meaDigitalOutputAlarmEntry24 1 }

meaDigitalOutputAlarmStatus24 OBJECT-TYPE
    SYNTAX    INTEGER (0..1)
    ACCESS    read-only
    STATUS    mandatory
    DESCRIPTION
        "0=No Alarm 1=Alarm"
    ::= { meaDigitalOutputAlarmEntry24 2 }

-- }}}
-- {{{ Entry 25

meaDigitalOutputAlarmEnable25 OBJECT-TYPE
    SYNTAX    INTEGER (0..1)
    ACCESS    read-write
    STATUS    mandatory
    DESCRIPTION
        "0=no alarm enable 1=alarm enable"
    ::= { meaDigitalOutputAlarmEntry25 1 }

meaDigitalOutputAlarmStatus25 OBJECT-TYPE
    SYNTAX    INTEGER (0..1)
    ACCESS    read-only
    STATUS    mandatory
    DESCRIPTION
        "0=No Alarm 1=Alarm"
    ::= { meaDigitalOutputAlarmEntry25 2 }

-- }}}
-- {{{ Entry 26

meaDigitalOutputAlarmEnable26 OBJECT-TYPE
    SYNTAX    INTEGER (0..1)
    ACCESS    read-write
    STATUS    mandatory
    DESCRIPTION
        "0=no alarm enable 1=alarm enable"
    ::= { meaDigitalOutputAlarmEntry26 1 }

meaDigitalOutputAlarmStatus26 OBJECT-TYPE
    SYNTAX    INTEGER (0..1)
    ACCESS    read-only
    STATUS    mandatory
    DESCRIPTION
        "0=No Alarm 1=Alarm"
    ::= { meaDigitalOutputAlarmEntry26 2 }

-- }}}
-- {{{ Entry 27

meaDigitalOutputAlarmEnable27 OBJECT-TYPE
    SYNTAX    INTEGER (0..1)
    ACCESS    read-write
    STATUS    mandatory
    DESCRIPTION
        "0=no alarm enable 1=alarm enable"
    ::= { meaDigitalOutputAlarmEntry27 1 }

meaDigitalOutputAlarmStatus27 OBJECT-TYPE
    SYNTAX    INTEGER (0..1)
    ACCESS    read-only
    STATUS    mandatory
    DESCRIPTION
        "0=No Alarm 1=Alarm"
    ::= { meaDigitalOutputAlarmEntry27 2 }

-- }}}
-- {{{ Entry 28

meaDigitalOutputAlarmEnable28 OBJECT-TYPE
    SYNTAX    INTEGER (0..1)
    ACCESS    read-write
    STATUS    mandatory
    DESCRIPTION
        "0=no alarm enable 1=alarm enable"
    ::= { meaDigitalOutputAlarmEntry28 1 }

meaDigitalOutputAlarmStatus28 OBJECT-TYPE
    SYNTAX    INTEGER (0..1)
    ACCESS    read-only
    STATUS    mandatory
    DESCRIPTION
        "0=No Alarm 1=Alarm"
    ::= { meaDigitalOutputAlarmEntry28 2 }

-- }}}
-- {{{ Entry 29

meaDigitalOutputAlarmEnable29 OBJECT-TYPE
    SYNTAX    INTEGER (0..1)
    ACCESS    read-write
    STATUS    mandatory
    DESCRIPTION
        "0=no alarm enable 1=alarm enable"
    ::= { meaDigitalOutputAlarmEntry29 1 }

meaDigitalOutputAlarmStatus29 OBJECT-TYPE
    SYNTAX    INTEGER (0..1)
    ACCESS    read-only
    STATUS    mandatory
    DESCRIPTION
        "0=No Alarm 1=Alarm"
    ::= { meaDigitalOutputAlarmEntry29 2 }

-- }}}
-- {{{ Entry 30

meaDigitalOutputAlarmEnable30 OBJECT-TYPE
    SYNTAX    INTEGER (0..1)
    ACCESS    read-write
    STATUS    mandatory
    DESCRIPTION
        "0=no alarm enable 1=alarm enable"
    ::= { meaDigitalOutputAlarmEntry30 1 }

meaDigitalOutputAlarmStatus30 OBJECT-TYPE
    SYNTAX    INTEGER (0..1)
    ACCESS    read-only
    STATUS    mandatory
    DESCRIPTION
        "0=No Alarm 1=Alarm"
    ::= { meaDigitalOutputAlarmEntry30 2 }

-- }}}
-- {{{ Entry 31

meaDigitalOutputAlarmEnable31 OBJECT-TYPE
    SYNTAX    INTEGER (0..1)
    ACCESS    read-write
    STATUS    mandatory
    DESCRIPTION
        "0=no alarm enable 1=alarm enable"
    ::= { meaDigitalOutputAlarmEntry31 1 }

meaDigitalOutputAlarmStatus31 OBJECT-TYPE
    SYNTAX    INTEGER (0..1)
    ACCESS    read-only
    STATUS    mandatory
    DESCRIPTION
        "0=No Alarm 1=Alarm"
    ::= { meaDigitalOutputAlarmEntry31 2 }

-- }}}
-- {{{ Entry 32

meaDigitalOutputAlarmEnable32 OBJECT-TYPE
    SYNTAX    INTEGER (0..1)
    ACCESS    read-write
    STATUS    mandatory
    DESCRIPTION
        "0=no alarm enable 1=alarm enable"
    ::= { meaDigitalOutputAlarmEntry32 1 }

meaDigitalOutputAlarmStatus32 OBJECT-TYPE
    SYNTAX    INTEGER (0..1)
    ACCESS    read-only
    STATUS    mandatory
    DESCRIPTION
        "0=No Alarm 1=Alarm"
    ::= { meaDigitalOutputAlarmEntry32 2 }

-- }}}

-- }}}

-- }}}
-- {{{ meaTest                 

-- {{{ meaTestAuxiliarySelfTest 

meaTestAuxiliarySelfTest  OBJECT-TYPE
    SYNTAX    INTEGER (0..100)
    ACCESS    read-only
    STATUS    mandatory
    DESCRIPTION 
        "0=OK else error code"
    ::= { meaTest 1 }

-- }}}
-- {{{ meaTestInitiateSelfTest  

meaTestInitiateSelfTest  OBJECT-TYPE
    SYNTAX    INTEGER (0..1)
    ACCESS    read-write
    STATUS    mandatory
    DESCRIPTION 
        "0=Cancel test, 1=Initiate self test"
    ::= { meaTest 2 }

-- }}}

-- }}}
-- {{{ meaControl              

meaAnalogControlsTable   OBJECT IDENTIFIER ::= { meaControl 1 }
meaDigitalControlsTable  OBJECT IDENTIFIER ::= { meaControl 2 }

-- {{{ meaAnalogControlTable Group   

meaAnalogControlEntry1  OBJECT IDENTIFIER ::= { meaAnalogControlsTable 1  }
meaAnalogControlEntry2  OBJECT IDENTIFIER ::= { meaAnalogControlsTable 2  }
meaAnalogControlEntry3  OBJECT IDENTIFIER ::= { meaAnalogControlsTable 3  }
meaAnalogControlEntry4  OBJECT IDENTIFIER ::= { meaAnalogControlsTable 4  }
meaAnalogControlEntry5  OBJECT IDENTIFIER ::= { meaAnalogControlsTable 5  }
meaAnalogControlEntry6  OBJECT IDENTIFIER ::= { meaAnalogControlsTable 6  }
meaAnalogControlEntry7  OBJECT IDENTIFIER ::= { meaAnalogControlsTable 7  }
meaAnalogControlEntry8  OBJECT IDENTIFIER ::= { meaAnalogControlsTable 8  }
meaAnalogControlEntry9  OBJECT IDENTIFIER ::= { meaAnalogControlsTable 9  }
meaAnalogControlEntry10 OBJECT IDENTIFIER ::= { meaAnalogControlsTable 10 }
meaAnalogControlEntry11 OBJECT IDENTIFIER ::= { meaAnalogControlsTable 11 }
meaAnalogControlEntry12 OBJECT IDENTIFIER ::= { meaAnalogControlsTable 12 }
meaAnalogControlEntry13 OBJECT IDENTIFIER ::= { meaAnalogControlsTable 13 }
meaAnalogControlEntry14 OBJECT IDENTIFIER ::= { meaAnalogControlsTable 14 }
meaAnalogControlEntry15 OBJECT IDENTIFIER ::= { meaAnalogControlsTable 15 }
meaAnalogControlEntry16 OBJECT IDENTIFIER ::= { meaAnalogControlsTable 16 }

-- meaAnalogControlTable
-- {{{ Entry 1

meaAnalogOutputsControl1 OBJECT-TYPE
    SYNTAX    INTEGER (0..9)
    ACCESS    read-write
    STATUS    mandatory
    DESCRIPTION
        "Complicated!"
    ::= { meaAnalogControlEntry1 1 }

meaAnalogOutputsUpperThresholdSource1 OBJECT-TYPE
    SYNTAX    INTEGER (0..2)
    ACCESS    read-write
    STATUS    mandatory
    DESCRIPTION
        "0=Analog 1=Temp 2=Humidity"
    ::= { meaAnalogControlEntry1 2 }

meaAnalogOutputsLowerThresholdSource1 OBJECT-TYPE
    SYNTAX    INTEGER (0..2)
    ACCESS    read-write
    STATUS    mandatory
    DESCRIPTION
        "0=Analog 1=Temp 2=Humidity"
    ::= { meaAnalogControlEntry1 3 }

-- }}}
-- {{{ Entry 2

meaAnalogOutputsControl2 OBJECT-TYPE
    SYNTAX    INTEGER (0..9)
    ACCESS    read-write
    STATUS    mandatory
    DESCRIPTION
        "Complicated!"
    ::= { meaAnalogControlEntry2 1 }

meaAnalogOutputsUpperThresholdSource2 OBJECT-TYPE
    SYNTAX    INTEGER (0..2)
    ACCESS    read-write
    STATUS    mandatory
    DESCRIPTION
        "0=Analog 1=Temp 2=Humidity"
    ::= { meaAnalogControlEntry2 2 }

meaAnalogOutputsLowerThresholdSource2 OBJECT-TYPE
    SYNTAX    INTEGER (0..2)
    ACCESS    read-write
    STATUS    mandatory
    DESCRIPTION
        "0=Analog 1=Temp 2=Humidity"
    ::= { meaAnalogControlEntry2 3 }

-- }}}
-- {{{ Entry 3

meaAnalogOutputsControl3 OBJECT-TYPE
    SYNTAX    INTEGER (0..9)
    ACCESS    read-write
    STATUS    mandatory
    DESCRIPTION
        "Complicated!"
    ::= { meaAnalogControlEntry3 1 }

meaAnalogOutputsUpperThresholdSource3 OBJECT-TYPE
    SYNTAX    INTEGER (0..2)
    ACCESS    read-write
    STATUS    mandatory
    DESCRIPTION
        "0=Analog 1=Temp 2=Humidity"
    ::= { meaAnalogControlEntry3 2 }

meaAnalogOutputsLowerThresholdSource3 OBJECT-TYPE
    SYNTAX    INTEGER (0..2)
    ACCESS    read-write
    STATUS    mandatory
    DESCRIPTION
        "0=Analog 1=Temp 2=Humidity"
    ::= { meaAnalogControlEntry3 3 }

-- }}}
-- {{{ Entry 4

meaAnalogOutputsControl4 OBJECT-TYPE
    SYNTAX    INTEGER (0..9)
    ACCESS    read-write
    STATUS    mandatory
    DESCRIPTION
        "Complicated!"
    ::= { meaAnalogControlEntry4 1 }

meaAnalogOutputsUpperThresholdSource4 OBJECT-TYPE
    SYNTAX    INTEGER (0..2)
    ACCESS    read-write
    STATUS    mandatory
    DESCRIPTION
        "0=Analog 1=Temp 2=Humidity"
    ::= { meaAnalogControlEntry4 2 }

meaAnalogOutputsLowerThresholdSource4 OBJECT-TYPE
    SYNTAX    INTEGER (0..2)
    ACCESS    read-write
    STATUS    mandatory
    DESCRIPTION
        "0=Analog 1=Temp 2=Humidity"
    ::= { meaAnalogControlEntry4 3 }

-- }}}
-- {{{ Entry 5

meaAnalogOutputsControl5 OBJECT-TYPE
    SYNTAX    INTEGER (0..9)
    ACCESS    read-write
    STATUS    mandatory
    DESCRIPTION
        "Complicated!"
    ::= { meaAnalogControlEntry5 1 }

meaAnalogOutputsUpperThresholdSource5 OBJECT-TYPE
    SYNTAX    INTEGER (0..2)
    ACCESS    read-write
    STATUS    mandatory
    DESCRIPTION
        "0=Analog 1=Temp 2=Humidity"
    ::= { meaAnalogControlEntry5 2 }

meaAnalogOutputsLowerThresholdSource5 OBJECT-TYPE
    SYNTAX    INTEGER (0..2)
    ACCESS    read-write
    STATUS    mandatory
    DESCRIPTION
        "0=Analog 1=Temp 2=Humidity"
    ::= { meaAnalogControlEntry5 3 }

-- }}}
-- {{{ Entry 6

meaAnalogOutputsControl6 OBJECT-TYPE
    SYNTAX    INTEGER (0..9)
    ACCESS    read-write
    STATUS    mandatory
    DESCRIPTION
        "Complicated!"
    ::= { meaAnalogControlEntry6 1 }

meaAnalogOutputsUpperThresholdSource6 OBJECT-TYPE
    SYNTAX    INTEGER (0..2)
    ACCESS    read-write
    STATUS    mandatory
    DESCRIPTION
        "0=Analog 1=Temp 2=Humidity"
    ::= { meaAnalogControlEntry6 2 }

meaAnalogOutputsLowerThresholdSource6 OBJECT-TYPE
    SYNTAX    INTEGER (0..2)
    ACCESS    read-write
    STATUS    mandatory
    DESCRIPTION
        "0=Analog 1=Temp 2=Humidity"
    ::= { meaAnalogControlEntry6 3 }

-- }}}
-- {{{ Entry 7

meaAnalogOutputsControl7 OBJECT-TYPE
    SYNTAX    INTEGER (0..9)
    ACCESS    read-write
    STATUS    mandatory
    DESCRIPTION
        "Complicated!"
    ::= { meaAnalogControlEntry7 1 }

meaAnalogOutputsUpperThresholdSource7 OBJECT-TYPE
    SYNTAX    INTEGER (0..2)
    ACCESS    read-write
    STATUS    mandatory
    DESCRIPTION
        "0=Analog 1=Temp 2=Humidity"
    ::= { meaAnalogControlEntry7 2 }

meaAnalogOutputsLowerThresholdSource7 OBJECT-TYPE
    SYNTAX    INTEGER (0..2)
    ACCESS    read-write
    STATUS    mandatory
    DESCRIPTION
        "0=Analog 1=Temp 2=Humidity"
    ::= { meaAnalogControlEntry7 3 }

-- }}}
-- {{{ Entry 8

meaAnalogOutputsControl8 OBJECT-TYPE
    SYNTAX    INTEGER (0..9)
    ACCESS    read-write
    STATUS    mandatory
    DESCRIPTION
        "Complicated!"
    ::= { meaAnalogControlEntry8 1 }

meaAnalogOutputsUpperThresholdSource8 OBJECT-TYPE
    SYNTAX    INTEGER (0..2)
    ACCESS    read-write
    STATUS    mandatory
    DESCRIPTION
        "0=Analog 1=Temp 2=Humidity"
    ::= { meaAnalogControlEntry8 2 }

meaAnalogOutputsLowerThresholdSource8 OBJECT-TYPE
    SYNTAX    INTEGER (0..2)
    ACCESS    read-write
    STATUS    mandatory
    DESCRIPTION
        "0=Analog 1=Temp 2=Humidity"
    ::= { meaAnalogControlEntry8 3 }

-- }}}
-- {{{ Entry 9

meaAnalogOutputsControl9 OBJECT-TYPE
    SYNTAX    INTEGER (0..9)
    ACCESS    read-write
    STATUS    mandatory
    DESCRIPTION
        "Complicated!"
    ::= { meaAnalogControlEntry9 1 }

meaAnalogOutputsUpperThresholdSource9 OBJECT-TYPE
    SYNTAX    INTEGER (0..2)
    ACCESS    read-write
    STATUS    mandatory
    DESCRIPTION
        "0=Analog 1=Temp 2=Humidity"
    ::= { meaAnalogControlEntry9 2 }

meaAnalogOutputsLowerThresholdSource9 OBJECT-TYPE
    SYNTAX    INTEGER (0..2)
    ACCESS    read-write
    STATUS    mandatory
    DESCRIPTION
        "0=Analog 1=Temp 2=Humidity"
    ::= { meaAnalogControlEntry9 3 }

-- }}}
-- {{{ Entry 10

meaAnalogOutputsControl10 OBJECT-TYPE
    SYNTAX    INTEGER (0..9)
    ACCESS    read-write
    STATUS    mandatory
    DESCRIPTION
        "Complicated!"
    ::= { meaAnalogControlEntry10 1 }

meaAnalogOutputsUpperThresholdSource10 OBJECT-TYPE
    SYNTAX    INTEGER (0..2)
    ACCESS    read-write
    STATUS    mandatory
    DESCRIPTION
        "0=Analog 1=Temp 2=Humidity"
    ::= { meaAnalogControlEntry10 2 }

meaAnalogOutputsLowerThresholdSource10 OBJECT-TYPE
    SYNTAX    INTEGER (0..2)
    ACCESS    read-write
    STATUS    mandatory
    DESCRIPTION
        "0=Analog 1=Temp 2=Humidity"
    ::= { meaAnalogControlEntry10 3 }

-- }}}
-- {{{ Entry 11

meaAnalogOutputsControl11 OBJECT-TYPE
    SYNTAX    INTEGER (0..9)
    ACCESS    read-write
    STATUS    mandatory
    DESCRIPTION
        "Complicated!"
    ::= { meaAnalogControlEntry11 1 }

meaAnalogOutputsUpperThresholdSource11 OBJECT-TYPE
    SYNTAX    INTEGER (0..2)
    ACCESS    read-write
    STATUS    mandatory
    DESCRIPTION
        "0=Analog 1=Temp 2=Humidity"
    ::= { meaAnalogControlEntry11 2 }

meaAnalogOutputsLowerThresholdSource11 OBJECT-TYPE
    SYNTAX    INTEGER (0..2)
    ACCESS    read-write
    STATUS    mandatory
    DESCRIPTION
        "0=Analog 1=Temp 2=Humidity"
    ::= { meaAnalogControlEntry11 3 }

-- }}}
-- {{{ Entry 12

meaAnalogOutputsControl12 OBJECT-TYPE
    SYNTAX    INTEGER (0..9)
    ACCESS    read-write
    STATUS    mandatory
    DESCRIPTION
        "Complicated!"
    ::= { meaAnalogControlEntry12 1 }

meaAnalogOutputsUpperThresholdSource12 OBJECT-TYPE
    SYNTAX    INTEGER (0..2)
    ACCESS    read-write
    STATUS    mandatory
    DESCRIPTION
        "0=Analog 1=Temp 2=Humidity"
    ::= { meaAnalogControlEntry12 2 }

meaAnalogOutputsLowerThresholdSource12 OBJECT-TYPE
    SYNTAX    INTEGER (0..2)
    ACCESS    read-write
    STATUS    mandatory
    DESCRIPTION
        "0=Analog 1=Temp 2=Humidity"
    ::= { meaAnalogControlEntry12 3 }

-- }}}
-- {{{ Entry 13

meaAnalogOutputsControl13 OBJECT-TYPE
    SYNTAX    INTEGER (0..9)
    ACCESS    read-write
    STATUS    mandatory
    DESCRIPTION
        "Complicated!"
    ::= { meaAnalogControlEntry13 1 }

meaAnalogOutputsUpperThresholdSource13 OBJECT-TYPE
    SYNTAX    INTEGER (0..2)
    ACCESS    read-write
    STATUS    mandatory
    DESCRIPTION
        "0=Analog 1=Temp 2=Humidity"
    ::= { meaAnalogControlEntry13 2 }

meaAnalogOutputsLowerThresholdSource13 OBJECT-TYPE
    SYNTAX    INTEGER (0..2)
    ACCESS    read-write
    STATUS    mandatory
    DESCRIPTION
        "0=Analog 1=Temp 2=Humidity"
    ::= { meaAnalogControlEntry13 3 }

-- }}}
-- {{{ Entry 14

meaAnalogOutputsControl14 OBJECT-TYPE
    SYNTAX    INTEGER (0..9)
    ACCESS    read-write
    STATUS    mandatory
    DESCRIPTION
        "Complicated!"
    ::= { meaAnalogControlEntry14 1 }

meaAnalogOutputsUpperThresholdSource14 OBJECT-TYPE
    SYNTAX    INTEGER (0..2)
    ACCESS    read-write
    STATUS    mandatory
    DESCRIPTION
        "0=Analog 1=Temp 2=Humidity"
    ::= { meaAnalogControlEntry14 2 }

meaAnalogOutputsLowerThresholdSource14 OBJECT-TYPE
    SYNTAX    INTEGER (0..2)
    ACCESS    read-write
    STATUS    mandatory
    DESCRIPTION
        "0=Analog 1=Temp 2=Humidity"
    ::= { meaAnalogControlEntry14 3 }

-- }}}
-- {{{ Entry 15

meaAnalogOutputsControl15 OBJECT-TYPE
    SYNTAX    INTEGER (0..9)
    ACCESS    read-write
    STATUS    mandatory
    DESCRIPTION
        "Complicated!"
    ::= { meaAnalogControlEntry15 1 }

meaAnalogOutputsUpperThresholdSource15 OBJECT-TYPE
    SYNTAX    INTEGER (0..2)
    ACCESS    read-write
    STATUS    mandatory
    DESCRIPTION
        "0=Analog 1=Temp 2=Humidity"
    ::= { meaAnalogControlEntry15 2 }

meaAnalogOutputsLowerThresholdSource15 OBJECT-TYPE
    SYNTAX    INTEGER (0..2)
    ACCESS    read-write
    STATUS    mandatory
    DESCRIPTION
        "0=Analog 1=Temp 2=Humidity"
    ::= { meaAnalogControlEntry15 3 }

-- }}}
-- {{{ Entry 16

meaAnalogOutputsControl16 OBJECT-TYPE
    SYNTAX    INTEGER (0..9)
    ACCESS    read-write
    STATUS    mandatory
    DESCRIPTION
        "Complicated!"
    ::= { meaAnalogControlEntry16 1 }

meaAnalogOutputsUpperThresholdSource16 OBJECT-TYPE
    SYNTAX    INTEGER (0..2)
    ACCESS    read-write
    STATUS    mandatory
    DESCRIPTION
        "0=Analog 1=Temp 2=Humidity"
    ::= { meaAnalogControlEntry16 2 }

meaAnalogOutputsLowerThresholdSource16 OBJECT-TYPE
    SYNTAX    INTEGER (0..2)
    ACCESS    read-write
    STATUS    mandatory
    DESCRIPTION
        "0=Analog 1=Temp 2=Humidity"
    ::= { meaAnalogControlEntry16 3 }

-- }}}


-- }}}
-- {{{ meaDigitalControlTable Group  

meaDigitalControlEntry1  OBJECT IDENTIFIER ::= { meaDigitalControlsTable 1  }
meaDigitalControlEntry2  OBJECT IDENTIFIER ::= { meaDigitalControlsTable 2  }
meaDigitalControlEntry3  OBJECT IDENTIFIER ::= { meaDigitalControlsTable 3  }
meaDigitalControlEntry4  OBJECT IDENTIFIER ::= { meaDigitalControlsTable 4  }
meaDigitalControlEntry5  OBJECT IDENTIFIER ::= { meaDigitalControlsTable 5  }
meaDigitalControlEntry6  OBJECT IDENTIFIER ::= { meaDigitalControlsTable 6  }
meaDigitalControlEntry7  OBJECT IDENTIFIER ::= { meaDigitalControlsTable 7  }
meaDigitalControlEntry8  OBJECT IDENTIFIER ::= { meaDigitalControlsTable 8  }
meaDigitalControlEntry9  OBJECT IDENTIFIER ::= { meaDigitalControlsTable 9  }
meaDigitalControlEntry10 OBJECT IDENTIFIER ::= { meaDigitalControlsTable 10 }
meaDigitalControlEntry11 OBJECT IDENTIFIER ::= { meaDigitalControlsTable 11 }
meaDigitalControlEntry12 OBJECT IDENTIFIER ::= { meaDigitalControlsTable 12 }
meaDigitalControlEntry13 OBJECT IDENTIFIER ::= { meaDigitalControlsTable 13 }
meaDigitalControlEntry14 OBJECT IDENTIFIER ::= { meaDigitalControlsTable 14 }
meaDigitalControlEntry15 OBJECT IDENTIFIER ::= { meaDigitalControlsTable 15 }
meaDigitalControlEntry16 OBJECT IDENTIFIER ::= { meaDigitalControlsTable 16 }
meaDigitalControlEntry17 OBJECT IDENTIFIER ::= { meaDigitalControlsTable 17 }
meaDigitalControlEntry18 OBJECT IDENTIFIER ::= { meaDigitalControlsTable 18 }
meaDigitalControlEntry19 OBJECT IDENTIFIER ::= { meaDigitalControlsTable 19 }
meaDigitalControlEntry20 OBJECT IDENTIFIER ::= { meaDigitalControlsTable 20 }
meaDigitalControlEntry21 OBJECT IDENTIFIER ::= { meaDigitalControlsTable 21 }
meaDigitalControlEntry22 OBJECT IDENTIFIER ::= { meaDigitalControlsTable 22 }
meaDigitalControlEntry23 OBJECT IDENTIFIER ::= { meaDigitalControlsTable 23 }
meaDigitalControlEntry24 OBJECT IDENTIFIER ::= { meaDigitalControlsTable 24 }
meaDigitalControlEntry25 OBJECT IDENTIFIER ::= { meaDigitalControlsTable 25 }
meaDigitalControlEntry26 OBJECT IDENTIFIER ::= { meaDigitalControlsTable 26 }
meaDigitalControlEntry27 OBJECT IDENTIFIER ::= { meaDigitalControlsTable 27 }
meaDigitalControlEntry28 OBJECT IDENTIFIER ::= { meaDigitalControlsTable 28 }
meaDigitalControlEntry29 OBJECT IDENTIFIER ::= { meaDigitalControlsTable 29 }
meaDigitalControlEntry30 OBJECT IDENTIFIER ::= { meaDigitalControlsTable 30 }
meaDigitalControlEntry31 OBJECT IDENTIFIER ::= { meaDigitalControlsTable 31 }
meaDigitalControlEntry32 OBJECT IDENTIFIER ::= { meaDigitalControlsTable 32 }

-- meaDigitalControlEntries
-- {{{ Entry 1

meaDigitalOutputsControlBooleanANDInput1 OBJECT-TYPE
    SYNTAX    DisplayString
    ACCESS    read-write
    STATUS    mandatory
    DESCRIPTION
        "Dnn=digital nn source Ann=analogue nn source no spaces used. Max 16 inputs"
    ::= { meaDigitalControlEntry1 1 }

meaDigitalOutputsControlBooleanORInput1 OBJECT-TYPE
    SYNTAX    DisplayString
    ACCESS    read-write
    STATUS    mandatory
    DESCRIPTION
        "Dnn=digital nn source Ann=analogue nn source no spaces used. Max 16 inputs"
    ::= { meaDigitalControlEntry1 2 }

meaDigitalOutputsControlBooleanOutputFunction1 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry1 3 }

-- }}}
-- {{{ Entry 2

meaDigitalOutputsControlBooleanANDInput2 OBJECT-TYPE
    SYNTAX    DisplayString
    ACCESS    read-write
    STATUS    mandatory
    DESCRIPTION
        "Dnn=digital nn source Ann=analogue nn source no spaces used. Max 16 inputs"
    ::= { meaDigitalControlEntry2 1 }

meaDigitalOutputsControlBooleanORInput2 OBJECT-TYPE
    SYNTAX    DisplayString
    ACCESS    read-write
    STATUS    mandatory
    DESCRIPTION
        "Dnn=digital nn source Ann=analogue nn source no spaces used. Max 16 inputs"
    ::= { meaDigitalControlEntry2 2 }

meaDigitalOutputsControlBooleanOutputFunction2 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry2 3 }

-- }}}
-- {{{ Entry 3

meaDigitalOutputsControlBooleanANDInput3 OBJECT-TYPE
    SYNTAX    DisplayString
    ACCESS    read-write
    STATUS    mandatory
    DESCRIPTION
        "Dnn=digital nn source Ann=analogue nn source no spaces used. Max 16 inputs"
    ::= { meaDigitalControlEntry3 1 }

meaDigitalOutputsControlBooleanORInput3 OBJECT-TYPE
    SYNTAX    DisplayString
    ACCESS    read-write
    STATUS    mandatory
    DESCRIPTION
        "Dnn=digital nn source Ann=analogue nn source no spaces used. Max 16 inputs"
    ::= { meaDigitalControlEntry3 2 }

meaDigitalOutputsControlBooleanOutputFunction3 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry3 3 }

-- }}}
-- {{{ Entry 4

meaDigitalOutputsControlBooleanANDInput4 OBJECT-TYPE
    SYNTAX    DisplayString
    ACCESS    read-write
    STATUS    mandatory
    DESCRIPTION
        "Dnn=digital nn source Ann=analogue nn source no spaces used. Max 16 inputs"
    ::= { meaDigitalControlEntry4 1 }

meaDigitalOutputsControlBooleanORInput4 OBJECT-TYPE
    SYNTAX    DisplayString
    ACCESS    read-write
    STATUS    mandatory
    DESCRIPTION
        "Dnn=digital nn source Ann=analogue nn source no spaces used. Max 16 inputs"
    ::= { meaDigitalControlEntry4 2 }

meaDigitalOutputsControlBooleanOutputFunction4 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry4 3 }

-- }}}
-- {{{ Entry 5

meaDigitalOutputsControlBooleanANDInput5 OBJECT-TYPE
    SYNTAX    DisplayString
    ACCESS    read-write
    STATUS    mandatory
    DESCRIPTION
        "Dnn=digital nn source Ann=analogue nn source no spaces used. Max 16 inputs"
    ::= { meaDigitalControlEntry5 1 }

meaDigitalOutputsControlBooleanORInput5 OBJECT-TYPE
    SYNTAX    DisplayString
    ACCESS    read-write
    STATUS    mandatory
    DESCRIPTION
        "Dnn=digital nn source Ann=analogue nn source no spaces used. Max 16 inputs"
    ::= { meaDigitalControlEntry5 2 }

meaDigitalOutputsControlBooleanOutputFunction5 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry5 3 }

-- }}}
-- {{{ Entry 6

meaDigitalOutputsControlBooleanANDInput6 OBJECT-TYPE
    SYNTAX    DisplayString
    ACCESS    read-write
    STATUS    mandatory
    DESCRIPTION
        "Dnn=digital nn source Ann=analogue nn source no spaces used. Max 16 inputs"
    ::= { meaDigitalControlEntry6 1 }

meaDigitalOutputsControlBooleanORInput6 OBJECT-TYPE
    SYNTAX    DisplayString
    ACCESS    read-write
    STATUS    mandatory
    DESCRIPTION
        "Dnn=digital nn source Ann=analogue nn source no spaces used. Max 16 inputs"
    ::= { meaDigitalControlEntry6 2 }

meaDigitalOutputsControlBooleanOutputFunction6 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry6 3 }

-- }}}
-- {{{ Entry 7

meaDigitalOutputsControlBooleanANDInput7 OBJECT-TYPE
    SYNTAX    DisplayString
    ACCESS    read-write
    STATUS    mandatory
    DESCRIPTION
        "Dnn=digital nn source Ann=analogue nn source no spaces used. Max 16 inputs"
    ::= { meaDigitalControlEntry7 1 }

meaDigitalOutputsControlBooleanORInput7 OBJECT-TYPE
    SYNTAX    DisplayString
    ACCESS    read-write
    STATUS    mandatory
    DESCRIPTION
        "Dnn=digital nn source Ann=analogue nn source no spaces used. Max 16 inputs"
    ::= { meaDigitalControlEntry7 2 }

meaDigitalOutputsControlBooleanOutputFunction7 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry7 3 }

-- }}}
-- {{{ Entry 8

meaDigitalOutputsControlBooleanANDInput8 OBJECT-TYPE
    SYNTAX    DisplayString
    ACCESS    read-write
    STATUS    mandatory
    DESCRIPTION
        "Dnn=digital nn source Ann=analogue nn source no spaces used. Max 16 inputs"
    ::= { meaDigitalControlEntry8 1 }

meaDigitalOutputsControlBooleanORInput8 OBJECT-TYPE
    SYNTAX    DisplayString
    ACCESS    read-write
    STATUS    mandatory
    DESCRIPTION
        "Dnn=digital nn source Ann=analogue nn source no spaces used. Max 16 inputs"
    ::= { meaDigitalControlEntry8 2 }

meaDigitalOutputsControlBooleanOutputFunction8 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry8 3 }

-- }}}
-- {{{ Entry 9

meaDigitalOutputsControlBooleanANDInput9 OBJECT-TYPE
    SYNTAX    DisplayString
    ACCESS    read-write
    STATUS    mandatory
    DESCRIPTION
        "Dnn=digital nn source Ann=analogue nn source no spaces used. Max 16 inputs"
    ::= { meaDigitalControlEntry9 1 }

meaDigitalOutputsControlBooleanORInput9 OBJECT-TYPE
    SYNTAX    DisplayString
    ACCESS    read-write
    STATUS    mandatory
    DESCRIPTION
        "Dnn=digital nn source Ann=analogue nn source no spaces used. Max 16 inputs"
    ::= { meaDigitalControlEntry9 2 }

meaDigitalOutputsControlBooleanOutputFunction9 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry9 3 }

-- }}}
-- {{{ Entry 10

meaDigitalOutputsControlBooleanANDInput10 OBJECT-TYPE
    SYNTAX    DisplayString
    ACCESS    read-write
    STATUS    mandatory
    DESCRIPTION
        "Dnn=digital nn source Ann=analogue nn source no spaces used. Max 16 inputs"
    ::= { meaDigitalControlEntry10 1 }

meaDigitalOutputsControlBooleanORInput10 OBJECT-TYPE
    SYNTAX    DisplayString
    ACCESS    read-write
    STATUS    mandatory
    DESCRIPTION
        "Dnn=digital nn source Ann=analogue nn source no spaces used. Max 16 inputs"
    ::= { meaDigitalControlEntry10 2 }

meaDigitalOutputsControlBooleanOutputFunction10 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry10 3 }

-- }}}
-- {{{ Entry 11

meaDigitalOutputsControlBooleanANDInput11 OBJECT-TYPE
    SYNTAX    DisplayString
    ACCESS    read-write
    STATUS    mandatory
    DESCRIPTION
        "Dnn=digital nn source Ann=analogue nn source no spaces used. Max 16 inputs"
    ::= { meaDigitalControlEntry11 1 }

meaDigitalOutputsControlBooleanORInput11 OBJECT-TYPE
    SYNTAX    DisplayString
    ACCESS    read-write
    STATUS    mandatory
    DESCRIPTION
        "Dnn=digital nn source Ann=analogue nn source no spaces used. Max 16 inputs"
    ::= { meaDigitalControlEntry11 2 }

meaDigitalOutputsControlBooleanOutputFunction11 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry11 3 }

-- }}}
-- {{{ Entry 12

meaDigitalOutputsControlBooleanANDInput12 OBJECT-TYPE
    SYNTAX    DisplayString
    ACCESS    read-write
    STATUS    mandatory
    DESCRIPTION
        "Dnn=digital nn source Ann=analogue nn source no spaces used. Max 16 inputs"
    ::= { meaDigitalControlEntry12 1 }

meaDigitalOutputsControlBooleanORInput12 OBJECT-TYPE
    SYNTAX    DisplayString
    ACCESS    read-write
    STATUS    mandatory
    DESCRIPTION
        "Dnn=digital nn source Ann=analogue nn source no spaces used. Max 16 inputs"
    ::= { meaDigitalControlEntry12 2 }

meaDigitalOutputsControlBooleanOutputFunction12 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry12 3 }

-- }}}
-- {{{ Entry 13

meaDigitalOutputsControlBooleanANDInput13 OBJECT-TYPE
    SYNTAX    DisplayString
    ACCESS    read-write
    STATUS    mandatory
    DESCRIPTION
        "Dnn=digital nn source Ann=analogue nn source no spaces used. Max 16 inputs"
    ::= { meaDigitalControlEntry13 1 }

meaDigitalOutputsControlBooleanORInput13 OBJECT-TYPE
    SYNTAX    DisplayString
    ACCESS    read-write
    STATUS    mandatory
    DESCRIPTION
        "Dnn=digital nn source Ann=analogue nn source no spaces used. Max 16 inputs"
    ::= { meaDigitalControlEntry13 2 }

meaDigitalOutputsControlBooleanOutputFunction13 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry13 3 }

-- }}}
-- {{{ Entry 14

meaDigitalOutputsControlBooleanANDInput14 OBJECT-TYPE
    SYNTAX    DisplayString
    ACCESS    read-write
    STATUS    mandatory
    DESCRIPTION
        "Dnn=digital nn source Ann=analogue nn source no spaces used. Max 16 inputs"
    ::= { meaDigitalControlEntry14 1 }

meaDigitalOutputsControlBooleanORInput14 OBJECT-TYPE
    SYNTAX    DisplayString
    ACCESS    read-write
    STATUS    mandatory
    DESCRIPTION
        "Dnn=digital nn source Ann=analogue nn source no spaces used. Max 16 inputs"
    ::= { meaDigitalControlEntry14 2 }

meaDigitalOutputsControlBooleanOutputFunction14 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry14 3 }

-- }}}
-- {{{ Entry 15

meaDigitalOutputsControlBooleanANDInput15 OBJECT-TYPE
    SYNTAX    DisplayString
    ACCESS    read-write
    STATUS    mandatory
    DESCRIPTION
        "Dnn=digital nn source Ann=analogue nn source no spaces used. Max 16 inputs"
    ::= { meaDigitalControlEntry15 1 }

meaDigitalOutputsControlBooleanORInput15 OBJECT-TYPE
    SYNTAX    DisplayString
    ACCESS    read-write
    STATUS    mandatory
    DESCRIPTION
        "Dnn=digital nn source Ann=analogue nn source no spaces used. Max 16 inputs"
    ::= { meaDigitalControlEntry15 2 }

meaDigitalOutputsControlBooleanOutputFunction15 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry15 3 }

-- }}}
-- {{{ Entry 16

meaDigitalOutputsControlBooleanANDInput16 OBJECT-TYPE
    SYNTAX    DisplayString
    ACCESS    read-write
    STATUS    mandatory
    DESCRIPTION
        "Dnn=digital nn source Ann=analogue nn source no spaces used. Max 16 inputs"
    ::= { meaDigitalControlEntry16 1 }

meaDigitalOutputsControlBooleanORInput16 OBJECT-TYPE
    SYNTAX    DisplayString
    ACCESS    read-write
    STATUS    mandatory
    DESCRIPTION
        "Dnn=digital nn source Ann=analogue nn source no spaces used. Max 16 inputs"
    ::= { meaDigitalControlEntry16 2 }

meaDigitalOutputsControlBooleanOutputFunction16 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry16 3 }

-- }}}
-- {{{ Entry 17

meaDigitalOutputsControlBooleanANDInput17 OBJECT-TYPE
    SYNTAX    DisplayString
    ACCESS    read-write
    STATUS    mandatory
    DESCRIPTION
        "Dnn=digital nn source Ann=analogue nn source no spaces used. Max 16 inputs"
    ::= { meaDigitalControlEntry17 1 }

meaDigitalOutputsControlBooleanORInput17 OBJECT-TYPE
    SYNTAX    DisplayString
    ACCESS    read-write
    STATUS    mandatory
    DESCRIPTION
        "Dnn=digital nn source Ann=analogue nn source no spaces used. Max 16 inputs"
    ::= { meaDigitalControlEntry17 2 }

meaDigitalOutputsControlBooleanOutputFunction17 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry17 3 }

-- }}}
-- {{{ Entry 18

meaDigitalOutputsControlBooleanANDInput18 OBJECT-TYPE
    SYNTAX    DisplayString
    ACCESS    read-write
    STATUS    mandatory
    DESCRIPTION
        "Dnn=digital nn source Ann=analogue nn source no spaces used. Max 16 inputs"
    ::= { meaDigitalControlEntry18 1 }

meaDigitalOutputsControlBooleanORInput18 OBJECT-TYPE
    SYNTAX    DisplayString
    ACCESS    read-write
    STATUS    mandatory
    DESCRIPTION
        "Dnn=digital nn source Ann=analogue nn source no spaces used. Max 16 inputs"
    ::= { meaDigitalControlEntry18 2 }

meaDigitalOutputsControlBooleanOutputFunction18 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry18 3 }

-- }}}
-- {{{ Entry 19

meaDigitalOutputsControlBooleanANDInput19 OBJECT-TYPE
    SYNTAX    DisplayString
    ACCESS    read-write
    STATUS    mandatory
    DESCRIPTION
        "Dnn=digital nn source Ann=analogue nn source no spaces used. Max 16 inputs"
    ::= { meaDigitalControlEntry19 1 }

meaDigitalOutputsControlBooleanORInput19 OBJECT-TYPE
    SYNTAX    DisplayString
    ACCESS    read-write
    STATUS    mandatory
    DESCRIPTION
        "Dnn=digital nn source Ann=analogue nn source no spaces used. Max 16 inputs"
    ::= { meaDigitalControlEntry19 2 }

meaDigitalOutputsControlBooleanOutputFunction19 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry19 3 }

-- }}}
-- {{{ Entry 20

meaDigitalOutputsControlBooleanANDInput20 OBJECT-TYPE
    SYNTAX    DisplayString
    ACCESS    read-write
    STATUS    mandatory
    DESCRIPTION
        "Dnn=digital nn source Ann=analogue nn source no spaces used. Max 16 inputs"
    ::= { meaDigitalControlEntry20 1 }

meaDigitalOutputsControlBooleanORInput20 OBJECT-TYPE
    SYNTAX    DisplayString
    ACCESS    read-write
    STATUS    mandatory
    DESCRIPTION
        "Dnn=digital nn source Ann=analogue nn source no spaces used. Max 16 inputs"
    ::= { meaDigitalControlEntry20 2 }

meaDigitalOutputsControlBooleanOutputFunction20 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry20 3 }

-- }}}
-- {{{ Entry 21

meaDigitalOutputsControlBooleanANDInput21 OBJECT-TYPE
    SYNTAX    DisplayString
    ACCESS    read-write
    STATUS    mandatory
    DESCRIPTION
        "Dnn=digital nn source Ann=analogue nn source no spaces used. Max 16 inputs"
    ::= { meaDigitalControlEntry21 1 }

meaDigitalOutputsControlBooleanORInput21 OBJECT-TYPE
    SYNTAX    DisplayString
    ACCESS    read-write
    STATUS    mandatory
    DESCRIPTION
        "Dnn=digital nn source Ann=analogue nn source no spaces used. Max 16 inputs"
    ::= { meaDigitalControlEntry21 2 }

meaDigitalOutputsControlBooleanOutputFunction21 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry21 3 }

-- }}}
-- {{{ Entry 22

meaDigitalOutputsControlBooleanANDInput22 OBJECT-TYPE
    SYNTAX    DisplayString
    ACCESS    read-write
    STATUS    mandatory
    DESCRIPTION
        "Dnn=digital nn source Ann=analogue nn source no spaces used. Max 16 inputs"
    ::= { meaDigitalControlEntry22 1 }

meaDigitalOutputsControlBooleanORInput22 OBJECT-TYPE
    SYNTAX    DisplayString
    ACCESS    read-write
    STATUS    mandatory
    DESCRIPTION
        "Dnn=digital nn source Ann=analogue nn source no spaces used. Max 16 inputs"
    ::= { meaDigitalControlEntry22 2 }

meaDigitalOutputsControlBooleanOutputFunction22 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry22 3 }

-- }}}
-- {{{ Entry 23

meaDigitalOutputsControlBooleanANDInput23 OBJECT-TYPE
    SYNTAX    DisplayString
    ACCESS    read-write
    STATUS    mandatory
    DESCRIPTION
        "Dnn=digital nn source Ann=analogue nn source no spaces used. Max 16 inputs"
    ::= { meaDigitalControlEntry23 1 }

meaDigitalOutputsControlBooleanORInput23 OBJECT-TYPE
    SYNTAX    DisplayString
    ACCESS    read-write
    STATUS    mandatory
    DESCRIPTION
        "Dnn=digital nn source Ann=analogue nn source no spaces used. Max 16 inputs"
    ::= { meaDigitalControlEntry23 2 }

meaDigitalOutputsControlBooleanOutputFunction23 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry23 3 }

-- }}}
-- {{{ Entry 24

meaDigitalOutputsControlBooleanANDInput24 OBJECT-TYPE
    SYNTAX    DisplayString
    ACCESS    read-write
    STATUS    mandatory
    DESCRIPTION
        "Dnn=digital nn source Ann=analogue nn source no spaces used. Max 16 inputs"
    ::= { meaDigitalControlEntry24 1 }

meaDigitalOutputsControlBooleanORInput24 OBJECT-TYPE
    SYNTAX    DisplayString
    ACCESS    read-write
    STATUS    mandatory
    DESCRIPTION
        "Dnn=digital nn source Ann=analogue nn source no spaces used. Max 16 inputs"
    ::= { meaDigitalControlEntry24 2 }

meaDigitalOutputsControlBooleanOutputFunction24 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry24 3 }

-- }}}
-- {{{ Entry 25

meaDigitalOutputsControlBooleanANDInput25 OBJECT-TYPE
    SYNTAX    DisplayString
    ACCESS    read-write
    STATUS    mandatory
    DESCRIPTION
        "Dnn=digital nn source Ann=analogue nn source no spaces used. Max 16 inputs"
    ::= { meaDigitalControlEntry25 1 }

meaDigitalOutputsControlBooleanORInput25 OBJECT-TYPE
    SYNTAX    DisplayString
    ACCESS    read-write
    STATUS    mandatory
    DESCRIPTION
        "Dnn=digital nn source Ann=analogue nn source no spaces used. Max 16 inputs"
    ::= { meaDigitalControlEntry25 2 }

meaDigitalOutputsControlBooleanOutputFunction25 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry25 3 }

-- }}}
-- {{{ Entry 26

meaDigitalOutputsControlBooleanANDInput26 OBJECT-TYPE
    SYNTAX    DisplayString
    ACCESS    read-write
    STATUS    mandatory
    DESCRIPTION
        "Dnn=digital nn source Ann=analogue nn source no spaces used. Max 16 inputs"
    ::= { meaDigitalControlEntry26 1 }

meaDigitalOutputsControlBooleanORInput26 OBJECT-TYPE
    SYNTAX    DisplayString
    ACCESS    read-write
    STATUS    mandatory
    DESCRIPTION
        "Dnn=digital nn source Ann=analogue nn source no spaces used. Max 16 inputs"
    ::= { meaDigitalControlEntry26 2 }

meaDigitalOutputsControlBooleanOutputFunction26 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry26 3 }

-- }}}
-- {{{ Entry 27

meaDigitalOutputsControlBooleanANDInput27 OBJECT-TYPE
    SYNTAX    DisplayString
    ACCESS    read-write
    STATUS    mandatory
    DESCRIPTION
        "Dnn=digital nn source Ann=analogue nn source no spaces used. Max 16 inputs"
    ::= { meaDigitalControlEntry27 1 }

meaDigitalOutputsControlBooleanORInput27 OBJECT-TYPE
    SYNTAX    DisplayString
    ACCESS    read-write
    STATUS    mandatory
    DESCRIPTION
        "Dnn=digital nn source Ann=analogue nn source no spaces used. Max 16 inputs"
    ::= { meaDigitalControlEntry27 2 }

meaDigitalOutputsControlBooleanOutputFunction27 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry27 3 }

-- }}}
-- {{{ Entry 28

meaDigitalOutputsControlBooleanANDInput28 OBJECT-TYPE
    SYNTAX    DisplayString
    ACCESS    read-write
    STATUS    mandatory
    DESCRIPTION
        "Dnn=digital nn source Ann=analogue nn source no spaces used. Max 16 inputs"
    ::= { meaDigitalControlEntry28 1 }

meaDigitalOutputsControlBooleanORInput28 OBJECT-TYPE
    SYNTAX    DisplayString
    ACCESS    read-write
    STATUS    mandatory
    DESCRIPTION
        "Dnn=digital nn source Ann=analogue nn source no spaces used. Max 16 inputs"
    ::= { meaDigitalControlEntry28 2 }

meaDigitalOutputsControlBooleanOutputFunction28 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry28 3 }

-- }}}
-- {{{ Entry 29

meaDigitalOutputsControlBooleanANDInput29 OBJECT-TYPE
    SYNTAX    DisplayString
    ACCESS    read-write
    STATUS    mandatory
    DESCRIPTION
        "Dnn=digital nn source Ann=analogue nn source no spaces used. Max 16 inputs"
    ::= { meaDigitalControlEntry29 1 }

meaDigitalOutputsControlBooleanORInput29 OBJECT-TYPE
    SYNTAX    DisplayString
    ACCESS    read-write
    STATUS    mandatory
    DESCRIPTION
        "Dnn=digital nn source Ann=analogue nn source no spaces used. Max 16 inputs"
    ::= { meaDigitalControlEntry29 2 }

meaDigitalOutputsControlBooleanOutputFunction29 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry29 3 }

-- }}}
-- {{{ Entry 30

meaDigitalOutputsControlBooleanANDInput30 OBJECT-TYPE
    SYNTAX    DisplayString
    ACCESS    read-write
    STATUS    mandatory
    DESCRIPTION
        "Dnn=digital nn source Ann=analogue nn source no spaces used. Max 16 inputs"
    ::= { meaDigitalControlEntry30 1 }

meaDigitalOutputsControlBooleanORInput30 OBJECT-TYPE
    SYNTAX    DisplayString
    ACCESS    read-write
    STATUS    mandatory
    DESCRIPTION
        "Dnn=digital nn source Ann=analogue nn source no spaces used. Max 16 inputs"
    ::= { meaDigitalControlEntry30 2 }

meaDigitalOutputsControlBooleanOutputFunction30 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry30 3 }

-- }}}
-- {{{ Entry 31

meaDigitalOutputsControlBooleanANDInput31 OBJECT-TYPE
    SYNTAX    DisplayString
    ACCESS    read-write
    STATUS    mandatory
    DESCRIPTION
        "Dnn=digital nn source Ann=analogue nn source no spaces used. Max 16 inputs"
    ::= { meaDigitalControlEntry31 1 }

meaDigitalOutputsControlBooleanORInput31 OBJECT-TYPE
    SYNTAX    DisplayString
    ACCESS    read-write
    STATUS    mandatory
    DESCRIPTION
        "Dnn=digital nn source Ann=analogue nn source no spaces used. Max 16 inputs"
    ::= { meaDigitalControlEntry31 2 }

meaDigitalOutputsControlBooleanOutputFunction31 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry31 3 }

-- }}}
-- {{{ Entry 32

meaDigitalOutputsControlBooleanANDInput32 OBJECT-TYPE
    SYNTAX    DisplayString
    ACCESS    read-write
    STATUS    mandatory
    DESCRIPTION
        "Dnn=digital nn source Ann=analogue nn source no spaces used. Max 16 inputs"
    ::= { meaDigitalControlEntry32 1 }

meaDigitalOutputsControlBooleanORInput32 OBJECT-TYPE
    SYNTAX    DisplayString
    ACCESS    read-write
    STATUS    mandatory
    DESCRIPTION
        "Dnn=digital nn source Ann=analogue nn source no spaces used. Max 16 inputs"
    ::= { meaDigitalControlEntry32 2 }

meaDigitalOutputsControlBooleanOutputFunction32 OBJECT-TYPE
    SYNTAX    INTEGER (0..7)
    ACCESS    read-write
    STATUS    mandatory
    DESCRIPTION
        "0=no output 1=(and)(no o/p)(alarm en) 2=(or)(no o/p)(alarm en) 3=(and)(o/p en)(no alarm) 4=(or)(o/p en)(no alarm) 5=(and)(o/p en)(alarm en) 6=(or)(o/p en)(alarm en) 7,8,9,10,11,12=(not)1,2,3,4,5,6"
    ::= { meaDigitalControlEntry32 3 }

-- }}}


-- }}}

-- }}}
-- {{{ meaConfig               

-- {{{ meaConfigDate         

meaConfigDate  OBJECT-TYPE
    SYNTAX    DisplayString
    ACCESS    read-write
    STATUS    mandatory
    DESCRIPTION 
        "yyyymmdd"
    ::= { meaConfig 1 }

-- }}}
-- {{{ meaConfigTime         

meaConfigTime  OBJECT-TYPE
    SYNTAX    DisplayString
    ACCESS    read-write
    STATUS    mandatory
    DESCRIPTION 
        "Time in hhmmss format"
    ::= { meaConfig 2 }

-- }}}
-- {{{ meaConfigBaud         

meaConfigBaud  OBJECT-TYPE
    SYNTAX    INTEGER (1..7)
    ACCESS    read-write
    STATUS    mandatory
    DESCRIPTION 
        "see documentation"
    ::= { meaConfig 3 }

-- }}}
-- {{{ meaConfigTimeout      

meaConfigTimeout  OBJECT-TYPE
    SYNTAX    INTEGER (10..9999)
    ACCESS    read-only
    STATUS    mandatory
    DESCRIPTION 
        "Worst case response time in mS for device"
    ::= { meaConfig 4 }

-- }}}
-- {{{ meaConfigMiscString1  

meaConfigMiscString1  OBJECT-TYPE
    SYNTAX    DisplayString
    ACCESS    read-write
    STATUS    mandatory
    DESCRIPTION 
        "Defined by Mfr"
    ::= { meaConfig 5 }

-- }}}
-- {{{ meaConfigMiscString2  

meaConfigMiscString2  OBJECT-TYPE
    SYNTAX    DisplayString
    ACCESS    read-write
    STATUS    mandatory
    DESCRIPTION 
        "Defined by Mfr"
    ::= { meaConfig 6 }

-- }}}
-- {{{ meaConfigMiscByte1    

meaConfigMiscByte1  OBJECT-TYPE
    SYNTAX    INTEGER (0..99)
    ACCESS    read-write
    STATUS    mandatory
    DESCRIPTION 
        "Defined by Mfr"
    ::= { meaConfig 7 }

-- }}}
-- {{{ meaConfigMiscByte2    

meaConfigMiscByte2 OBJECT-TYPE
    SYNTAX    INTEGER (0..99)
    ACCESS    read-write
    STATUS    mandatory
    DESCRIPTION 
        "Defined by Mfr"
    ::= { meaConfig 8 }

-- }}}
-- {{{ meaConfigMiscByte3    

meaConfigMiscByte3  OBJECT-TYPE
    SYNTAX    INTEGER (0..99)
    ACCESS    read-write
    STATUS    mandatory
    DESCRIPTION 
        "Defined by Mfr"
    ::= { meaConfig 9 }

-- }}}
-- {{{ meaConfigMiscByte4    

meaConfigMiscByte4  OBJECT-TYPE
    SYNTAX    INTEGER (0..99)
    ACCESS    read-write
    STATUS    mandatory
    DESCRIPTION 
        "Defined by Mfr"
    ::= { meaConfig 10}

-- }}}
-- {{{ meaConfigMiscShort1   

meaConfigMiscShort1  OBJECT-TYPE
    SYNTAX    INTEGER (0..9999)
    ACCESS    read-write
    STATUS    mandatory
    DESCRIPTION 
        "Defined by Mfr"
    ::= { meaConfig 11 }

-- }}}
-- {{{ meaConfigMiscShort2   

meaConfigMiscShort2  OBJECT-TYPE
    SYNTAX    INTEGER (0..9999)
    ACCESS    read-write
    STATUS    mandatory
    DESCRIPTION 
        "Defined by Mfr"
    ::= { meaConfig 12 }

-- }}}
-- {{{ meaConfigMiscShort3   

meaConfigMiscShort3  OBJECT-TYPE
    SYNTAX    INTEGER (0..9999)
    ACCESS    read-write
    STATUS    mandatory
    DESCRIPTION 
        "Defined by Mfr"
    ::= { meaConfig 13 }

-- }}}
-- {{{ meaConfigMiscShort4   

meaConfigMiscShort4  OBJECT-TYPE
    SYNTAX    INTEGER (0..9999)
    ACCESS    read-write
    STATUS    mandatory
    DESCRIPTION 
        "Defined by Mfr"
    ::= { meaConfig 14 }

-- }}}
-- {{{ meaConfigMiscLong1    

meaConfigMiscLong1  OBJECT-TYPE
    SYNTAX    INTEGER (0..999999)
    ACCESS    read-write
    STATUS    mandatory
    DESCRIPTION 
        "Defined by Mfr"
    ::= { meaConfig 15 }

-- }}}
-- {{{ meaConfigMiscLong2    

meaConfigMiscLong2  OBJECT-TYPE
    SYNTAX    INTEGER (0..999999)
    ACCESS    read-write
    STATUS    mandatory
    DESCRIPTION 
        "Defined by Mfr"
    ::= { meaConfig 16 }

-- }}}
-- {{{ meaConfigMiscLong3    

meaConfigMiscLong3  OBJECT-TYPE
    SYNTAX    INTEGER (0..999999)
    ACCESS    read-write
    STATUS    mandatory
    DESCRIPTION 
        "Defined by Mfr"
    ::= { meaConfig 17 }

-- }}}
-- {{{ meaConfigMiscLong4    

meaConfigMiscLong4  OBJECT-TYPE
    SYNTAX    INTEGER (0..999999)
    ACCESS    read-write
    STATUS    mandatory
    DESCRIPTION 
        "Defined by Mfr"
    ::= { meaConfig 18 }

-- }}}

-- }}}

-- }}}
-- {{{ meaTraps    

meaTrapAnalogAlarms             OBJECT IDENTIFIER ::= { meaTraps 1 }
meaTrapDigitalInputAlarms       OBJECT IDENTIFIER ::= { meaTraps 2 }
meaTrapDigitalOutputAlarms      OBJECT IDENTIFIER ::= { meaTraps 3 }


-- {{{ meaTrapAnalogAlarms

meaTrapAnalogAlarm1Raised   TRAP-TYPE
    ENTERPRISE mea1
    DESCRIPTION
        "Analog Alarm 1 has been raised"
    ::= 1

meaTrapAnalogAlarm1Cleared   TRAP-TYPE
    ENTERPRISE mea1
    DESCRIPTION
        "Analog Alarm 1 has been cleared"
    ::= 2

meaTrapAnalogAlarm2Raised   TRAP-TYPE
    ENTERPRISE mea1
    DESCRIPTION
        "Analog Alarm 2 has been raised"
    ::= 3

meaTrapAnalogAlarm2Cleared   TRAP-TYPE
    ENTERPRISE mea1
    DESCRIPTION
        "Analog Alarm 2 has been cleared"
    ::= 4

meaTrapAnalogAlarm3Raised   TRAP-TYPE
    ENTERPRISE mea1
    DESCRIPTION
        "Analog Alarm 3 has been raised"
    ::= 5

meaTrapAnalogAlarm3Cleared   TRAP-TYPE
    ENTERPRISE mea1
    DESCRIPTION
        "Analog Alarm 3 has been cleared"
    ::= 6

meaTrapAnalogAlarm4Raised   TRAP-TYPE
    ENTERPRISE mea1
    DESCRIPTION
        "Analog Alarm 4 has been raised"
    ::= 7

meaTrapAnalogAlarm4Cleared   TRAP-TYPE
    ENTERPRISE mea1
    DESCRIPTION
        "Analog Alarm 4 has been cleared"
    ::= 8

meaTrapAnalogAlarm5Raised   TRAP-TYPE
    ENTERPRISE mea1
    DESCRIPTION
        "Analog Alarm 5 has been raised"
    ::= 9

meaTrapAnalogAlarm5Cleared   TRAP-TYPE
    ENTERPRISE mea1
    DESCRIPTION
        "Analog Alarm 5 has been cleared"
    ::= 10

meaTrapAnalogAlarm6Raised   TRAP-TYPE
    ENTERPRISE mea1
    DESCRIPTION
        "Analog Alarm 6 has been raised"
    ::= 11

meaTrapAnalogAlarm6Cleared   TRAP-TYPE
    ENTERPRISE mea1
    DESCRIPTION
        "Analog Alarm 6 has been cleared"
    ::= 12

meaTrapAnalogAlarm7Raised   TRAP-TYPE
    ENTERPRISE mea1
    DESCRIPTION
        "Analog Alarm 7 has been raised"
    ::= 13

meaTrapAnalogAlarm7Cleared   TRAP-TYPE
    ENTERPRISE mea1
    DESCRIPTION
        "Analog Alarm 7 has been cleared"
    ::= 14

meaTrapAnalogAlarm8Raised   TRAP-TYPE
    ENTERPRISE mea1
    DESCRIPTION
        "Analog Alarm 8 has been raised"
    ::= 15

meaTrapAnalogAlarm8Cleared   TRAP-TYPE
    ENTERPRISE mea1
    DESCRIPTION
        "Analog Alarm 8 has been cleared"
    ::= 16

meaTrapAnalogAlarm9Raised   TRAP-TYPE
    ENTERPRISE mea1
    DESCRIPTION
        "Analog Alarm 9 has been raised"
    ::= 17

meaTrapAnalogAlarm9Cleared   TRAP-TYPE
    ENTERPRISE mea1
    DESCRIPTION
        "Analog Alarm 9 has been cleared"
    ::= 18

meaTrapAnalogAlarm10Raised   TRAP-TYPE
    ENTERPRISE mea1
    DESCRIPTION
        "Analog Alarm 10 has been raised"
    ::= 19

meaTrapAnalogAlarm10Cleared   TRAP-TYPE
    ENTERPRISE mea1
    DESCRIPTION
        "Analog Alarm 10 has been cleared"
    ::= 20

meaTrapAnalogAlarm11Raised   TRAP-TYPE
    ENTERPRISE mea1
    DESCRIPTION
        "Analog Alarm 11 has been raised"
    ::= 21

meaTrapAnalogAlarm11Cleared   TRAP-TYPE
    ENTERPRISE mea1
    DESCRIPTION
        "Analog Alarm 11 has been cleared"
    ::= 22

meaTrapAnalogAlarm12Raised   TRAP-TYPE
    ENTERPRISE mea1
    DESCRIPTION
        "Analog Alarm 12 has been raised"
    ::= 23

meaTrapAnalogAlarm12Cleared   TRAP-TYPE
    ENTERPRISE mea1
    DESCRIPTION
        "Analog Alarm 12 has been cleared"
    ::= 24

meaTrapAnalogAlarm13Raised   TRAP-TYPE
    ENTERPRISE mea1
    DESCRIPTION
        "Analog Alarm 13 has been raised"
    ::= 25

meaTrapAnalogAlarm13Cleared   TRAP-TYPE
    ENTERPRISE mea1
    DESCRIPTION
        "Analog Alarm 13 has been cleared"
    ::= 26

meaTrapAnalogAlarm14Raised   TRAP-TYPE
    ENTERPRISE mea1
    DESCRIPTION
        "Analog Alarm 14 has been raised"
    ::= 27

meaTrapAnalogAlarm14Cleared   TRAP-TYPE
    ENTERPRISE mea1
    DESCRIPTION
        "Analog Alarm 14 has been cleared"
    ::= 28

meaTrapAnalogAlarm15Raised   TRAP-TYPE
    ENTERPRISE mea1
    DESCRIPTION
        "Analog Alarm 15 has been raised"
    ::= 29

meaTrapAnalogAlarm15Cleared   TRAP-TYPE
    ENTERPRISE mea1
    DESCRIPTION
        "Analog Alarm 15 has been cleared"
    ::= 30

meaTrapAnalogAlarm16Raised   TRAP-TYPE
    ENTERPRISE mea1
    DESCRIPTION
        "Analog Alarm 16 has been raised"
    ::= 31

meaTrapAnalogAlarm16Cleared   TRAP-TYPE
    ENTERPRISE mea1
    DESCRIPTION
        "Analog Alarm 16 has been cleared"
    ::= 32

-- }}}
-- {{{ meaTrapDigitalInputAlarms

meaTrapDigitalInputAlarm1Raised   TRAP-TYPE
    ENTERPRISE mea1
    DESCRIPTION
        "Digital Input Alarm 1 has been raised"
    ::= 33

meaTrapDigitalInputAlarm1Cleared   TRAP-TYPE
    ENTERPRISE mea1
    DESCRIPTION
        "Digital Input Alarm 1 has been cleared"
    ::= 34

meaTrapDigitalInputAlarm2Raised   TRAP-TYPE
    ENTERPRISE mea1
    DESCRIPTION
        "Digital Input Alarm 2 has been raised"
    ::= 35

meaTrapDigitalInputAlarm2Cleared   TRAP-TYPE
    ENTERPRISE mea1
    DESCRIPTION
        "Digital Input Alarm 2 has been cleared"
    ::= 36

meaTrapDigitalInputAlarm3Raised   TRAP-TYPE
    ENTERPRISE mea1
    DESCRIPTION
        "Digital Input Alarm 3 has been raised"
    ::= 37

meaTrapDigitalInputAlarm3Cleared   TRAP-TYPE
    ENTERPRISE mea1
    DESCRIPTION
        "Digital Input Alarm 3 has been cleared"
    ::= 38

meaTrapDigitalInputAlarm4Raised   TRAP-TYPE
    ENTERPRISE mea1
    DESCRIPTION
        "Digital Input Alarm 4 has been raised"
    ::= 39

meaTrapDigitalInputAlarm4Cleared   TRAP-TYPE
    ENTERPRISE mea1
    DESCRIPTION
        "Digital Input Alarm 4 has been cleared"
    ::= 40

meaTrapDigitalInputAlarm5Raised   TRAP-TYPE
    ENTERPRISE mea1
    DESCRIPTION
        "Digital Input Alarm 5 has been raised"
    ::= 41

meaTrapDigitalInputAlarm5Cleared   TRAP-TYPE
    ENTERPRISE mea1
    DESCRIPTION
        "Digital Input Alarm 5 has been cleared"
    ::= 42

meaTrapDigitalInputAlarm6Raised   TRAP-TYPE
    ENTERPRISE mea1
    DESCRIPTION
        "Digital Input Alarm 6 has been raised"
    ::= 43

meaTrapDigitalInputAlarm6Cleared   TRAP-TYPE
    ENTERPRISE mea1
    DESCRIPTION
        "Digital Input Alarm 6 has been cleared"
    ::= 44

meaTrapDigitalInputAlarm7Raised   TRAP-TYPE
    ENTERPRISE mea1
    DESCRIPTION
        "Digital Input Alarm 7 has been raised"
    ::= 45

meaTrapDigitalInputAlarm7Cleared   TRAP-TYPE
    ENTERPRISE mea1
    DESCRIPTION
        "Digital Input Alarm 7 has been cleared"
    ::= 46

meaTrapDigitalInputAlarm8Raised   TRAP-TYPE
    ENTERPRISE mea1
    DESCRIPTION
        "Digital Input Alarm 8 has been raised"
    ::= 47

meaTrapDigitalInputAlarm8Cleared   TRAP-TYPE
    ENTERPRISE mea1
    DESCRIPTION
        "Digital Input Alarm 8 has been cleared"
    ::= 48

meaTrapDigitalInputAlarm9Raised   TRAP-TYPE
    ENTERPRISE mea1
    DESCRIPTION
        "Digital Input Alarm 9 has been raised"
    ::= 49

meaTrapDigitalInputAlarm9Cleared   TRAP-TYPE
    ENTERPRISE mea1
    DESCRIPTION
        "Digital Input Alarm 9 has been cleared"
    ::= 50

meaTrapDigitalInputAlarm10Raised   TRAP-TYPE
    ENTERPRISE mea1
    DESCRIPTION
        "Digital Input Alarm 10 has been raised"
    ::= 51

meaTrapDigitalInputAlarm10Cleared   TRAP-TYPE
    ENTERPRISE mea1
    DESCRIPTION
        "Digital Input Alarm 10 has been cleared"
    ::= 52

meaTrapDigitalInputAlarm11Raised   TRAP-TYPE
    ENTERPRISE mea1
    DESCRIPTION
        "Digital Input Alarm 11 has been raised"
    ::= 53

meaTrapDigitalInputAlarm11Cleared   TRAP-TYPE
    ENTERPRISE mea1
    DESCRIPTION
        "Digital Input Alarm 11 has been cleared"
    ::= 54

meaTrapDigitalInputAlarm12Raised   TRAP-TYPE
    ENTERPRISE mea1
    DESCRIPTION
        "Digital Input Alarm 12 has been raised"
    ::= 55

meaTrapDigitalInputAlarm12Cleared   TRAP-TYPE
    ENTERPRISE mea1
    DESCRIPTION
        "Digital Input Alarm 12 has been cleared"
    ::= 56

meaTrapDigitalInputAlarm13Raised   TRAP-TYPE
    ENTERPRISE mea1
    DESCRIPTION
        "Digital Input Alarm 13 has been raised"
    ::= 57

meaTrapDigitalInputAlarm13Cleared   TRAP-TYPE
    ENTERPRISE mea1
    DESCRIPTION
        "Digital Input Alarm 13 has been cleared"
    ::= 58

meaTrapDigitalInputAlarm14Raised   TRAP-TYPE
    ENTERPRISE mea1
    DESCRIPTION
        "Digital Input Alarm 14 has been raised"
    ::= 59

meaTrapDigitalInputAlarm14Cleared   TRAP-TYPE
    ENTERPRISE mea1
    DESCRIPTION
        "Digital Input Alarm 14 has been cleared"
    ::= 60

meaTrapDigitalInputAlarm15Raised   TRAP-TYPE
    ENTERPRISE mea1
    DESCRIPTION
        "Digital Input Alarm 15 has been raised"
    ::= 61

meaTrapDigitalInputAlarm15Cleared   TRAP-TYPE
    ENTERPRISE mea1
    DESCRIPTION
        "Digital Input Alarm 15 has been cleared"
    ::= 62

meaTrapDigitalInputAlarm16Raised   TRAP-TYPE
    ENTERPRISE mea1
    DESCRIPTION
        "Digital Input Alarm 16 has been raised"
    ::= 63

meaTrapDigitalInputAlarm16Cleared   TRAP-TYPE
    ENTERPRISE mea1
    DESCRIPTION
        "Digital Input Alarm 16 has been cleared"
    ::= 64

meaTrapDigitalInputAlarm17Raised   TRAP-TYPE
    ENTERPRISE mea1
    DESCRIPTION
        "Digital Input Alarm 17 has been raised"
    ::= 65

meaTrapDigitalInputAlarm17Cleared   TRAP-TYPE
    ENTERPRISE mea1
    DESCRIPTION
        "Digital Input Alarm 17 has been cleared"
    ::= 66

meaTrapDigitalInputAlarm18Raised   TRAP-TYPE
    ENTERPRISE mea1
    DESCRIPTION
        "Digital Input Alarm 18 has been raised"
    ::= 67

meaTrapDigitalInputAlarm18Cleared   TRAP-TYPE
    ENTERPRISE mea1
    DESCRIPTION
        "Digital Input Alarm 18 has been cleared"
    ::= 68

meaTrapDigitalInputAlarm19Raised   TRAP-TYPE
    ENTERPRISE mea1
    DESCRIPTION
        "Digital Input Alarm 19 has been raised"
    ::= 69

meaTrapDigitalInputAlarm19Cleared   TRAP-TYPE
    ENTERPRISE mea1
    DESCRIPTION
        "Digital Input Alarm 19 has been cleared"
    ::= 70

meaTrapDigitalInputAlarm20Raised   TRAP-TYPE
    ENTERPRISE mea1
    DESCRIPTION
        "Digital Input Alarm 20 has been raised"
    ::= 71

meaTrapDigitalInputAlarm20Cleared   TRAP-TYPE
    ENTERPRISE mea1
    DESCRIPTION
        "Digital Input Alarm 20 has been cleared"
    ::= 72

meaTrapDigitalInputAlarm21Raised   TRAP-TYPE
    ENTERPRISE mea1
    DESCRIPTION
        "Digital Input Alarm 21 has been raised"
    ::= 73

meaTrapDigitalInputAlarm21Cleared   TRAP-TYPE
    ENTERPRISE mea1
    DESCRIPTION
        "Digital Input Alarm 21 has been cleared"
    ::= 74

meaTrapDigitalInputAlarm22Raised   TRAP-TYPE
    ENTERPRISE mea1
    DESCRIPTION
        "Digital Input Alarm 22 has been raised"
    ::= 75

meaTrapDigitalInputAlarm22Cleared   TRAP-TYPE
    ENTERPRISE mea1
    DESCRIPTION
        "Digital Input Alarm 22 has been cleared"
    ::= 76

meaTrapDigitalInputAlarm23Raised   TRAP-TYPE
    ENTERPRISE mea1
    DESCRIPTION
        "Digital Input Alarm 23 has been raised"
    ::= 77

meaTrapDigitalInputAlarm23Cleared   TRAP-TYPE
    ENTERPRISE mea1
    DESCRIPTION
        "Digital Input Alarm 23 has been cleared"
    ::= 78

meaTrapDigitalInputAlarm24Raised   TRAP-TYPE
    ENTERPRISE mea1
    DESCRIPTION
        "Digital Input Alarm 24 has been raised"
    ::= 79

meaTrapDigitalInputAlarm24Cleared   TRAP-TYPE
    ENTERPRISE mea1
    DESCRIPTION
        "Digital Input Alarm 24 has been cleared"
    ::= 80

meaTrapDigitalInputAlarm25Raised   TRAP-TYPE
    ENTERPRISE mea1
    DESCRIPTION
        "Digital Input Alarm 25 has been raised"
    ::= 81

meaTrapDigitalInputAlarm25Cleared   TRAP-TYPE
    ENTERPRISE mea1
    DESCRIPTION
        "Digital Input Alarm 25 has been cleared"
    ::= 82

meaTrapDigitalInputAlarm26Raised   TRAP-TYPE
    ENTERPRISE mea1
    DESCRIPTION
        "Digital Input Alarm 26 has been raised"
    ::= 83

meaTrapDigitalInputAlarm26Cleared   TRAP-TYPE
    ENTERPRISE mea1
    DESCRIPTION
        "Digital Input Alarm 26 has been cleared"
    ::= 84

meaTrapDigitalInputAlarm27Raised   TRAP-TYPE
    ENTERPRISE mea1
    DESCRIPTION
        "Digital Input Alarm 27 has been raised"
    ::= 85

meaTrapDigitalInputAlarm27Cleared   TRAP-TYPE
    ENTERPRISE mea1
    DESCRIPTION
        "Digital Input Alarm 27 has been cleared"
    ::= 86

meaTrapDigitalInputAlarm28Raised   TRAP-TYPE
    ENTERPRISE mea1
    DESCRIPTION
        "Digital Input Alarm 28 has been raised"
    ::= 87

meaTrapDigitalInputAlarm28Cleared   TRAP-TYPE
    ENTERPRISE mea1
    DESCRIPTION
        "Digital Input Alarm 28 has been cleared"
    ::= 88

meaTrapDigitalInputAlarm29Raised   TRAP-TYPE
    ENTERPRISE mea1
    DESCRIPTION
        "Digital Input Alarm 29 has been raised"
    ::= 89

meaTrapDigitalInputAlarm29Cleared   TRAP-TYPE
    ENTERPRISE mea1
    DESCRIPTION
        "Digital Input Alarm 29 has been cleared"
    ::= 90

meaTrapDigitalInputAlarm30Raised   TRAP-TYPE
    ENTERPRISE mea1
    DESCRIPTION
        "Digital Input Alarm 30 has been raised"
    ::= 91

meaTrapDigitalInputAlarm30Cleared   TRAP-TYPE
    ENTERPRISE mea1
    DESCRIPTION
        "Digital Input Alarm 30 has been cleared"
    ::= 92

meaTrapDigitalInputAlarm31Raised   TRAP-TYPE
    ENTERPRISE mea1
    DESCRIPTION
        "Digital Input Alarm 31 has been raised"
    ::= 93

meaTrapDigitalInputAlarm31Cleared   TRAP-TYPE
    ENTERPRISE mea1
    DESCRIPTION
        "Digital Input Alarm 31 has been cleared"
    ::= 94

meaTrapDigitalInputAlarm32Raised   TRAP-TYPE
    ENTERPRISE mea1
    DESCRIPTION
        "Digital Input Alarm 32 has been raised"
    ::= 95

meaTrapDigitalInputAlarm32Cleared   TRAP-TYPE
    ENTERPRISE mea1
    DESCRIPTION
        "Digital Input Alarm 32 has been cleared"
    ::= 96

-- }}}
-- {{{ meaTrapDigitalOutputAlarms

meaTrapDigitalOutputAlarm1Raised   TRAP-TYPE
    ENTERPRISE mea1
    DESCRIPTION
        "Digital Output Alarm 1 has been raised"
    ::= 97

meaTrapDigitalOutputAlarm1Cleared   TRAP-TYPE
    ENTERPRISE mea1
    DESCRIPTION
        "Digital Output Alarm 1 has been cleared"
    ::= 98

meaTrapDigitalOutputAlarm2Raised   TRAP-TYPE
    ENTERPRISE mea1
    DESCRIPTION
        "Digital Output Alarm 2 has been raised"
    ::= 99

meaTrapDigitalOutputAlarm2Cleared   TRAP-TYPE
    ENTERPRISE mea1
    DESCRIPTION
        "Digital Output Alarm 2 has been cleared"
    ::= 100

meaTrapDigitalOutputAlarm3Raised   TRAP-TYPE
    ENTERPRISE mea1
    DESCRIPTION
        "Digital Output Alarm 3 has been raised"
    ::= 101

meaTrapDigitalOutputAlarm3Cleared   TRAP-TYPE
    ENTERPRISE mea1
    DESCRIPTION
        "Digital Output Alarm 3 has been cleared"
    ::= 102

meaTrapDigitalOutputAlarm4Raised   TRAP-TYPE
    ENTERPRISE mea1
    DESCRIPTION
        "Digital Output Alarm 4 has been raised"
    ::= 103

meaTrapDigitalOutputAlarm4Cleared   TRAP-TYPE
    ENTERPRISE mea1
    DESCRIPTION
        "Digital Output Alarm 4 has been cleared"
    ::= 104

meaTrapDigitalOutputAlarm5Raised   TRAP-TYPE
    ENTERPRISE mea1
    DESCRIPTION
        "Digital Output Alarm 5 has been raised"
    ::= 105

meaTrapDigitalOutputAlarm5Cleared   TRAP-TYPE
    ENTERPRISE mea1
    DESCRIPTION
        "Digital Output Alarm 5 has been cleared"
    ::= 106

meaTrapDigitalOutputAlarm6Raised   TRAP-TYPE
    ENTERPRISE mea1
    DESCRIPTION
        "Digital Output Alarm 6 has been raised"
    ::= 107

meaTrapDigitalOutputAlarm6Cleared   TRAP-TYPE
    ENTERPRISE mea1
    DESCRIPTION
        "Digital Output Alarm 6 has been cleared"
    ::= 108

meaTrapDigitalOutputAlarm7Raised   TRAP-TYPE
    ENTERPRISE mea1
    DESCRIPTION
        "Digital Output Alarm 7 has been raised"
    ::= 109

meaTrapDigitalOutputAlarm7Cleared   TRAP-TYPE
    ENTERPRISE mea1
    DESCRIPTION
        "Digital Output Alarm 7 has been cleared"
    ::= 110

meaTrapDigitalOutputAlarm8Raised   TRAP-TYPE
    ENTERPRISE mea1
    DESCRIPTION
        "Digital Output Alarm 8 has been raised"
    ::= 111

meaTrapDigitalOutputAlarm8Cleared   TRAP-TYPE
    ENTERPRISE mea1
    DESCRIPTION
        "Digital Output Alarm 8 has been cleared"
    ::= 112

meaTrapDigitalOutputAlarm9Raised   TRAP-TYPE
    ENTERPRISE mea1
    DESCRIPTION
        "Digital Output Alarm 9 has been raised"
    ::= 113

meaTrapDigitalOutputAlarm9Cleared   TRAP-TYPE
    ENTERPRISE mea1
    DESCRIPTION
        "Digital Output Alarm 9 has been cleared"
    ::= 114

meaTrapDigitalOutputAlarm10Raised   TRAP-TYPE
    ENTERPRISE mea1
    DESCRIPTION
        "Digital Output Alarm 10 has been raised"
    ::= 115

meaTrapDigitalOutputAlarm10Cleared   TRAP-TYPE
    ENTERPRISE mea1
    DESCRIPTION
        "Digital Output Alarm 10 has been cleared"
    ::= 116

meaTrapDigitalOutputAlarm11Raised   TRAP-TYPE
    ENTERPRISE mea1
    DESCRIPTION
        "Digital Output Alarm 11 has been raised"
    ::= 117

meaTrapDigitalOutputAlarm11Cleared   TRAP-TYPE
    ENTERPRISE mea1
    DESCRIPTION
        "Digital Output Alarm 11 has been cleared"
    ::= 118

meaTrapDigitalOutputAlarm12Raised   TRAP-TYPE
    ENTERPRISE mea1
    DESCRIPTION
        "Digital Output Alarm 12 has been raised"
    ::= 119

meaTrapDigitalOutputAlarm12Cleared   TRAP-TYPE
    ENTERPRISE mea1
    DESCRIPTION
        "Digital Output Alarm 12 has been cleared"
    ::= 120

meaTrapDigitalOutputAlarm13Raised   TRAP-TYPE
    ENTERPRISE mea1
    DESCRIPTION
        "Digital Output Alarm 13 has been raised"
    ::= 121

meaTrapDigitalOutputAlarm13Cleared   TRAP-TYPE
    ENTERPRISE mea1
    DESCRIPTION
        "Digital Output Alarm 13 has been cleared"
    ::= 122

meaTrapDigitalOutputAlarm14Raised   TRAP-TYPE
    ENTERPRISE mea1
    DESCRIPTION
        "Digital Output Alarm 14 has been raised"
    ::= 123

meaTrapDigitalOutputAlarm14Cleared   TRAP-TYPE
    ENTERPRISE mea1
    DESCRIPTION
        "Digital Output Alarm 14 has been cleared"
    ::= 124

meaTrapDigitalOutputAlarm15Raised   TRAP-TYPE
    ENTERPRISE mea1
    DESCRIPTION
        "Digital Output Alarm 15 has been raised"
    ::= 125

meaTrapDigitalOutputAlarm15Cleared   TRAP-TYPE
    ENTERPRISE mea1
    DESCRIPTION
        "Digital Output Alarm 15 has been cleared"
    ::= 126

meaTrapDigitalOutputAlarm16Raised   TRAP-TYPE
    ENTERPRISE mea1
    DESCRIPTION
        "Digital Output Alarm 16 has been raised"
    ::= 127

meaTrapDigitalOutputAlarm16Cleared   TRAP-TYPE
    ENTERPRISE mea1
    DESCRIPTION
        "Digital Output Alarm 16 has been cleared"
    ::= 128

meaTrapDigitalOutputAlarm17Raised   TRAP-TYPE
    ENTERPRISE mea1
    DESCRIPTION
        "Digital Output Alarm 17 has been raised"
    ::= 129

meaTrapDigitalOutputAlarm17Cleared   TRAP-TYPE
    ENTERPRISE mea1
    DESCRIPTION
        "Digital Output Alarm 17 has been cleared"
    ::= 130

meaTrapDigitalOutputAlarm18Raised   TRAP-TYPE
    ENTERPRISE mea1
    DESCRIPTION
        "Digital Output Alarm 18 has been raised"
    ::= 131

meaTrapDigitalOutputAlarm18Cleared   TRAP-TYPE
    ENTERPRISE mea1
    DESCRIPTION
        "Digital Output Alarm 18 has been cleared"
    ::= 132

meaTrapDigitalOutputAlarm19Raised   TRAP-TYPE
    ENTERPRISE mea1
    DESCRIPTION
        "Digital Output Alarm 19 has been raised"
    ::= 133

meaTrapDigitalOutputAlarm19Cleared   TRAP-TYPE
    ENTERPRISE mea1
    DESCRIPTION
        "Digital Output Alarm 19 has been cleared"
    ::= 134

meaTrapDigitalOutputAlarm20Raised   TRAP-TYPE
    ENTERPRISE mea1
    DESCRIPTION
        "Digital Output Alarm 20 has been raised"
    ::= 135

meaTrapDigitalOutputAlarm20Cleared   TRAP-TYPE
    ENTERPRISE mea1
    DESCRIPTION
        "Digital Output Alarm 20 has been cleared"
    ::= 136

meaTrapDigitalOutputAlarm21Raised   TRAP-TYPE
    ENTERPRISE mea1
    DESCRIPTION
        "Digital Output Alarm 21 has been raised"
    ::= 137

meaTrapDigitalOutputAlarm21Cleared   TRAP-TYPE
    ENTERPRISE mea1
    DESCRIPTION
        "Digital Output Alarm 21 has been cleared"
    ::= 138

meaTrapDigitalOutputAlarm22Raised   TRAP-TYPE
    ENTERPRISE mea1
    DESCRIPTION
        "Digital Output Alarm 22 has been raised"
    ::= 139

meaTrapDigitalOutputAlarm22Cleared   TRAP-TYPE
    ENTERPRISE mea1
    DESCRIPTION
        "Digital Output Alarm 22 has been cleared"
    ::= 140

meaTrapDigitalOutputAlarm23Raised   TRAP-TYPE
    ENTERPRISE mea1
    DESCRIPTION
        "Digital Output Alarm 23 has been raised"
    ::= 141

meaTrapDigitalOutputAlarm23Cleared   TRAP-TYPE
    ENTERPRISE mea1
    DESCRIPTION
        "Digital Output Alarm 23 has been cleared"
    ::= 142

meaTrapDigitalOutputAlarm24Raised   TRAP-TYPE
    ENTERPRISE mea1
    DESCRIPTION
        "Digital Output Alarm 24 has been raised"
    ::= 143

meaTrapDigitalOutputAlarm24Cleared   TRAP-TYPE
    ENTERPRISE mea1
    DESCRIPTION
        "Digital Output Alarm 24 has been cleared"
    ::= 144

meaTrapDigitalOutputAlarm25Raised   TRAP-TYPE
    ENTERPRISE mea1
    DESCRIPTION
        "Digital Output Alarm 25 has been raised"
    ::= 145

meaTrapDigitalOutputAlarm25Cleared   TRAP-TYPE
    ENTERPRISE mea1
    DESCRIPTION
        "Digital Output Alarm 25 has been cleared"
    ::= 146

meaTrapDigitalOutputAlarm26Raised   TRAP-TYPE
    ENTERPRISE mea1
    DESCRIPTION
        "Digital Output Alarm 26 has been raised"
    ::= 147

meaTrapDigitalOutputAlarm26Cleared   TRAP-TYPE
    ENTERPRISE mea1
    DESCRIPTION
        "Digital Output Alarm 26 has been cleared"
    ::= 148

meaTrapDigitalOutputAlarm27Raised   TRAP-TYPE
    ENTERPRISE mea1
    DESCRIPTION
        "Digital Output Alarm 27 has been raised"
    ::= 149

meaTrapDigitalOutputAlarm27Cleared   TRAP-TYPE
    ENTERPRISE mea1
    DESCRIPTION
        "Digital Output Alarm 27 has been cleared"
    ::= 150

meaTrapDigitalOutputAlarm28Raised   TRAP-TYPE
    ENTERPRISE mea1
    DESCRIPTION
        "Digital Output Alarm 28 has been raised"
    ::= 151

meaTrapDigitalOutputAlarm28Cleared   TRAP-TYPE
    ENTERPRISE mea1
    DESCRIPTION
        "Digital Output Alarm 28 has been cleared"
    ::= 152

meaTrapDigitalOutputAlarm29Raised   TRAP-TYPE
    ENTERPRISE mea1
    DESCRIPTION
        "Digital Output Alarm 29 has been raised"
    ::= 153

meaTrapDigitalOutputAlarm29Cleared   TRAP-TYPE
    ENTERPRISE mea1
    DESCRIPTION
        "Digital Output Alarm 29 has been cleared"
    ::= 154

meaTrapDigitalOutputAlarm30Raised   TRAP-TYPE
    ENTERPRISE mea1
    DESCRIPTION
        "Digital Output Alarm 30 has been raised"
    ::= 155

meaTrapDigitalOutputAlarm30Cleared   TRAP-TYPE
    ENTERPRISE mea1
    DESCRIPTION
        "Digital Output Alarm 30 has been cleared"
    ::= 156

meaTrapDigitalOutputAlarm31Raised   TRAP-TYPE
    ENTERPRISE mea1
    DESCRIPTION
        "Digital Output Alarm 31 has been raised"
    ::= 157

meaTrapDigitalOutputAlarm31Cleared   TRAP-TYPE
    ENTERPRISE mea1
    DESCRIPTION
        "Digital Output Alarm 31 has been cleared"
    ::= 158

meaTrapDigitalOutputAlarm32Raised   TRAP-TYPE
    ENTERPRISE mea1
    DESCRIPTION
        "Digital Output Alarm 32 has been raised"
    ::= 159

meaTrapDigitalOutputAlarm32Cleared   TRAP-TYPE
    ENTERPRISE mea1
    DESCRIPTION
        "Digital Output Alarm 32 has been cleared"
    ::= 160

-- }}}

-- }}}

-- {{{ meaTH    

meaEnvHumidity        OBJECT IDENTIFIER ::= { meaTH 1 }
meaEnvTemperature     OBJECT IDENTIFIER ::= { meaTH 2 }

-- {{{ meaEnvHumidity

meaEnvHumidityEnableMonitoring  OBJECT-TYPE
    SYNTAX    INTEGER (0..1)
    ACCESS    read-only
    STATUS    mandatory
    DESCRIPTION
        "Setting to one enables monitoring of Humidity"
    ::= { meaEnvHumidity 1 }

meaEnvCurrentHumidity  OBJECT-TYPE
    SYNTAX    INTEGER (0..1000)
    ACCESS    read-only
    STATUS    mandatory
    DESCRIPTION
        "The current humidity reading in 0.1%"
    ::= { meaEnvHumidity 2 }

meaEnvHumidityLowerThreshold  OBJECT-TYPE
    SYNTAX    INTEGER (0..1000)
    ACCESS    read-only
    STATUS    mandatory
    DESCRIPTION
        "The Lower humidity threshold in 0.1%"
    ::= { meaEnvHumidity 3 }

meaEnvHumidityUpperThreshold  OBJECT-TYPE
    SYNTAX    INTEGER (0..1000)
    ACCESS    read-only
    STATUS    mandatory
    DESCRIPTION
        "The Upper humidity threshold in 0.1%"
    ::= { meaEnvHumidity 4 }

meaEnvHumidityCalibrationOffset  OBJECT-TYPE
    SYNTAX    INTEGER (-100..100)
    ACCESS    read-only
    STATUS    mandatory
    DESCRIPTION
        "Calibration offset in 0.1%"	
    ::= { meaEnvHumidity 5 }

meaLowHumidity              TRAP-TYPE
    ENTERPRISE meaEnvHumidity
    VARIABLES { meaEnvCurrentHumidity }
    DESCRIPTION
        "The NetCom-th unit is below the low humidity threshold."
    ::= 21

meaHighHumidity             TRAP-TYPE
    ENTERPRISE meaEnvHumidity
    VARIABLES { meaEnvCurrentHumidity }
    DESCRIPTION
        "The NetCom-th unit is above the high humidity threshold."
    ::= 22

meaHumidityReturnToNormal   TRAP-TYPE
    ENTERPRISE meaEnvHumidity
    VARIABLES { meaEnvCurrentHumidity }
    DESCRIPTION
        "The NetCom-th unit has returned to normal humidity"
    ::= 23

-- }}}
-- {{{ meaEnvTemperature

meaEnvTemperatureEnableMonitoring  OBJECT-TYPE
    SYNTAX    INTEGER (0..1)
    ACCESS    read-only
    STATUS    mandatory
    DESCRIPTION
        "Setting to one enables monitoring of Temperature"
    ::= { meaEnvTemperature 1 }

meaEnvCurrentTemperature  OBJECT-TYPE
    SYNTAX    INTEGER (-200..1000)
    ACCESS    read-only
    STATUS    mandatory
    DESCRIPTION
        "The current temperature reading in 0.1%"
    ::= { meaEnvTemperature 2 }

meaEnvTemperatureLowerThreshold  OBJECT-TYPE
    SYNTAX    INTEGER (-200..1000)
    ACCESS    read-only
    STATUS    mandatory
    DESCRIPTION
        "The Lower temperature threshold in 0.1 degrees"
    ::= { meaEnvTemperature 3 }

meaEnvTemperatureUpperThreshold  OBJECT-TYPE
    SYNTAX    INTEGER (-200..1000)
    ACCESS    read-only
    STATUS    mandatory
    DESCRIPTION
        "The Upper temperature threshold in 0.1 degrees"
    ::= { meaEnvTemperature 4 }

meaEnvTemperatureCalibrationOffset  OBJECT-TYPE
    SYNTAX    INTEGER (-100..100)
    ACCESS    read-only
    STATUS    mandatory
    DESCRIPTION
        "Calibration offset in 0.1 degrees"	
    ::= { meaEnvTemperature 5 }

meaLowTemperature            TRAP-TYPE
    ENTERPRISE meaEnvTemperature
    VARIABLES { meaEnvCurrentTemperature }
    DESCRIPTION
        "The NetCom-th unit is below the lower temperature threshold."
    ::= 31

meaHighTemperature           TRAP-TYPE
    ENTERPRISE meaEnvTemperature
    VARIABLES { meaEnvCurrentTemperature }
    DESCRIPTION
        "The NetCom-th unit is above the high temperature threshold."
    ::= 32

meaTemperatureReturnToNormal   TRAP-TYPE
    ENTERPRISE meaEnvTemperature
    VARIABLES { meaEnvCurrentTemperature }
    DESCRIPTION
        "The NetCom-th unit has returned to normal temperature"
    ::= 33

-- }}}

-- }}}
END
