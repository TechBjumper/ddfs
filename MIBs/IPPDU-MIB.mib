IPPDU-MIB DEFINITIONS ::= BEGIN

IMPORTS
    enterprises, Counter,
    TimeTicks, Gauge                FROM RFC1155-SMI
    OBJECT-TYPE                     FROM RFC-1212
    sysUpTime, DisplayString		  FROM RFC1213-MIB
TRAP-TYPE                           FROM RFC-1215;

ePDU OBJECT IDENTIFIER ::= { enterprises 30966 }
ip-PDU OBJECT IDENTIFIER ::= { ePDU 10 }
ipPDU OBJECT IDENTIFIER ::= { ip-PDU 3 }
deviceInfo OBJECT IDENTIFIER ::= { ipPDU 1 }
statusInfo OBJECT IDENTIFIER ::= { ipPDU 2 }

DeviceName OBJECT-TYPE
    SYNTAX DisplayString (SIZE (255))
    ACCESS read-write
    STATUS optional
    DESCRIPTION
            "device name."
    ::= { deviceInfo 1 }

mVoltageA OBJECT-TYPE
    SYNTAX INTEGER (0..65535)
    ACCESS read-only
    STATUS optional
    DESCRIPTION
            "Master Line 1 total votage."
    ::= { statusInfo 1 }

mVoltageB OBJECT-TYPE
    SYNTAX INTEGER (0..65535)
    ACCESS read-only
    STATUS optional
    DESCRIPTION
            "Master Line 2 total votage."
    ::= { statusInfo 2 }    

mVoltageC OBJECT-TYPE
    SYNTAX INTEGER (0..65535)
    ACCESS read-only
    STATUS optional
    DESCRIPTION
            "Master Line 3 total votage."
    ::= { statusInfo 3 }

mCurrentA OBJECT-TYPE
    SYNTAX INTEGER (0..65535)
    ACCESS read-only
    STATUS optional
    DESCRIPTION
            "Master Line 1 total current.Magnified 10 times."
    ::= { statusInfo 4 }

mCurrentB OBJECT-TYPE
    SYNTAX INTEGER (0..65535)
    ACCESS read-only
    STATUS optional
    DESCRIPTION
            "Master Line 2 total current.Magnified 10 times."
    ::= { statusInfo 5 }    

mCurrentC OBJECT-TYPE
    SYNTAX INTEGER (0..65535)
    ACCESS read-only
    STATUS optional
    DESCRIPTION
            "Master Line 3 total current.Magnified 10 times."
    ::= { statusInfo 6 }
    
mEnergyA OBJECT-TYPE
    SYNTAX INTEGER (0..65535)
    ACCESS read-only
    STATUS optional
    DESCRIPTION
            "Master Line 1 energy .Magnified 10 times."
    ::= { statusInfo 7 }
mEnergyB OBJECT-TYPE
    SYNTAX INTEGER (0..65535)
    ACCESS read-only
    STATUS optional
    DESCRIPTION
            "Master Line 2 energy .Magnified 10 times."
    ::= { statusInfo 8 }
mEnergyC OBJECT-TYPE
    SYNTAX INTEGER (0..65535)
    ACCESS read-only
    STATUS optional
    DESCRIPTION
            "Master Line 3 energy .Magnified 10 times."
    ::= { statusInfo 9 }  
mTemperature OBJECT-TYPE
    SYNTAX INTEGER (0..65535)
    ACCESS read-only
    STATUS optional
    DESCRIPTION
            "Master Temperature"
    ::= { statusInfo 10 }
mHumidity OBJECT-TYPE
    SYNTAX INTEGER (0..65535)
    ACCESS read-only
    STATUS optional
    DESCRIPTION
            "Master Humidity"
    ::= { statusInfo 11 }    
    
    
sOneVoltageA OBJECT-TYPE
    SYNTAX INTEGER (0..65535)
    ACCESS read-only
    STATUS optional
    DESCRIPTION
            "SlaveOne Line 1 total votage."
    ::= { statusInfo 12 }

sOneVoltageB OBJECT-TYPE
    SYNTAX INTEGER (0..65535)
    ACCESS read-only
    STATUS optional
    DESCRIPTION
            "SlaveOne Line 2 total votage."
    ::= { statusInfo 13 }    

sOneVoltageC OBJECT-TYPE
    SYNTAX INTEGER (0..65535)
    ACCESS read-only
    STATUS optional
    DESCRIPTION
            "SlaveOne Line 3 total votage."
    ::= { statusInfo 14 }

sOneCurrentA OBJECT-TYPE
    SYNTAX INTEGER (0..65535)
    ACCESS read-only
    STATUS optional
    DESCRIPTION
            "SlaveOne Line 1 total current.Magnified 10 times."
    ::= { statusInfo 15 }

sOneCurrentB OBJECT-TYPE
    SYNTAX INTEGER (0..65535)
    ACCESS read-only
    STATUS optional
    DESCRIPTION
            "SlaveOne Line 2 total current.Magnified 10 times."
    ::= { statusInfo 16 }    

sOneCurrentC OBJECT-TYPE
    SYNTAX INTEGER (0..65535)
    ACCESS read-only
    STATUS optional
    DESCRIPTION
            "SlaveOne Line 3 total current.Magnified 10 times."
    ::= { statusInfo 17 }
    
sOneEnergyA OBJECT-TYPE
    SYNTAX INTEGER (0..65535)
    ACCESS read-only
    STATUS optional
    DESCRIPTION
            "SlaveOne Line 1 energy .Magnified 10 times."
    ::= { statusInfo 18 }
sOneEnergyB OBJECT-TYPE
    SYNTAX INTEGER (0..65535)
    ACCESS read-only
    STATUS optional
    DESCRIPTION
            "SlaveOne Line 2 energy .Magnified 10 times."
    ::= { statusInfo 19 }
sOneEnergyC OBJECT-TYPE
    SYNTAX INTEGER (0..65535)
    ACCESS read-only
    STATUS optional
    DESCRIPTION
            "SlaveOne Line 3 energy .Magnified 10 times."
    ::= { statusInfo 20 } 
sOneTem OBJECT-TYPE
    SYNTAX INTEGER (0..65535)
    ACCESS read-only
    STATUS optional
    DESCRIPTION
            "SlaveOne  Temperature"
    ::= { statusInfo 21 }
sOneHum OBJECT-TYPE
    SYNTAX INTEGER (0..65535)
    ACCESS read-only
    STATUS optional
    DESCRIPTION
            "SlaveOne  Humidity"
    ::= { statusInfo 22 }          
    
            
sTwoVoltageA OBJECT-TYPE
    SYNTAX INTEGER (0..65535)
    ACCESS read-only
    STATUS optional
    DESCRIPTION
            "SlaveTwo Line 1 total votage."
    ::= { statusInfo 23 }

sTwoVoltageB OBJECT-TYPE
    SYNTAX INTEGER (0..65535)
    ACCESS read-only
    STATUS optional
    DESCRIPTION
            "SlaveTwo Line 2 total votage."
    ::= { statusInfo 24 }    

sTwoVoltageC OBJECT-TYPE
    SYNTAX INTEGER (0..65535)
    ACCESS read-only
    STATUS optional
    DESCRIPTION
            "SlaveTwo Line 3 total votage."
    ::= { statusInfo 25 }

sTwoCurrentA OBJECT-TYPE
    SYNTAX INTEGER (0..65535)
    ACCESS read-only
    STATUS optional
    DESCRIPTION
            "SlaveTwo Line 1 total current.Magnified 10 times."
    ::= { statusInfo 26 }

sTwoCurrentB OBJECT-TYPE
    SYNTAX INTEGER (0..65535)
    ACCESS read-only
    STATUS optional
    DESCRIPTION
            "SlaveTwo Line 2 total current.Magnified 10 times."
    ::= { statusInfo 27 }    

sTwoCurrentC OBJECT-TYPE
    SYNTAX INTEGER (0..65535)
    ACCESS read-only
    STATUS optional
    DESCRIPTION
            "SlaveTwo Line 3 total current.Magnified 10 times."
    ::= { statusInfo 28 }
    
sTwoEnergyA OBJECT-TYPE
    SYNTAX INTEGER (0..65535)
    ACCESS read-only
    STATUS optional
    DESCRIPTION
            "SlaveTwo Line 1 energy .Magnified 10 times."
    ::= { statusInfo 29 }
sTwoEnergyB OBJECT-TYPE
    SYNTAX INTEGER (0..65535)
    ACCESS read-only
    STATUS optional
    DESCRIPTION
            "SlaveTwo Line 2 energy .Magnified 10 times."
    ::= { statusInfo 30 }
sTwoEnergyC OBJECT-TYPE
    SYNTAX INTEGER (0..65535)
    ACCESS read-only
    STATUS optional
    DESCRIPTION
            "SlaveTwo Line 3 energy .Magnified 10 times."
    ::= { statusInfo 31 } 
sTwoTem OBJECT-TYPE
    SYNTAX INTEGER (0..65535)
    ACCESS read-only
    STATUS optional
    DESCRIPTION
            "SlaveTwo  Temperature"
    ::= { statusInfo 32 }
sTwoHum OBJECT-TYPE
    SYNTAX INTEGER (0..65535)
    ACCESS read-only
    STATUS optional
    DESCRIPTION
            "SlaveTwo  Humidity"
    ::= { statusInfo 33 }       
      
      
      
sThreeVoltageA OBJECT-TYPE
    SYNTAX INTEGER (0..65535)
    ACCESS read-only
    STATUS optional
    DESCRIPTION
            "SlaveThree Line 1 total votage."
    ::= { statusInfo 34 }

sThreeVoltageB OBJECT-TYPE
    SYNTAX INTEGER (0..65535)
    ACCESS read-only
    STATUS optional
    DESCRIPTION
            "SlaveThree Line 2 total votage."
    ::= { statusInfo 35 }    

sThreeVoltageC OBJECT-TYPE
    SYNTAX INTEGER (0..65535)
    ACCESS read-only
    STATUS optional
    DESCRIPTION
            "SlaveThree Line 3 total votage."
    ::= { statusInfo 36 }

sThreeCurrentA OBJECT-TYPE
    SYNTAX INTEGER (0..65535)
    ACCESS read-only
    STATUS optional
    DESCRIPTION
            "SlaveThree Line 1 total current.Magnified 10 times."
    ::= { statusInfo 37 }

sThreeCurrentB OBJECT-TYPE
    SYNTAX INTEGER (0..65535)
    ACCESS read-only
    STATUS optional
    DESCRIPTION
            "SlaveThree Line 2 total current.Magnified 10 times."
    ::= { statusInfo 38 }    

sThreeCurrentC OBJECT-TYPE
    SYNTAX INTEGER (0..65535)
    ACCESS read-only
    STATUS optional
    DESCRIPTION
            "SlaveThree Line 3 total current.Magnified 10 times."
    ::= { statusInfo 39 }
    
sThreeEnergyA OBJECT-TYPE
    SYNTAX INTEGER (0..65535)
    ACCESS read-only
    STATUS optional
    DESCRIPTION
            "SlaveThree Line 1 energy .Magnified 10 times."
    ::= { statusInfo 40 }
sThreeEnergyB OBJECT-TYPE
    SYNTAX INTEGER (0..65535)
    ACCESS read-only
    STATUS optional
    DESCRIPTION
            "SlaveThree Line 2 energy .Magnified 10 times."
    ::= { statusInfo 41 }
sThreeEnergyC OBJECT-TYPE
    SYNTAX INTEGER (0..65535)
    ACCESS read-only
    STATUS optional
    DESCRIPTION
            "SlaveThree Line 3 energy .Magnified 10 times."
    ::= { statusInfo 42 } 
sThreeTem OBJECT-TYPE
    SYNTAX INTEGER (0..65535)
    ACCESS read-only
    STATUS optional
    DESCRIPTION
            "SlaveThree  Temperature"
    ::= { statusInfo 43 }
sThreeHum OBJECT-TYPE
    SYNTAX INTEGER (0..65535)
    ACCESS read-only
    STATUS optional
    DESCRIPTION
            "SlaveThree  Humidity"
    ::= { statusInfo 44 }            


sFourVoltageA OBJECT-TYPE
    SYNTAX INTEGER (0..65535)
    ACCESS read-only
    STATUS optional
    DESCRIPTION
            "SlaveFour Line 1 total votage."
    ::= { statusInfo 45 }

sFourVoltageB OBJECT-TYPE
    SYNTAX INTEGER (0..65535)
    ACCESS read-only
    STATUS optional
    DESCRIPTION
            "SlaveFour Line 2 total votage."
    ::= { statusInfo 46 }    

sFourVoltageC OBJECT-TYPE
    SYNTAX INTEGER (0..65535)
    ACCESS read-only
    STATUS optional
    DESCRIPTION
            "SlaveFour Line 3 total votage."
    ::= { statusInfo 47 }

sFourCurrentA OBJECT-TYPE
    SYNTAX INTEGER (0..65535)
    ACCESS read-only
    STATUS optional
    DESCRIPTION
            "SlaveFour Line 1 total current.Magnified 10 times."
    ::= { statusInfo 48 }

sFourCurrentB OBJECT-TYPE
    SYNTAX INTEGER (0..65535)
    ACCESS read-only
    STATUS optional
    DESCRIPTION
            "SlaveFour Line 2 total current.Magnified 10 times."
    ::= { statusInfo 49 }    

sFourCurrentC OBJECT-TYPE
    SYNTAX INTEGER (0..65535)
    ACCESS read-only
    STATUS optional
    DESCRIPTION
            "SlaveFour Line 3 total current.Magnified 10 times."
    ::= { statusInfo 50 }
    
sFourEnergyA OBJECT-TYPE
    SYNTAX INTEGER (0..65535)
    ACCESS read-only
    STATUS optional
    DESCRIPTION
            "SlaveFour Line 1 energy .Magnified 10 times."
    ::= { statusInfo 51 }
sFourEnergyB OBJECT-TYPE
    SYNTAX INTEGER (0..65535)
    ACCESS read-only
    STATUS optional
    DESCRIPTION
            "SlaveFour Line 2 energy .Magnified 10 times."
    ::= { statusInfo 52 }
sFourEnergyC OBJECT-TYPE
    SYNTAX INTEGER (0..65535)
    ACCESS read-only
    STATUS optional
    DESCRIPTION
            "SlaveFour Line 3 energy .Magnified 10 times."
    ::= { statusInfo 53 } 
sFourTem OBJECT-TYPE
    SYNTAX INTEGER (0..65535)
    ACCESS read-only
    STATUS optional
    DESCRIPTION
            "SlaveFour  Temperature"
    ::= { statusInfo 54 }
sFourHum OBJECT-TYPE
    SYNTAX INTEGER (0..65535)
    ACCESS read-only
    STATUS optional
    DESCRIPTION
            "SlaveFour  Humidity"
    ::= { statusInfo 55 }        






END
