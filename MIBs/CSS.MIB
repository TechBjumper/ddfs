--
--Defines CSS-MIB for SNMP agent extension
--Contents:	Global Registration Module

--CSS  OIDs - Enterprise 14748
--Version:		2.16  	
--Date Started:		21 July, 2003
--Last Updated:		20 May, 2011

-- Reviewed & developed by NK
--         software engineer
--         Computer Support Systems Pty Ltd

-- Updates
--			 04 December  2003 - input sensor readings for Safeguard Network Adapter
--			 22 January   2004 - new product SafetyNet inserted
--			 07 June      2004 - finalising SafetyNet MIB items for two universal analogue sensors
--			 01 July      2004 - finalising SafetyNet MIB items for firmware upgrades
--			 12 July      2004 - adding SafetyNet Lite MIB items
--			 11 August    2004 - adding SafetyNet Lite MIB IP monitoring items
--			 12 August    2004 - adding SafetyNet Micro MIB items
--			 24 August    2004 - trap notification methods added
--			 03 September 2004 - adding SafetyNet Plus MIB items
--			 21 October   2004 - added modem parameters
--			 01 March     2005 - finalising and release of safetynetmicro
--			 22 July      2005 - safetynetmicro with PPP added
--			 29 April     2006 - i-Rack 20 way added (No traps) 
--			 16 October   2006 - i-Rack 6 way added 
--			 26 October   2006 - SafetyNet Plus entries added to handle A/C Sequence Controller Traps   
--			 18 December  2006 - Fixed compatible issues - A.W  
--			 12 February  2007 - i-Rack 16 way added
--			 04 March	  2007 - i-Rack 08 way added, created Traps
--			 18 April	  2007 - i-Rack 06 way added, created Traps        
--			 23 April	  2007 - i-Rack 20 way added, created Traps
--			 13 May		  2007 - i-Rack 20 way added, created Traps for Sensors
--			 15 May		  2007 - i-Rack 16 way  traps added
--			 25 June	  2008 - SafetyNet Series 5 Product added
--			 06 October	  2008 - iRack Current Only product added	
--			 25 April	  2009 - added Temp/Humd type sensor to SafetyNet Series 5
--			 10 June	  2009 - Removed SafetyNet Series 5. Version 0.12 issued.
--			 15 October	  2009 - Added iRack20way Traps to handle Environmentals
--			 05 January	  2011 - Added iRack4way Device
--			 20 May		  2011 - Added iRack4way Device support for Environmentals

-- Copyright (c) 2011 CSSPL.

CSS-MIB DEFINITIONS ::= BEGIN

IMPORTS
--	MODULE-IDENTITY				FROM SNMPv2-SMI   

	OBJECT-TYPE				FROM RFC-1212
		
--	Counter, TimeTicks,
	enterprises,IpAddress 	FROM RFC1155-SMI

	DisplayString			FROM RFC1213-MIB

	TRAP-TYPE				FROM RFC-1215     
	
;
		


computerSupportSystems  OBJECT IDENTIFIER ::= { enterprises 14748 } -- assigned by IANA
--MODULE-IDENTITY
--
--     LAST-UPDATED    "201101052210Z"  January, 2011
--     ORGANIZATION "Computer Support Systems Pty Ltd"
--     CONTACT-INFO 
--	  
--	  	"Nilkamal Kandamudali
--		Email: support@csspl.com.au
--		nilkamalk@optusnet.com.au"
--																		
--    DESCRIPTION
--      "This MIB module defines MIB objects for products of Computer Support Systems."
--       
--		REVISION    "200612182200Z" December  18, 2006
--      DESCRIPTION "MIB Structure updated by A.W to keep compatibility"
--
--       REVISION    "200610262200Z" October  26, 2006
--      DESCRIPTION "MIB Structure developed for SafetyNet Plus A/C Sequence Controller "
--
--       REVISION    "200610162200Z"  October  16, 2006
--      DESCRIPTION "MIB Structure developed for i-Rack 6 Way"    
--
--		REVISION    "200604292300Z" April 29, 2006
--      DESCRIPTION "MIB Structure developed for i-Rack 20 Way" 
--                                        
--		REVISION    "200507221100Z" July 22, 2005
--      DESCRIPTION "Added PPP to SafetyNet family on SafetyNet Micro"
--
--		REVISION    "200412101000Z" December 10, 2004
--      DESCRIPTION "Added modem error codes for the SafetyNet family"
--
--		REVISION    "200409030900Z" September 03, 2004
--      DESCRIPTION "SafetyNet Family added, Trap notifications added"
--		
--		REVISION    "200312040900Z" December 04, 2003
--      DESCRIPTION "Initial version."		
    

				
      

		 


products    		OBJECT IDENTIFIER ::= { computerSupportSystems 1 }
	
safeguard   		OBJECT IDENTIFIER ::= { products 2 }
safetynet   		OBJECT IDENTIFIER ::= { products 3 }
safetynetlite  		OBJECT IDENTIFIER ::= { products 4 }
safetynetmicro  	OBJECT IDENTIFIER ::= { products 5 }
safetynetplus		OBJECT IDENTIFIER ::= { products 6 }

sgReadings		OBJECT IDENTIFIER ::= { safeguard 1 }
sgTraps  		OBJECT IDENTIFIER ::= { safeguard 2 }
snReadings   	OBJECT IDENTIFIER ::= { safetynet 1 }
snTraps			OBJECT IDENTIFIER ::= { safetynet 2 }
snlReadings		OBJECT IDENTIFIER ::= { safetynetlite 1 }
snlTraps		OBJECT IDENTIFIER ::= { safetynetlite 2 }
snmReadings		OBJECT IDENTIFIER ::= { safetynetmicro 1 }
snmTraps		OBJECT IDENTIFIER ::= { safetynetmicro 2 }
snpReadings		OBJECT IDENTIFIER ::= { safetynetplus 1 }
snpTraps		OBJECT IDENTIFIER ::= { safetynetplus 2 }




oemProducts		OBJECT IDENTIFIER ::= { computerSupportSystems 2 }
iRack20Way		OBJECT IDENTIFIER ::= { oemProducts 1 }    
iRack6Way		OBJECT IDENTIFIER ::= { oemProducts 2 } 
iRack16Way		OBJECT IDENTIFIER ::= { oemProducts 3 } 
iRack8Way		OBJECT IDENTIFIER ::= { oemProducts 4 }  
iRack12Way		OBJECT IDENTIFIER ::= { oemProducts 5 }
iRackCurrentMonitoring	OBJECT IDENTIFIER ::= { oemProducts 6 }
iRack4Way		OBJECT IDENTIFIER ::= { oemProducts 7 }




iRackParams20Way		OBJECT IDENTIFIER ::= {iRack20Way 1}
outletStatus20Way		OBJECT IDENTIFIER ::= {iRack20Way 2}
currentConsumption20Way OBJECT IDENTIFIER ::= {iRack20Way 3} 
iRack20WayTraps		OBJECT IDENTIFIER ::= { iRack20Way 4 }

iRackParams6Way		OBJECT IDENTIFIER ::= {iRack6Way 1}
outletStatus6Way	OBJECT IDENTIFIER ::= {iRack6Way 2}
currentConsumption6Way OBJECT IDENTIFIER ::= {iRack6Way 3}
iRack6WayTraps		OBJECT IDENTIFIER ::= { iRack6Way 4 }

iRackParams4Way		OBJECT IDENTIFIER ::= {iRack4Way 1}
outletStatus4Way	OBJECT IDENTIFIER ::= {iRack4Way 2}
currentConsumption4Way OBJECT IDENTIFIER ::= {iRack4Way 3}
iRack4WayTraps		OBJECT IDENTIFIER ::= { iRack4Way 4 }
   
iRackParams16Way		OBJECT IDENTIFIER ::= {iRack16Way 1}
outletStatus16Way	OBJECT IDENTIFIER ::= {iRack16Way 2}
currentConsumption16Way OBJECT IDENTIFIER ::= {iRack16Way 3}  
iRack16WayTraps		OBJECT IDENTIFIER ::= { iRack16Way 4 }

iRackParams8Way		OBJECT IDENTIFIER ::= {iRack8Way 1}
outletStatus8Way	OBJECT IDENTIFIER ::= {iRack8Way 2}
currentConsumption8Way OBJECT IDENTIFIER ::= {iRack8Way 3} 
iRack8WayTraps		OBJECT IDENTIFIER ::= { iRack8Way 4 }
                                                            
                                                          
iRackParams12Way		OBJECT IDENTIFIER ::= {iRack12Way 1}
outletStatus12Way	OBJECT IDENTIFIER ::= {iRack12Way 2}
currentConsumption12Way OBJECT IDENTIFIER ::= {iRack12Way 3} 
iRack12WayTraps		OBJECT IDENTIFIER ::= { iRack12Way 4 }

iRackParamsCurrentMonitoring		OBJECT IDENTIFIER ::= {iRackCurrentMonitoring 1}
currentConsumptionCurrentMonitoring	OBJECT IDENTIFIER ::= {iRackCurrentMonitoring 2} 
iRackCurrentMonitoringTraps			OBJECT IDENTIFIER ::= { iRackCurrentMonitoring 3 }
                                                            




	



 
-- Safeguard MIB
-- Parameters (Prefix sg) for safeguard       
-- Parameters (Prefix sn) for safetynet   
-- Parameters (Prefix snl) for safetynetlite
-- Parameters (Prefix snm) for safetynetmicrolite
-- Parameters (Prefix snp) for safetynetplus


sensorReading01 OBJECT-TYPE
	SYNTAX  	INTEGER(0..1000)
	ACCESS		read-only
	STATUS		mandatory
	DESCRIPTION	"Safeguard Sensor 01 Reading (use multiplier 0.1 for actual reading)"
::= { sgReadings 1 }

sensorReading02 OBJECT-TYPE
	SYNTAX  	INTEGER(0..1000)
	ACCESS		read-only
	STATUS		mandatory
	DESCRIPTION	"Safeguard Sensor 02 Reading (use multiplier 0.1 for actual reading)"
::= { sgReadings 2 }

sensorReading03 OBJECT-TYPE
	SYNTAX  	INTEGER(0..1000)
	ACCESS		read-only
	STATUS		mandatory
	DESCRIPTION	"Safeguard Sensor 03 Reading (use multiplier 0.1 for actual reading)"
::= { sgReadings 3 }

sensorReading04 OBJECT-TYPE
	SYNTAX  	INTEGER(0..1000)
	ACCESS		read-only
	STATUS		mandatory
	DESCRIPTION	"Safeguard Sensor 04 Reading (use multiplier 0.1 for actual reading)"
::= { sgReadings 4 }

sensorReading05 OBJECT-TYPE
	SYNTAX  	INTEGER(0..1000)
	ACCESS		read-only
	STATUS		mandatory
	DESCRIPTION	"Safeguard Sensor 05 Reading (use multiplier 0.1 for actual reading)"
::= { sgReadings 5 }

sensorReading06 OBJECT-TYPE
	SYNTAX  	INTEGER(0..1000)
	ACCESS		read-only
	STATUS		mandatory
	DESCRIPTION	"Safeguard Sensor 06 Reading (use multiplier 0.1 for actual reading)"
::= { sgReadings 6 }

sensorReading07 OBJECT-TYPE
	SYNTAX  	INTEGER(0..1000)
	ACCESS		read-only
	STATUS		mandatory
	DESCRIPTION	"Safeguard Sensor 07 Reading (use multiplier 0.1 for actual reading)"
::= { sgReadings 7 }

sensorReading08 OBJECT-TYPE
	SYNTAX  	INTEGER(0..1000)
	ACCESS		read-only
	STATUS		mandatory
	DESCRIPTION	"Safeguard Sensor 08 Reading (use multiplier 0.1 for actual reading)"
::= { sgReadings 8 }

sensorReading09 OBJECT-TYPE
	SYNTAX  	INTEGER(0..1000)
	ACCESS		read-only
	STATUS		mandatory
	DESCRIPTION	"Safeguard Sensor 09 Reading (use multiplier 0.1 for actual reading)"
::= { sgReadings 9 }

sensorReading10 OBJECT-TYPE
	SYNTAX  	INTEGER(0..1000)
	ACCESS		read-only
	STATUS		mandatory
	DESCRIPTION	"Safeguard Sensor 10 Reading (use multiplier 0.1 for actual reading)"
::= { sgReadings 10 }

sensorReading11 OBJECT-TYPE
	SYNTAX  	INTEGER(0..1000)
	ACCESS		read-only
	STATUS		mandatory
	DESCRIPTION	"Safeguard Sensor 11 Reading (use multiplier 0.1 for actual reading)"
::= { sgReadings 11 }

sensorReading12 OBJECT-TYPE
	SYNTAX  	INTEGER(0..1000)
	ACCESS		read-only
	STATUS		mandatory
	DESCRIPTION	"Safeguard Sensor 12 Reading (use multiplier 0.1 for actual reading)"
::= { sgReadings 12 }

sensorReading13 OBJECT-TYPE
	SYNTAX  	INTEGER(0..1000)
	ACCESS		read-only
	STATUS		mandatory
	DESCRIPTION	"Safeguard Sensor 13 Reading (use multiplier 0.1 for actual reading)"
::= { sgReadings 13 }

sensorReading14 OBJECT-TYPE
	SYNTAX  	INTEGER(0..1000)
	ACCESS		read-only
	STATUS		mandatory
	DESCRIPTION	"Safeguard Sensor 14 Reading (use multiplier 0.1 for actual reading)"
::= { sgReadings 14 }

sensorReading15 OBJECT-TYPE
	SYNTAX  	INTEGER(0..1000)
	ACCESS		read-only
	STATUS		mandatory
	DESCRIPTION	"Safeguard Sensor 15 Reading (use multiplier 0.1 for actual reading)"
::= { sgReadings 15 }

sensorReading16 OBJECT-TYPE
	SYNTAX  	INTEGER(0..1000)
	ACCESS		read-only
	STATUS		mandatory
	DESCRIPTION	"Safeguard Sensor 16 Reading (use multiplier 0.1 for actual reading)"
::= { sgReadings 16 }

sensorReading17 OBJECT-TYPE
	SYNTAX  	INTEGER(0..1000)
	ACCESS		read-only
	STATUS		mandatory
	DESCRIPTION	"Safeguard Sensor 17 Reading (use multiplier 0.1 for actual reading)"
::= { sgReadings 17 }

sensorReading18 OBJECT-TYPE
	SYNTAX  	INTEGER(0..1000)
	ACCESS		read-only
	STATUS		mandatory
	DESCRIPTION	"Safeguard Sensor 18 Reading (use multiplier 0.1 for actual reading)"
::= { sgReadings 18 }

sensorReading19 OBJECT-TYPE
	SYNTAX  	INTEGER(0..1000)
	ACCESS		read-only
	STATUS		mandatory
	DESCRIPTION	"Safeguard Sensor 19 Reading (use multiplier 0.1 for actual reading)"
::= { sgReadings 19 }

sensorReading20 OBJECT-TYPE
	SYNTAX  	INTEGER(0..1000)
	ACCESS		read-only
	STATUS		mandatory
	DESCRIPTION	"Safeguard Sensor 20 Reading (use multiplier 0.1 for actual reading)"
::= { sgReadings 20 }

sensorReading21 OBJECT-TYPE
	SYNTAX  	INTEGER(0..1000)
	ACCESS		read-only
	STATUS		mandatory
	DESCRIPTION	"Safeguard Sensor 21 Reading (use multiplier 0.1 for actual reading)"
::= { sgReadings 21 }

sensorReading22 OBJECT-TYPE
	SYNTAX  	INTEGER(0..1000)
	ACCESS		read-only
	STATUS		mandatory
	DESCRIPTION	"Safeguard Sensor 22 Reading (use multiplier 0.1 for actual reading)"
::= { sgReadings 22 }

sensorReading23 OBJECT-TYPE
	SYNTAX  	INTEGER(0..1000)
	ACCESS		read-only
	STATUS		mandatory
	DESCRIPTION	"Safeguard Sensor 23 Reading (use multiplier 0.1 for actual reading)"
::= { sgReadings 23 }

sensorReading24 OBJECT-TYPE
	SYNTAX  	INTEGER(0..1000)
	ACCESS		read-only
	STATUS		mandatory
	DESCRIPTION	"Safeguard Sensor 24 Reading (use multiplier 0.1 for actual reading)"
::= { sgReadings 24 }

sensorReading25 OBJECT-TYPE
	SYNTAX  	INTEGER(0..1000)
	ACCESS		read-only
	STATUS		mandatory
	DESCRIPTION	"Safeguard Sensor 25 Reading (use multiplier 0.1 for actual reading)"
::= { sgReadings 25 }

sensorReading26 OBJECT-TYPE
	SYNTAX  	INTEGER(0..1000)
	ACCESS		read-only
	STATUS		mandatory
	DESCRIPTION	"Safeguard Sensor 26 Reading (use multiplier 0.1 for actual reading)"
::= { sgReadings 26 }

sensorReading27 OBJECT-TYPE
	SYNTAX  	INTEGER(0..1000)
	ACCESS		read-only
	STATUS		mandatory
	DESCRIPTION	"Safeguard Sensor 27 Reading (use multiplier 0.1 for actual reading)"
::= { sgReadings 27 }

sensorReading28 OBJECT-TYPE
	SYNTAX  	INTEGER(0..1000)
	ACCESS		read-only
	STATUS		mandatory
	DESCRIPTION	"Safeguard Sensor 28 Reading (use multiplier 0.1 for actual reading)"
::= { sgReadings 28 }

sensorReading29 OBJECT-TYPE
	SYNTAX  	INTEGER(0..1000)
	ACCESS		read-only
	STATUS		mandatory
	DESCRIPTION	"Safeguard Sensor 29 Reading (use multiplier 0.1 for actual reading)"
::= { sgReadings 29 }

sensorReading30 OBJECT-TYPE
	SYNTAX  	INTEGER(0..1000)
	ACCESS		read-only
	STATUS		mandatory
	DESCRIPTION	"Safeguard Sensor 30 Reading (use multiplier 0.1 for actual reading)"
::= { sgReadings 30 }

sensorReading31 OBJECT-TYPE
	SYNTAX  	INTEGER(0..1000)
	ACCESS		read-only
	STATUS		mandatory
	DESCRIPTION	"Safeguard Sensor 31 Reading (use multiplier 0.1 for actual reading)"
::= { sgReadings 31 }


sensorReading32 OBJECT-TYPE
	SYNTAX  	INTEGER(0..1000)
	ACCESS		read-only
	STATUS		mandatory
	DESCRIPTION	"Safeguard Sensor 32 Reading (use multiplier 0.1 for actual reading)"
::= { sgReadings 32 }


safeguardMessageString OBJECT-TYPE
	SYNTAX		DisplayString (SIZE (0..63))
	ACCESS		read-only
	STATUS		mandatory
	DESCRIPTION	"Safeguard Alert/Warning/Alarm or Event Message."
::= { sgTraps 1 } 




-- Safetynet Descriptions from here

analogueOneReading OBJECT-TYPE
	SYNTAX  	INTEGER(-200..1200)
	ACCESS		read-only
	STATUS		mandatory
	DESCRIPTION	"Current SafetyNet Analogue Sensor One Reading  (use multiplier 0.1 for actual reading)"
::= { snReadings 1 }

analogueTwoReading OBJECT-TYPE
	SYNTAX  	INTEGER(-200..1200)
	ACCESS		read-only
	STATUS		mandatory
	DESCRIPTION	"Current SafetyNet Analogue Sensor Two Reading (use multiplier 0.1 for actual reading)"
::= { snReadings 2 }

smokeSensorReading OBJECT-TYPE
	SYNTAX  	INTEGER(0..1)
	ACCESS		read-only
	STATUS		mandatory
	DESCRIPTION	"SafetyNet Smoke Sensor Status  (0 = OFF, 1 = ON)"
::= { snReadings 3 }

fluidSensorReading OBJECT-TYPE
	SYNTAX  	INTEGER(0..1)
	ACCESS		read-only
	STATUS		mandatory
	DESCRIPTION	"SafetyNet Fluid Sensor Status  (0 = OFF, 1 = ON)"
::= { snReadings 4 }

digitalSensor01Reading OBJECT-TYPE
	SYNTAX  	INTEGER(0..1)
	ACCESS		read-only
	STATUS		mandatory
	DESCRIPTION	"SafetyNet Digital Sensor 01 Status  (0 = OFF, 1 = ON)"
::= { snReadings 5 }

digitalSensor02Reading OBJECT-TYPE
	SYNTAX  	INTEGER(0..1)
	ACCESS		read-only
	STATUS		mandatory
	DESCRIPTION	"SafetyNet Digital Sensor 02 Status  (0 = OFF, 1 = ON)"
::= { snReadings 6 }

digitalSensor03Reading OBJECT-TYPE
	SYNTAX  	INTEGER(0..1)
	ACCESS		read-only
	STATUS		mandatory
	DESCRIPTION	"SafetyNet Digital Sensor 03 Status  (0 = OFF, 1 = ON)"
::= { snReadings 7 }


digitalSensor04Reading OBJECT-TYPE
	SYNTAX  	INTEGER(0..1)
	ACCESS		read-only
	STATUS		mandatory
	DESCRIPTION	"SafetyNet Digital Sensor 04 Status  (0 = OFF, 1 = ON)"
::= { snReadings 8 }

safetyNetMessageString OBJECT-TYPE
	SYNTAX		DisplayString (SIZE (0..80))
	ACCESS		read-only
	STATUS		mandatory
	DESCRIPTION	"Message giving more detailed information on alarms/alerts/notifications."
::= { snTraps 1 } 
                       
safetyNetAlarmAnalogueSensorOne OBJECT-TYPE
	SYNTAX  	INTEGER(0..6)
	ACCESS		read-only
	STATUS		mandatory
	DESCRIPTION	"Alarm for analogue sensor one
0 = level OK
1 = level at high warning limit
2 = level at high alarm limit
3 = level at high shutdown limit
4 = level at low warning limit
5 = level at low alarm limit
6 = level at low shutdown limit"
	::= { snTraps 2 }

safetyNetAlarmAnalogueSensorTwo OBJECT-TYPE
	SYNTAX  	INTEGER(0..6)
	ACCESS		read-only
	STATUS		mandatory
	DESCRIPTION	"Alarm for analogue sensor two
0 = level OK
1 = level at high warning limit
2 = level at high alarm limit
3 = level at high shutdown limit
4 = level at low warning limit
5 = level at low alarm limit
6 = level at low shutdown limit"
	::= { snTraps 3 }


safetyNetAlarmSensor OBJECT-TYPE
	SYNTAX  	INTEGER(1..9)
	ACCESS		read-only
	STATUS		mandatory
	DESCRIPTION	"Alarm/Alert for Sensor
1 = Analogue Sensor One
2 = Analogue Sensor Two
3 = Smoke
4 = Fluid
5 = Digital 01
6 = Digital 02
7 = Digital 03
8 = Digital 04
9 = IP Monitoring"
	::= { snTraps 4 }

safetyNetSensorCleared OBJECT-TYPE
	SYNTAX  	INTEGER(3..9)
	ACCESS		read-only
	STATUS		mandatory
	DESCRIPTION	"Alarm cleared for Sensor
3 = Smoke
4 = Fluid
5 = Digital 01
6 = Digital 02
7 = Digital 03
8 = Digital 04
9 = IP Monitoring"
	::= { snTraps 5 }

safetyNetSoftwareNotification OBJECT-TYPE
	SYNTAX  	INTEGER(0..14)
	ACCESS		read-only
	STATUS		mandatory
	DESCRIPTION	"Software Notification
0 = Software watchdogtimer reset 
1 = Device reset manually via software
2 = Memory self-check failed, contact CSS
3 = Administration configuration (device settings/password) update detected
4 = Sensor/Relay configuration update detected
5 = Time update detected
6 = SMS configuration detected
7 = SNMP configuration detected
8 = Graph data cleared via web interface
9 = Alarm and event log cleared via web interface
10 = Firmware update detected
11 = Factory defaults loaded
12 = IP monitoring alarm activated SafetyBoot power cycle command
13 = IP monitoring alarm attempted to activate SafetyBoot power cycle command, aborted due to SafetyBoot being OFF
14 = IP monitoring alarm attempted to communicate with SafetyBoot. No response from SafetyBoot. Please check IP address of SafetyBoot"
	::= { snTraps 6 }

safetyNetHardwareNotification OBJECT-TYPE
	SYNTAX  	INTEGER(0..8)
	ACCESS		read-only
	STATUS		mandatory
	DESCRIPTION	"Hardware Error
0 = Mains failure detected
1 = Mains failure cleared and active
2 = Internal low battery detected
3 = Internal low battery alarm cleared
4 = Sensor number one faulty or disconnected
5 = Sensor number two faulty or disconnected
6 = Sensor number one back in order
7 = Sensor number two back in order
8 = Other hardware error"
	::= { snTraps 7 }


-- Safetynetlite Descriptions from here

safetyNetLiteTMPReading OBJECT-TYPE
	SYNTAX  	INTEGER(-200..1200)
	ACCESS		read-only
	STATUS		mandatory
	DESCRIPTION	"Current SafetyNet Lite Temperature Reading  (use multiplier 0.1 for actual reading)"
::= { snlReadings 1 }

safetyNetLiteHMDReading OBJECT-TYPE
	SYNTAX  	INTEGER(0..1000)
	ACCESS		read-only
	STATUS		mandatory
	DESCRIPTION	"Current SafetyNet Lite Humidity Reading (use multiplier 0.1 for actual reading)"
::= { snlReadings 2 }

digiSensor01Reading OBJECT-TYPE
	SYNTAX  	INTEGER(0..1)
	ACCESS		read-only
	STATUS		mandatory
	DESCRIPTION	"SafetyNet Lite Digital Sensor 01 Status  (0 = OFF, 1 = ON)"
::= { snlReadings 3 }

digiSensor02Reading OBJECT-TYPE
	SYNTAX  	INTEGER(0..1)
	ACCESS		read-only
	STATUS		mandatory
	DESCRIPTION	"SafetyNet Lite Digital Sensor 02 Status  (0 = OFF, 1 = ON)"
::= { snlReadings 4 }

digiSensor03Reading OBJECT-TYPE
	SYNTAX  	INTEGER(0..1)
	ACCESS		read-only
	STATUS		mandatory
	DESCRIPTION	"SafetyNet Lite Digital Sensor 03 Status  (0 = OFF, 1 = ON)"
::= { snlReadings 5 }


safetyNetLiteMsgString OBJECT-TYPE
	SYNTAX		DisplayString (SIZE (0..80))
	ACCESS		read-only
	STATUS		mandatory
	DESCRIPTION	"Message giving more detailed information on alarms/alerts/notifications on SafetyNet Lite."
::= { snlTraps 1 } 
                       
safetyNetLiteTemperature OBJECT-TYPE
	SYNTAX  	INTEGER(0..6)
	ACCESS		read-only
	STATUS		mandatory
	DESCRIPTION	"Temperature alarm 
0 = level OK
1 = level at high warning limit
2 = level at high alarm limit
3 = level at high shutdown limit
4 = level at low warning limit
5 = level at low alarm limit
6 = level at low shutdown limit"
	::= { snlTraps 2 }

safetyNetLiteHumidity OBJECT-TYPE
	SYNTAX  	INTEGER(0..6)
	ACCESS		read-only
	STATUS		mandatory
	DESCRIPTION	"Humidity alarm
0 = level OK
1 = level at high warning limit
2 = level at high alarm limit
3 = level at high shutdown limit
4 = level at low warning limit
5 = level at low alarm limit
6 = level at low shutdown limit"
	::= { snlTraps 3 }


safetyNetLiteAlarmSensor OBJECT-TYPE
	SYNTAX  	INTEGER(1..6)
	ACCESS		read-only
	STATUS		mandatory
	DESCRIPTION	"Alarm/Alert on Sensor
1 = Temperature
2 = Humidity
3 = Digital 01
4 = Digital 02
5 = Digital 03
6 = IP Monitoring"
	::= { snlTraps 4 }

safetyNetLiteSensorCleared OBJECT-TYPE
	SYNTAX  	INTEGER(3..6)
	ACCESS		read-only
	STATUS		mandatory
	DESCRIPTION	"Alarm cleared on Sensor
3 = Digital 01
4 = Digital 02
5 = Digital 03
6 = IP Monitoring"
	::= { snlTraps 5 }

safetyNetLiteSWNotification OBJECT-TYPE
	SYNTAX  	INTEGER(0..15)
	ACCESS		read-only
	STATUS		mandatory
	DESCRIPTION	"Software Notification
0 = Software watchdogtimer reset 
1 = Device reset manually via software
2 = Memory self-check failed, contact CSS
3 = Administration configuration (device settings/password) update detected
4 = Sensor/Relay configuration update detected
5 = Time update detected
6 = SMS/Modem configuration detected
7 = SNMP configuration detected
8 = Graph data cleared via web interface
9 = Alarm and event log cleared via web interface
10 = Firmware Update detected
11 = Factory defaults loaded
12 = IP monitoring alarm activated SafetyBoot power cycle command
13 = IP monitoring alarm attempted to activate SafetyBoot power cycle command, aborted due to SafetyBoot being OFF
14 = IP monitoring alarm attempted to communicate with SafetyBoot. No response from SafetyBoot. Please check IP address of SafetyBoot
15 = Test alarm initiated via the web interface. Sample Alarm."
	::= { snlTraps 6 }

safetyNetLiteHWNotification OBJECT-TYPE
	SYNTAX  	INTEGER(0..19)
	ACCESS		read-only
	STATUS		mandatory
	DESCRIPTION	"Hardware Error
0 = Mains failure detected
1 = Mains failure alarm cleared
2 = Internal low battery detected
3 = Internal low battery alarm cleared
4 = Analogue sensor faulty or disconnected
5 = Analogue sensor back in order
6 = Modem not detected. Modem initialisation error. SMS messages will fail.
7 = No response over 45 seconds. Abandoned SMS sending
8 = No dial tone. Abandoned sending SMS
9 = BUSY tone. Abandoned sending SMS
10 = Time out on receiving 'ID ='. Abandoned sending SMS
11 = Service provider did not respond with 'ID='. Abandoned sending SMS 
12 = Password ACK timeout. Abandoned sending SMS
13 = Service provider did not acknowledge SMS password. Abandoned sending SMS
14 = Message attempted to be sent. ACK or NAK timeout. Abandoned sending SMS
15 = Message NAK by service provider. Abandoned sending SMS
16 = Service provider dropped call due to length of call exceeded maximum time. Abandoned sending SMS
17 = Routine dial tone check failed. Please check if telephone cable is connected to the modem
18 = Dial tone detected by modem
19 = Other hardware error"
	::= { snlTraps 7 }

-- SafetynetMicro Descriptions from here

snMicroTemperatureReading OBJECT-TYPE
	SYNTAX  	INTEGER(-200..1200)
	ACCESS		read-only
	STATUS		mandatory
	DESCRIPTION	"Current SafetyNet Micro Temperature Reading  (use multiplier 0.1 for actual reading)"
::= { snmReadings 1 }

snMicroHumidityReading OBJECT-TYPE
	SYNTAX  	INTEGER(0..1000)
	ACCESS		read-only
	STATUS		mandatory
	DESCRIPTION	"Current SafetyNet Micro Humidity Reading (use multiplier 0.1 for actual reading)"
::= { snmReadings 2 }

snMicroDigitalSensorOneReading OBJECT-TYPE
	SYNTAX  	INTEGER(0..1)
	ACCESS		read-only
	STATUS		mandatory
	DESCRIPTION	"SafetyNet Micro Digital Sensor 01 Status  (0 = OFF, 1 = ON)"
::= { snmReadings 3 }

snMicroDigitalSensorTwoReading OBJECT-TYPE
	SYNTAX  	INTEGER(0..1)
	ACCESS		read-only
	STATUS		mandatory
	DESCRIPTION	"SafetyNet Micro Digital Sensor 02 Status  (0 = OFF, 1 = ON)"
::= { snmReadings 4 }

safetyNetMicroMsgString OBJECT-TYPE
	SYNTAX		DisplayString (SIZE (0..80))
	ACCESS		read-only
	STATUS		mandatory
	DESCRIPTION	"Message giving more detailed information on alarms/alerts/notifications on SafetyNet Micro."
::= { snmTraps 1 } 
                       
safetyNetMicroTemperature OBJECT-TYPE
	SYNTAX  	INTEGER(0..6)
	ACCESS		read-only
	STATUS		mandatory
	DESCRIPTION	"Temperature alarm 
0 = level OK
1 = level at high warning limit
2 = level at high alarm limit
3 = level at high shutdown limit
4 = level at low warning limit
5 = level at low alarm limit
6 = level at low shutdown limit"
	::= { snmTraps 2 }

safetyNetMicroHumidity OBJECT-TYPE
	SYNTAX  	INTEGER(0..6)
	ACCESS		read-only
	STATUS		mandatory
	DESCRIPTION	"Humidity alarm
0 = level OK
1 = level at high warning limit
2 = level at high alarm limit
3 = level at high shutdown limit
4 = level at low warning limit
5 = level at low alarm limit
6 = level at low shutdown limit"
	::= { snmTraps 3 }


safetyNetMicroAlarmSensor OBJECT-TYPE
	SYNTAX  	INTEGER(1..5)
	ACCESS		read-only
	STATUS		mandatory
	DESCRIPTION	"Alarm/Alert on Sensor
1 = Temperature
2 = Humidity
3 = Digital 01
4 = Digital 02
5 = IP Monitoring"
	::= { snmTraps 4 }

safetyNetMicroSensorCleared OBJECT-TYPE
	SYNTAX  	INTEGER(3..5)
	ACCESS		read-only
	STATUS		mandatory
	DESCRIPTION	"Alarm cleared on Sensor
3 = Digital 01
4 = Digital 02
5 = IP Monitoring"
	::= { snmTraps 5 }

safetyNetMicroSWNotification OBJECT-TYPE
	SYNTAX  	INTEGER(0..18)
	ACCESS		read-only
	STATUS		mandatory
	DESCRIPTION	"Software Notification
0 = Software watchdogtimer reset 
1 = Device reset manually via software
2 = Memory self-check failed, contact CSS
3 = Administration configuration (device settings/password) update detected
4 = Sensor/PPP configuration update detected
5 = Time update detected
6 = SMS/Modem configuration detected
7 = SNMP configuration detected
8 = Graph data cleared via web interface
9 = Alarm and event log cleared via web interface
10 = Firmware update detected
11 = Factory defaults loaded
12 = IP monitoring alarm activated SafetyBoot power cycle command
13 = IP monitoring alarm attempted to activate SafetyBoot power cycle command, aborted due to SafetyBoot being OFF
14 = IP monitoring alarm attempted to communicate with SafetyBoot. No response from SafetyBoot. Please check IP address of SafetyBoot
15 = Test alarm initiated via the web interface. Sample Alarm.
16 = License/Registration key(s) updated
17 = PPP Session established by an external user
18 = PPP Session auto initiated by SafetyNet Micro"
	::= { snmTraps 6 }

safetyNetMicroHWNotification OBJECT-TYPE
	SYNTAX  	INTEGER(0..3)
	ACCESS		read-only
	STATUS		mandatory
	DESCRIPTION	"Hardware Error/Clear Error
1 = Temperature/Humidity sensor faulty or disconnected
2 = Temperature/Humidity sensor back in order
3 = Modem not detected. Modem initialisation error. SMS messages will fail.
4 = No response over 45 seconds. Abandoned SMS sending
5 = No dial tone. Abandoned sending SMS
6 = BUSY tone. Abandoned sending SMS
7 = Time out on receiving 'ID ='. Abandoned sending SMS
8 = Service provider did not respond with 'ID='. Abandoned sending SMS 
9 = Password ACK timeout. Abandoned sending SMS
10 = Service provider did not acknowledge SMS password. Abandoned sending SMS
11 = Message attempted to be sent. ACK or NAK timeout. Abandoned sending SMS
12 = Message NAK by service provider. Abandoned sending SMS
13 = Service provider dropped call due to length of call exceeded maximum time. Abandoned sending SMS
14 = Routine dial tone check failed. Please check if telephone cable is connected to the modem
15 = Dial tone detected by modem
16 = Ethernet disconnection notified via PPP"
	::= { snmTraps 7 }


-- Safetynetplus Descriptions from here

safetynetplusTempOneReading OBJECT-TYPE
	SYNTAX  	INTEGER(-200..1200)
	ACCESS		read-only
	STATUS		mandatory
	DESCRIPTION	"SafetyNet Plus temperature sensor one reading  (use multiplier 0.1 for actual reading)"
::= { snpReadings 1 }

safetynetplusHumidityOneReading OBJECT-TYPE
	SYNTAX  	INTEGER(0..1000)
	ACCESS		read-only
	STATUS		mandatory
	DESCRIPTION	"SafetyNet Plus humiduty sensor one reading (use multiplier 0.1 for actual reading)"
::= { snpReadings 2 }

safetynetplusTempTwoReading OBJECT-TYPE
	SYNTAX  	INTEGER(-200..1200)
	ACCESS		read-only
	STATUS		mandatory
	DESCRIPTION	"SafetyNet PLus temperature sensor one reading  (use multiplier 0.1 for actual reading)"
::= { snpReadings 3 }

safetynetplusHumidityTwoReading OBJECT-TYPE
	SYNTAX  	INTEGER(0..1000)
	ACCESS		read-only
	STATUS		mandatory
	DESCRIPTION	"SafetyNet Plus humidity sensor two reading (use multiplier 0.1 for actual reading)"
::= { snpReadings 4 }


safetynetplusDigital01Reading OBJECT-TYPE
	SYNTAX  	INTEGER(0..1)
	ACCESS		read-only
	STATUS		mandatory
	DESCRIPTION	"SafetyNet Plus digital sensor 01 status  (0 = OFF, 1 = ON)"
::= { snpReadings 5 }

safetynetplusDigital02Reading OBJECT-TYPE
	SYNTAX  	INTEGER(0..1)
	ACCESS		read-only
	STATUS		mandatory
	DESCRIPTION	"SafetyNet Plus digital sensor 02 status  (0 = OFF, 1 = ON)"
::= { snpReadings 6 }

safetynetplusDigital03Reading OBJECT-TYPE
	SYNTAX  	INTEGER(0..1)
	ACCESS		read-only
	STATUS		mandatory
	DESCRIPTION	"SafetyNet Plus digital sensor 03 status  (0 = OFF, 1 = ON)"
::= { snpReadings 7 }


safetynetplusDigital04Reading OBJECT-TYPE
	SYNTAX  	INTEGER(0..1)
	ACCESS		read-only
	STATUS		mandatory
	DESCRIPTION	"SafetyNet Plus digital sensor 04 status  (0 = OFF, 1 = ON)"
::= { snpReadings 8 }

safetynetplusDigital05Reading OBJECT-TYPE
	SYNTAX  	INTEGER(0..1)
	ACCESS		read-only
	STATUS		mandatory
	DESCRIPTION	"SafetyNet Plus digital sensor 05 status  (0 = OFF, 1 = ON)"
::= { snpReadings 9 }


safetynetplusDigital06Reading OBJECT-TYPE
	SYNTAX  	INTEGER(0..1)
	ACCESS		read-only
	STATUS		mandatory
	DESCRIPTION	"SafetyNet Plus digital sensor 06 status  (0 = OFF, 1 = ON)"
::= { snpReadings 10 }

safetynetplusMessageString OBJECT-TYPE
	SYNTAX		DisplayString (SIZE (0..80))
	ACCESS		read-only
	STATUS		mandatory
	DESCRIPTION	"Message giving more detailed information on alarms/alerts/notifications on SafetyNet Plus."
::= { snpTraps 1 } 
                       
safetynetplusAlarmTemperatureOne OBJECT-TYPE
	SYNTAX  	INTEGER(0..6)
	ACCESS		read-only
	STATUS		mandatory
	DESCRIPTION	"Alarm for temperature sensor one
0 = level OK
1 = level at high warning limit
2 = level at high alarm limit
3 = level at high shutdown limit
4 = level at low warning limit
5 = level at low alarm limit
6 = level at low shutdown limit"
	::= { snpTraps 2 }

safetynetplusAlarmHumidityOne OBJECT-TYPE
	SYNTAX  	INTEGER(0..6)
	ACCESS		read-only
	STATUS		mandatory
	DESCRIPTION	"Alarm for humidity sensor one
0 = level OK
1 = level at high warning limit
2 = level at high alarm limit
3 = level at high shutdown limit
4 = level at low warning limit
5 = level at low alarm limit
6 = level at low shutdown limit"
	::= { snpTraps 3 }

safetynetplusAlarmTemperatureTwo OBJECT-TYPE
	SYNTAX  	INTEGER(0..6)
	ACCESS		read-only
	STATUS		mandatory
	DESCRIPTION	"Alarm for temperature sensor two
0 = level OK
1 = level at high warning limit
2 = level at high alarm limit
3 = level at high shutdown limit
4 = level at low warning limit
5 = level at low alarm limit
6 = level at low shutdown limit"
	::= { snpTraps 4 }

safetynetplusAlarmHumidityTwo OBJECT-TYPE
	SYNTAX  	INTEGER(0..6)
	ACCESS		read-only
	STATUS		mandatory
	DESCRIPTION	"Alarm for humidity sensor two
0 = level OK
1 = level at high warning limit
2 = level at high alarm limit
3 = level at high shutdown limit
4 = level at low warning limit
5 = level at low alarm limit
6 = level at low shutdown limit"
	::= { snpTraps 5 }


safetynetplusAlarmSensor OBJECT-TYPE
	SYNTAX  	INTEGER(1..11)
	ACCESS		read-only
	STATUS		mandatory
	DESCRIPTION	"Alarm/Alert for Sensor
1 = Temperature 01
2 = Humidity 01
3 = Temperature 02
4 = Humidity 02
5 = Digital 01
6 = Digital 02
7 = Digital 03
8 = Digital 04
9 = Digital 05
10 = Digital 06
11 = IP Monitoring"
	::= { snpTraps 6 }

safetynetplusSensorCleared OBJECT-TYPE
	SYNTAX  	INTEGER(5..11)
	ACCESS		read-only
	STATUS		mandatory
	DESCRIPTION	"Alarm cleared for Sensor
5 = Digital 01
6 = Digital 02
7 = Digital 03
8 = Digital 04
9 = Digital 05
10 = Digital 06
11 = IP Monitoring"
	::= { snpTraps 7 }

safetynetplusSWNotification OBJECT-TYPE
	SYNTAX  	INTEGER(0..21)
	ACCESS		read-only
	STATUS		mandatory
	DESCRIPTION	"Software Notification for SafetyNet Plus
0 = Software watchdogtimer reset 
1 = Device reset manually via software
2 = Memory self-check failed, contact CSS
3 = Administration configuration (device settings/password) update detected
4 = Sensor/Relay configuration update detected
5 = Time update detected
6 = SMS/Modem configuration detected
7 = SNMP configuration detected
8 = Graph data cleared via web interface
9 = Alarm and event log cleared via web interface
10 = Firmware Update detected
11 = Factory defaults loaded
12 = IP monitoring alarm activated SafetyBoot power cycle command
13 = IP monitoring alarm attempted to activate SafetyBoot power cycle command, aborted due to SafetyBoot being OFF
14 = IP monitoring alarm attempted to communicate with SafetyBoot. No response from SafetyBoot. Please check IP address of SafetyBoot
15 = Test alarm initiated via the web interface. Sample Alarm
16 = A/C Sequence Controller Enabled
17 = TMP alarm(s)/Input 1 or 2 activating both relays
18 = TMP or Inputs 1,2 cleared. Exiting bypassing relays
19 = A/C Seq: Cycle Activation - Relay 1 OFF, Relay 2 ON
20 = A/C Seq: Cycle Activation - Relay 1 ON, Relay 2 OFF
21 = A/C Sequence Controller Disabled"

	::= { snpTraps 8 }

safetynetplusHWNotification OBJECT-TYPE
	SYNTAX  	INTEGER(0..21)
	ACCESS		read-only
	STATUS		mandatory
	DESCRIPTION	"Hardware Error on SafetyNet Plus
0 = Mains failure detected
1 = Mains failure alarm cleared
2 = Internal low battery detected
3 = Internal low battery alarm cleared
4 = Analogue sensor number one faulty or disconnected
5 = Analogue sensor number two faulty or disconnected
6 = Analogue sensor number one back in order
7 = Analogue sensor number two back in order
8 = Modem not detected. Modem initialisation error. SMS messages will fail.
9 = No response over 45 seconds. Abandoned SMS sending
10 = No dial tone. Abandoned sending SMS
11 = BUSY tone. Abandoned sending SMS
12 = Time out on receiving 'ID ='. Abandoned sending SMS
13 = Service provider did not respond with 'ID='. Abandoned sending SMS 
14 = Password ACK timeout. Abandoned sending SMS
15 = Service provider did not acknowledge SMS password. Abandoned sending SMS
16 = Message attempted to be sent. ACK or NAK timeout. Abandoned sending SMS
17 = Message NAK by service provider. Abandoned sending SMS
18 = Service provider dropped call due to length of call exceeded maximum time. Abandoned sending SMS
19 = Routine dial tone check failed. Please check if telephone cable is connected to the modem
20 = Dial tone detected by modem
21 = Other hardware error"
	::= { snpTraps 9 }

	
-- Tree expansion for iRack   



deviceName20Way OBJECT-TYPE
	SYNTAX  	DisplayString (SIZE (30))
	ACCESS		read-write
	STATUS		mandatory
	DESCRIPTION	"i-Rack Device Name Parameter" 
::= { iRackParams20Way 1 }   

deviceLocation20Way OBJECT-TYPE
	SYNTAX  	DisplayString (SIZE (30))
	ACCESS		read-write
	STATUS		mandatory
	DESCRIPTION	"i-Rack Device Location Parameter"
::= { iRackParams20Way 2 }  

ipAddr20Way OBJECT-TYPE
	SYNTAX  	IpAddress
	ACCESS		read-only
	STATUS		mandatory
	DESCRIPTION	"i-Rack IP Address"
::= { iRackParams20Way 3 }

sysDescription20Way OBJECT-TYPE
	SYNTAX  	DisplayString (SIZE (30))
	ACCESS		read-only
	STATUS		mandatory
	DESCRIPTION	"i-Rack Description"
::= { iRackParams20Way 4 }  

modelNumber20Way OBJECT-TYPE
	SYNTAX  	DisplayString (SIZE (5))
	ACCESS	read-only
	STATUS		mandatory
	DESCRIPTION	"i-Rack Model Number"
::= { iRackParams20Way 5 }
                              
outlet1-20Way OBJECT-TYPE
	SYNTAX  	INTEGER(0..1000)
	ACCESS		read-only
	STATUS 		mandatory
	DESCRIPTION	"i-Rack Outlet 1 Status
	00 = OUTLET OFF
	01 = OUTLET ON
	02 = OUTLET REBOOTING
	03 = STARTING UP
	"
::= { outletStatus20Way 1 }  

outlet2-20Way OBJECT-TYPE
	SYNTAX  	INTEGER(0..1000)
	ACCESS		read-only
	STATUS		mandatory
	DESCRIPTION	"i-Rack Outlet 2 Status
	00 = OUTLET OFF
	01 = OUTLET ON
	02 = OUTLET REBOOTING
	03 = STARTING UP
	"
::= { outletStatus20Way 2 }


outlet3-20Way OBJECT-TYPE
	SYNTAX  	INTEGER(0..1000)
	ACCESS		read-only
	STATUS		mandatory
	DESCRIPTION	"i-Rack Outlet 3 Status
	00 = OUTLET OFF
	01 = OUTLET ON
	02 = OUTLET REBOOTING
	03 = STARTING UP 	
	"
::= { outletStatus20Way 3 }


outlet4-20Way OBJECT-TYPE
	SYNTAX  	INTEGER(0..1000)
	ACCESS		read-only
	STATUS		mandatory
	DESCRIPTION	"i-Rack Outlet 4 Status
	00 = OUTLET OFF
	01 = OUTLET ON
	02 = OUTLET REBOOTING
	03 = STARTING UP
	"
::= { outletStatus20Way 4 }

outlet5-20Way OBJECT-TYPE
	SYNTAX  	INTEGER(0..1000)
	ACCESS		read-only
	STATUS		mandatory
	DESCRIPTION	"i-Rack Outlet 5 Status
	00 = OUTLET OFF
	01 = OUTLET ON
	02 = OUTLET REBOOTING
	03 = STARTING UP
	"
::= { outletStatus20Way 5 }

outlet6-20Way OBJECT-TYPE
	SYNTAX  	INTEGER(0..1000)
	ACCESS		read-only
	STATUS		mandatory
	DESCRIPTION	"i-Rack Outlet 6 Status
	00 = OUTLET OFF
	01 = OUTLET ON
	02 = OUTLET REBOOTING
	03 = STARTING UP
	"
::= { outletStatus20Way 6 }

outlet7-20Way OBJECT-TYPE
	SYNTAX  	INTEGER(0..1000)
	ACCESS		read-only
	STATUS		mandatory
	DESCRIPTION	"i-Rack Outlet 7 Status
	00 = OUTLET OFF
	01 = OUTLET ON
	02 = OUTLET REBOOTING
	03 = STARTING UP
	"
::= { outletStatus20Way 7 }

outlet8-20Way OBJECT-TYPE
	SYNTAX  	INTEGER(0..1000)
	ACCESS		read-only
	STATUS		mandatory
	DESCRIPTION	"i-Rack Outlet 8 Status
	00 = OUTLET OFF
	01 = OUTLET ON
	02 = OUTLET REBOOTING
	03 = STARTING UP
	"
::= { outletStatus20Way 8 }

outlet9-20Way OBJECT-TYPE
	SYNTAX  	INTEGER(0..1000)
	ACCESS		read-only
	STATUS		mandatory
	DESCRIPTION	"i-Rack Outlet 9 Status
	00 = OUTLET OFF
	01 = OUTLET ON
	02 = OUTLET REBOOTING
	03 = STARTING UP
	"
::= { outletStatus20Way 9 }

outlet10-20Way OBJECT-TYPE
	SYNTAX  	INTEGER(0..1000)
	ACCESS		read-only
	STATUS		mandatory
	DESCRIPTION	"i-Rack Outlet 10 Status
	00 = OUTLET OFF
	01 = OUTLET ON
	02 = OUTLET REBOOTING
	03 = STARTING UP
	"
::= { outletStatus20Way 10 }

outlet11-20Way OBJECT-TYPE
	SYNTAX  	INTEGER(0..1000)
	ACCESS		read-only
	STATUS		mandatory
	DESCRIPTION	"i-Rack Outlet 11 Status
	00 = OUTLET OFF
	01 = OUTLET ON
	02 = OUTLET REBOOTING
	03 = STARTING UP
	"
::= { outletStatus20Way 11 }

outlet12-20Way OBJECT-TYPE
	SYNTAX  	INTEGER(0..1000)
	ACCESS		read-only
	STATUS		mandatory
	DESCRIPTION	"i-Rack Outlet 12 Status
	00 = OUTLET OFF
	01 = OUTLET ON
	02 = OUTLET REBOOTING
	03 = STARTING UP
	"
::= { outletStatus20Way 12 }

outlet13-20Way OBJECT-TYPE
	SYNTAX  	INTEGER(0..1000)
	ACCESS		read-only
	STATUS		mandatory
	DESCRIPTION	"i-Rack Outlet 13 Status
	00 = OUTLET OFF
	01 = OUTLET ON
	02 = OUTLET REBOOTING
	03 = STARTING UP
	"
::= { outletStatus20Way 13 }

outlet14-20Way OBJECT-TYPE
	SYNTAX  	INTEGER(0..1000)
	ACCESS		read-only
	STATUS		mandatory
	DESCRIPTION	"i-Rack Outlet 14 Status
	00 = OUTLET OFF
	01 = OUTLET ON
	02 = OUTLET REBOOTING
	03 = STARTING UP
	"
::= { outletStatus20Way 14 }

outlet15-20Way OBJECT-TYPE
	SYNTAX  	INTEGER(0..1000)
	ACCESS		read-only
	STATUS		mandatory
	DESCRIPTION	"i-Rack Outlet 15 Status
	00 = OUTLET OFF
	01 = OUTLET ON
	02 = OUTLET REBOOTING
	03 = STARTING UP
	"
::= { outletStatus20Way 15 }

outlet16-20Way OBJECT-TYPE
	SYNTAX  	INTEGER(0..1000)
	ACCESS		read-only
	STATUS		mandatory
	DESCRIPTION	"i-Rack Outlet 16 Status
	00 = OUTLET OFF
	01 = OUTLET ON
	02 = OUTLET REBOOTING
	03 = STARTING UP
	"
::= { outletStatus20Way 16 }

outlet17-20Way OBJECT-TYPE
	SYNTAX  	INTEGER(0..1000)
	ACCESS		read-only
	STATUS		mandatory
	DESCRIPTION	"i-Rack Outlet 17 Status
	00 = OUTLET OFF
	01 = OUTLET ON
	02 = OUTLET REBOOTING
	03 = STARTING UP
	"
::= { outletStatus20Way 17 }

outlet18-20Way OBJECT-TYPE
	SYNTAX  	INTEGER(0..1000)
	ACCESS		read-only
	STATUS		mandatory
	DESCRIPTION	"i-Rack Outlet 18 Status
	00 = OUTLET OFF
	01 = OUTLET ON
	02 = OUTLET REBOOTING
	03 = STARTING UP
	"
::= { outletStatus20Way 18 }

outlet19-20Way OBJECT-TYPE
	SYNTAX  	INTEGER(0..1000)
	ACCESS		read-only
	STATUS		mandatory
	DESCRIPTION	"i-Rack Outlet 19 Status
	00 = OUTLET OFF
	01 = OUTLET ON
	02 = OUTLET REBOOTING
	03 = STARTING UP
	"
::= { outletStatus20Way 19 }

outlet20-20Way OBJECT-TYPE
	SYNTAX  	INTEGER(0..1000)
	ACCESS		read-only
	STATUS		mandatory
	DESCRIPTION	"i-Rack Outlet 20 Status
	00 = OUTLET OFF
	01 = OUTLET ON
	02 = OUTLET REBOOTING
	03 = STARTING UP
	"
::= { outletStatus20Way 20 }


currentConsumed-20Way OBJECT-TYPE
	SYNTAX  	INTEGER(0..1000)
	ACCESS		read-only
	STATUS		mandatory
	DESCRIPTION	"i-Rack total current consumption. This value is in milli amperes"
::= { currentConsumption20Way 1 }

iRack20WayMessageString OBJECT-TYPE
	SYNTAX		DisplayString (SIZE (0..80))
	ACCESS		read-only
	STATUS		mandatory
	DESCRIPTION	"Message giving more detailed information on alarms/alerts/notifications on iRack."
::= { iRack20WayTraps 1 } 
                       
iRack20WayCurrentLoadStatus OBJECT-TYPE
	SYNTAX  	INTEGER(0..6)
	ACCESS		read-only
	STATUS		mandatory
	DESCRIPTION	"Alarm for Current Load Sensor
0 = level OK
1 = level at warning level
2 = level at alarm level
3 = level at critical level"
::= { iRack20WayTraps 2 }


iRack20WayTemperatureAlarmStatus OBJECT-TYPE
	SYNTAX  	INTEGER(0..6)
	ACCESS		read-only
	STATUS		mandatory
	DESCRIPTION	"Alarm for Temperature Sensor
0 = level OK
1 = level at high warning level
2 = level at high alarm level
3 = level at high shutdown level
4 = level at low warning level
5 = level at low alarm level
6 = level at low shutdown level"
::= { iRack20WayTraps 3 }

iRack20WayHumidityAlarmStatus OBJECT-TYPE
	SYNTAX  	INTEGER(0..6)
	ACCESS		read-only
	STATUS		mandatory
	DESCRIPTION	"Alarm for Humidity Sensor
0 = level OK
1 = level at high warning level
2 = level at high alarm level
3 = level at high shutdown level
4 = level at low warning level
5 = level at low alarm level
6 = level at low shutdown level"
::= { iRack20WayTraps 4 }  

iRack20WayDigitalOneStatus OBJECT-TYPE
	SYNTAX  	INTEGER(0..1)
	ACCESS		read-only
	STATUS		mandatory
	DESCRIPTION	"Alarm for Digital Sensor One
0 = OK
1 = Alarm"
::= { iRack20WayTraps 5 }
 
iRack20WayDigitalTwoStatus OBJECT-TYPE
	SYNTAX  	INTEGER(0..1)
	ACCESS		read-only
	STATUS		mandatory
	DESCRIPTION	"Alarm for Digital Sensor Two
0 = OK
1 = Alarm"
::= { iRack20WayTraps 6 } 

iRack20WayTemperature OBJECT-TYPE
	SYNTAX  	INTEGER(0..1000)
	ACCESS		read-only
	STATUS		mandatory
	DESCRIPTION	"i-Rack temperature sensor reading (use multiplier 0.1 for actual reading)"
::= { iRack20WayTraps 7 } 

iRack20WayHumidity OBJECT-TYPE
	SYNTAX  	INTEGER(0..1000)
	ACCESS		read-only
	STATUS		mandatory
	DESCRIPTION	"i-Rack humidity sensor reading (use multiplier 0.1 for actual reading)"
::= { iRack20WayTraps 8 }





-- Tree expansion for iRack 6 Way



deviceName6Way OBJECT-TYPE
	SYNTAX  	DisplayString (SIZE (30))
	ACCESS		read-write
	STATUS		mandatory
	DESCRIPTION	"i-Rack Device Name Parameter" 
::= { iRackParams6Way 1 }   

deviceLocation6Way OBJECT-TYPE
	SYNTAX  	DisplayString (SIZE (30))
	ACCESS		read-write
	STATUS		mandatory
	DESCRIPTION	"i-Rack Device Location Parameter"
::= { iRackParams6Way 2 }  

ipAddr6Way OBJECT-TYPE
	SYNTAX  	IpAddress
	ACCESS	read-only
	STATUS		mandatory
	DESCRIPTION	"i-Rack IP Address"
::= { iRackParams6Way 3 }

sysDescription6Way OBJECT-TYPE
	SYNTAX  	DisplayString (SIZE (30))
	ACCESS		read-only
	STATUS		mandatory
	DESCRIPTION	"i-Rack Description"
::= { iRackParams6Way 4 }  

modelNumber6Way OBJECT-TYPE
	SYNTAX  	DisplayString (SIZE (5))
	ACCESS		read-only
	STATUS		mandatory
	DESCRIPTION	"i-Rack Model Number"
::= { iRackParams6Way 5 }

                                    
outlet1-6Way OBJECT-TYPE
	SYNTAX  	INTEGER(0..1000)
	ACCESS		read-only
	STATUS		mandatory
	DESCRIPTION	"i-Rack Outlet 1 Status
	00 = OUTLET OFF
	01 = OUTLET ON
	02 = OUTLET REBOOTING
	03 = STARTING UP
	"
::= { outletStatus6Way 1 }

outlet2-6Way OBJECT-TYPE
	SYNTAX  	INTEGER(0..1000)
	ACCESS		read-only
	STATUS		mandatory
	DESCRIPTION	"i-Rack Outlet 2 Status
	00 = OUTLET OFF
	01 = OUTLET ON
	02 = OUTLET REBOOTING
	03 = STARTING UP
	"
::= { outletStatus6Way 2 }


outlet3-6Way OBJECT-TYPE
	SYNTAX  	INTEGER(0..1000)
	ACCESS		read-only
	STATUS		mandatory
	DESCRIPTION	"i-Rack Outlet 3 Status
	00 = OUTLET OFF
	01 = OUTLET ON
	02 = OUTLET REBOOTING
	03 = STARTING UP
	"
::= { outletStatus6Way 3 }


outlet4-6Way OBJECT-TYPE
	SYNTAX  	INTEGER(0..1000)
	ACCESS		read-only
	STATUS		mandatory
	DESCRIPTION	"i-Rack Outlet 4 Status
	00 = OUTLET OFF
	01 = OUTLET ON
	02 = OUTLET REBOOTING
	03 = STARTING UP
	"
::= { outletStatus6Way 4 }

outlet5-6Way OBJECT-TYPE
	SYNTAX  	INTEGER(0..1000)
	ACCESS		read-only
	STATUS		mandatory
	DESCRIPTION	"i-Rack Outlet 5 Status
	00 = OUTLET OFF
	01 = OUTLET ON
	02 = OUTLET REBOOTING
	03 = STARTING UP
	"
::= { outletStatus6Way 5 }

outlet6-6Way OBJECT-TYPE
	SYNTAX  	INTEGER(0..1000)
	ACCESS		read-only
	STATUS		mandatory
	DESCRIPTION	"i-Rack Outlet 6 Status
	00 = OUTLET OFF
	01 = OUTLET ON
	02 = OUTLET REBOOTING
	03 = STARTING UP
	"
::= { outletStatus6Way 6 }



currentConsumed-6Way OBJECT-TYPE
	SYNTAX  	INTEGER(0..1000)
	ACCESS		read-only
	STATUS		mandatory
	DESCRIPTION	"i-Rack total current consumption. This value is in milli amperes"
::= { currentConsumption6Way 1 }  

iRack6WayMessageString OBJECT-TYPE
	SYNTAX		DisplayString (SIZE (0..80))
	ACCESS		read-only
	STATUS		mandatory
	DESCRIPTION	"Message giving more detailed information on alarms/alerts/notifications on iRack."
::= { iRack6WayTraps 1 }  

iRack6WayCurrentLoadStatus OBJECT-TYPE
	SYNTAX  	INTEGER(0..6)
	ACCESS		read-only
	STATUS		mandatory
	DESCRIPTION	"Alarm for Current Load Sensor
0 = level OK
1 = level at warning level
2 = level at alarm level
3 = level at critical level"
::= { iRack6WayTraps 2 }


-- Tree expansion for iRack 4 Way

deviceName4Way OBJECT-TYPE
	SYNTAX  	DisplayString (SIZE (30))
	ACCESS		read-write
	STATUS		mandatory
	DESCRIPTION	"i-Rack Device Name Parameter" 
::= { iRackParams4Way 1 }   

deviceLocation4Way OBJECT-TYPE
	SYNTAX  	DisplayString (SIZE (30))
	ACCESS		read-write
	STATUS		mandatory
	DESCRIPTION	"i-Rack Device Location Parameter"
::= { iRackParams4Way 2 }  

ipAddr4Way OBJECT-TYPE
	SYNTAX  	IpAddress
	ACCESS	read-only
	STATUS		mandatory
	DESCRIPTION	"i-Rack IP Address"
::= { iRackParams4Way 3 }

sysDescription4Way OBJECT-TYPE
	SYNTAX  	DisplayString (SIZE (30))
	ACCESS		read-only
	STATUS		mandatory
	DESCRIPTION	"i-Rack Description"
::= { iRackParams4Way 4 }  

modelNumber4Way OBJECT-TYPE
	SYNTAX  	DisplayString (SIZE (5))
	ACCESS		read-only
	STATUS		mandatory
	DESCRIPTION	"i-Rack Model Number"
::= { iRackParams4Way 5 }

                                    
outlet1-4Way OBJECT-TYPE
	SYNTAX  	INTEGER(0..1000)
	ACCESS		read-only
	STATUS		mandatory
	DESCRIPTION	"i-Rack Outlet 1 Status
	00 = OUTLET OFF
	01 = OUTLET ON
	02 = OUTLET REBOOTING
	03 = STARTING UP
	"
::= { outletStatus4Way 1 }

outlet2-4Way OBJECT-TYPE
	SYNTAX  	INTEGER(0..1000)
	ACCESS		read-only
	STATUS		mandatory
	DESCRIPTION	"i-Rack Outlet 2 Status
	00 = OUTLET OFF
	01 = OUTLET ON
	02 = OUTLET REBOOTING
	03 = STARTING UP
	"
::= { outletStatus4Way 2 }


outlet3-4Way OBJECT-TYPE
	SYNTAX  	INTEGER(0..1000)
	ACCESS		read-only
	STATUS		mandatory
	DESCRIPTION	"i-Rack Outlet 3 Status
	00 = OUTLET OFF
	01 = OUTLET ON
	02 = OUTLET REBOOTING
	03 = STARTING UP
	"
::= { outletStatus4Way 3 }


outlet4-4Way OBJECT-TYPE
	SYNTAX  	INTEGER(0..1000)
	ACCESS		read-only
	STATUS		mandatory
	DESCRIPTION	"i-Rack Outlet 4 Status
	00 = OUTLET OFF
	01 = OUTLET ON
	02 = OUTLET REBOOTING
	03 = STARTING UP
	"
::= { outletStatus4Way 4 }

currentConsumed-4Way OBJECT-TYPE
	SYNTAX  	INTEGER(0..1000)
	ACCESS		read-only
	STATUS		mandatory
	DESCRIPTION	"i-Rack total current consumption. This value is in milli amperes"
::= { currentConsumption4Way 1 }  

iRack4WayMessageString OBJECT-TYPE
	SYNTAX		DisplayString (SIZE (0..80))
	ACCESS		read-only
	STATUS		mandatory
	DESCRIPTION	"Message giving more detailed information on alarms/alerts/notifications on iRack."
::= { iRack4WayTraps 1 }  

iRack4WayCurrentLoadStatus OBJECT-TYPE
	SYNTAX  	INTEGER(0..6)
	ACCESS		read-only
	STATUS		mandatory
	DESCRIPTION	"Alarm for Current Load Sensor
0 = level OK
1 = level at warning level
2 = level at alarm level
3 = level at critical level"
::= { iRack4WayTraps 2 }

iRack4WayTemperatureAlarmStatus OBJECT-TYPE
	SYNTAX  	INTEGER(0..6)
	ACCESS		read-only
	STATUS		mandatory
	DESCRIPTION	"Alarm for Temperature Sensor
0 = level OK
1 = level at high warning level
2 = level at high alarm level
3 = level at high shutdown level
4 = level at low warning level
5 = level at low alarm level
6 = level at low shutdown level"
::= { iRack4WayTraps 3 }

iRack4WayHumidityAlarmStatus OBJECT-TYPE
	SYNTAX  	INTEGER(0..6)
	ACCESS		read-only
	STATUS		mandatory
	DESCRIPTION	"Alarm for Humidity Sensor
0 = level OK
1 = level at high warning level
2 = level at high alarm level
3 = level at high shutdown level
4 = level at low warning level
5 = level at low alarm level
6 = level at low shutdown level"
::= { iRack4WayTraps 4 }  

iRack4WayDigitalOneStatus OBJECT-TYPE
	SYNTAX  	INTEGER(0..1)
	ACCESS		read-only
	STATUS		mandatory
	DESCRIPTION	"Alarm for Digital Sensor One
0 = OK
1 = Alarm"
::= { iRack4WayTraps 5 }
 
iRack4WayDigitalTwoStatus OBJECT-TYPE
	SYNTAX  	INTEGER(0..1)
	ACCESS		read-only
	STATUS		mandatory
	DESCRIPTION	"Alarm for Digital Sensor Two
0 = OK
1 = Alarm"
::= { iRack4WayTraps 6 } 

iRack4WayTemperature OBJECT-TYPE
	SYNTAX  	INTEGER(0..1000)
	ACCESS		read-only
	STATUS		mandatory
	DESCRIPTION	"i-Rack temperature sensor reading (use multiplier 0.1 for actual reading)"
::= { iRack4WayTraps 7 } 

iRack4WayHumidity OBJECT-TYPE
	SYNTAX  	INTEGER(0..1000)
	ACCESS		read-only
	STATUS		mandatory
	DESCRIPTION	"i-Rack humidity sensor reading (use multiplier 0.1 for actual reading)"
::= { iRack4WayTraps 8 }


 
-- Tree expansion for iRack 16 Way  



deviceName16Way OBJECT-TYPE
	SYNTAX  	DisplayString (SIZE (30))
	ACCESS		read-write
	STATUS		mandatory
	DESCRIPTION	"i-Rack Device Name Parameter" 
::= { iRackParams16Way 1 }   

deviceLocation16Way OBJECT-TYPE
	SYNTAX  	DisplayString (SIZE (30))
	ACCESS		read-write
	STATUS		mandatory
	DESCRIPTION	"i-Rack Device Location Parameter"
::= { iRackParams16Way 2 }  

ipAddr16Way OBJECT-TYPE
	SYNTAX  	IpAddress
	ACCESS		read-only
	STATUS		mandatory
	DESCRIPTION	"i-Rack IP Address"
::= { iRackParams16Way 3 }

sysDescription16Way OBJECT-TYPE
	SYNTAX  	DisplayString (SIZE (30))
	ACCESS		read-only
	STATUS		mandatory
	DESCRIPTION	"i-Rack Description"
::= { iRackParams16Way 4 }  

modelNumber16Way OBJECT-TYPE
	SYNTAX  	DisplayString (SIZE (5))
	ACCESS	read-only
	STATUS		mandatory
	DESCRIPTION	"i-Rack Model Number"
::= { iRackParams16Way 5 }
                              
outlet1-16Way OBJECT-TYPE
	SYNTAX  	INTEGER(0..1000)
	ACCESS		read-only
	STATUS 		mandatory
	DESCRIPTION	"i-Rack Outlet 1 Status
	00 = OUTLET OFF
	01 = OUTLET ON
	02 = OUTLET REBOOTING
	03 = STARTING UP
	"
::= { outletStatus16Way 1 }  

outlet2-16Way OBJECT-TYPE
	SYNTAX  	INTEGER(0..1000)
	ACCESS		read-only
	STATUS		mandatory
	DESCRIPTION	"i-Rack Outlet 2 Status
	00 = OUTLET OFF
	01 = OUTLET ON
	02 = OUTLET REBOOTING
	03 = STARTING UP
	"
::= { outletStatus16Way 2 }


outlet3-16Way OBJECT-TYPE
	SYNTAX  	INTEGER(0..1000)
	ACCESS		read-only
	STATUS		mandatory
	DESCRIPTION	"i-Rack Outlet 3 Status
	00 = OUTLET OFF
	01 = OUTLET ON
	02 = OUTLET REBOOTING
	03 = STARTING UP 	
	"
::= { outletStatus16Way 3 }


outlet4-16Way OBJECT-TYPE
	SYNTAX  	INTEGER(0..1000)
	ACCESS		read-only
	STATUS		mandatory
	DESCRIPTION	"i-Rack Outlet 4 Status
	00 = OUTLET OFF
	01 = OUTLET ON
	02 = OUTLET REBOOTING
	03 = STARTING UP
	"
::= { outletStatus16Way 4 }

outlet5-16Way OBJECT-TYPE
	SYNTAX  	INTEGER(0..1000)
	ACCESS		read-only
	STATUS		mandatory
	DESCRIPTION	"i-Rack Outlet 5 Status
	00 = OUTLET OFF
	01 = OUTLET ON
	02 = OUTLET REBOOTING
	03 = STARTING UP
	"
::= { outletStatus16Way 5 }

outlet6-16Way OBJECT-TYPE
	SYNTAX  	INTEGER(0..1000)
	ACCESS		read-only
	STATUS		mandatory
	DESCRIPTION	"i-Rack Outlet 6 Status
	00 = OUTLET OFF
	01 = OUTLET ON
	02 = OUTLET REBOOTING
	03 = STARTING UP
	"
::= { outletStatus16Way 6 }

outlet7-16Way OBJECT-TYPE
	SYNTAX  	INTEGER(0..1000)
	ACCESS		read-only
	STATUS		mandatory
	DESCRIPTION	"i-Rack Outlet 7 Status
	00 = OUTLET OFF
	01 = OUTLET ON
	02 = OUTLET REBOOTING
	03 = STARTING UP
	"
::= { outletStatus16Way 7 }

outlet8-16Way OBJECT-TYPE
	SYNTAX  	INTEGER(0..1000)
	ACCESS		read-only
	STATUS		mandatory
	DESCRIPTION	"i-Rack Outlet 8 Status
	00 = OUTLET OFF
	01 = OUTLET ON
	02 = OUTLET REBOOTING
	03 = STARTING UP
	"
::= { outletStatus16Way 8 }

outlet9-16Way OBJECT-TYPE
	SYNTAX  	INTEGER(0..1000)
	ACCESS		read-only
	STATUS		mandatory
	DESCRIPTION	"i-Rack Outlet 9 Status
	00 = OUTLET OFF
	01 = OUTLET ON
	02 = OUTLET REBOOTING
	03 = STARTING UP
	"
::= { outletStatus16Way 9 }

outlet10-16Way OBJECT-TYPE
	SYNTAX  	INTEGER(0..1000)
	ACCESS		read-only
	STATUS		mandatory
	DESCRIPTION	"i-Rack Outlet 10 Status
	00 = OUTLET OFF
	01 = OUTLET ON
	02 = OUTLET REBOOTING
	03 = STARTING UP
	"
::= { outletStatus16Way 10 }

outlet11-16Way OBJECT-TYPE
	SYNTAX  	INTEGER(0..1000)
	ACCESS		read-only
	STATUS		mandatory
	DESCRIPTION	"i-Rack Outlet 11 Status
	00 = OUTLET OFF
	01 = OUTLET ON
	02 = OUTLET REBOOTING
	03 = STARTING UP
	"
::= { outletStatus16Way 11 }

outlet12-16Way OBJECT-TYPE
	SYNTAX  	INTEGER(0..1000)
	ACCESS		read-only
	STATUS		mandatory
	DESCRIPTION	"i-Rack Outlet 12 Status
	00 = OUTLET OFF
	01 = OUTLET ON
	02 = OUTLET REBOOTING
	03 = STARTING UP
	"
::= { outletStatus16Way 12 }

outlet13-16Way OBJECT-TYPE
	SYNTAX  	INTEGER(0..1000)
	ACCESS		read-only
	STATUS		mandatory
	DESCRIPTION	"i-Rack Outlet 13 Status
	00 = OUTLET OFF
	01 = OUTLET ON
	02 = OUTLET REBOOTING
	03 = STARTING UP
	"
::= { outletStatus16Way 13 }

outlet14-16Way OBJECT-TYPE
	SYNTAX  	INTEGER(0..1000)
	ACCESS		read-only
	STATUS		mandatory
	DESCRIPTION	"i-Rack Outlet 14 Status
	00 = OUTLET OFF
	01 = OUTLET ON
	02 = OUTLET REBOOTING
	03 = STARTING UP
	"
::= { outletStatus16Way 14 }

outlet15-16Way OBJECT-TYPE
	SYNTAX  	INTEGER(0..1000)
	ACCESS		read-only
	STATUS		mandatory
	DESCRIPTION	"i-Rack Outlet 15 Status
	00 = OUTLET OFF
	01 = OUTLET ON
	02 = OUTLET REBOOTING
	03 = STARTING UP
	"
::= { outletStatus16Way 15 }

outlet16-16Way OBJECT-TYPE
	SYNTAX  	INTEGER(0..1000)
	ACCESS		read-only
	STATUS		mandatory
	DESCRIPTION	"i-Rack Outlet 16 Status
	00 = OUTLET OFF
	01 = OUTLET ON
	02 = OUTLET REBOOTING
	03 = STARTING UP
	"
::= { outletStatus16Way 16 }

currentConsumed-16Way OBJECT-TYPE
	SYNTAX  	INTEGER(0..1000)
	ACCESS		read-only
	STATUS		mandatory
	DESCRIPTION	"i-Rack total current consumption. This value is in milli amperes"
::= { currentConsumption16Way 1 }   

iRack16WayMessageString OBJECT-TYPE
	SYNTAX		DisplayString (SIZE (0..80))
	ACCESS		read-only
	STATUS		mandatory
	DESCRIPTION	"Message giving more detailed information on alarms/alerts/notifications on iRack."
::= { iRack16WayTraps 1 } 
                       
iRack16WayCurrentLoadStatus OBJECT-TYPE
	SYNTAX  	INTEGER(0..6)
	ACCESS		read-only
	STATUS		mandatory
	DESCRIPTION	"Alarm for Current Load Sensor
0 = level OK
1 = level at warning level
2 = level at alarm level
3 = level at critical level"
::= { iRack16WayTraps 2 }



-- Tree expansion for iRack 16 Way  



deviceName8Way OBJECT-TYPE
	SYNTAX  	DisplayString (SIZE (30))
	ACCESS		read-write
	STATUS		mandatory
	DESCRIPTION	"i-Rack Device Name Parameter" 
::= { iRackParams8Way 1 }   

deviceLocation8Way OBJECT-TYPE
	SYNTAX  	DisplayString (SIZE (30))
	ACCESS		read-write
	STATUS		mandatory
	DESCRIPTION	"i-Rack Device Location Parameter"
::= { iRackParams8Way 2 }  

ipAddr8Way OBJECT-TYPE
	SYNTAX  	IpAddress
	ACCESS		read-only
	STATUS		mandatory
	DESCRIPTION	"i-Rack IP Address"
::= { iRackParams8Way 3 }

sysDescription8Way OBJECT-TYPE
	SYNTAX  	DisplayString (SIZE (30))
	ACCESS		read-only
	STATUS		mandatory
	DESCRIPTION	"i-Rack Description"
::= { iRackParams8Way 4 }  

modelNumber8Way OBJECT-TYPE
	SYNTAX  	DisplayString (SIZE (5))
	ACCESS	read-only
	STATUS		mandatory
	DESCRIPTION	"i-Rack Model Number"
::= { iRackParams8Way 5 }
                              
outlet1-8Way OBJECT-TYPE
	SYNTAX  	INTEGER(0..1000)
	ACCESS		read-only
	STATUS 		mandatory
	DESCRIPTION	"i-Rack Outlet 1 Status
	00 = OUTLET OFF
	01 = OUTLET ON
	02 = OUTLET REBOOTING
	03 = STARTING UP
	"
::= { outletStatus8Way 1 }  

outlet2-8Way OBJECT-TYPE
	SYNTAX  	INTEGER(0..1000)
	ACCESS		read-only
	STATUS		mandatory
	DESCRIPTION	"i-Rack Outlet 2 Status
	00 = OUTLET OFF
	01 = OUTLET ON
	02 = OUTLET REBOOTING
	03 = STARTING UP
	"
::= { outletStatus8Way 2 }


outlet3-8Way OBJECT-TYPE
	SYNTAX  	INTEGER(0..1000)
	ACCESS		read-only
	STATUS		mandatory
	DESCRIPTION	"i-Rack Outlet 3 Status
	00 = OUTLET OFF
	01 = OUTLET ON
	02 = OUTLET REBOOTING
	03 = STARTING UP 	
	"
::= { outletStatus8Way 3 }


outlet4-8Way OBJECT-TYPE
	SYNTAX  	INTEGER(0..1000)
	ACCESS		read-only
	STATUS		mandatory
	DESCRIPTION	"i-Rack Outlet 4 Status
	00 = OUTLET OFF
	01 = OUTLET ON
	02 = OUTLET REBOOTING
	03 = STARTING UP
	"
::= { outletStatus8Way 4 }

outlet5-8Way OBJECT-TYPE
	SYNTAX  	INTEGER(0..1000)
	ACCESS		read-only
	STATUS		mandatory
	DESCRIPTION	"i-Rack Outlet 5 Status
	00 = OUTLET OFF
	01 = OUTLET ON
	02 = OUTLET REBOOTING
	03 = STARTING UP
	"
::= { outletStatus8Way 5 }

outlet6-8Way OBJECT-TYPE
	SYNTAX  	INTEGER(0..1000)
	ACCESS		read-only
	STATUS		mandatory
	DESCRIPTION	"i-Rack Outlet 6 Status
	00 = OUTLET OFF
	01 = OUTLET ON
	02 = OUTLET REBOOTING
	03 = STARTING UP
	"
::= { outletStatus8Way 6 }

outlet7-8Way OBJECT-TYPE
	SYNTAX  	INTEGER(0..1000)
	ACCESS		read-only
	STATUS		mandatory
	DESCRIPTION	"i-Rack Outlet 7 Status
	00 = OUTLET OFF
	01 = OUTLET ON
	02 = OUTLET REBOOTING
	03 = STARTING UP
	"
::= { outletStatus8Way 7 }

outlet8-8Way OBJECT-TYPE
	SYNTAX  	INTEGER(0..1000)
	ACCESS		read-only
	STATUS		mandatory
	DESCRIPTION	"i-Rack Outlet 8 Status
	00 = OUTLET OFF
	01 = OUTLET ON
	02 = OUTLET REBOOTING
	03 = STARTING UP
	"
::= { outletStatus8Way 8 }


currentConsumed-8Way OBJECT-TYPE
	SYNTAX  	INTEGER(0..1000)
	ACCESS		read-only
	STATUS		mandatory
	DESCRIPTION	"i-Rack total current consumption. This value is in milli amperes"
::= { currentConsumption8Way 1 }  

iRack8WayMessageString OBJECT-TYPE
	SYNTAX		DisplayString (SIZE (0..80))
	ACCESS		read-only
	STATUS		mandatory
	DESCRIPTION	"Message giving more detailed information on alarms/alerts/notifications on iRack."
::= { iRack8WayTraps 1 } 
                       
iRack8WayCurrentLoadStatus OBJECT-TYPE
	SYNTAX  	INTEGER(0..3)
	ACCESS		read-only
	STATUS		mandatory
	DESCRIPTION	"Alarm for Current Load Sensor
0 = level OK
1 = level at warning level
2 = level at alarm level
3 = level at critical level"
::= { iRack8WayTraps 2 } 

iRack8WayTemperatureAlarmStatus OBJECT-TYPE
	SYNTAX  	INTEGER(0..6)
	ACCESS		read-only
	STATUS		mandatory
	DESCRIPTION	"Alarm for Temperature Sensor
0 = level OK
1 = level at high warning level
2 = level at high alarm level
3 = level at high shutdown level
4 = level at low warning level
5 = level at low alarm level
6 = level at low shutdown level"
::= { iRack8WayTraps 3 }

iRack8WayHumidityAlarmStatus OBJECT-TYPE
	SYNTAX  	INTEGER(0..6)
	ACCESS		read-only
	STATUS		mandatory
	DESCRIPTION	"Alarm for Humidity Sensor
0 = level OK
1 = level at high warning level
2 = level at high alarm level
3 = level at high shutdown level
4 = level at low warning level
5 = level at low alarm level
6 = level at low shutdown level"
::= { iRack8WayTraps 4 }  

iRack8WayDigitalOneStatus OBJECT-TYPE
	SYNTAX  	INTEGER(0..1)
	ACCESS		read-only
	STATUS		mandatory
	DESCRIPTION	"Alarm for Digital Sensor One
0 = OK
1 = Alarm"
::= { iRack8WayTraps 5 }
 
iRack8WayDigitalTwoStatus OBJECT-TYPE
	SYNTAX  	INTEGER(0..1)
	ACCESS		read-only
	STATUS		mandatory
	DESCRIPTION	"Alarm for Digital Sensor Two
0 = OK
1 = Alarm"
::= { iRack8WayTraps 6 } 

iRack8WayTemperature OBJECT-TYPE
	SYNTAX  	INTEGER(0..1000)
	ACCESS		read-only
	STATUS		mandatory
	DESCRIPTION	"i-Rack temperature sensor reading (use multiplier 0.1 for actual reading)"
::= { iRack8WayTraps 7 } 

iRack8WayHumidity OBJECT-TYPE
	SYNTAX  	INTEGER(0..1000)
	ACCESS		read-only
	STATUS		mandatory
	DESCRIPTION	"i-Rack humidity sensor reading (use multiplier 0.1 for actual reading)"
::= { iRack8WayTraps 8 }

iRack8WayOutletID OBJECT-TYPE
	SYNTAX  	INTEGER(0..8)
	ACCESS		read-only
	STATUS		mandatory
	DESCRIPTION	"i-Rack Outlet ID. User Action on this ID"
::= { iRack8WayTraps 9 }

 
iRack8WayOutletIDAction OBJECT-TYPE
	SYNTAX  	INTEGER(0..2)
	ACCESS		read-only
	STATUS		mandatory
	DESCRIPTION	"i-Rack Outlet Action
0 = OFF
1 = ON
2 = REBOOT"
::= { iRack8WayTraps 10 } 

iRack8WayGlobalAction OBJECT-TYPE
	SYNTAX  	INTEGER(0..2)
	ACCESS		read-only
	STATUS		mandatory
	DESCRIPTION	"i-Rack Outlet Global Action
0 = OFF
1 = ON
2 = REBOOT"
::= { iRack8WayTraps 11 } 




deviceName12Way OBJECT-TYPE
	SYNTAX  	DisplayString (SIZE (30))
	ACCESS		read-write
	STATUS		mandatory
	DESCRIPTION	"i-Rack Device Name Parameter" 
::= { iRackParams12Way 1 }   

deviceLocation12Way OBJECT-TYPE
	SYNTAX  	DisplayString (SIZE (30))
	ACCESS		read-write
	STATUS		mandatory
	DESCRIPTION	"i-Rack Device Location Parameter"
::= { iRackParams12Way 2 }  

ipAddr12Way OBJECT-TYPE
	SYNTAX  	IpAddress
	ACCESS		read-only
	STATUS		mandatory
	DESCRIPTION	"i-Rack IP Address"
::= { iRackParams12Way 3 }

sysDescription12Way OBJECT-TYPE
	SYNTAX  	DisplayString (SIZE (30))
	ACCESS		read-only
	STATUS		mandatory
	DESCRIPTION	"i-Rack Description"
::= { iRackParams12Way 4 }  

modelNumber12Way OBJECT-TYPE
	SYNTAX  	DisplayString (SIZE (5))
	ACCESS	read-only
	STATUS		mandatory
	DESCRIPTION	"i-Rack Model Number"
::= { iRackParams12Way 5 }
                              
outlet1-12Way OBJECT-TYPE
	SYNTAX  	INTEGER(0..1000)
	ACCESS		read-only
	STATUS 		mandatory
	DESCRIPTION	"i-Rack Outlet 1 Status
	00 = OUTLET OFF
	01 = OUTLET ON
	02 = OUTLET REBOOTING
	03 = STARTING UP
	"
::= { outletStatus12Way 1 }  

outlet2-12Way OBJECT-TYPE
	SYNTAX  	INTEGER(0..1000)
	ACCESS		read-only
	STATUS		mandatory
	DESCRIPTION	"i-Rack Outlet 2 Status
	00 = OUTLET OFF
	01 = OUTLET ON
	02 = OUTLET REBOOTING
	03 = STARTING UP
	"
::= { outletStatus12Way 2 }


outlet3-12Way OBJECT-TYPE
	SYNTAX  	INTEGER(0..1000)
	ACCESS		read-only
	STATUS		mandatory
	DESCRIPTION	"i-Rack Outlet 3 Status
	00 = OUTLET OFF
	01 = OUTLET ON
	02 = OUTLET REBOOTING
	03 = STARTING UP 	
	"
::= { outletStatus12Way 3 }


outlet4-12Way OBJECT-TYPE
	SYNTAX  	INTEGER(0..1000)
	ACCESS		read-only
	STATUS		mandatory
	DESCRIPTION	"i-Rack Outlet 4 Status
	00 = OUTLET OFF
	01 = OUTLET ON
	02 = OUTLET REBOOTING
	03 = STARTING UP
	"
::= { outletStatus12Way 4 }

outlet5-12Way OBJECT-TYPE
	SYNTAX  	INTEGER(0..1000)
	ACCESS		read-only
	STATUS		mandatory
	DESCRIPTION	"i-Rack Outlet 5 Status
	00 = OUTLET OFF
	01 = OUTLET ON
	02 = OUTLET REBOOTING
	03 = STARTING UP
	"
::= { outletStatus12Way 5 }

outlet6-12Way OBJECT-TYPE
	SYNTAX  	INTEGER(0..1000)
	ACCESS		read-only
	STATUS		mandatory
	DESCRIPTION	"i-Rack Outlet 6 Status
	00 = OUTLET OFF
	01 = OUTLET ON
	02 = OUTLET REBOOTING
	03 = STARTING UP
	"
::= { outletStatus12Way 6 }

outlet7-12Way OBJECT-TYPE
	SYNTAX  	INTEGER(0..1000)
	ACCESS		read-only
	STATUS		mandatory
	DESCRIPTION	"i-Rack Outlet 7 Status
	00 = OUTLET OFF
	01 = OUTLET ON
	02 = OUTLET REBOOTING
	03 = STARTING UP
	"
::= { outletStatus12Way 7 }

outlet8-12Way OBJECT-TYPE
	SYNTAX  	INTEGER(0..1000)
	ACCESS		read-only
	STATUS		mandatory
	DESCRIPTION	"i-Rack Outlet 8 Status
	00 = OUTLET OFF
	01 = OUTLET ON
	02 = OUTLET REBOOTING
	03 = STARTING UP
	"
::= { outletStatus12Way 8 }

outlet9-12Way OBJECT-TYPE
	SYNTAX  	INTEGER(0..1000)
	ACCESS		read-only
	STATUS		mandatory
	DESCRIPTION	"i-Rack Outlet 9 Status
	00 = OUTLET OFF
	01 = OUTLET ON
	02 = OUTLET REBOOTING
	03 = STARTING UP
	"
::= { outletStatus12Way 9 }

outlet10-12Way OBJECT-TYPE
	SYNTAX  	INTEGER(0..1000)
	ACCESS		read-only
	STATUS		mandatory
	DESCRIPTION	"i-Rack Outlet 10 Status
	00 = OUTLET OFF
	01 = OUTLET ON
	02 = OUTLET REBOOTING
	03 = STARTING UP
	"
::= { outletStatus12Way 10 }

outlet11-12Way OBJECT-TYPE
	SYNTAX  	INTEGER(0..1000)
	ACCESS		read-only
	STATUS		mandatory
	DESCRIPTION	"i-Rack Outlet 11 Status
	00 = OUTLET OFF
	01 = OUTLET ON
	02 = OUTLET REBOOTING
	03 = STARTING UP
	"
::= { outletStatus12Way 11 }

outlet12-12Way OBJECT-TYPE
	SYNTAX  	INTEGER(0..1000)
	ACCESS		read-only
	STATUS		mandatory
	DESCRIPTION	"i-Rack Outlet 12 Status
	00 = OUTLET OFF
	01 = OUTLET ON
	02 = OUTLET REBOOTING
	03 = STARTING UP
	"
::= { outletStatus12Way 12 }

currentConsumed-12Way OBJECT-TYPE
	SYNTAX  	INTEGER(0..1000)
	ACCESS		read-only
	STATUS		mandatory
	DESCRIPTION	"i-Rack total current consumption. This value is in milli amperes"
::= { currentConsumption12Way 1 }

iRack12WayMessageString OBJECT-TYPE
	SYNTAX		DisplayString (SIZE (0..80))
	ACCESS		read-only
	STATUS		mandatory
	DESCRIPTION	"Message giving more detailed information on alarms/alerts/notifications on iRack."
::= { iRack12WayTraps 1 } 
                       
iRack12WayCurrentLoadStatus OBJECT-TYPE
	SYNTAX  	INTEGER(0..6)
	ACCESS		read-only
	STATUS		mandatory
	DESCRIPTION	"Alarm for Current Load Sensor
0 = level OK
1 = level at warning level
2 = level at alarm level
3 = level at critical level"
::= { iRack12WayTraps 2 }





-- iRackCurrentMonitoring

deviceName-CurrentMonitoring OBJECT-TYPE
	SYNTAX  	DisplayString (SIZE (30))
	ACCESS		read-write
	STATUS		mandatory
	DESCRIPTION	"i-Rack Device Name Parameter" 
::= { iRackParamsCurrentMonitoring 1 }   

deviceLocation-CurrentMonitoring OBJECT-TYPE
	SYNTAX  	DisplayString (SIZE (30))
	ACCESS		read-write
	STATUS		mandatory
	DESCRIPTION	"i-Rack Device Location Parameter"
::= { iRackParamsCurrentMonitoring 2 }  

ipAddr-CurrentMonitoring OBJECT-TYPE
	SYNTAX  	IpAddress
	ACCESS		read-only
	STATUS		mandatory
	DESCRIPTION	"i-Rack IP Address"
::= { iRackParamsCurrentMonitoring 3 }

sysDescription-CurrentMonitoring OBJECT-TYPE
	SYNTAX  	DisplayString (SIZE (30))
	ACCESS		read-only
	STATUS		mandatory
	DESCRIPTION	"i-Rack Description"
::= { iRackParamsCurrentMonitoring 4 }  

modelNumber-CurrentMonitoring OBJECT-TYPE
	SYNTAX  	DisplayString (SIZE (5))
	ACCESS	read-only
	STATUS		mandatory
	DESCRIPTION	"i-Rack Model Number"
::= { iRackParamsCurrentMonitoring 5 }
                              
currentConsumed-CurrentMonitoring OBJECT-TYPE
	SYNTAX  	INTEGER(0..1000)
	ACCESS		read-only
	STATUS		mandatory
	DESCRIPTION	"i-Rack total current consumption. This value is in milli amperes"
::= { currentConsumptionCurrentMonitoring 1 }  

iRack-CurrentMonitoring-MessageString OBJECT-TYPE
	SYNTAX		DisplayString (SIZE (0..80))
	ACCESS		read-only
	STATUS		mandatory
	DESCRIPTION	"Message giving more detailed information on alarms/alerts/notifications on iRack."
::= { iRackCurrentMonitoringTraps 1 } 
                       
iRack-CurrentMonitoring-CurrentLoadStatus OBJECT-TYPE
	SYNTAX  	INTEGER(0..3)
	ACCESS		read-only
	STATUS		mandatory
	DESCRIPTION	"Alarm for Current Load Sensor
0 = level OK
1 = level at warning level
2 = level at alarm level
3 = level at critical level"
::= { iRackCurrentMonitoringTraps 2 } 

iRack-CurrentMonitoring-TemperatureAlarmStatus OBJECT-TYPE
	SYNTAX  	INTEGER(0..6)
	ACCESS		read-only
	STATUS		mandatory
	DESCRIPTION	"Alarm for Temperature Sensor
0 = level OK
1 = level at high warning level
2 = level at high alarm level
3 = level at high shutdown level
4 = level at low warning level
5 = level at low alarm level
6 = level at low shutdown level"
::= { iRackCurrentMonitoringTraps 3 }

iRack-CurrentMonitoring-HumidityAlarmStatus OBJECT-TYPE
	SYNTAX  	INTEGER(0..6)
	ACCESS		read-only
	STATUS		mandatory
	DESCRIPTION	"Alarm for Humidity Sensor
0 = level OK
1 = level at high warning level
2 = level at high alarm level
3 = level at high shutdown level
4 = level at low warning level
5 = level at low alarm level
6 = level at low shutdown level"
::= { iRackCurrentMonitoringTraps 4 }  

iRack-CurrentMonitoring-DigitalOneStatus OBJECT-TYPE
	SYNTAX  	INTEGER(0..1)
	ACCESS		read-only
	STATUS		mandatory
	DESCRIPTION	"Alarm for Digital Sensor One
0 = OK
1 = Alarm"
::= { iRackCurrentMonitoringTraps 5 }
 
iRack-CurrentMonitoring-DigitalTwoStatus OBJECT-TYPE
	SYNTAX  	INTEGER(0..1)
	ACCESS		read-only
	STATUS		mandatory
	DESCRIPTION	"Alarm for Digital Sensor Two
0 = OK
1 = Alarm"
::= { iRackCurrentMonitoringTraps 6 } 

iRack-CurrentMonitoring-Temperature OBJECT-TYPE
	SYNTAX  	INTEGER(0..1000)
	ACCESS		read-only
	STATUS		mandatory
	DESCRIPTION	"i-Rack temperature sensor reading (use multiplier 0.1 for actual reading)"
::= { iRackCurrentMonitoringTraps 7 } 

iRack-CurrentMonitoring-Humidity OBJECT-TYPE
	SYNTAX  	INTEGER(0..1000)
	ACCESS		read-only
	STATUS		mandatory
	DESCRIPTION	"i-Rack humidity sensor reading (use multiplier 0.1 for actual reading)"
::= { iRackCurrentMonitoringTraps 8 }

 
 

 -- Traps for use by CSS Products

          -- Traps for the Spanning Tree Protocol

			hardwareErrorNotification TRAP-TYPE
         	  ENTERPRISE  computerSupportSystems
              DESCRIPTION
                      "A hardware error notification trap is sent when any of the
							 hardware components go into an alarm stage.
							 
							 Trap notifications apply only to the SafetyNet
							 product family."
              ::= 2

         alarmNotification TRAP-TYPE
         	  ENTERPRISE  computerSupportSystems
              DESCRIPTION
                      "An alarm notification trap is sent when any of the
							 monitored inputs go into an alarm stage.
							 
							 Trap notifications apply only to the SafetyNet
							 product family."
              ::= 3

			alarmClearNotification TRAP-TYPE
         	  ENTERPRISE  computerSupportSystems
              DESCRIPTION
                      "An alarm clear notification trap is sent when any of the
							 monitored inputs go into an alarm clear stage after being
							 at an alarm stage.
							 
							 Trap notifications apply only to the SafetyNet
							 product family."
              ::= 4

		   softwareNotificationUpdate TRAP-TYPE
         	  ENTERPRISE  computerSupportSystems
              DESCRIPTION
                      "A software notification update trap is sent when any an update
							 or configuration change is detected on a unit.
							 
							 Trap notifications apply only to the SafetyNet
							 product family."
              ::= 5


			softwareErrorNotification TRAP-TYPE
         	  ENTERPRISE  computerSupportSystems
              DESCRIPTION
                      "A software error notification trap is sent when some kind
							  of unwanted software error occurs within the unit.
							  
							  Trap notifications apply only to the SafetyNet
							  product family."
              ::= 6

END
