--
-- CAREL-denco.MIB
-- MIB generated by CAREL
-- Tuesday, 05 September 2006
--

    CAREL-denco DEFINITIONS ::= BEGIN
 
		IMPORTS
			OBJECT-GROUP
				FROM SNMPv2-CONF			
			sysContact, sysName, sysLocation			
				FROM SNMPv2-MIB
			enterprises, MODULE-IDENTITY			
				FROM SNMPv2-SMI;		
		
        denco MODULE-IDENTITY
      		LAST-UPDATED  "200609051102Z"		-- September 05, 2006 at 11:02 GMT
      		ORGANIZATION  "CAREL SpA"
      		CONTACT-INFO
                "
                        Carel SpA
                        Via dell'Industria, 11
                        35020 Brugine (PD) Italy
                        Tel: +39 049 9716611
                        E-mail: carel@carel.com
                "
      		DESCRIPTION
                "This is the MIB module for the ahu_pco_v18 device."
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
   			DESCRIPTION "Code of the Agent. 2=pCOWeb."
		::= { systm 2 }
		
		-- 1.3.6.1.4.1.9839.2
		instruments OBJECT IDENTIFIER ::= { carel 2 }
		
		-- 1.3.6.1.4.1.9839.2.0
 		pCOWebInfo OBJECT IDENTIFIER ::= { instruments 0 }
		

		-- 1.3.6.1.4.1.9839.2.0.10
		pCOStatusgroup OBJECT IDENTIFIER ::= { pCOWebInfo 10 }
		
		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }
		
		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.

-- 1.3.6.1.4.1.9839.2.1
denco OBJECT IDENTIFIER ::= { instruments 1 }

-- 1.3.6.1.4.1.9839.2.1.1
digitalObjects OBJECT IDENTIFIER ::= { denco 1 }


-- 1.3.6.1.4.1.9839.2.1.1.1
     bMS_ON_OFF OBJECT-TYPE
          SYNTAX Integer32 (0..1)
          UNITS "N/A"
          MAX-ACCESS read-write
          STATUS current
          DESCRIPTION "BMS Unit On/Off"
           ::= { digitalObjects 1 }


-- 1.3.6.1.4.1.9839.2.1.1.2
     on_off_timezones OBJECT-TYPE
          SYNTAX Integer32 (0..1)
          UNITS "N/A"
          MAX-ACCESS read-write
          STATUS current
          DESCRIPTION "Enable Unit On/Off by Time zones "
           ::= { digitalObjects 2 }


-- 1.3.6.1.4.1.9839.2.1.1.3
     en_time_zones_t OBJECT-TYPE
          SYNTAX Integer32 (0..1)
          UNITS "N/A"
          MAX-ACCESS read-write
          STATUS current
          DESCRIPTION "Enable Unit Temperature Set Point Adjustment by Time zones "
           ::= { digitalObjects 3 }


-- 1.3.6.1.4.1.9839.2.1.1.4
     en_time_zones_h OBJECT-TYPE
          SYNTAX Integer32 (0..1)
          UNITS "N/A"
          MAX-ACCESS read-write
          STATUS current
          DESCRIPTION "Enable Unit Humidity Set Point Adjustment by Time zones"
           ::= { digitalObjects 4 }


-- 1.3.6.1.4.1.9839.2.1.1.5
     mAL_RETURN_AIR_TEMP OBJECT-TYPE
          SYNTAX Integer32 (0..1)
          UNITS "N/A"
          MAX-ACCESS read-only
          STATUS current
          DESCRIPTION "Return Air Temperature Sensor Fail Alarm"
           ::= { digitalObjects 5 }


-- 1.3.6.1.4.1.9839.2.1.1.6
     mAL_RETURN_AIR_HUM OBJECT-TYPE
          SYNTAX Integer32 (0..1)
          UNITS "N/A"
          MAX-ACCESS read-only
          STATUS current
          DESCRIPTION "Return Air Humidity Sensor Fail Alarm"
           ::= { digitalObjects 6 }


-- 1.3.6.1.4.1.9839.2.1.1.7
     mAL_COND_PRESS1 OBJECT-TYPE
          SYNTAX Integer32 (0..1)
          UNITS "N/A"
          MAX-ACCESS read-only
          STATUS current
          DESCRIPTION "Condensing pressure 1 Sensor Fail Alarm"
           ::= { digitalObjects 7 }


-- 1.3.6.1.4.1.9839.2.1.1.8
     mAL_COND_PRESS2 OBJECT-TYPE
          SYNTAX Integer32 (0..1)
          UNITS "N/A"
          MAX-ACCESS read-only
          STATUS current
          DESCRIPTION "Condensing pressure 2 Sensor Fail Alarm"
           ::= { digitalObjects 8 }


-- 1.3.6.1.4.1.9839.2.1.1.9
     mAL_CW_TEMP OBJECT-TYPE
          SYNTAX Integer32 (0..1)
          UNITS "N/A"
          MAX-ACCESS read-only
          STATUS current
          DESCRIPTION "Water Temperature Sensor Fail Alarm"
           ::= { digitalObjects 9 }


-- 1.3.6.1.4.1.9839.2.1.1.10
     mAL_SUPPLY_AIR_TEMP OBJECT-TYPE
          SYNTAX Integer32 (0..1)
          UNITS "N/A"
          MAX-ACCESS read-only
          STATUS current
          DESCRIPTION "Supply Air Temperature Sensor Fail Alarm"
           ::= { digitalObjects 10 }


-- 1.3.6.1.4.1.9839.2.1.1.11
     mAL_SUPPLY_AIR_HUM OBJECT-TYPE
          SYNTAX Integer32 (0..1)
          UNITS "N/A"
          MAX-ACCESS read-only
          STATUS current
          DESCRIPTION "Supply Air Humidity Sensor Fail Alarm"
           ::= { digitalObjects 11 }


-- 1.3.6.1.4.1.9839.2.1.1.12
     mAL_AIRFLOW_FAIL OBJECT-TYPE
          SYNTAX Integer32 (0..1)
          UNITS "N/A"
          MAX-ACCESS read-only
          STATUS current
          DESCRIPTION "Airflow Fail Alarm"
           ::= { digitalObjects 12 }


-- 1.3.6.1.4.1.9839.2.1.1.13
     mAL_FILTER_BLOCKED OBJECT-TYPE
          SYNTAX Integer32 (0..1)
          UNITS "N/A"
          MAX-ACCESS read-only
          STATUS current
          DESCRIPTION "Filter Blocked Alarm"
           ::= { digitalObjects 13 }


-- 1.3.6.1.4.1.9839.2.1.1.14
     mAL_WATER_DETECTION OBJECT-TYPE
          SYNTAX Integer32 (0..1)
          UNITS "N/A"
          MAX-ACCESS read-only
          STATUS current
          DESCRIPTION "Water Detection Alarm"
           ::= { digitalObjects 14 }


-- 1.3.6.1.4.1.9839.2.1.1.15
     mAL_AUXILIARY_ALARM OBJECT-TYPE
          SYNTAX Integer32 (0..1)
          UNITS "N/A"
          MAX-ACCESS read-only
          STATUS current
          DESCRIPTION "Auxiliary Alarm"
           ::= { digitalObjects 15 }


-- 1.3.6.1.4.1.9839.2.1.1.16
     mAL_HIGH_CONTROL_TEMP OBJECT-TYPE
          SYNTAX Integer32 (0..1)
          UNITS "N/A"
          MAX-ACCESS read-only
          STATUS current
          DESCRIPTION "High Control Temperature Alarm"
           ::= { digitalObjects 16 }


-- 1.3.6.1.4.1.9839.2.1.1.17
     mAL_LOW_CONTROL_TEMP OBJECT-TYPE
          SYNTAX Integer32 (0..1)
          UNITS "N/A"
          MAX-ACCESS read-only
          STATUS current
          DESCRIPTION "Low Control Temperature Alarm"
           ::= { digitalObjects 17 }


-- 1.3.6.1.4.1.9839.2.1.1.18
     mAL_HIGH_CONTROL_HUM OBJECT-TYPE
          SYNTAX Integer32 (0..1)
          UNITS "N/A"
          MAX-ACCESS read-only
          STATUS current
          DESCRIPTION "High Control Humidity Alarm"
           ::= { digitalObjects 18 }


-- 1.3.6.1.4.1.9839.2.1.1.19
     mAL_LOW_CONTROL_HUM OBJECT-TYPE
          SYNTAX Integer32 (0..1)
          UNITS "N/A"
          MAX-ACCESS read-only
          STATUS current
          DESCRIPTION "Low Control Humidity Alarm"
           ::= { digitalObjects 19 }


-- 1.3.6.1.4.1.9839.2.1.1.20
     mAL_LOW_SUPPLY_AIR_TEMP OBJECT-TYPE
          SYNTAX Integer32 (0..1)
          UNITS "N/A"
          MAX-ACCESS read-only
          STATUS current
          DESCRIPTION "Low Supply Temperature Alarm"
           ::= { digitalObjects 20 }


-- 1.3.6.1.4.1.9839.2.1.1.21
     mAL_HIGH_SUPPLY_AIR_HUM OBJECT-TYPE
          SYNTAX Integer32 (0..1)
          UNITS "N/A"
          MAX-ACCESS read-only
          STATUS current
          DESCRIPTION "High Supply Humidity Alarm"
           ::= { digitalObjects 21 }


-- 1.3.6.1.4.1.9839.2.1.1.22
     mAL_KLIXON OBJECT-TYPE
          SYNTAX Integer32 (0..1)
          UNITS "N/A"
          MAX-ACCESS read-only
          STATUS current
          DESCRIPTION "Klixon Trip Alarm"
           ::= { digitalObjects 22 }


-- 1.3.6.1.4.1.9839.2.1.1.23
     mAL_HP_TRIP_1 OBJECT-TYPE
          SYNTAX Integer32 (0..1)
          UNITS "N/A"
          MAX-ACCESS read-only
          STATUS current
          DESCRIPTION "Compressor 1 High Pressure Trip Alarm"
           ::= { digitalObjects 23 }


-- 1.3.6.1.4.1.9839.2.1.1.24
     mAL_HP_TRIP_2 OBJECT-TYPE
          SYNTAX Integer32 (0..1)
          UNITS "N/A"
          MAX-ACCESS read-only
          STATUS current
          DESCRIPTION "Compressor 2 High Pressure Trip Alarm"
           ::= { digitalObjects 24 }


-- 1.3.6.1.4.1.9839.2.1.1.25
     mAL_HP_TRIP_3 OBJECT-TYPE
          SYNTAX Integer32 (0..1)
          UNITS "N/A"
          MAX-ACCESS read-only
          STATUS current
          DESCRIPTION "Compressor 3 High Pressure Trip Alarm"
           ::= { digitalObjects 25 }


-- 1.3.6.1.4.1.9839.2.1.1.26
     mAL_HP_TRIP_4 OBJECT-TYPE
          SYNTAX Integer32 (0..1)
          UNITS "N/A"
          MAX-ACCESS read-only
          STATUS current
          DESCRIPTION "Compressor 4 High Pressure Trip Alarm"
           ::= { digitalObjects 26 }


-- 1.3.6.1.4.1.9839.2.1.1.27
     mAL_HP_TRIP_CIRC1_TANDEM OBJECT-TYPE
          SYNTAX Integer32 (0..1)
          UNITS "N/A"
          MAX-ACCESS read-only
          STATUS current
          DESCRIPTION "Circuit 1 (VRF) High Pressure Trip Alarm"
           ::= { digitalObjects 27 }


-- 1.3.6.1.4.1.9839.2.1.1.28
     mAL_HP_TRIP_CIRC2_TANDEM OBJECT-TYPE
          SYNTAX Integer32 (0..1)
          UNITS "N/A"
          MAX-ACCESS read-only
          STATUS current
          DESCRIPTION "Circuit 2 (VRF) High Pressure Trip Alarm"
           ::= { digitalObjects 28 }


-- 1.3.6.1.4.1.9839.2.1.1.29
     mAL_LP_TRIP_1 OBJECT-TYPE
          SYNTAX Integer32 (0..1)
          UNITS "N/A"
          MAX-ACCESS read-only
          STATUS current
          DESCRIPTION "Compressor 1 Low Pressure Trip Alarm"
           ::= { digitalObjects 29 }


-- 1.3.6.1.4.1.9839.2.1.1.30
     mAL_LP_TRIP_2 OBJECT-TYPE
          SYNTAX Integer32 (0..1)
          UNITS "N/A"
          MAX-ACCESS read-only
          STATUS current
          DESCRIPTION "Compressor 2 Low Pressure Trip Alarm"
           ::= { digitalObjects 30 }


-- 1.3.6.1.4.1.9839.2.1.1.31
     mAL_LP_TRIP_3 OBJECT-TYPE
          SYNTAX Integer32 (0..1)
          UNITS "N/A"
          MAX-ACCESS read-only
          STATUS current
          DESCRIPTION "Compressor 3 Low Pressure Trip Alarm"
           ::= { digitalObjects 31 }


-- 1.3.6.1.4.1.9839.2.1.1.32
     mAL_LP_TRIP_4 OBJECT-TYPE
          SYNTAX Integer32 (0..1)
          UNITS "N/A"
          MAX-ACCESS read-only
          STATUS current
          DESCRIPTION "Compressor 4 Low Pressure Trip Alarm"
           ::= { digitalObjects 32 }


-- 1.3.6.1.4.1.9839.2.1.1.33
     mAL_LP_TRIP_CIRC1_TANDEM OBJECT-TYPE
          SYNTAX Integer32 (0..1)
          UNITS "N/A"
          MAX-ACCESS read-only
          STATUS current
          DESCRIPTION "Circuit 1 (VRF) Low Pressure Trip Alarm"
           ::= { digitalObjects 33 }


-- 1.3.6.1.4.1.9839.2.1.1.34
     mAL_LP_TRIP_CIRC2_TANDEM OBJECT-TYPE
          SYNTAX Integer32 (0..1)
          UNITS "N/A"
          MAX-ACCESS read-only
          STATUS current
          DESCRIPTION "Circuit 2 (VRF) Low Pressure Trip Alarm"
           ::= { digitalObjects 34 }


-- 1.3.6.1.4.1.9839.2.1.1.35
     mAL_PLAN OBJECT-TYPE
          SYNTAX Integer32 (0..1)
          UNITS "N/A"
          MAX-ACCESS read-only
          STATUS current
          DESCRIPTION "Denconet Comms Alarm"
           ::= { digitalObjects 35 }


-- 1.3.6.1.4.1.9839.2.1.1.36
     malarm1_1 OBJECT-TYPE
          SYNTAX Integer32 (0..1)
          UNITS "N/A"
          MAX-ACCESS read-only
          STATUS current
          DESCRIPTION "Humidifier High Current Alarm"
           ::= { digitalObjects 36 }


-- 1.3.6.1.4.1.9839.2.1.1.37
     malarm1_3 OBJECT-TYPE
          SYNTAX Integer32 (0..1)
          UNITS "N/A"
          MAX-ACCESS read-only
          STATUS current
          DESCRIPTION "Humidifier Lack Of Water Alarm"
           ::= { digitalObjects 37 }


-- 1.3.6.1.4.1.9839.2.1.1.38
     malarm1_2 OBJECT-TYPE
          SYNTAX Integer32 (0..1)
          UNITS "N/A"
          MAX-ACCESS read-only
          STATUS current
          DESCRIPTION "Humidifier Low Current Alarm"
           ::= { digitalObjects 38 }


-- 1.3.6.1.4.1.9839.2.1.1.39
     mal_clock OBJECT-TYPE
          SYNTAX Integer32 (0..1)
          UNITS "N/A"
          MAX-ACCESS read-only
          STATUS current
          DESCRIPTION "Clock Alarm"
           ::= { digitalObjects 39 }


-- 1.3.6.1.4.1.9839.2.1.1.40
     mal_Probe_D1 OBJECT-TYPE
          SYNTAX Integer32 (0..1)
          UNITS "N/A"
          MAX-ACCESS read-only
          STATUS current
          DESCRIPTION "EEV Driver 1 Probe Fail Alarm"
           ::= { digitalObjects 40 }


-- 1.3.6.1.4.1.9839.2.1.1.41
     mal_Eeprom_D1 OBJECT-TYPE
          SYNTAX Integer32 (0..1)
          UNITS "N/A"
          MAX-ACCESS read-only
          STATUS current
          DESCRIPTION "EEV Driver 1 Eeprom Alarm"
           ::= { digitalObjects 41 }


-- 1.3.6.1.4.1.9839.2.1.1.42
     mal_Step_Motor_d1 OBJECT-TYPE
          SYNTAX Integer32 (0..1)
          UNITS "N/A"
          MAX-ACCESS read-only
          STATUS current
          DESCRIPTION "EEV Driver 1 Stepper Motor Alarm"
           ::= { digitalObjects 42 }


-- 1.3.6.1.4.1.9839.2.1.1.43
     mal_Battery_D1 OBJECT-TYPE
          SYNTAX Integer32 (0..1)
          UNITS "N/A"
          MAX-ACCESS read-only
          STATUS current
          DESCRIPTION "EEV Driver 1 Battery Alarm"
           ::= { digitalObjects 43 }


-- 1.3.6.1.4.1.9839.2.1.1.44
     mal_MOP_Delay_D1 OBJECT-TYPE
          SYNTAX Integer32 (0..1)
          UNITS "N/A"
          MAX-ACCESS read-only
          STATUS current
          DESCRIPTION "EEV Driver 1 High Evaporating Pressure Alarm"
           ::= { digitalObjects 44 }


-- 1.3.6.1.4.1.9839.2.1.1.45
     mal_LOP_Delay_D1 OBJECT-TYPE
          SYNTAX Integer32 (0..1)
          UNITS "N/A"
          MAX-ACCESS read-only
          STATUS current
          DESCRIPTION "EEV Driver 1 Low Evaporating Pressure Alarm"
           ::= { digitalObjects 45 }


-- 1.3.6.1.4.1.9839.2.1.1.46
     mal_Low_SHeat_D1 OBJECT-TYPE
          SYNTAX Integer32 (0..1)
          UNITS "N/A"
          MAX-ACCESS read-only
          STATUS current
          DESCRIPTION "EEV Driver 1 Low Superheat Alarm"
           ::= { digitalObjects 46 }


-- 1.3.6.1.4.1.9839.2.1.1.47
     mal_Vlv_Not_Closed_d1 OBJECT-TYPE
          SYNTAX Integer32 (0..1)
          UNITS "N/A"
          MAX-ACCESS read-only
          STATUS current
          DESCRIPTION "EEV Driver 1 Valve Not Closed At Power Off Alarm"
           ::= { digitalObjects 47 }


-- 1.3.6.1.4.1.9839.2.1.1.48
     mal_High_SHeat_d1 OBJECT-TYPE
          SYNTAX Integer32 (0..1)
          UNITS "N/A"
          MAX-ACCESS read-only
          STATUS current
          DESCRIPTION "EEV Driver 1 High Suction Temperature Alarm"
           ::= { digitalObjects 48 }


-- 1.3.6.1.4.1.9839.2.1.1.49
     mal_Probe_D2 OBJECT-TYPE
          SYNTAX Integer32 (0..1)
          UNITS "N/A"
          MAX-ACCESS read-only
          STATUS current
          DESCRIPTION "EEV Driver 2 Probe Fail Alarm"
           ::= { digitalObjects 49 }


-- 1.3.6.1.4.1.9839.2.1.1.50
     mal_Eeprom_D2 OBJECT-TYPE
          SYNTAX Integer32 (0..1)
          UNITS "N/A"
          MAX-ACCESS read-only
          STATUS current
          DESCRIPTION "EEV Driver 2 Eeprom Alarm"
           ::= { digitalObjects 50 }


-- 1.3.6.1.4.1.9839.2.1.1.51
     mal_Step_Motor_d2 OBJECT-TYPE
          SYNTAX Integer32 (0..1)
          UNITS "N/A"
          MAX-ACCESS read-only
          STATUS current
          DESCRIPTION "EEV Driver 2 Stepper Motor Alarm"
           ::= { digitalObjects 51 }


-- 1.3.6.1.4.1.9839.2.1.1.52
     mal_Battery_D2 OBJECT-TYPE
          SYNTAX Integer32 (0..1)
          UNITS "N/A"
          MAX-ACCESS read-only
          STATUS current
          DESCRIPTION "EEV Driver 2 Battery Alarm"
           ::= { digitalObjects 52 }


-- 1.3.6.1.4.1.9839.2.1.1.53
     mal_MOP_Delay_D2 OBJECT-TYPE
          SYNTAX Integer32 (0..1)
          UNITS "N/A"
          MAX-ACCESS read-only
          STATUS current
          DESCRIPTION "EEV Driver 2 High Evaporating Pressure Alarm"
           ::= { digitalObjects 53 }


-- 1.3.6.1.4.1.9839.2.1.1.54
     mal_LOP_Delay_D2 OBJECT-TYPE
          SYNTAX Integer32 (0..1)
          UNITS "N/A"
          MAX-ACCESS read-only
          STATUS current
          DESCRIPTION "EEV Driver 2 Low Evaporating Pressure Alarm"
           ::= { digitalObjects 54 }


-- 1.3.6.1.4.1.9839.2.1.1.55
     mal_Low_SHeat_D2 OBJECT-TYPE
          SYNTAX Integer32 (0..1)
          UNITS "N/A"
          MAX-ACCESS read-only
          STATUS current
          DESCRIPTION "EEV Driver 2 Low Superheat Alarm"
           ::= { digitalObjects 55 }


-- 1.3.6.1.4.1.9839.2.1.1.56
     mal_Vlv_Not_Closed_d2 OBJECT-TYPE
          SYNTAX Integer32 (0..1)
          UNITS "N/A"
          MAX-ACCESS read-only
          STATUS current
          DESCRIPTION "EEV Driver 2 Valve Not Closed At Power Off Alarm"
           ::= { digitalObjects 56 }


-- 1.3.6.1.4.1.9839.2.1.1.57
     mal_High_SHeat_d2 OBJECT-TYPE
          SYNTAX Integer32 (0..1)
          UNITS "N/A"
          MAX-ACCESS read-only
          STATUS current
          DESCRIPTION "EEV Driver 2 High Suction Temperature Alarm"
           ::= { digitalObjects 57 }


-- 1.3.6.1.4.1.9839.2.1.1.58
     malarm1 OBJECT-TYPE
          SYNTAX Integer32 (0..1)
          UNITS "N/A"
          MAX-ACCESS read-only
          STATUS current
          DESCRIPTION "Humidifier High Conductivity Alarm"
           ::= { digitalObjects 58 }


-- 1.3.6.1.4.1.9839.2.1.1.59
     malarm2 OBJECT-TYPE
          SYNTAX Integer32 (0..1)
          UNITS "N/A"
          MAX-ACCESS read-only
          STATUS current
          DESCRIPTION "Humidifier High Conductivity Warning"
           ::= { digitalObjects 59 }


-- 1.3.6.1.4.1.9839.2.1.1.60
     malarm1_4 OBJECT-TYPE
          SYNTAX Integer32 (0..1)
          UNITS "N/A"
          MAX-ACCESS read-only
          STATUS current
          DESCRIPTION "Humidifier Low Production Alarm"
           ::= { digitalObjects 60 }


-- 1.3.6.1.4.1.9839.2.1.1.61
     malarm1_5 OBJECT-TYPE
          SYNTAX Integer32 (0..1)
          UNITS "N/A"
          MAX-ACCESS read-only
          STATUS current
          DESCRIPTION "Humidifier Drain Alarm"
           ::= { digitalObjects 61 }


-- 1.3.6.1.4.1.9839.2.1.1.62
     malarm1_6 OBJECT-TYPE
          SYNTAX Integer32 (0..1)
          UNITS "N/A"
          MAX-ACCESS read-only
          STATUS current
          DESCRIPTION "Humidifier Cylinder Full Alarm"
           ::= { digitalObjects 62 }


-- 1.3.6.1.4.1.9839.2.1.1.63
     malarm1_7 OBJECT-TYPE
          SYNTAX Integer32 (0..1)
          UNITS "N/A"
          MAX-ACCESS read-only
          STATUS current
          DESCRIPTION "Humidifier Cylinder Pre-Exhaustion Warming"
           ::= { digitalObjects 63 }


-- 1.3.6.1.4.1.9839.2.1.1.64
     malarm1_8 OBJECT-TYPE
          SYNTAX Integer32 (0..1)
          UNITS "N/A"
          MAX-ACCESS read-only
          STATUS current
          DESCRIPTION "Humidifier Foam Presence Detected Warning"
           ::= { digitalObjects 64 }


-- 1.3.6.1.4.1.9839.2.1.1.65
     malarm1_9 OBJECT-TYPE
          SYNTAX Integer32 (0..1)
          UNITS "N/A"
          MAX-ACCESS read-only
          STATUS current
          DESCRIPTION "Humidifier Cylinder Exhaustion Warning"
           ::= { digitalObjects 65 }


-- 1.3.6.1.4.1.9839.2.1.1.66
     mAlarm1_10 OBJECT-TYPE
          SYNTAX Integer32 (0..1)
          UNITS "N/A"
          MAX-ACCESS read-only
          STATUS current
          DESCRIPTION "Humidifier Cylinder Exhausted Alarm"
           ::= { digitalObjects 66 }


-- 1.3.6.1.4.1.9839.2.1.1.67
     mAlarm1_11 OBJECT-TYPE
          SYNTAX Integer32 (0..1)
          UNITS "N/A"
          MAX-ACCESS read-only
          STATUS current
          DESCRIPTION "Humidifier Cylinder Maintenance Recommended"
           ::= { digitalObjects 67 }


-- 1.3.6.1.4.1.9839.2.1.1.68
     mAL_MAINT_FAN OBJECT-TYPE
          SYNTAX Integer32 (0..1)
          UNITS "N/A"
          MAX-ACCESS read-only
          STATUS current
          DESCRIPTION "Unit Fan Maintenance Alarm"
           ::= { digitalObjects 68 }


-- 1.3.6.1.4.1.9839.2.1.1.69
     mAL_MAINT_HEATER1 OBJECT-TYPE
          SYNTAX Integer32 (0..1)
          UNITS "N/A"
          MAX-ACCESS read-only
          STATUS current
          DESCRIPTION "Heater 1 Maintenance Alarm"
           ::= { digitalObjects 69 }


-- 1.3.6.1.4.1.9839.2.1.1.70
     mAL_MAINT_HEATER2 OBJECT-TYPE
          SYNTAX Integer32 (0..1)
          UNITS "N/A"
          MAX-ACCESS read-only
          STATUS current
          DESCRIPTION "Heater 2 Maintenance Alarm"
           ::= { digitalObjects 70 }


-- 1.3.6.1.4.1.9839.2.1.1.71
     mAL_MAINT_0_10_HEAT OBJECT-TYPE
          SYNTAX Integer32 (0..1)
          UNITS "N/A"
          MAX-ACCESS read-only
          STATUS current
          DESCRIPTION "0 - 10V Heating Maintenance Alarm"
           ::= { digitalObjects 71 }


-- 1.3.6.1.4.1.9839.2.1.1.72
     mAL_MAINT_DODC_HEAT OBJECT-TYPE
          SYNTAX Integer32 (0..1)
          UNITS "N/A"
          MAX-ACCESS read-only
          STATUS current
          DESCRIPTION "DODC Heating Maintenance Alarm"
           ::= { digitalObjects 72 }


-- 1.3.6.1.4.1.9839.2.1.1.73
     mAL_MAINT_COMP1 OBJECT-TYPE
          SYNTAX Integer32 (0..1)
          UNITS "N/A"
          MAX-ACCESS read-only
          STATUS current
          DESCRIPTION "Compressor 1 Maintenance Alarm"
           ::= { digitalObjects 73 }


-- 1.3.6.1.4.1.9839.2.1.1.74
     mAL_MAINT_COMP2 OBJECT-TYPE
          SYNTAX Integer32 (0..1)
          UNITS "N/A"
          MAX-ACCESS read-only
          STATUS current
          DESCRIPTION "Compressor 2 Maintenance Alarm"
           ::= { digitalObjects 74 }


-- 1.3.6.1.4.1.9839.2.1.1.75
     mAL_MAINT_COMP3 OBJECT-TYPE
          SYNTAX Integer32 (0..1)
          UNITS "N/A"
          MAX-ACCESS read-only
          STATUS current
          DESCRIPTION "Compressor 3 Maintenance Alarm"
           ::= { digitalObjects 75 }


-- 1.3.6.1.4.1.9839.2.1.1.76
     mAL_MAINT_COMP4 OBJECT-TYPE
          SYNTAX Integer32 (0..1)
          UNITS "N/A"
          MAX-ACCESS read-only
          STATUS current
          DESCRIPTION "Compressor 4 Maintenance Alarm"
           ::= { digitalObjects 76 }


-- 1.3.6.1.4.1.9839.2.1.1.77
     mAL_MAINT_0_10_COOL OBJECT-TYPE
          SYNTAX Integer32 (0..1)
          UNITS "N/A"
          MAX-ACCESS read-only
          STATUS current
          DESCRIPTION "0 - 10V Cooling Maintenance Alarm"
           ::= { digitalObjects 77 }


-- 1.3.6.1.4.1.9839.2.1.1.78
     mAL_MAINT_DODC_COOL OBJECT-TYPE
          SYNTAX Integer32 (0..1)
          UNITS "N/A"
          MAX-ACCESS read-only
          STATUS current
          DESCRIPTION "DODC Cooling Maintenance Alarm"
           ::= { digitalObjects 78 }


-- 1.3.6.1.4.1.9839.2.1.1.79
     mAL_MAINT_COND OBJECT-TYPE
          SYNTAX Integer32 (0..1)
          UNITS "N/A"
          MAX-ACCESS read-only
          STATUS current
          DESCRIPTION "Condenser Fan Maintenance Alarm"
           ::= { digitalObjects 79 }


-- 1.3.6.1.4.1.9839.2.1.1.80
     mAL_MAINT_REM_HUM OBJECT-TYPE
          SYNTAX Integer32 (0..1)
          UNITS "N/A"
          MAX-ACCESS read-only
          STATUS current
          DESCRIPTION "Remote Humidifier Maintenance Alarm"
           ::= { digitalObjects 80 }


-- 1.3.6.1.4.1.9839.2.1.1.81
     mAL_MAINT_DEHUM OBJECT-TYPE
          SYNTAX Integer32 (0..1)
          UNITS "N/A"
          MAX-ACCESS read-only
          STATUS current
          DESCRIPTION "Dehum Maintenance Alarm"
           ::= { digitalObjects 81 }


-- 1.3.6.1.4.1.9839.2.1.1.82
     mAL_MAINT_DRYCOOL1 OBJECT-TYPE
          SYNTAX Integer32 (0..1)
          UNITS "N/A"
          MAX-ACCESS read-only
          STATUS current
          DESCRIPTION "Dry Cooler Fan 1 Maintenance Alarm"
           ::= { digitalObjects 82 }


-- 1.3.6.1.4.1.9839.2.1.1.83
     mAL_MAINT_DRYCOOL2 OBJECT-TYPE
          SYNTAX Integer32 (0..1)
          UNITS "N/A"
          MAX-ACCESS read-only
          STATUS current
          DESCRIPTION "Dry Cooler Fan 2 Maintenance Alarm"
           ::= { digitalObjects 83 }


-- 1.3.6.1.4.1.9839.2.1.1.84
     mAL_MAINT_AMBICOOL OBJECT-TYPE
          SYNTAX Integer32 (0..1)
          UNITS "N/A"
          MAX-ACCESS read-only
          STATUS current
          DESCRIPTION "Ambicool Maintenance Alarm"
           ::= { digitalObjects 84 }


-- 1.3.6.1.4.1.9839.2.1.1.85
     mAL_REF_LEAK_DETECTION OBJECT-TYPE
          SYNTAX Integer32 (0..1)
          UNITS "N/A"
          MAX-ACCESS read-only
          STATUS current
          DESCRIPTION "Refrigerant Leak Detection Alarm"
           ::= { digitalObjects 85 }


-- 1.3.6.1.4.1.9839.2.1.1.86
     rESET_ALARMS_BMS OBJECT-TYPE
          SYNTAX Integer32 (0..1)
          UNITS "N/A"
          MAX-ACCESS read-only
          STATUS current
          DESCRIPTION "Alarm Reset By BMS"
           ::= { digitalObjects 86 }


-- 1.3.6.1.4.1.9839.2.1.2
analogObjects OBJECT IDENTIFIER ::= { denco 2 }


-- 1.3.6.1.4.1.9839.2.1.2.1
     control_temp OBJECT-TYPE
          SYNTAX Integer32 (-32767..32767)
          UNITS "N/A"
          MAX-ACCESS read-only
          STATUS current
          DESCRIPTION "Control Temperature"
           ::= { analogObjects 1 }


-- 1.3.6.1.4.1.9839.2.1.2.2
     control_hum OBJECT-TYPE
          SYNTAX Integer32 (-32767..32767)
          UNITS "N/A"
          MAX-ACCESS read-only
          STATUS current
          DESCRIPTION "Control Humidity"
           ::= { analogObjects 2 }


-- 1.3.6.1.4.1.9839.2.1.2.3
     return_Air_Temp OBJECT-TYPE
          SYNTAX Integer32 (-32767..32767)
          UNITS "N/A"
          MAX-ACCESS read-only
          STATUS current
          DESCRIPTION "Return Air Temperature"
           ::= { analogObjects 3 }


-- 1.3.6.1.4.1.9839.2.1.2.4
     return_Air_Hum OBJECT-TYPE
          SYNTAX Integer32 (-32767..32767)
          UNITS "N/A"
          MAX-ACCESS read-only
          STATUS current
          DESCRIPTION "Return Air Humidity"
           ::= { analogObjects 4 }


-- 1.3.6.1.4.1.9839.2.1.2.5
     disp_cool_demand OBJECT-TYPE
          SYNTAX Integer32 (-32767..32767)
          UNITS "N/A"
          MAX-ACCESS read-only
          STATUS current
          DESCRIPTION "Cooling Demand"
           ::= { analogObjects 5 }


-- 1.3.6.1.4.1.9839.2.1.2.6
     disp_heat_demand OBJECT-TYPE
          SYNTAX Integer32 (-32767..32767)
          UNITS "N/A"
          MAX-ACCESS read-only
          STATUS current
          DESCRIPTION "Heating Demand"
           ::= { analogObjects 6 }


-- 1.3.6.1.4.1.9839.2.1.2.7
     disp_hum_demand OBJECT-TYPE
          SYNTAX Integer32 (-32767..32767)
          UNITS "N/A"
          MAX-ACCESS read-only
          STATUS current
          DESCRIPTION "Humidity Demand"
           ::= { analogObjects 7 }


-- 1.3.6.1.4.1.9839.2.1.2.8
     disp_dehum_demand OBJECT-TYPE
          SYNTAX Integer32 (-32767..32767)
          UNITS "N/A"
          MAX-ACCESS read-only
          STATUS current
          DESCRIPTION "Dehum Demand"
           ::= { analogObjects 8 }


-- 1.3.6.1.4.1.9839.2.1.2.9
     ambicool_demand OBJECT-TYPE
          SYNTAX Integer32 (-32767..32767)
          UNITS "N/A"
          MAX-ACCESS read-only
          STATUS current
          DESCRIPTION "Ambicool Demand"
           ::= { analogObjects 9 }


-- 1.3.6.1.4.1.9839.2.1.2.10
     supply_air_temp OBJECT-TYPE
          SYNTAX Integer32 (-32767..32767)
          UNITS "N/A"
          MAX-ACCESS read-only
          STATUS current
          DESCRIPTION "Supply Air Temperature"
           ::= { analogObjects 10 }


-- 1.3.6.1.4.1.9839.2.1.2.11
     supply_air_hum OBJECT-TYPE
          SYNTAX Integer32 (-32767..32767)
          UNITS "N/A"
          MAX-ACCESS read-only
          STATUS current
          DESCRIPTION "Supply Air Humidity"
           ::= { analogObjects 11 }


-- 1.3.6.1.4.1.9839.2.1.2.12
     water_temp OBJECT-TYPE
          SYNTAX Integer32 (-32767..32767)
          UNITS "N/A"
          MAX-ACCESS read-only
          STATUS current
          DESCRIPTION "Water Temperature"
           ::= { analogObjects 12 }


-- 1.3.6.1.4.1.9839.2.1.2.13
     cond_press1 OBJECT-TYPE
          SYNTAX Integer32 (-32767..32767)
          UNITS "N/A"
          MAX-ACCESS read-only
          STATUS current
          DESCRIPTION "Condensing Pressure 1"
           ::= { analogObjects 13 }


-- 1.3.6.1.4.1.9839.2.1.2.14
     cond_press2 OBJECT-TYPE
          SYNTAX Integer32 (-32767..32767)
          UNITS "N/A"
          MAX-ACCESS read-only
          STATUS current
          DESCRIPTION "Condensing Pressure 2"
           ::= { analogObjects 14 }


-- 1.3.6.1.4.1.9839.2.1.2.15
     sel_set_temp OBJECT-TYPE
          SYNTAX Integer32 (-32767..32767)
          UNITS "N/A"
          MAX-ACCESS read-write
          STATUS current
          DESCRIPTION "Temperature Set Point"
           ::= { analogObjects 15 }


-- 1.3.6.1.4.1.9839.2.1.2.16
     sel_set_hum OBJECT-TYPE
          SYNTAX Integer32 (-32767..32767)
          UNITS "N/A"
          MAX-ACCESS read-write
          STATUS current
          DESCRIPTION "Humidity Set Point"
           ::= { analogObjects 16 }


-- 1.3.6.1.4.1.9839.2.1.2.17
     set_temp1 OBJECT-TYPE
          SYNTAX Integer32 (-32767..32767)
          UNITS "N/A"
          MAX-ACCESS read-write
          STATUS current
          DESCRIPTION "Time Zone 1 Temperature Set Point"
           ::= { analogObjects 17 }


-- 1.3.6.1.4.1.9839.2.1.2.18
     set_temp2 OBJECT-TYPE
          SYNTAX Integer32 (-32767..32767)
          UNITS "N/A"
          MAX-ACCESS read-write
          STATUS current
          DESCRIPTION "Time Zone 2 Temperature Set Point"
           ::= { analogObjects 18 }


-- 1.3.6.1.4.1.9839.2.1.2.19
     set_temp3 OBJECT-TYPE
          SYNTAX Integer32 (-32767..32767)
          UNITS "N/A"
          MAX-ACCESS read-write
          STATUS current
          DESCRIPTION "Time Zone 3 Temperature Set Point"
           ::= { analogObjects 19 }

-- 1.3.6.1.4.1.9839.2.1.2.20
     set_temp4 OBJECT-TYPE
          SYNTAX Integer32 (-32767..32767)
          UNITS "N/A"
          MAX-ACCESS read-write
          STATUS current
          DESCRIPTION "Time Zone 4 Temperature Set Point"
           ::= { analogObjects 20 }


-- 1.3.6.1.4.1.9839.2.1.2.21
     set_hum1 OBJECT-TYPE
          SYNTAX Integer32 (-32767..32767)
          UNITS "N/A"
          MAX-ACCESS read-write
          STATUS current
          DESCRIPTION "Time Zone 1 Humidity Set Point"
           ::= { analogObjects 21 }


-- 1.3.6.1.4.1.9839.2.1.2.22
     set_hum2 OBJECT-TYPE
          SYNTAX Integer32 (-32767..32767)
          UNITS "N/A"
          MAX-ACCESS read-write
          STATUS current
          DESCRIPTION "Time Zone 2 Humidity Set Point"
           ::= { analogObjects 22 }


-- 1.3.6.1.4.1.9839.2.1.2.23
     set_hum3 OBJECT-TYPE
          SYNTAX Integer32 (-32767..32767)
          UNITS "N/A"
          MAX-ACCESS read-write
          STATUS current
          DESCRIPTION "Time Zone 3 Humidity Set Point"
           ::= { analogObjects 23 }


-- 1.3.6.1.4.1.9839.2.1.2.24
     set_hum4 OBJECT-TYPE
          SYNTAX Integer32 (-32767..32767)
          UNITS "N/A"
          MAX-ACCESS read-write
          STATUS current
          DESCRIPTION "Time Zone 4 Humidity Set Point"
           ::= { analogObjects 24 }


-- 1.3.6.1.4.1.9839.2.1.2.25
     cool_dead_zone OBJECT-TYPE
          SYNTAX Integer32 (-32767..32767)
          UNITS "N/A"
          MAX-ACCESS read-write
          STATUS current
          DESCRIPTION "Cooling Dead Zone"
           ::= { analogObjects 25 }


-- 1.3.6.1.4.1.9839.2.1.2.26
     cool_prop_band OBJECT-TYPE
          SYNTAX Integer32 (-32767..32767)
          UNITS "N/A"
          MAX-ACCESS read-write
          STATUS current
          DESCRIPTION "Cooling Proportional Band"
           ::= { analogObjects 26 }


-- 1.3.6.1.4.1.9839.2.1.2.27
     heat_dead_zone OBJECT-TYPE
          SYNTAX Integer32 (-32767..32767)
          UNITS "N/A"
          MAX-ACCESS read-write
          STATUS current
          DESCRIPTION "Heating Dead Zone"
           ::= { analogObjects 27 }


-- 1.3.6.1.4.1.9839.2.1.2.28
     heat_prop_band OBJECT-TYPE
          SYNTAX Integer32 (-32767..32767)
          UNITS "N/A"
          MAX-ACCESS read-write
          STATUS current
          DESCRIPTION "Heating Proportional Band"
           ::= { analogObjects 28 }


-- 1.3.6.1.4.1.9839.2.1.2.29
     dehum_dead_zone OBJECT-TYPE
          SYNTAX Integer32 (-32767..32767)
          UNITS "N/A"
          MAX-ACCESS read-write
          STATUS current
          DESCRIPTION "Dehum Dead Zone"
           ::= { analogObjects 29 }


-- 1.3.6.1.4.1.9839.2.1.2.30
     dehum_prop_band OBJECT-TYPE
          SYNTAX Integer32 (-32767..32767)
          UNITS "N/A"
          MAX-ACCESS read-write
          STATUS current
          DESCRIPTION "Dehum Proportional Band"
           ::= { analogObjects 30 }


-- 1.3.6.1.4.1.9839.2.1.2.31
     hum_dead_zone OBJECT-TYPE
          SYNTAX Integer32 (-32767..32767)
          UNITS "N/A"
          MAX-ACCESS read-write
          STATUS current
          DESCRIPTION "Humidity Dead Zone"
           ::= { analogObjects 31 }


-- 1.3.6.1.4.1.9839.2.1.2.32
     hum_prop_band OBJECT-TYPE
          SYNTAX Integer32 (-32767..32767)
          UNITS "N/A"
          MAX-ACCESS read-write
          STATUS current
          DESCRIPTION "Humidity Proportional Band"
           ::= { analogObjects 32 }


-- 1.3.6.1.4.1.9839.2.1.2.33
     freecool_water_setpoint OBJECT-TYPE
          SYNTAX Integer32 (-32767..32767)
          UNITS "N/A"
          MAX-ACCESS read-write
          STATUS current
          DESCRIPTION "Free Cool Water Set Point"
           ::= { analogObjects 33 }


-- 1.3.6.1.4.1.9839.2.1.2.34
     freecool_water_diff OBJECT-TYPE
          SYNTAX Integer32 (-32767..32767)
          UNITS "N/A"
          MAX-ACCESS read-write
          STATUS current
          DESCRIPTION "Dry Cooler Stage Differential"
           ::= { analogObjects 34 }


-- 1.3.6.1.4.1.9839.2.1.2.35
     chilled_water_setpoint OBJECT-TYPE
          SYNTAX Integer32 (-32767..32767)
          UNITS "N/A"
          MAX-ACCESS read-write
          STATUS current
          DESCRIPTION "Combicool Chilled Water Temperature Limit"
           ::= { analogObjects 35 }


-- 1.3.6.1.4.1.9839.2.1.2.36
     temp_alarm_band OBJECT-TYPE
          SYNTAX Integer32 (-32767..32767)
          UNITS "N/A"
          MAX-ACCESS read-write
          STATUS current
          DESCRIPTION "Temperature Alarm Band"
           ::= { analogObjects 36 }


-- 1.3.6.1.4.1.9839.2.1.2.37
     hum_alarm_band OBJECT-TYPE
          SYNTAX Integer32 (-32767..32767)
          UNITS "N/A"
          MAX-ACCESS read-write
          STATUS current
          DESCRIPTION "Humidity Alarm Band"
           ::= { analogObjects 37 }


-- 1.3.6.1.4.1.9839.2.1.2.38
     tILE_UNIT_AVERAGE_TEMP OBJECT-TYPE
          SYNTAX Integer32 (-32767..32767)
          UNITS "N/A"
          MAX-ACCESS read-write
          STATUS current
          DESCRIPTION "Tile Unit (LECU) Average Temperature"
           ::= { analogObjects 38 }

-- 1.3.6.1.4.1.9839.2.1.3
integerObjects OBJECT IDENTIFIER ::= { denco 3 }

-- 1.3.6.1.4.1.9839.2.1.3.1
     serial_number_1 OBJECT-TYPE
          SYNTAX Integer32 (-32767..32767)
          UNITS "N/A"
          MAX-ACCESS read-only
          STATUS current
          DESCRIPTION "Unit Serial Number Digit 1"
           ::= { integerObjects 1 }

-- 1.3.6.1.4.1.9839.2.1.3.2
     serial_number_2 OBJECT-TYPE
          SYNTAX Integer32 (-32767..32767)
          UNITS "N/A"
          MAX-ACCESS read-only
          STATUS current
          DESCRIPTION "Unit Serial Number Digit 2"
           ::= { integerObjects 2 }


-- 1.3.6.1.4.1.9839.2.1.3.3
     serial_number_3 OBJECT-TYPE
          SYNTAX Integer32 (-32767..32767)
          UNITS "N/A"
          MAX-ACCESS read-only
          STATUS current
          DESCRIPTION "Unit Serial Number Digit 3"
           ::= { integerObjects 3 }


-- 1.3.6.1.4.1.9839.2.1.3.4
     serial_number_4 OBJECT-TYPE
          SYNTAX Integer32 (-32767..32767)
          UNITS "N/A"
          MAX-ACCESS read-only
          STATUS current
          DESCRIPTION "Unit Serial Number Digit 4"
           ::= { integerObjects 4 }


-- 1.3.6.1.4.1.9839.2.1.3.5
     serial_number_5 OBJECT-TYPE
          SYNTAX Integer32 (-32767..32767)
          UNITS "N/A"
          MAX-ACCESS read-only
          STATUS current
          DESCRIPTION "Unit Serial Number Digit 5"
           ::= { integerObjects 5 }


-- 1.3.6.1.4.1.9839.2.1.3.6
     serial_number_6 OBJECT-TYPE
          SYNTAX Integer32 (-32767..32767)
          UNITS "N/A"
          MAX-ACCESS read-only
          STATUS current
          DESCRIPTION "Unit Serial Number Digit 6"
           ::= { integerObjects 6 }


-- 1.3.6.1.4.1.9839.2.1.3.7
     serial_number_7 OBJECT-TYPE
          SYNTAX Integer32 (-32767..32767)
          UNITS "N/A"
          MAX-ACCESS read-only
          STATUS current
          DESCRIPTION "Unit Serial Number Digit 7"
           ::= { integerObjects 7 }


-- 1.3.6.1.4.1.9839.2.1.3.8
     commission_date_day OBJECT-TYPE
          SYNTAX Integer32 (-32767..32767)
          UNITS "N/A"
          MAX-ACCESS read-only
          STATUS current
          DESCRIPTION "Unit Commission Date Day"
           ::= { integerObjects 8 }


-- 1.3.6.1.4.1.9839.2.1.3.9
     commission_date_month OBJECT-TYPE
          SYNTAX Integer32 (-32767..32767)
          UNITS "N/A"
          MAX-ACCESS read-only
          STATUS current
          DESCRIPTION "Unit Commission Date Month"
           ::= { integerObjects 9 }


-- 1.3.6.1.4.1.9839.2.1.3.10
     commission_date_year OBJECT-TYPE
          SYNTAX Integer32 (-32767..32767)
          UNITS "N/A"
          MAX-ACCESS read-only
          STATUS current
          DESCRIPTION "Unit Commission Date Year"
           ::= { integerObjects 10 }


-- 1.3.6.1.4.1.9839.2.1.3.11
     f1_hour_on1 OBJECT-TYPE
          SYNTAX Integer32 (-32767..32767)
          UNITS "N/A"
          MAX-ACCESS read-only
          STATUS current
          DESCRIPTION "Unit On/Off Time zone F1-1 On Hour "
           ::= { integerObjects 11 }


-- 1.3.6.1.4.1.9839.2.1.3.12
     f1_min_on1 OBJECT-TYPE
          SYNTAX Integer32 (-32767..32767)
          UNITS "N/A"
          MAX-ACCESS read-write
          STATUS current
          DESCRIPTION "Unit On/Off Time zone F1-1 On Minute"
           ::= { integerObjects 12 }


-- 1.3.6.1.4.1.9839.2.1.3.13
     f1_hour_off1 OBJECT-TYPE
          SYNTAX Integer32 (-32767..32767)
          UNITS "N/A"
          MAX-ACCESS read-write
          STATUS current
          DESCRIPTION "Unit On/Off Time zone F1-1 Off Hour "
           ::= { integerObjects 13 }


-- 1.3.6.1.4.1.9839.2.1.3.14
     f1_min_off1 OBJECT-TYPE
          SYNTAX Integer32 (-32767..32767)
          UNITS "N/A"
          MAX-ACCESS read-write
          STATUS current
          DESCRIPTION "Unit On/Off Time zone F1-1 Off Minute"
           ::= { integerObjects 14 }


-- 1.3.6.1.4.1.9839.2.1.3.15
     f1_hour_on2 OBJECT-TYPE
          SYNTAX Integer32 (-32767..32767)
          UNITS "N/A"
          MAX-ACCESS read-write
          STATUS current
          DESCRIPTION "Unit On/Off Time zone F1-2 On Hour "
           ::= { integerObjects 15 }


-- 1.3.6.1.4.1.9839.2.1.3.16
     f1_min_on2 OBJECT-TYPE
          SYNTAX Integer32 (-32767..32767)
          UNITS "N/A"
          MAX-ACCESS read-write
          STATUS current
          DESCRIPTION "Unit On/Off Time zone F1-2 On Minute"
           ::= { integerObjects 16 }


-- 1.3.6.1.4.1.9839.2.1.3.17
     f1_hour_off2 OBJECT-TYPE
          SYNTAX Integer32 (-32767..32767)
          UNITS "N/A"
          MAX-ACCESS read-write
          STATUS current
          DESCRIPTION "Unit On/Off Time zone F1-2 Off Hour "
           ::= { integerObjects 17 }


-- 1.3.6.1.4.1.9839.2.1.3.18
     f1_min_off2 OBJECT-TYPE
          SYNTAX Integer32 (-32767..32767)
          UNITS "N/A"
          MAX-ACCESS read-write
          STATUS current
          DESCRIPTION "Unit On/Off Time zone F1-2 Off Minute"
           ::= { integerObjects 18 }


-- 1.3.6.1.4.1.9839.2.1.3.19
     f2_hour_on OBJECT-TYPE
          SYNTAX Integer32 (-32767..32767)
          UNITS "N/A"
          MAX-ACCESS read-write
          STATUS current
          DESCRIPTION "Unit On/Off Time zone F2 On Hour "
           ::= { integerObjects 19 }


-- 1.3.6.1.4.1.9839.2.1.3.20
     f2_min_on OBJECT-TYPE
          SYNTAX Integer32 (-32767..32767)
          UNITS "N/A"
          MAX-ACCESS read-write
          STATUS current
          DESCRIPTION "Unit On/Off Time zone F2 On Minute"
           ::= { integerObjects 20 }


-- 1.3.6.1.4.1.9839.2.1.3.21
     f2_hour_off OBJECT-TYPE
          SYNTAX Integer32 (-32767..32767)
          UNITS "N/A"
          MAX-ACCESS read-write
          STATUS current
          DESCRIPTION "Unit On/Off Time zone F2 Off Hour "
           ::= { integerObjects 21 }


-- 1.3.6.1.4.1.9839.2.1.3.22
     f2_min_off OBJECT-TYPE
          SYNTAX Integer32 (-32767..32767)
          UNITS "N/A"
          MAX-ACCESS read-write
          STATUS current
          DESCRIPTION "Unit On/Off Time zone F2 Off Minute"
           ::= { integerObjects 22 }


-- 1.3.6.1.4.1.9839.2.1.3.23
     monday_type OBJECT-TYPE
          SYNTAX Integer32 (-32767..32767)
          UNITS "N/A"
          MAX-ACCESS read-write
          STATUS current
          DESCRIPTION "Monday Time Zone Selection (0=F1, 1=F2, 2=F3 &3=F4)"
           ::= { integerObjects 23 }


-- 1.3.6.1.4.1.9839.2.1.3.24
     tuesday_type OBJECT-TYPE
          SYNTAX Integer32 (-32767..32767)
          UNITS "N/A"
          MAX-ACCESS read-write
          STATUS current
          DESCRIPTION "Tuesday Time Zone Selection"
           ::= { integerObjects 24 }


-- 1.3.6.1.4.1.9839.2.1.3.25
     wednesday_type OBJECT-TYPE
          SYNTAX Integer32 (-32767..32767)
          UNITS "N/A"
          MAX-ACCESS read-write
          STATUS current
          DESCRIPTION "Wednesday Time Zone Selection"
           ::= { integerObjects 25 }


-- 1.3.6.1.4.1.9839.2.1.3.26
     thursday_type OBJECT-TYPE
          SYNTAX Integer32 (-32767..32767)
          UNITS "N/A"
          MAX-ACCESS read-write
          STATUS current
          DESCRIPTION "Thursday Time Zone Selection"
           ::= { integerObjects 26 }


-- 1.3.6.1.4.1.9839.2.1.3.27
     friday_type OBJECT-TYPE
          SYNTAX Integer32 (-32767..32767)
          UNITS "N/A"
          MAX-ACCESS read-write
          STATUS current
          DESCRIPTION "Friday Time Zone Selection"
           ::= { integerObjects 27 }


-- 1.3.6.1.4.1.9839.2.1.3.28
     saturday_type OBJECT-TYPE
          SYNTAX Integer32 (-32767..32767)
          UNITS "N/A"
          MAX-ACCESS read-write
          STATUS current
          DESCRIPTION "Saturday Time Zone Selection"
           ::= { integerObjects 28 }


-- 1.3.6.1.4.1.9839.2.1.3.29
     sunday_type OBJECT-TYPE
          SYNTAX Integer32 (-32767..32767)
          UNITS "N/A"
          MAX-ACCESS read-write
          STATUS current
          DESCRIPTION "Sunday Time Zone Selection"
           ::= { integerObjects 29 }


-- 1.3.6.1.4.1.9839.2.1.3.30
     temp_hour1 OBJECT-TYPE
          SYNTAX Integer32 (-32767..32767)
          UNITS "N/A"
          MAX-ACCESS read-write
          STATUS current
          DESCRIPTION "Temperature set point Time zone 1 Hour"
           ::= { integerObjects 30 }


-- 1.3.6.1.4.1.9839.2.1.3.31
     temp_minute1 OBJECT-TYPE
          SYNTAX Integer32 (-32767..32767)
          UNITS "N/A"
          MAX-ACCESS read-write
          STATUS current
          DESCRIPTION "Temperature set point Time zone 1 Minute"
           ::= { integerObjects 31 }


-- 1.3.6.1.4.1.9839.2.1.3.32
     temp_hour2 OBJECT-TYPE
          SYNTAX Integer32 (-32767..32767)
          UNITS "N/A"
          MAX-ACCESS read-write
          STATUS current
          DESCRIPTION "Temperature set point Time zone 2 Hour"
           ::= { integerObjects 32 }


-- 1.3.6.1.4.1.9839.2.1.3.33
     temp_minute2 OBJECT-TYPE
          SYNTAX Integer32 (-32767..32767)
          UNITS "N/A"
          MAX-ACCESS read-write
          STATUS current
          DESCRIPTION "Temperature set point Time zone 2 Minute"
           ::= { integerObjects 33 }


-- 1.3.6.1.4.1.9839.2.1.3.34
     temp_hour3 OBJECT-TYPE
          SYNTAX Integer32 (-32767..32767)
          UNITS "N/A"
          MAX-ACCESS read-write
          STATUS current
          DESCRIPTION "Temperature set point Time zone 3 Hour"
           ::= { integerObjects 34 }


-- 1.3.6.1.4.1.9839.2.1.3.35
     temp_minute3 OBJECT-TYPE
          SYNTAX Integer32 (-32767..32767)
          UNITS "N/A"
          MAX-ACCESS read-write
          STATUS current
          DESCRIPTION "Temperature set point Time zone 3 Minute"
           ::= { integerObjects 35 }


-- 1.3.6.1.4.1.9839.2.1.3.36
     temp_hour4 OBJECT-TYPE
          SYNTAX Integer32 (-32767..32767)
          UNITS "N/A"
          MAX-ACCESS read-write
          STATUS current
          DESCRIPTION "Temperature set point Time zone 4 Hour"
           ::= { integerObjects 36 }


-- 1.3.6.1.4.1.9839.2.1.3.37
     temp_minute4 OBJECT-TYPE
          SYNTAX Integer32 (-32767..32767)
          UNITS "N/A"
          MAX-ACCESS read-write
          STATUS current
          DESCRIPTION "Temperature set point Time zone 4 Minute"
           ::= { integerObjects 37 }


-- 1.3.6.1.4.1.9839.2.1.3.38
     hum_hour1 OBJECT-TYPE
          SYNTAX Integer32 (-32767..32767)
          UNITS "N/A"
          MAX-ACCESS read-write
          STATUS current
          DESCRIPTION "Humidity set point Time zone 1 Hour"
           ::= { integerObjects 38 }


-- 1.3.6.1.4.1.9839.2.1.3.39
     hum_minute1 OBJECT-TYPE
          SYNTAX Integer32 (-32767..32767)
          UNITS "N/A"
          MAX-ACCESS read-write
          STATUS current
          DESCRIPTION "Humidity set point Time zone 1 Minute"
           ::= { integerObjects 39 }


-- 1.3.6.1.4.1.9839.2.1.3.40
     hum_hour2 OBJECT-TYPE
          SYNTAX Integer32 (-32767..32767)
          UNITS "N/A"
          MAX-ACCESS read-write
          STATUS current
          DESCRIPTION "Humidity set point Time zone 2 Hour"
           ::= { integerObjects 40 }


-- 1.3.6.1.4.1.9839.2.1.3.41
     hum_minute2 OBJECT-TYPE
          SYNTAX Integer32 (-32767..32767)
          UNITS "N/A"
          MAX-ACCESS read-write
          STATUS current
          DESCRIPTION "Humidity set point Time zone 2 Minute"
           ::= { integerObjects 41 }


-- 1.3.6.1.4.1.9839.2.1.3.42
     hum_hour3 OBJECT-TYPE
          SYNTAX Integer32 (-32767..32767)
          UNITS "N/A"
          MAX-ACCESS read-write
          STATUS current
          DESCRIPTION "Humidity set point Time zone 3 Hour"
           ::= { integerObjects 42 }


-- 1.3.6.1.4.1.9839.2.1.3.43
     hum_minute3 OBJECT-TYPE
          SYNTAX Integer32 (-32767..32767)
          UNITS "N/A"
          MAX-ACCESS read-write
          STATUS current
          DESCRIPTION "Humidity set point Time zone 3 Minute"
           ::= { integerObjects 43 }


-- 1.3.6.1.4.1.9839.2.1.3.44
     hum_hour4 OBJECT-TYPE
          SYNTAX Integer32 (-32767..32767)
          UNITS "N/A"
          MAX-ACCESS read-write
          STATUS current
          DESCRIPTION "Humidity set point Time zone 4 Hour"
           ::= { integerObjects 44 }


-- 1.3.6.1.4.1.9839.2.1.3.45
     hum_minute4 OBJECT-TYPE
          SYNTAX Integer32 (-32767..32767)
          UNITS "N/A"
          MAX-ACCESS read-write
          STATUS current
          DESCRIPTION "Humidity set point Time zone 4 Minute"
           ::= { integerObjects 45 }


-- 1.3.6.1.4.1.9839.2.1.3.46
     x_h_main_fan OBJECT-TYPE
          SYNTAX Integer32 (-32767..32767)
          UNITS "N/A"
          MAX-ACCESS read-only
          STATUS current
          DESCRIPTION "Unit Fan Run Hours (high part)"
           ::= { integerObjects 46 }


-- 1.3.6.1.4.1.9839.2.1.3.47
     x_l_main_fan OBJECT-TYPE
          SYNTAX Integer32 (-32767..32767)
          UNITS "N/A"
          MAX-ACCESS read-only
          STATUS current
          DESCRIPTION "Unit Fan Run Hours (low part)"
           ::= { integerObjects 47 }


-- 1.3.6.1.4.1.9839.2.1.3.48
     h_hour_comp1 OBJECT-TYPE
          SYNTAX Integer32 (-32767..32767)
          UNITS "N/A"
          MAX-ACCESS read-only
          STATUS current
          DESCRIPTION "Compressor 1 Run Hours (high part)"
           ::= { integerObjects 48 }


-- 1.3.6.1.4.1.9839.2.1.3.49
     l_hour_comp1 OBJECT-TYPE
          SYNTAX Integer32 (-32767..32767)
          UNITS "N/A"
          MAX-ACCESS read-only
          STATUS current
          DESCRIPTION "Compressor 1 Run Hours (low part)"
           ::= { integerObjects 49 }


-- 1.3.6.1.4.1.9839.2.1.3.50
     h_hour_comp2 OBJECT-TYPE
          SYNTAX Integer32 (-32767..32767)
          UNITS "N/A"
          MAX-ACCESS read-only
          STATUS current
          DESCRIPTION "Compressor 2 Run Hours (high part)"
           ::= { integerObjects 50 }


-- 1.3.6.1.4.1.9839.2.1.3.51
     l_hour_comp2 OBJECT-TYPE
          SYNTAX Integer32 (-32767..32767)
          UNITS "N/A"
          MAX-ACCESS read-only
          STATUS current
          DESCRIPTION "Compressor 2 Run Hours (low part)"
           ::= { integerObjects 51 }


-- 1.3.6.1.4.1.9839.2.1.3.52
     h_hour_comp3 OBJECT-TYPE
          SYNTAX Integer32 (-32767..32767)
          UNITS "N/A"
          MAX-ACCESS read-only
          STATUS current
          DESCRIPTION "Compressor 3 Run Hours (high part)"
           ::= { integerObjects 52 }


-- 1.3.6.1.4.1.9839.2.1.3.53
     l_hour_comp3 OBJECT-TYPE
          SYNTAX Integer32 (-32767..32767)
          UNITS "N/A"
          MAX-ACCESS read-only
          STATUS current
          DESCRIPTION "Compressor 3 Run Hours (low part)"
           ::= { integerObjects 53 }


-- 1.3.6.1.4.1.9839.2.1.3.54
     h_hour_comp4 OBJECT-TYPE
          SYNTAX Integer32 (-32767..32767)
          UNITS "N/A"
          MAX-ACCESS read-only
          STATUS current
          DESCRIPTION "Compressor 4 Run Hours (high part)"
           ::= { integerObjects 54 }


-- 1.3.6.1.4.1.9839.2.1.3.55
     l_hour_comp4 OBJECT-TYPE
          SYNTAX Integer32 (-32767..32767)
          UNITS "N/A"
          MAX-ACCESS read-only
          STATUS current
          DESCRIPTION "Compressor 4 Run Hours (low part)"
           ::= { integerObjects 55 }


-- 1.3.6.1.4.1.9839.2.1.3.56
     h_hour_0_10_cool OBJECT-TYPE
          SYNTAX Integer32 (-32767..32767)
          UNITS "N/A"
          MAX-ACCESS read-only
          STATUS current
          DESCRIPTION "0 - 10v Cooling Run Hours (high part)"
           ::= { integerObjects 56 }


-- 1.3.6.1.4.1.9839.2.1.3.57
     l_hour_0_10_cool OBJECT-TYPE
          SYNTAX Integer32 (-32767..32767)
          UNITS "N/A"
          MAX-ACCESS read-only
          STATUS current
          DESCRIPTION "0 - 10v Cooling Run Hours (low part)"
           ::= { integerObjects 57 }


-- 1.3.6.1.4.1.9839.2.1.3.58
     h_hour_dodc_cool OBJECT-TYPE
          SYNTAX Integer32 (-32767..32767)
          UNITS "N/A"
          MAX-ACCESS read-only
          STATUS current
          DESCRIPTION "DODC Cooling Run Hours (high part)"
           ::= { integerObjects 58 }


-- 1.3.6.1.4.1.9839.2.1.3.59
     l_hour_dodc_cool OBJECT-TYPE
          SYNTAX Integer32 (-32767..32767)
          UNITS "N/A"
          MAX-ACCESS read-only
          STATUS current
          DESCRIPTION "DODC Cooling Run Hours (low part)"
           ::= { integerObjects 59 }


-- 1.3.6.1.4.1.9839.2.1.3.60
     h_hour_ambicool OBJECT-TYPE
          SYNTAX Integer32 (-32767..32767)
          UNITS "N/A"
          MAX-ACCESS read-only
          STATUS current
          DESCRIPTION "Ambicool Run Hours (high part)"
           ::= { integerObjects 60 }


-- 1.3.6.1.4.1.9839.2.1.3.61
     l_hour_ambicool OBJECT-TYPE
          SYNTAX Integer32 (-32767..32767)
          UNITS "N/A"
          MAX-ACCESS read-only
          STATUS current
          DESCRIPTION "Ambicool Run Hours (low part)"
           ::= { integerObjects 61 }


-- 1.3.6.1.4.1.9839.2.1.3.62
     h_hour_heater1 OBJECT-TYPE
          SYNTAX Integer32 (-32767..32767)
          UNITS "N/A"
          MAX-ACCESS read-only
          STATUS current
          DESCRIPTION "Heater 1 Run Hours (high part)"
           ::= { integerObjects 62 }


-- 1.3.6.1.4.1.9839.2.1.3.63
     l_hour_heater1 OBJECT-TYPE
          SYNTAX Integer32 (-32767..32767)
          UNITS "N/A"
          MAX-ACCESS read-only
          STATUS current
          DESCRIPTION "Heater 1 Run Hours (low part)"
           ::= { integerObjects 63 }


-- 1.3.6.1.4.1.9839.2.1.3.64
     h_hour_heater2 OBJECT-TYPE
          SYNTAX Integer32 (-32767..32767)
          UNITS "N/A"
          MAX-ACCESS read-only
          STATUS current
          DESCRIPTION "Heater 2 Run Hours (high part)"
           ::= { integerObjects 64 }


-- 1.3.6.1.4.1.9839.2.1.3.65
     l_hour_heater2 OBJECT-TYPE
          SYNTAX Integer32 (-32767..32767)
          UNITS "N/A"
          MAX-ACCESS read-only
          STATUS current
          DESCRIPTION "Heater 2 Run Hours (low part)"
           ::= { integerObjects 65 }


-- 1.3.6.1.4.1.9839.2.1.3.66
     h_hour_0_10_heat OBJECT-TYPE
          SYNTAX Integer32 (-32767..32767)
          UNITS "N/A"
          MAX-ACCESS read-only
          STATUS current
          DESCRIPTION "0 - 10v Heating Run Hours (high part)"
           ::= { integerObjects 66 }


-- 1.3.6.1.4.1.9839.2.1.3.67
     l_hour_0_10_heat OBJECT-TYPE
          SYNTAX Integer32 (-32767..32767)
          UNITS "N/A"
          MAX-ACCESS read-only
          STATUS current
          DESCRIPTION "0 - 10v Heating Run Hours (low part)"
           ::= { integerObjects 67 }


-- 1.3.6.1.4.1.9839.2.1.3.68
     h_hour_dodc_heat OBJECT-TYPE
          SYNTAX Integer32 (-32767..32767)
          UNITS "N/A"
          MAX-ACCESS read-only
          STATUS current
          DESCRIPTION "DODC Heating Run Hours (high part)"
           ::= { integerObjects 68 }


-- 1.3.6.1.4.1.9839.2.1.3.69
     l_hour_dodc_heat OBJECT-TYPE
          SYNTAX Integer32 (-32767..32767)
          UNITS "N/A"
          MAX-ACCESS read-only
          STATUS current
          DESCRIPTION "DODC Heating Run Hours (low part)"
           ::= { integerObjects 69 }


-- 1.3.6.1.4.1.9839.2.1.3.70
     h_hour_dehum OBJECT-TYPE
          SYNTAX Integer32 (-32767..32767)
          UNITS "N/A"
          MAX-ACCESS read-only
          STATUS current
          DESCRIPTION "Dehum Run Hours (high part)"
           ::= { integerObjects 70 }


-- 1.3.6.1.4.1.9839.2.1.3.71
     l_hour_dehum OBJECT-TYPE
          SYNTAX Integer32 (-32767..32767)
          UNITS "N/A"
          MAX-ACCESS read-only
          STATUS current
          DESCRIPTION "Dehum Run Hours (low part)"
           ::= { integerObjects 71 }



	END

--
-- CAREL-denco.MIB
--
