-- Toshiba MIB
-- MIB for Toshiba G9000 Uninterruptible Power Supply
--
--{iso(1) org(3) dod(6) internet(1) private(4) enterprises(1)
-- toshiba(186) equ(1) equups(19) ticups(2) rmti4 (5) upsG9000-G2020v2(8)}

--=============================================================================

TOSHIBAUPS-MIB-ADD DEFINITIONS ::= BEGIN

--=============================================================================
--=============================================================================
-- Update: March 8, 2016
-- By    : Edwin Rubio, Toshiba International Corp.
-- For   : G9000/G2020v2 First Draft MIB
--==============================================================================
--=============================================================================
-- Update: June 19, 2017
-- By    : Edwin Rubio, Toshiba International Corp.
-- For   : Added EPO alarm and trap
--==============================================================================

IMPORTS
 DisplayString, TimeStamp, TimeInterval, TestAndIncr, AutonomousType
 FROM SNMPv2-TC
 enterprises
 FROM RFC1155-SMI
 OBJECT-TYPE
 FROM RFC-1212
 TRAP-TYPE
 FROM RFC-1215;
       
 PositiveInteger    ::= INTEGER (0..2147483647)
 NonNegativeInteger ::= INTEGER (0..2147483647)


toshiba     OBJECT IDENTIFIER ::= { enterprises 186 }
equ         OBJECT IDENTIFIER ::= { toshiba 1 }
equUPS      OBJECT IDENTIFIER ::= { equ 19 }
ticUPS      OBJECT IDENTIFIER ::= { equUPS 2 }
rmti4       OBJECT IDENTIFIER ::= { ticUPS 5 }
upsG9000-G2020v2    OBJECT IDENTIFIER ::= { rmti4 8 }

upsIdent    OBJECT IDENTIFIER ::= { upsG9000-G2020v2 1 }
upsInput    OBJECT IDENTIFIER ::= { upsG9000-G2020v2 2 }
upsOutput   OBJECT IDENTIFIER ::= { upsG9000-G2020v2 3 }
upsBypass   OBJECT IDENTIFIER ::= { upsG9000-G2020v2 4 }
upsDCBus   	OBJECT IDENTIFIER ::= { upsG9000-G2020v2 5 }
upsBattery  OBJECT IDENTIFIER ::= { upsG9000-G2020v2 6 }
upsAlarm    OBJECT IDENTIFIER ::= { upsG9000-G2020v2 7 }
upsConfig   OBJECT IDENTIFIER ::= { upsG9000-G2020v2 8 }
upsTime     OBJECT IDENTIFIER ::= { upsG9000-G2020v2 9 }
upsTrap     OBJECT IDENTIFIER ::= { upsG9000-G2020v2 10 }

-- ===========================================================================
-- upsIdentification – Group 1
-- Device Identification group
-- All objects in this group are set at device initialization and remain static.
--===========================================================================

upsIdentManufacturer OBJECT-TYPE
      SYNTAX DisplayString (SIZE (0..31))
      ACCESS read-only
      STATUS mandatory
      DESCRIPTION
          "The name of the UPS manufacturer."
      ::= { upsIdent 1 }

upsIdentTypeform OBJECT-TYPE
      SYNTAX DisplayString (SIZE (0..127))
      ACCESS read-only
      STATUS mandatory
      DESCRIPTION
          "The UPS Model designation."
      ::= { upsIdent 2 }

upsIdentUPSFirmwareVersion OBJECT-TYPE
      SYNTAX DisplayString (SIZE(0..63))
      ACCESS read-only
      STATUS mandatory
      DESCRIPTION
          "The UPS firmware version."
      ::= { upsIdent 3 }

upsIdentSysName OBJECT-TYPE
      SYNTAX DisplayString (SIZE(0..63))
      ACCESS read-write
      STATUS mandatory
      DESCRIPTION
          "A string identifying the UPS.  This object is
           set by the administrator."
      ::= { upsIdent 4 }

upsIdentAttachedDevices OBJECT-TYPE
      SYNTAX DisplayString (SIZE(0..63))
      ACCESS read-write
      STATUS mandatory
      DESCRIPTION
          "A string identifying the devices attached to the
           output(s) of the UPS.  This object is set by
           the administrator."
      ::= { upsIdent 5 }
	  
upsIdentIdNumber OBJECT-TYPE
      SYNTAX DisplayString (SIZE(0..63))
      ACCESS read-only
      STATUS mandatory
      DESCRIPTION
          "This identifies the ID number of a G9000 that is in a parallel system. If not in a parallel system it will display N/A."
      ::= { upsIdent 6 }

--===========================================================================
-- upsInput – Group 2
--
-- Input group.
-- ===========================================================================

upsInputNumOfPhases OBJECT-TYPE
     SYNTAX NonNegativeInteger
     ACCESS read-only
     STATUS mandatory
     DESCRIPTION
           "Number of input lines.  This data is used by upsInputNumLines."
     ::= { upsInput 1 }

upsInputLLVoltageAB OBJECT-TYPE
     SYNTAX NonNegativeInteger
     UNITS "RMS Volts"
     ACCESS read-only
     STATUS mandatory
     DESCRIPTION
         "The input line to line voltage for AB in RMS volts."
     ::= { upsInput 2 }

upsInputLLVoltageBC OBJECT-TYPE
     SYNTAX NonNegativeInteger
     UNITS "RMS Volts"
     ACCESS read-only
     STATUS mandatory
     DESCRIPTION
         "The input line to line voltage for BC in RMS volts."
     ::= { upsInput 3 }

upsInputLLVoltageCA OBJECT-TYPE
     SYNTAX NonNegativeInteger
     UNITS "RMS Volts"
     ACCESS read-only
     STATUS mandatory
     DESCRIPTION
         "The input line to line voltage for CA in RMS volts."
     ::= { upsInput 4 }

upsInputLLVoltagePercentAB OBJECT-TYPE
     SYNTAX NonNegativeInteger
     UNITS "Percentage"
     ACCESS read-only
     STATUS mandatory
     DESCRIPTION
         "The input line to line voltage percent for AB."
     ::= { upsInput 5 }

upsInputLLVoltagePercentBC OBJECT-TYPE
     SYNTAX NonNegativeInteger
     UNITS "Percentage"
     ACCESS read-only
     STATUS mandatory
     DESCRIPTION
         "The input line to line voltage percent for BC."
     ::= { upsInput 6 }

upsInputLLVoltagePercentCA OBJECT-TYPE
     SYNTAX NonNegativeInteger
     UNITS "Percentage"
     ACCESS read-only
     STATUS mandatory
     DESCRIPTION
         "The input line to line voltage percent for CA."
     ::= { upsInput 7 }

upsInputCurrentPhaseA OBJECT-TYPE
     SYNTAX NonNegativeInteger
     UNITS "0.1 RMS Amps"
     ACCESS read-only
     STATUS mandatory
     DESCRIPTION
         "The input phase current for Phase A."
     ::= { upsInput 8 }

upsInputCurrentPhaseB OBJECT-TYPE
     SYNTAX NonNegativeInteger
     UNITS "0.1 RMS Amps"
     ACCESS read-only
     STATUS mandatory
     DESCRIPTION
         "The input phase current unit for Phase B."
     ::= { upsInput 9 }

upsInputCurrentPhaseC OBJECT-TYPE
     SYNTAX NonNegativeInteger
     UNITS "0.1 RMS Amps"
     ACCESS read-only
     STATUS mandatory
     DESCRIPTION
         "The input phase current unit for Phase C."
     ::= { upsInput 10 }

upsInputFrequency OBJECT-TYPE
     SYNTAX NonNegativeInteger
     UNITS "0.1 Hertz"
     ACCESS read-only
     STATUS mandatory
     DESCRIPTION
         "The input frequency unit 0.1 Hertz."
     ::= { upsInput 11 }

upsInputActivePowerA OBJECT-TYPE
     SYNTAX NonNegativeInteger
     UNITS "Watts"
     ACCESS read-only
     STATUS mandatory
     DESCRIPTION
         "The magnitude of the present input true power for phase A."
     ::= { upsInput 12 }

upsInputActivePowerB OBJECT-TYPE
     SYNTAX NonNegativeInteger
     UNITS "Watts"
     ACCESS read-only
     STATUS mandatory
     DESCRIPTION
         "The magnitude of the present input true power for phase B."
     ::= { upsInput 13 }

upsInputActivePowerC OBJECT-TYPE
     SYNTAX NonNegativeInteger
     UNITS "Watts"
     ACCESS read-only
     STATUS mandatory
     DESCRIPTION
         "The magnitude of the present input true power for phase C."
     ::= { upsInput 14 }

upsInputTotalActivePower OBJECT-TYPE
    SYNTAX  NonNegativeInteger
    UNITS "Watts"
    ACCESS  read-only
    STATUS  mandatory
    DESCRIPTION
        "The magnitude of the total input true power."
    ::= { upsInput  15 }

upsInputRatedLLVoltage OBJECT-TYPE
     SYNTAX NonNegativeInteger
     UNITS "RMS Volts"
     ACCESS read-only
     STATUS mandatory
     DESCRIPTION
         "The input line to line rated voltage in RMS volts."
     ::= { upsInput 16 }

-- ===========================================================================
-- upsOutput – Group 3
--
-- Output group
-- ===========================================================================

upsOutputSource OBJECT-TYPE
     SYNTAX     INTEGER {
           other(1),
           none(2),
           normal(3),
           bypass(4),
           battery(5), 
		   standby (6), 
		   powerconditioner(7)
     }
     ACCESS read-only
     STATUS mandatory
     DESCRIPTION
         "The present source of output power.  The enumeration
             none(2) indicates that there is no source of output
             power (and therefore no output power), for example,
             the system has opened the output breaker."
     ::= { upsOutput 1 }

upsOutputNumOfPhases OBJECT-TYPE
     SYNTAX NonNegativeInteger
     ACCESS read-only
     STATUS mandatory
     DESCRIPTION
         "The number of output lines utilized in this device."
     ::= { upsOutput 2 }


upsOutputLLVoltageAB OBJECT-TYPE
     SYNTAX NonNegativeInteger
     UNITS "RMS Volts"
     ACCESS read-only
     STATUS mandatory
     DESCRIPTION
         "The output line to line voltage for AB in RMS volts."
     ::= { upsOutput 3 }

upsOutputLLVoltageBC OBJECT-TYPE
     SYNTAX NonNegativeInteger
     UNITS "RMS Volts"
     ACCESS read-only
     STATUS mandatory
     DESCRIPTION
         "The output line to line voltage for BC in RMS volts."
     ::= { upsOutput 4 }

upsOutputLLVoltageCA OBJECT-TYPE
     SYNTAX NonNegativeInteger
     UNITS "RMS Volts"
     ACCESS read-only
     STATUS mandatory
     DESCRIPTION
         "The output line to line voltage for CA in RMS volts."
     ::= { upsOutput 5 }

upsOutputCurrentPhaseA OBJECT-TYPE
     SYNTAX NonNegativeInteger
     UNITS "RMS Amps"
     ACCESS read-only
     STATUS mandatory
     DESCRIPTION
         "The Output phase current for phase A in amps."
     ::= { upsOutput 6 }

upsOutputCurrentPhaseB OBJECT-TYPE
     SYNTAX NonNegativeInteger
     UNITS "RMS Amps"
     ACCESS read-only
     STATUS mandatory
     DESCRIPTION
         "The Output phase current for phase B in amps."
     ::= { upsOutput 7 }

upsOutputCurrentPhaseC OBJECT-TYPE
     SYNTAX NonNegativeInteger
     UNITS "RMS Amps"
     ACCESS read-only
     STATUS mandatory
     DESCRIPTION
         "The Output phase current for phase C in amps."
     ::= { upsOutput 8 }

upsOutputFrequency OBJECT-TYPE
     SYNTAX NonNegativeInteger
     UNITS "0.1 Hertz"
     ACCESS read-only
     STATUS mandatory
     DESCRIPTION
         "The Output Frequency for phase A in 1/10 of HZ."
     ::= { upsOutput 9 }

upsOutputCurrentPercentA OBJECT-TYPE
     SYNTAX INTEGER
     UNITS  "PERCENT"
     ACCESS read-only
     STATUS mandatory
     DESCRIPTION
         "The output current for phase A in percent."
     ::= { upsOutput 10 }

upsOutputCurrentPercentB OBJECT-TYPE
     SYNTAX INTEGER
     UNITS  "PERCENT"
     ACCESS read-only
     STATUS mandatory
     DESCRIPTION
         "The output current for phase B in percent."
     ::= { upsOutput 11 }

upsOutputCurrentPercentC OBJECT-TYPE
     SYNTAX INTEGER
     UNITS  "PERCENT"
     ACCESS read-only
     STATUS mandatory
     DESCRIPTION
         "The output current for phase C in percent."
     ::= { upsOutput 12 }

upsOutputTotalActivePower OBJECT-TYPE
     SYNTAX NonNegativeInteger
     UNITS "kWatts"
     ACCESS read-only
     STATUS mandatory
     DESCRIPTION
         "The output active power."
     ::= { upsOutput 13 }

upsOutputTotalActivePowerPercent OBJECT-TYPE
     SYNTAX NonNegativeInteger
     UNITS "percentage"
     ACCESS read-only
     STATUS mandatory
     DESCRIPTION
         "The output active power in percent."
     ::= { upsOutput 14 }

upsOutputPowerFactor OBJECT-TYPE
     SYNTAX NonNegativeInteger
     UNITS "0.01"
     ACCESS read-only
     STATUS mandatory
     DESCRIPTION
         "The UPS output power factor."
     ::= { upsOutput 15 }

upsOutputRatedActivePower OBJECT-TYPE
     SYNTAX NonNegativeInteger
     UNITS "Watts"
     ACCESS read-only
     STATUS mandatory
     DESCRIPTION
         "The output rated active power for the UPS."
     ::= { upsOutput 16 }

upsOutputRatedApparentPower OBJECT-TYPE
     SYNTAX NonNegativeInteger
     UNITS "VA"
     ACCESS read-only
     STATUS mandatory
     DESCRIPTION
         "The output rated apparent power for the UPS."
     ::= { upsOutput 17 }

upsOutputRatedLLVoltage OBJECT-TYPE
     SYNTAX NonNegativeInteger
     UNITS "RMS Volts"
     ACCESS read-only
     STATUS mandatory
     DESCRIPTION
         "The output rated line to line voltage for the UPS."
     ::= { upsOutput 18 }

-- ===========================================================================
-- upsBypass – Group 4
-- ===========================================================================

upsBypassNumOfPhases OBJECT-TYPE
     SYNTAX NonNegativeInteger
     ACCESS read-only
     STATUS mandatory
     DESCRIPTION
         "The number of bypass lines utilized."
     ::= { upsBypass 1 }

upsBypassLLVoltageAB OBJECT-TYPE
     SYNTAX NonNegativeInteger
     UNITS "RMS Volts"
     ACCESS read-only
     STATUS mandatory
     DESCRIPTION
         "The Bypass line to line voltage for AB in RMS volts."
     ::= { upsBypass 2 }

upsBypassLLVoltageBC OBJECT-TYPE
     SYNTAX NonNegativeInteger
     UNITS "RMS Volts"
     ACCESS read-only
     STATUS mandatory
     DESCRIPTION
         "The Bypass line to line voltage for BC in RMS volts."
     ::= { upsBypass 3 }

upsBypassLLVoltageCA OBJECT-TYPE
     SYNTAX NonNegativeInteger
     UNITS "RMS Volts"
     ACCESS read-only
     STATUS mandatory
     DESCRIPTION
         "The Bypass line to line voltage for CA in RMS volts."
     ::= { upsBypass 4 }

upsBypassFrequency OBJECT-TYPE
     SYNTAX NonNegativeInteger
     UNITS "0.1 Hertz"
     ACCESS read-only
     STATUS mandatory
     DESCRIPTION
         "The Bypass frequency in 0.1 Hertz."
     ::= { upsBypass 5 }

-- ===========================================================================
-- upsDCBus - Group 5
-- The UPS DC Bus Data Group
-- ===========================================================================
upsDCBusTotalVoltage OBJECT-TYPE
    SYNTAX INTEGER
    UNITS  "DC Volts"
    ACCESS read-only
    STATUS mandatory
    DESCRIPTION
        "The Total DC Bus voltage in DC volts."
    ::= { upsDCBus 1 }
	
upsDCBusPositiveVoltage OBJECT-TYPE
    SYNTAX INTEGER
    UNITS  "DC Volts"
    ACCESS read-only
    STATUS mandatory
    DESCRIPTION
        "The DC Bus positive voltage in DC volts."
    ::= { upsDCBus 2 }

upsDCBusNegativeVoltage OBJECT-TYPE
    SYNTAX INTEGER
    UNITS  "DC Volts"
    ACCESS read-only
    STATUS mandatory
    DESCRIPTION
        "The DC Bus negative voltage in DC volts."
    ::= { upsDCBus 3 }
	
--===========================================================================
-- upsBattery – Group 
--
-- The Battery group.
-- ===========================================================================

upsBatteryStatus OBJECT-TYPE
 SYNTAX    INTEGER {
           unknown(1),
           batteryNormal(2),
           batteryLow(3),
           batteryDepleted(4),
           batteryDischarging(5),
           batteryFailure(6)
     }
     ACCESS read-only
     STATUS mandatory
     DESCRIPTION
         "The indication of the capacity remaining in the UPS system's batteries.  A value of batteryNormal indicates that the remaining run time  sufficient to handle the load.  A value of batteryLow indicates the battery level is low.  Continued operation in battery mode will deplate batteries.  A value of batteryDepleted indicates that the UPS will be unable to sustain the present load when and if the utility power is lost (including the possibility that the utility power is currently absent and the UPS is unable to sustain the output). A value of batteryDischarging indicates UPS system is in Battery power. "
     ::= { upsBattery 1 }

upsElapsedTimeOnBatteryPower OBJECT-TYPE
       SYNTAX  NonNegativeInteger
       UNITS      "seconds"
       ACCESS     read-only
       STATUS     mandatory
       DESCRIPTION
               "If the unit is on battery power, the elapsed time
               since the UPS on battery power, or the
               time since the network management subsystem was last
               restarted, whichever is less.  Zero shall be returned
               if the unit is not on battery power."
       ::= { upsBattery 2 }

upsEstimatedBatteryRuntime OBJECT-TYPE
     SYNTAX PositiveInteger
     UNITS "minutes"
     ACCESS read-only
     STATUS mandatory
     DESCRIPTION
         "An estimate of the time to battery charge depletion
          under the present load conditions if the utility power
          is off and remains off, or if it were to be lost and
          remain off."
     ::= { upsBattery 3 }

upsBatteryVoltage OBJECT-TYPE
     SYNTAX NonNegativeInteger
     UNITS "Volt DC"
     ACCESS read-only
     STATUS mandatory
     DESCRIPTION
         "The battery voltage DC."
     ::= { upsBattery 4 }

upsBatteryVoltagePercent OBJECT-TYPE
     SYNTAX NonNegativeInteger
     UNITS "percentage"
     ACCESS read-only
     STATUS mandatory
     DESCRIPTION
         "Battery voltage in percent."
     ::= { upsBattery 5 }

upsBatteryEstimatedCharge OBJECT-TYPE
     SYNTAX INTEGER(0..100)
     UNITS "percentage"
     ACCESS read-only
     STATUS mandatory
     DESCRIPTION
         "An estimate of the charge to battery charge depletion
           under the present load conditions if the utility power
           is off and remains off, or if it were to be lost and
           remain off."
     ::= { upsBattery 6 }

upsBatteryDischargeCurrent OBJECT-TYPE
     SYNTAX Integer32
     UNITS "percentage"
     ACCESS read-only
     STATUS mandatory
     DESCRIPTION
         "The present battery discharge Current in percent."
     ::= { upsBattery 7 }

upsBatteryChargeCurrent OBJECT-TYPE
     SYNTAX Integer32
     UNITS "percentage"
     ACCESS read-only
     STATUS mandatory
     DESCRIPTION
         "The present battery charge Current in percent."
     ::= { upsBattery 8 }

upsBatteryModel OBJECT-TYPE
     SYNTAX DisplayString (SIZE(0..15))
     ACCESS read-write
     STATUS mandatory
     DESCRIPTION
         "The Battery manufacturer."
     ::= { upsBattery 9 }

upsBatteryInSeries OBJECT-TYPE
     SYNTAX NonNegativeInteger
     ACCESS read-write
     STATUS mandatory
     DESCRIPTION
         "The Battery rated holding time in minutes."
     ::= { upsBattery 10 }

upsBatteryNumStrings OBJECT-TYPE
     SYNTAX NonNegativeInteger
     ACCESS read-write
     STATUS mandatory
     DESCRIPTION
         "The Battery rated holding time in minutes."
     ::= { upsBattery 11 }

upsBatteryRatedAmpereHour OBJECT-TYPE
     SYNTAX NonNegativeInteger
     UNITS "Ampere Hour"
     ACCESS read-write
     STATUS mandatory
     DESCRIPTION
         "The Battery rated holding time in minutes."
     ::= { upsBattery 12 }

upsBatteryRatedBackupTime OBJECT-TYPE
     SYNTAX DisplayString (SIZE(0..8))
     UNITS "minutes"
     ACCESS read-write
     STATUS mandatory
     DESCRIPTION
         "The Battery rated holding time in minutes."
     ::= { upsBattery 13 }

upsBatteryInstallationDate OBJECT-TYPE
    SYNTAX DisplayString (SIZE(10))
    ACCESS read-only
    STATUS mandatory
    DESCRIPTION
        "The battery install date."
    ::= { upsBattery 14 }

-- ===========================================================================
-- upsAlarm – Group 7
-- ===========================================================================

upsAlarmsPresent OBJECT-TYPE
    SYNTAX Gauge32
    ACCESS read-only
    STATUS mandatory
    DESCRIPTION
        "The present number of active alarm conditions."
    ::= { upsAlarm 1 }

upsAlarmTable OBJECT-TYPE
    SYNTAX  SEQUENCE OF UpsAlarmEntry
    ACCESS  not-accessible
    STATUS  mandatory
    DESCRIPTION
           "A list of alarm table entries.  The table contains
               zero, one, or many rows at any moment, depending upon
               the number of alarm conditions in effect.  The table
               is initially empty at agent startup.  The agent
               creates a row in the table each time a condition is
               detected and deletes that row when that condition no
               longer pertains.  The agent creates the first row with
               upsAlarmId equal to 1, and increments the value of
               upsAlarmId each time a new row is created, wrapping to
               the first free value greater than or equal to 1 when
               the maximum value of upsAlarmId would otherwise be
               exceeded.  Consequently, after multiple operations,
               the table may become sparse, e.g., containing entries
               for rows 95, 100, 101, and 203 and the entries should
               not be assumed to be in chronological order because
               upsAlarmId might have wrapped.

               Alarms are named by an OBJECT IDENTIFIER,
               upsAlarmDescr, to allow a single table to
               reflect well known alarms plus alarms defined by a
               particular implementation, i.e., as documented in the
               private enterprise MIB definition for the device.  No
               two rows will have the same value of upsAlarmDescr,
               since alarms define conditions.  In order to meet this
               requirement, care should be taken in the definition of
               alarm conditions to insure that a system cannot enter
               the same condition multiple times simultaneously.

               The number of rows in the table at any given time is
               reflected by the value of upsAlarmsPresent."
    ::= { upsAlarm  2 }

upsAlarmEntry OBJECT-TYPE
    SYNTAX  UpsAlarmEntry
    ACCESS  not-accessible
    STATUS  mandatory
    DESCRIPTION
        "An entry containing information applicable to a
         particular alarm."
    INDEX { upsAlarmId }
    ::= { upsAlarmTable  1 }

UpsAlarmEntry ::=
    SEQUENCE {
             upsAlarmId            PositiveInteger,
             upsAlarmDescr         AutonomousType,
             upsAlarmTime          TimeStamp
         }

-- ===========================================================================
-- upsAlarmTable/upsAlarmEntry/upsAlarmId
-- ===========================================================================

upsAlarmId OBJECT-TYPE
     SYNTAX PositiveInteger
     ACCESS not-accessible
     STATUS mandatory
     DESCRIPTION
         "A unique identifier for an alarm condition.  This
          value must remain constant."
     ::= { upsAlarmEntry 1 }

upsAlarmDescr OBJECT-TYPE
     SYNTAX  AutonomousType
     ACCESS read-only
     STATUS mandatory
     DESCRIPTION
         "A reference to an alarm description object.  The
             object referenced should not be accessible, but rather
             be used to provide a unique description of the alarm
             condition."
     ::= { upsAlarmEntry 2 }

-- ===========================================================================
-- .../upsAlarmTime
-- ===========================================================================

upsAlarmTime OBJECT-TYPE
     SYNTAX TimeStamp
     ACCESS read-only
     STATUS mandatory
     DESCRIPTION
         "The value of sysUpTime when the alarm condition was
          detected.  If the alarm condition was detected at the
          time of agent startup and presumably existed before
          agent startup, the value of upsAlarmTime shall equal 0."
     ::= { upsAlarmEntry 3 }


upsWellKnownAlarms OBJECT IDENTIFIER ::= { upsAlarm  3 }

upsAlarmFault OBJECT-TYPE 
     SYNTAX INTEGER
     ACCESS read-only
     STATUS mandatory
     DESCRIPTION
         "Fault: A UPS fault/Alarm condition exists."
     ::= { upsWellKnownAlarms 1 }
	 
upsAlarmWarning OBJECT-TYPE 
     SYNTAX INTEGER
     ACCESS read-only
     STATUS mandatory
     DESCRIPTION
         "Warning: A UPS Warning alarm condition exists."
     ::= { upsWellKnownAlarms 2 }

upsAlarmOnBattery OBJECT-TYPE
     SYNTAX INTEGER
     ACCESS read-only
     STATUS mandatory
     DESCRIPTION
         "Info: The UPS is on Battery mode; it is supplying output power from its batteries."
     ::= { upsWellKnownAlarms 3 }

upsAlarmBatteryLow OBJECT-TYPE
     SYNTAX INTEGER
     ACCESS read-only
     STATUS mandatory
     DESCRIPTION
          "Warning: The battery level is low.  It has dropped to less than 90% of its nominal value. Continued operation in Battery Mode will deplete Batteries and result in UPS output shut down.  Reduce critical load to increase battery runtime."
     ::= { upsWellKnownAlarms 4 }

upsAlarmBatteryDepleted OBJECT-TYPE
     SYNTAX INTEGER
     ACCESS read-only
     STATUS mandatory
     DESCRIPTION
         "Warning: UPS contains depleted batteries, it will be unable to support critical loads.  Shut down excess equipment to reduce Load."
     ::= { upsWellKnownAlarms 5 }

upsAlarmBatteryOverheat OBJECT-TYPE
     SYNTAX INTEGER
     ACCESS read-only
     STATUS mandatory
     DESCRIPTION
         "Fault: Detection of over temperature at the batteries."
     ::= { upsWellKnownAlarms 6 }

upsAlarmBatteryVoltageAbnormal OBJECT-TYPE
     SYNTAX INTEGER
     ACCESS read-only
     STATUS mandatory
     DESCRIPTION
         "Fault: Battery voltage is abnormality."
     ::= { upsWellKnownAlarms 7 }


upsAlarmUPSOverheat OBJECT-TYPE 
     SYNTAX INTEGER
     ACCESS read-only
     STATUS mandatory
     DESCRIPTION
         "Fault: The UPS is overheating (warning is given when the internal temperature reaches and exceeds 50?C rise @ 40?C ambient).  Check   to see if the ambient temperature is abnormally high (40?C or   more). If so, turn on air conditioning. Also, check ventilation fan   at the back of the UPS for operation or obstructions. Otherwise,  shut down the UPS and contact your Toshiba authorized service   center."
     ::= { upsWellKnownAlarms 8 }

upsAlarmPowerFailure OBJECT-TYPE 
     SYNTAX INTEGER
     ACCESS read-only
     STATUS mandatory
     DESCRIPTION
         "Info: Power Failure."
     ::= { upsWellKnownAlarms 9 }

upsAlarmUPSOverload OBJECT-TYPE 
     SYNTAX INTEGER
     ACCESS read-only
     STATUS mandatory
     DESCRIPTION
         "Fault: The UPS is overloaded. UPS will switch to bypass operation or shut down if no action is taken. Shut down excess equipment to reduce Load."
     ::= { upsWellKnownAlarms 10 }
	 
upsAlarmUserDefinedOverloadWarning OBJECT-TYPE 
    SYNTAX INTEGER
    ACCESS read-only
    STATUS mandatory
    DESCRIPTION
        "Warning: The inverter output load % is greater than the user defined overload set point (default: 110%)."
    ::= { upsWellKnownAlarms 11 }

upsAlarmOnBypass OBJECT-TYPE 
     SYNTAX INTEGER
     ACCESS read-only
     STATUS mandatory
     DESCRIPTION
         "Warning: The UPS is in Stop (Bypass) mode."
     ::= { upsWellKnownAlarms 12 }

upsAlarmOutputOff OBJECT-TYPE 
SYNTAX INTEGER
     ACCESS read-only
     STATUS mandatory
     DESCRIPTION
         "Info: The UPS output is off."
     ::= { upsWellKnownAlarms 13 }

upsAlarmAsyncOperation OBJECT-TYPE 
SYNTAX INTEGER
     ACCESS read-only
     STATUS mandatory
     DESCRIPTION
         "Warning: Async Operation"
     ::= { upsWellKnownAlarms 14 }

upsAlarmDCBusOverCurrent OBJECT-TYPE 
SYNTAX INTEGER
     ACCESS read-only
     STATUS mandatory
     DESCRIPTION
         "Fault: UPS is reporting a DC bus overcurrent condition.  Contact your Toshiba authorized service center for examination of a DCOC fault."
     ::= { upsWellKnownAlarms 15 }

upsAlarmDCBusOverVoltage OBJECT-TYPE 
SYNTAX INTEGER
     ACCESS read-only
     STATUS mandatory
     DESCRIPTION
         "Fault: UPS is reporting a DC bus overvoltage condition.  Contact your Toshiba authorized service center for examination of a DCOV fault."
     ::= { upsWellKnownAlarms 16 }

upsAlarmDCBusUnderVoltage OBJECT-TYPE 
     SYNTAX INTEGER
     ACCESS read-only
     STATUS mandatory
     DESCRIPTION
         "Fault: UPS is reporting a DC bus undervoltage condition.  Contact your 
          Toshiba authorized service center for examination of a DCUV fault."
     ::= { upsWellKnownAlarms 17 }

upsAlarmDCBusImbalanced OBJECT-TYPE 
     SYNTAX INTEGER
     ACCESS read-only
     STATUS mandatory
     DESCRIPTION
         "Fault: The DC imbalanced alarm detection."
      ::= { upsWellKnownAlarms 18 }

upsAlarmOutputUnderVoltage OBJECT-TYPE 
 SYNTAX INTEGER
     ACCESS read-only
     STATUS mandatory
     DESCRIPTION
         "Fault: UPS is reporting an output undervoltage condition.  Contact your Toshiba authorized service center for examination of a INVUV fault."
     ::= { upsWellKnownAlarms 19 }

upsAlarmOutputOverVoltage OBJECT-TYPE 
 SYNTAX INTEGER
     ACCESS read-only
     STATUS mandatory
     DESCRIPTION
         "Fault: UPS is reporting an output overvoltage condition.  Contact your 
          Toshiba authorized service center for examination of a INVOV fault."
     ::= { upsWellKnownAlarms 20 }

upsAlarmInverterOverload OBJECT-TYPE 
 SYNTAX INTEGER
     ACCESS read-only
     STATUS mandatory
     DESCRIPTION
         "Fault: Short time over-current has been detected."
     ::= { upsWellKnownAlarms 21 }

upsAlarmInverterOvercurrent OBJECT-TYPE 
 SYNTAX INTEGER
     ACCESS read-only
     STATUS mandatory
     DESCRIPTION
         "Fault: Detection of inverter overcurrent."
     ::= { upsWellKnownAlarms 22 }

upsAlarmRemotEyeCommError OBJECT-TYPE 
 SYNTAX INTEGER
     ACCESS read-only
     STATUS mandatory
     DESCRIPTION
         "Warning: Communication error between the RemotEye 4 and the UPS."
     ::= { upsWellKnownAlarms 23 }
	 
upsAlarmFanFailureFault OBJECT-TYPE 
 SYNTAX INTEGER
     ACCESS read-only
     STATUS mandatory
     DESCRIPTION
         "Fault: Fan Failure fault."
     ::= { upsWellKnownAlarms 24 }
	 
upsAlarmInputVoltageAbnormal OBJECT-TYPE 
 SYNTAX INTEGER
     ACCESS read-only
     STATUS mandatory
     DESCRIPTION
         "Warning: Input voltage voltage is abnormal."
     ::= { upsWellKnownAlarms 25 }
	
upsAlarmBatteryCB2Opened OBJECT-TYPE 
 SYNTAX INTEGER
     ACCESS read-only
     STATUS mandatory
     DESCRIPTION
         "Warning: Battery CB2 Opened."
     ::= { upsWellKnownAlarms 26 }
	 
upsAlarmConverterInputContactorCB1Opened OBJECT-TYPE 
 SYNTAX INTEGER
     ACCESS read-only
     STATUS mandatory
     DESCRIPTION
         "Warning: Converter Input Contactor CB1 Opened."
     ::= { upsWellKnownAlarms 27 }
	 
upsAlarm52SOpened OBJECT-TYPE 
 SYNTAX INTEGER
     ACCESS read-only
     STATUS mandatory
     DESCRIPTION
         "Warning: 52S Opened."
     ::= { upsWellKnownAlarms 28 }
	 
upsAlarm52COpened OBJECT-TYPE 
 SYNTAX INTEGER
     ACCESS read-only
     STATUS mandatory
     DESCRIPTION
         "Warning: 52C Opened."
     ::= { upsWellKnownAlarms 29 }
	 
upsAlarmFanFailureWarning OBJECT-TYPE 
 SYNTAX INTEGER
     ACCESS read-only
     STATUS mandatory
     DESCRIPTION
		 "Warning: Fan Failure warning."
	 ::= { upsWellKnownAlarms 30 }

upsAlarmEPOFault OBJECT-TYPE 
 SYNTAX INTEGER
     ACCESS read-only
     STATUS mandatory
     DESCRIPTION
		 "Fault: EPO (emergency power off) alarm."
	 ::= { upsWellKnownAlarms 31 }
		 
-- ===========================================================================
-- upsConfig – Group 8 
-- Config data
-- 1) All 'upsConfig' data is to be stored in NV-RAM inside the agent   device.
-- 2) All 'upsConfig' data is to be checked at each agent startup
-- 3) If initial values present at startup, replace with default values
--    unless specified otherwise.
-- ===========================================================================

upsConfigModelIDString OBJECT-TYPE
     SYNTAX DisplayString (SIZE (0..63))
     ACCESS read-only
     STATUS mandatory
     DESCRIPTION
        "UPS Model ID string.  This string contains codes for the UPS series,input voltage, output voltage, output VA, and addition option."
     ::= { upsConfig 1 }

upsConfigUPSFirmwareVersion OBJECT-TYPE
     SYNTAX DisplayString (SIZE (0..63))
     ACCESS read-only
     STATUS mandatory
     DESCRIPTION
         "The UPS software version."
     ::= { upsConfig 2 }

upsConfigUPSSysSetup OBJECT-TYPE
     SYNTAX    INTEGER {
           singleModuleSys(1),
           multiModuleSys(2)
     }
     ACCESS read-only
     STATUS mandatory
     DESCRIPTION
         "Indicates is the UPS is part of a Multi-Module System or a Single-Module System."
     ::= { upsConfig 3 }
	 
upsConfigInputNumOfPhases OBJECT-TYPE
    SYNTAX NonNegativeInteger 
    ACCESS read-only
    STATUS mandatory
    DESCRIPTION
        "Number of input lines.  This data is used by upsInputNumLines."
    ::= { upsConfig 4 }

upsConfigRatedInputFrequency OBJECT-TYPE
    SYNTAX  NonNegativeInteger
    UNITS "0.1 Hertz"
    ACCESS  read-only
    STATUS  mandatory
    DESCRIPTION
        "The nominal input frequency.  On those systems which
         support read-write access to this object, if there is
         an attempt to set this variable to a value that is not
         supported, the request must be rejected and the agent
         shall respond with an appropriate error message, i.e.,
         badValue for SNMPv1, or inconsistentValue for SNMPv2."
     ::= { upsConfig 5 }

upsConfigRatedInputLLVoltage OBJECT-TYPE
    SYNTAX  NonNegativeInteger
    UNITS "RMS Volts"
    ACCESS  read-write
    STATUS  mandatory
    DESCRIPTION
        "The magnitude of the nominal input voltage.  On those
         systems which support read-write access to this
         object, if there is an attempt to set this variable to
         a value that is not supported, the request must be
         rejected and the agent shall respond with an
         appropriate error message, i.e., badValue for SNMPv1,
         or inconsistentValue for SNMPv2."
     ::= { upsConfig 6 }

upsConfigRatedInputPowerFactor OBJECT-TYPE
    SYNTAX PositiveInteger
    UNITS "0.01"
    ACCESS read-only
    STATUS mandatory
    DESCRIPTION
        "UNITS are in hundredths.  For 0.95 = 95."
    ::= { upsConfig 7 }

upsConfigOutputNumOfPhases OBJECT-TYPE
    SYNTAX NonNegativeInteger
    ACCESS read-only
    STATUS mandatory
    DESCRIPTION
        "Number of output lines.  This data is used by upsOutputNumLines."
    ::= { upsConfig 8 }

upsConfigRatedOutputFrequency OBJECT-TYPE
    SYNTAX  NonNegativeInteger
    UNITS "0.1 Hertz"
    ACCESS  read-only
    STATUS  mandatory
    DESCRIPTION
        "The nominal output frequency.  On those systems which
         support read-write access to this object, if there is
         an attempt to set this variable to a value that is not
         supported, the request must be rejected and the agent
         shall respond with an appropriate error message, i.e.,
         bad Value for SNMPv1, or inconsistent Value for SNMPv2."
     ::= { upsConfig 9 }

upsConfigRatedOutputLLVoltage OBJECT-TYPE
    SYNTAX NonNegativeInteger 
    UNITS "RMS Volts"
    ACCESS  read-write
    STATUS  mandatory
    DESCRIPTION
        "The magnitude of the nominal output voltage.  On
         those systems which support read-write access to this
         object, if there is an attempt to set this variable to
         a value that is not supported, the request must be
         rejected and the agent shall respond with an
         appropriate error message, i.e., bad Value for SNMPv1,
         or inconsistent Value for SNMPv2."
     ::= { upsConfig 10 }

upsConfigRatedOutputApperentPower OBJECT-TYPE
    SYNTAX  NonNegativeInteger
    UNITS "Volt-Amps"
    ACCESS  read-only
    STATUS  mandatory
    DESCRIPTION
        "The magnitude of the nominal Volt-Amp rating."
    ::= { upsConfig 11 }

upsConfigRatedOutputActivePower OBJECT-TYPE
    SYNTAX  NonNegativeInteger
    UNITS "KWatts"
    ACCESS  read-only
    STATUS  mandatory
    DESCRIPTION
        "The magnitude of the nominal true power rating."
    ::= { upsConfig 12 }

upsConfigRatedOutputPowerFactor OBJECT-TYPE
     SYNTAX NonNegativeInteger
     UNITS "0.01"
     ACCESS read-only
     STATUS mandatory
     DESCRIPTION
         "UNITS are in hundredths.  For 0.70 = 70."
     ::= { upsConfig 13 }

upsConfigBypassNumOfPhases OBJECT-TYPE
     SYNTAX NonNegativeInteger
     ACCESS read-only
     STATUS mandatory
     DESCRIPTION
         "The number of bypass lines utilized."
     ::= { upsConfig 14 }

upsConfigLowVoltageTransferPoint OBJECT-TYPE
     SYNTAX NonNegativeInteger
     UNITS "percentage"
     ACCESS  read-write
     STATUS  mandatory
     DESCRIPTION
         "The minimum input line voltage allowed before the UPS
          system transfers to battery backup."
     ::= { upsConfig 15 }

upsConfigHighVoltageTransferPoint OBJECT-TYPE
     SYNTAX NonNegativeInteger
     UNITS "percentage"
     ACCESS  read-write
     STATUS  mandatory
     DESCRIPTION
         "The maximum line voltage allowed before the UPS
          system transfers to battery backup."
     ::= { upsConfig 16 }

upsConfigBatteryInSeries OBJECT-TYPE
     SYNTAX NonNegativeInteger 
     ACCESS read-write
     STATUS mandatory
     DESCRIPTION
         "The number of batteries in each string connected in series."
     ::= { upsConfig 17 }

upsConfigBatteryNumStrings OBJECT-TYPE
     SYNTAX NonNegativeInteger 
     ACCESS read-write
     STATUS mandatory
     DESCRIPTION
         "The number of parallel battery strings."
     ::= { upsConfig 18 }

upsConfigRatedBatteryVoltage OBJECT-TYPE
     SYNTAX NonNegativeInteger
     UNITS "Volts DC"
     ACCESS read-write
     STATUS mandatory
     DESCRIPTION
         "Rated voltage of a single battery."
     ::= { upsConfig 19 }

upsConfigRatedBatteryAmpereHour OBJECT-TYPE
    SYNTAX INTEGER
    UNITS "Ahr"
    ACCESS read-write
    STATUS mandatory
    DESCRIPTION
        "The rated battery in ampere hour."
    ::= { upsConfig 20 }

upsConfigBatteryModel OBJECT-TYPE
     SYNTAX DisplayString (SIZE (0..31))
     ACCESS read-write
     STATUS mandatory
     DESCRIPTION
         "The manufacturer of the battery."
     ::= { upsConfig 21 }

upsConfigBatteryRatedBackupTime OBJECT-TYPE
     SYNTAX NonNegativeInteger
     UNITS "minutes"
     ACCESS read-write
     STATUS mandatory
     DESCRIPTION
         "The rated duration batteries can hold when unit is in backup mode with full load."
     ::= { upsConfig 22 }

upsConfigUserDefinedOverloadSetPoint OBJECT-TYPE
    SYNTAX INTEGER
	UNITS "%"
    ACCESS read-write
    STATUS mandatory
    DESCRIPTION 
        "The maximum output load % defined by the user."
    ::= { upsConfig 23 }

upsConfigBatteryInstallationDate OBJECT-TYPE
    SYNTAX DisplayString (SIZE(10))
    UNITS "mm/dd/yyyy"
    ACCESS read-write
    STATUS mandatory
    DESCRIPTION
        "The battery install date."
    ::= { upsConfig 24 }

upsConfigSysName OBJECT-TYPE
      SYNTAX DisplayString (SIZE(0..31))
      ACCESS read-write
      STATUS mandatory
      DESCRIPTION
          "A string identifying the UPS.  This object is
           set by the administrator."
      ::= { upsConfig 25 }

upsConfigAttachedDevices OBJECT-TYPE
      SYNTAX DisplayString (SIZE(0..31))
      ACCESS read-write
      STATUS mandatory
      DESCRIPTION
          "A string identifying the devices attached to the
           output(s) of the UPS.  This object is set by
           the administrator."
      ::= { upsConfig 26 }

upsConfigPassword OBJECT-TYPE
    SYNTAX DisplayString (SIZE(0..31))
    ACCESS read-write
    STATUS mandatory
    DESCRIPTION
        "Password."
    ::= { upsConfig 27 }

-- ===========================================================================
-- upsTime – Group 9
--
-- Time group
-- ===========================================================================

upsTimeRealDate OBJECT-TYPE
     SYNTAX DisplayString (SIZE (0..31))
     ACCESS read-write
     STATUS mandatory
     DESCRIPTION
        "UPS Present date: year-month-date-day of the week."
     ::= { upsTime 1  }

upsTimeRealTime OBJECT-TYPE
     SYNTAX DisplayString (SIZE (0..31))
     ACCESS read-write
     STATUS mandatory
     DESCRIPTION
         "UPS Present time (military format): hour-minute-second.  For example,2:00pm would be 14:00:00."
     ::= { upsTime 2  }

--
--=======================================================================
-- upsTraps – Group 10
--
-- Traps group
-- 
--=======================================================================

upsTrapFault TRAP-TYPE
    ENTERPRISE upsG9000-G2020v2
    DESCRIPTION
        "Alarm: One or more fault/status alarm(s) reported."
    ::= 1

upsTrapFaultClear TRAP-TYPE
    ENTERPRISE upsG9000-G2020v2  
    DESCRIPTION
        "Alarm Clear: One or more fault/status reported."
    ::= 2
	
upsTrapWarning TRAP-TYPE
    ENTERPRISE upsG9000-G2020v2  
    DESCRIPTION
        "Alarm: A UPS Warning alarm condition exists."
    ::= 3

upsTrapWarningClear TRAP-TYPE
    ENTERPRISE upsG9000-G2020v2  
    DESCRIPTION
        "Alarm Clear: A UPS Warning alarm condition exists."
    ::= 4
	 
upsTrapOnBattery TRAP-TYPE
      ENTERPRISE upsG9000-G2020v2 
      DESCRIPTION
          "Info: The UPS is on Battery Mode."
      ::= 5  

upsTrapOnBatteryClear TRAP-TYPE
      ENTERPRISE upsG9000-G2020v2 
      DESCRIPTION
          "Info Clear: The UPS is on Battery Mode."
      ::= 6 

upsTrapBatteryLow TRAP-TYPE
      ENTERPRISE upsG9000-G2020v2 
      DESCRIPTION
          "Warning: Battery Low Voltage."
      ::= 7

upsTrapBatteryLowClear TRAP-TYPE
      ENTERPRISE upsG9000-G2020v2 
      DESCRIPTION
          "Warning Clear: Battery Low Voltage."
      ::= 8

upsTrapBatteryDepleted TRAP-TYPE
      ENTERPRISE upsG9000-G2020v2 
      DESCRIPTION
          "Warning: UPS contains depleted batteries, it will be unable to support critical loads. Shutdown excess equipment to reduce load."
      ::= 9 

upsTrapBatteryDepletedClear TRAP-TYPE
      ENTERPRISE upsG9000-G2020v2 
      DESCRIPTION
          "Warning Clear: UPS contains depleted batteries, it will be unable to support critical loads. Shutdown excess equipment to reduce load.."
      ::= 10 

upsTrapBatteryOverheat TRAP-TYPE
      ENTERPRISE upsG9000-G2020v2 
      DESCRIPTION
          "Fault: Battery Overheat."
      ::= 11

upsTrapBatteryOverheatClear TRAP-TYPE
      ENTERPRISE upsG9000-G2020v2 
      DESCRIPTION
          "Fault Clear: Battery Overheat."
      ::= 12

upsTrapBatteryVoltageAbnormal TRAP-TYPE
      ENTERPRISE upsG9000-G2020v2 
      DESCRIPTION
          "Fault: Battery Voltage Abnormal. Contact your Toshiba authorized service center for examination."
      ::= 13

upsTrapBatteryVoltageAbnormalClear TRAP-TYPE
      ENTERPRISE upsG9000-G2020v2 
      DESCRIPTION
          "Fault Clear: Battery Voltage Abnormal. Contact your Toshiba authorized service center for examination."
      ::= 14

upsTrapUPSOverheat TRAP-TYPE
      ENTERPRISE upsG9000-G2020v2 
      DESCRIPTION
          "Fault: UPS Overheat, heatsinks temperature exceeds thermal settings. Contact your Toshiba authorized service center for examination."
      ::= 15

upsTrapUPSOverheatClear TRAP-TYPE
      ENTERPRISE upsG9000-G2020v2 
      DESCRIPTION
          "Fault Clear: UPS Overheat, heatsinks temperature exceeds thermal settings. Contact your Toshiba authorized service center for examination."
      ::= 16

upsTrapPowerFailure TRAP-TYPE
      ENTERPRISE upsG9000-G2020v2 
      DESCRIPTION
          "Info: Power Failure."
      ::= 17

upsTrapPowerFailureClear TRAP-TYPE
      ENTERPRISE upsG9000-G2020v2 
      DESCRIPTION
          "Info Clear: PowerFailure."
      ::= 18

upsTrapUPSOverload TRAP-TYPE
      ENTERPRISE upsG9000-G2020v2 
      DESCRIPTION
          "Fault: UPS Overload (OL), the output load exceeds the rated current. Decrease load."
      ::= 19

upsTrapUPSOverloadClear TRAP-TYPE
      ENTERPRISE upsG9000-G2020v2 
      DESCRIPTION
          "Fault Clear: UPS Overload (OL), the output load exceeds the rated current. Decrease load."
      ::= 20
	  
upsTrapUserDefinedOverloadWarning TRAP-TYPE 
    ENTERPRISE upsG9000-G2020v2 
    DESCRIPTION
        "Warning: The inverter output load % is greater than the user defined overload set point (default: 110%)."
	  ::= 21
	
upsTrapUserDefinedOverloadWarningClear TRAP-TYPE 
    ENTERPRISE upsG9000-G2020v2 
    DESCRIPTION
        "Warning Clear: The inverter output load % is greater than the user defined overload set point (default: 110%)."
      ::= 22

upsTrapOnBypass TRAP-TYPE
      ENTERPRISE upsG9000-G2020v2 
      DESCRIPTION
          "Warning:On Bypass."
      ::= 23

upsTrapOnBypassClear TRAP-TYPE
      ENTERPRISE upsG9000-G2020v2 
      DESCRIPTION
          "Warning Clear: On Bypass."
      ::= 24

upsTrapOutputOff TRAP-TYPE
      ENTERPRISE upsG9000-G2020v2 
      DESCRIPTION
          "Info: The UPS output is off."
      ::= 25 

upsTrapOutputOffClear TRAP-TYPE
      ENTERPRISE upsG9000-G2020v2 
      DESCRIPTION
          "Info Clear: The UPS output is off."
      ::= 26 

upsTrapAsyncOperation TRAP-TYPE
      ENTERPRISE upsG9000-G2020v2 
      DESCRIPTION
          "Warning: Inverter Synchronous."
      ::= 27  

upsTrapAsyncOperationClear TRAP-TYPE
      ENTERPRISE upsG9000-G2020v2 
      DESCRIPTION
          "Warning Clear: Inverter Synchronous."
      ::= 28

upsTrapDCBusOverCurrent TRAP-TYPE
      ENTERPRISE upsG9000-G2020v2 
      DESCRIPTION
          "Fault: DC Overcurrent (DCOC). Contact your Toshiba authorized service center for examination."
      ::= 29

upsTrapDCBusOverCurrentClear TRAP-TYPE
      ENTERPRISE upsG9000-G2020v2 
      DESCRIPTION
          "Fault Clear: DC Overcurrent (DCOC). Contact your Toshiba authorized service center for examination."
      ::= 30

upsTrapDCBusOverVoltage TRAP-TYPE
      ENTERPRISE upsG9000-G2020v2 
      DESCRIPTION
          "Fault: DC Overvoltage (DCOV). Contact your Toshiba authorized service center for examination."
      ::= 31

upsTrapDCBusOverVoltageClear TRAP-TYPE
      ENTERPRISE upsG9000-G2020v2 
      DESCRIPTION
          "Fault Clear: DC Overvoltage (DCOV). Contact your Toshiba authorized service center for examination."
      ::= 32

upsTrapDCBusUnderVoltage TRAP-TYPE
      ENTERPRISE upsG9000-G2020v2 
      DESCRIPTION
          "Fault: DC Undervoltage (DCUV). Contact your Toshiba authorized service center for examination."
      ::= 33

upsTrapDCBusUnderVoltageClear TRAP-TYPE
      ENTERPRISE upsG9000-G2020v2 
      DESCRIPTION
          "Fault Clear: DC Undervoltage (DCUV). Contact your Toshiba authorized service center for examination."
      ::= 34

upsTrapDCBusImbalance TRAP-TYPE
      ENTERPRISE upsG9000-G2020v2 
      DESCRIPTION
          "Fault: DC Unbalance. Contact your Toshiba authorized service center for examination."
      ::= 35

upsTrapDCBusImbalanceClear TRAP-TYPE
      ENTERPRISE upsG9000-G2020v2 
      DESCRIPTION
          "Fault Clear: DC Unbalance. Contact your Toshiba authorized service center for examination."
      ::= 36

upsTrapOutputUnderVoltage TRAP-TYPE
      ENTERPRISE upsG9000-G2020v2 
      DESCRIPTION
          "Fault: Output Undervoltage. Contact your Toshiba authorized service center for examination."
      ::= 37

upsTrapOutputUnderVoltageClear TRAP-TYPE
      ENTERPRISE upsG9000-G2020v2 
      DESCRIPTION
          "Fault Clear: Output Undervoltage. Contact your Toshiba authorized service center for examination."
      ::= 38

upsTrapOutputOverVoltage TRAP-TYPE
      ENTERPRISE upsG9000-G2020v2 
      DESCRIPTION
          "Fault: Output Overvoltage (VLOV). Contact your Toshiba authorized service center for examination."
      ::= 39

upsTrapOutputOverVoltageClear TRAP-TYPE
      ENTERPRISE upsG9000-G2020v2 
      DESCRIPTION
          "Fault Clear: Output Overvoltage (VLOV). Contact your Toshiba authorized service center for examination."
      ::= 40

upsTrapInverterOverload TRAP-TYPE
      ENTERPRISE upsG9000-G2020v2 
      DESCRIPTION
          "Fault: UPS Overload, short time over-current has been detected during On-Line operation. Decrease Load."
      ::= 41

upsTrapInverterOverloadClear TRAP-TYPE
      ENTERPRISE upsG9000-G2020v2 
      DESCRIPTION
          "Fault Clear: UPS Overload, short time over-current has been detected during On-Line operation. Decrease Load."
      ::= 42

upsTrapInverterOvercurrent TRAP-TYPE
      ENTERPRISE upsG9000-G2020v2 
      DESCRIPTION
          "Fault: Inverter Overcurrent. Contact your Toshiba authorized service center for examination."
      ::= 43

upsTrapInverterOvercurrentClear TRAP-TYPE
      ENTERPRISE upsG9000-G2020v2 
      DESCRIPTION
          "Fault Clear: Inverter Overcurrent. Contact your Toshiba authorized service center for examination."
      ::= 44

upsTrapRemotEyeCommError TRAP-TYPE
      ENTERPRISE upsG9000-G2020v2 
      DESCRIPTION
          "Warning: RemotEye UPS communication error."
      ::= 45

upsTrapRemotEyeCommErrorClear TRAP-TYPE
      ENTERPRISE upsG9000-G2020v2 
      DESCRIPTION
          "Warning Clear:RemotEye UPS communication error."
      ::= 46
	  
upsTrapFanFailureFault TRAP-TYPE
      ENTERPRISE upsG9000-G2020v2 
      DESCRIPTION
          "Fault: Fan Failure fault."
      ::= 47
	  
upsTrapFanFailureFaultClear TRAP-TYPE
      ENTERPRISE upsG9000-G2020v2 
      DESCRIPTION
          "Fault Clear: Fan Failure fault."
      ::= 48
	  
upsTrapInputVoltageAbnormal TRAP-TYPE
      ENTERPRISE upsG9000-G2020v2 
      DESCRIPTION
          "Warning: Input voltage voltage is abnormal."
      ::= 49
	  
upsTrapInputVoltageAbnormalClear TRAP-TYPE
      ENTERPRISE upsG9000-G2020v2 
      DESCRIPTION
          "Warning Clear: Input voltage voltage is abnormal."
      ::= 50

upsTrapBatteryCB2Opened TRAP-TYPE
      ENTERPRISE upsG9000-G2020v2 
      DESCRIPTION
          "Warning: Battery CB2 Opened."
      ::= 51
	  
upsTrapBatteryCB2OpenedClear TRAP-TYPE
      ENTERPRISE upsG9000-G2020v2 
      DESCRIPTION
          "Warning Clear: Battery CB2 Opened."
      ::= 52

upsTrapConverterInputContactorCB1Opened TRAP-TYPE
      ENTERPRISE upsG9000-G2020v2 
      DESCRIPTION
          "Warning: Converter Input Contactor CB1 Opened."
      ::= 53
	  
upsTrapConverterInputContactorCB1OpenedClear TRAP-TYPE
      ENTERPRISE upsG9000-G2020v2 
      DESCRIPTION
          "Warning Clear: Converter Input Contactor CB1 Opened."
      ::= 54
	  
upsTrap52SOpened TRAP-TYPE
      ENTERPRISE upsG9000-G2020v2 
      DESCRIPTION
          "Warning: 52S Opened."
      ::= 55
	  
upsTrap52SOpenedClear TRAP-TYPE
      ENTERPRISE upsG9000-G2020v2 
      DESCRIPTION
          "Warning Clear: 52S Opened."
      ::= 56
	  
upsTrap52COpened TRAP-TYPE
      ENTERPRISE upsG9000-G2020v2 
      DESCRIPTION
          "Warning: 52C Opened."
      ::= 57
	  
upsTrap52COpenedClear TRAP-TYPE
      ENTERPRISE upsG9000-G2020v2 
      DESCRIPTION
          "Warning Clear: 52C Opened."
      ::= 58

upsTrapFanFailureWarning TRAP-TYPE
      ENTERPRISE upsG9000-G2020v2 
      DESCRIPTION
          "Warning: Fan Failure warning."
      ::= 59
	  
upsTrapFanFailureWarningClear TRAP-TYPE
      ENTERPRISE upsG9000-G2020v2 
      DESCRIPTION
          "Warning Clear: Fan Failure warning."
      ::= 60
	  
upsTrapEPOFault TRAP-TYPE
      ENTERPRISE upsG9000-G2020v2 
      DESCRIPTION
          "Fault: EPO (emergency power off) alarm."
      ::= 61
	  
upsTrapEPOFaultClear TRAP-TYPE
      ENTERPRISE upsG9000-G2020v2 
      DESCRIPTION
          "Fault Clear: EPO (emergency power off) alarm."
      ::= 62

END
