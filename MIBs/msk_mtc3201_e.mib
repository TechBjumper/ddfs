-- ============================================================================
-- MIYAKAWA.MTC3201 MIB(2009.08.18)
--
-- Copyright (c) 2007 MIYAKAWA ELECTRIC WORKS LTD.
-- All rights reserved.
-- 
-- ============================================================================

MIYAKAWA-MIB DEFINITIONS ::= BEGIN

--IMPORTS
--	MODULE-IDENTITY,
--	OBJECT-TYPE,
--	enterprises
--		FROM SNMPv2-SMI
--	;
	
    miyakawa 				MODULE-IDENTITY								-- 1.3.6.1.4.1.14703
        LAST-UPDATED	    "200908180000Z"
        ORGANIZATION	    "(C) MIYAKAWA, INC."
        CONTACT-INFO        "http://www.msk.co.jp/"
        DESCRIPTION         "TERMS-pro MTC3201 MIB"
        REVISION			"200908180000Z"
        DESCRIPTION			""
        ::= { enterprises 14703 }
	
	dsiunit				OBJECT IDENTIFIER	::= { miyakawa 2 }			-- 1.3.6.1.4.1.14703.2
	dsiSystem			OBJECT IDENTIFIER	::= { dsiunit 1 }			-- 1.3.6.1.4.1.14703.2.1
	dsiStatus 			OBJECT IDENTIFIER	::= { dsiunit 2 }			-- 1.3.6.1.4.1.14703.2.2
--	pdu 				OBJECT IDENTIFIER	:== { dsiunit 3 }			-- 1.3.6.1.4.1.14703.2.3
	sysIunit			OBJECT IDENTIFIER	::= { dsiSystem 1 }			-- 1.3.6.1.4.1.14703.2.1.1
	sysCunit			OBJECT IDENTIFIER	::= { dsiSystem 2 }			-- 1.3.6.1.4.1.14703.2.1.2
	dsiSensorTable 		OBJECT IDENTIFIER	::= { dsiStatus 2 }			-- 1.3.6.1.4.1.14703.2.2.2
	dsiSensorEntry 		OBJECT IDENTIFIER	::= { dsiSensorTable 1 }	-- 1.3.6.1.4.1.14703.2.2.2.1
	dsiSnsgp 			OBJECT IDENTIFIER	::= { dsiSensorEntry 2 }	-- 1.3.6.1.4.1.14703.2.2.2.1.2
	dsiSensorAveTable 	OBJECT IDENTIFIER	::= { dsiStatus 3 }			-- 1.3.6.1.4.1.14703.2.2.3
	dsiSensorAveEntry	OBJECT IDENTIFIER	::= { dsiSensorAveTable 1 }	-- 1.3.6.1.4.1.14703.2.2.3.1
	dsiSnsAvegp 		OBJECT IDENTIFIER	::= { dsiSensorAveEntry 2 }	-- 1.3.6.1.4.1.14703.2.2.3.1.2
	dsiSensorBtmTable 	OBJECT IDENTIFIER	::= { dsiStatus 4 }			-- 1.3.6.1.4.1.14703.2.2.4
	dsiSensorBtmEntry 	OBJECT IDENTIFIER	::= { dsiSensorBtmTable 1 }	-- 1.3.6.1.4.1.14703.2.2.4.1
	dsiSnsBtmgp 		OBJECT IDENTIFIER	::= { dsiSensorBtmEntry 2 }	-- 1.3.6.1.4.1.14703.2.2.4.1.2
	
	-- 
	-- TC6401/MTC3201/MTC501/ZTC3201
	-- 
	
	sysIunitVersion	 	OBJECT-TYPE										-- 1.3.6.1.4.1.14703.2.1.1.1
		SYNTAX			OCTET STRING ( SIZE (4) )
		MAX-ACCESS		read-only
		STATUS			current
		DESCRIPTION		"Integrate Unit Version"
		::= { sysIunit 1 }
	
	sysIunitMemory 		OBJECT-TYPE										-- 1.3.6.1.4.1.14703.2.1.1.2
		SYNTAX			INTEGER ( 1 )
		MAX-ACCESS		read-only
		STATUS			current
		DESCRIPTION		"Integrate Unit Memory Error"
		::= { sysIunit 2 }
	
	sysIunitManagerIpAddress OBJECT-TYPE								-- 1.3.6.1.4.1.14703.2.1.1.3
		SYNTAX			IpAddress
		MAX-ACCESS		read-write
		STATUS			current
		DESCRIPTION		"SNMP Manager IP Address"
		::= { sysIunit 3 }
	
	-- Sensor Peak
	
	cunitPeak01			OBJECT-TYPE
		SYNTAX			OCTET STRING ( SIZE (96) )
		MAX-ACCESS		read-only
		STATUS			current
		DESCRIPTION		"The Sensor01 of Integrate Unit"
		::= { dsiSnsgp 1 }
	
	cunitPeak02 		OBJECT-TYPE
		SYNTAX			OCTET STRING ( SIZE (96) )
		MAX-ACCESS		read-only
		STATUS			current
		DESCRIPTION		"The Sensor02 of Integrate Unit"
		::= { dsiSnsgp 2 }
	
	cunitPeak03 		OBJECT-TYPE
		SYNTAX			OCTET STRING ( SIZE (96) )
		MAX-ACCESS		read-only
		STATUS			current
		DESCRIPTION		"The Sensor03 of Integrate Unit"
		::= { dsiSnsgp 3 }
	
	cunitPeak04 		OBJECT-TYPE
		SYNTAX			OCTET STRING ( SIZE (96) )
		MAX-ACCESS		read-only
		STATUS			current
		DESCRIPTION		"The Sensor04 of Integrate Unit"
		::= { dsiSnsgp 4 }
	
	cunitPeak05 		OBJECT-TYPE
		SYNTAX			OCTET STRING ( SIZE (96) )
		MAX-ACCESS		read-only
		STATUS			current
		DESCRIPTION		"The Sensor05 of Integrate Unit"
		::= { dsiSnsgp 5 }
	
	cunitPeak06 		OBJECT-TYPE
		SYNTAX			OCTET STRING ( SIZE (96) )
		MAX-ACCESS		read-only
		STATUS			current
		DESCRIPTION		"The Sensor06 of Integrate Unit"
		::= { dsiSnsgp 6 }
	
	cunitPeak07 		OBJECT-TYPE
		SYNTAX			OCTET STRING ( SIZE (96) )
		MAX-ACCESS		read-only
		STATUS			current
		DESCRIPTION		"The Sensor07 of Integrate Unit"
		::= { dsiSnsgp 7 }
	
	cunitPeak08 		OBJECT-TYPE
		SYNTAX			OCTET STRING ( SIZE (96) )
		MAX-ACCESS		read-only
		STATUS			current
		DESCRIPTION		"The Sensor08 of Integrate Unit"
		::= { dsiSnsgp 8 }
	
	cunitPeak09 		OBJECT-TYPE
		SYNTAX			OCTET STRING ( SIZE (96) )
		MAX-ACCESS		read-only
		STATUS			current
		DESCRIPTION		"The Sensor09 of Integrate Unit"
		::= { dsiSnsgp 9 }
	
	cunitPeak10 		OBJECT-TYPE
		SYNTAX			OCTET STRING ( SIZE (96) )
		MAX-ACCESS		read-only
		STATUS			current
		DESCRIPTION		"The Sensor10 of Integrate Unit"
		::= { dsiSnsgp 10 }
	
	-- cunitPeak11 -> cunitPeak64
	
	-- Sensor Average
	
	cunitAve01 			OBJECT-TYPE
		SYNTAX			OCTET STRING ( SIZE (96) )
		MAX-ACCESS		read-only
		STATUS			current
		DESCRIPTION		"The Sensor01 of Integrate Unit"
		::= { dsiSnsAvegp 1 }
	
	cunitAve02 			OBJECT-TYPE
		SYNTAX			OCTET STRING ( SIZE (96) )
		MAX-ACCESS		read-only
		STATUS			current
		DESCRIPTION		"The Sensor02 of Integrate Unit"
		::= { dsiSnsAvegp 2 }
	
	cunitAve03 			OBJECT-TYPE
		SYNTAX			OCTET STRING ( SIZE (96) )
		MAX-ACCESS		read-only
		STATUS			current
		DESCRIPTION		"The Sensor03 of Integrate Unit"
		::= { dsiSnsAvegp 3 }
	
	cunitAve04 			OBJECT-TYPE
		SYNTAX			OCTET STRING ( SIZE (96) )
		MAX-ACCESS		read-only
		STATUS			current
		DESCRIPTION		"The Sensor04 of Integrate Unit"
		::= { dsiSnsAvegp 4 }
	
	cunitAve05 			OBJECT-TYPE
		SYNTAX			OCTET STRING ( SIZE (96) )
		MAX-ACCESS		read-only
		STATUS			current
		DESCRIPTION		"The Sensor05 of Integrate Unit"
		::= { dsiSnsAvegp 5 }
	
	cunitAve06 			OBJECT-TYPE
		SYNTAX			OCTET STRING ( SIZE (96) )
		MAX-ACCESS		read-only
		STATUS			current
		DESCRIPTION		"The Sensor06 of Integrate Unit"
		::= { dsiSnsAvegp 6 }
	
	cunitAve07 			OBJECT-TYPE
		SYNTAX			OCTET STRING ( SIZE (96) )
		MAX-ACCESS		read-only
		STATUS			current
		DESCRIPTION		"The Sensor07 of Integrate Unit"
		::= { dsiSnsAvegp 7 }
	
	cunitAve08 			OBJECT-TYPE
		SYNTAX			OCTET STRING ( SIZE (96) )
		MAX-ACCESS		read-only
		STATUS			current
		DESCRIPTION		"The Sensor08 of Integrate Unit"
		::= { dsiSnsAvegp 8 }
	
	cunitAve09 			OBJECT-TYPE
		SYNTAX			OCTET STRING ( SIZE (96) )
		MAX-ACCESS		read-only
		STATUS			current
		DESCRIPTION		"The Sensor09 of Integrate Unit"
		::= { dsiSnsAvegp 9 }
	
	cunitAve10 			OBJECT-TYPE
		SYNTAX			OCTET STRING ( SIZE (96) )
		MAX-ACCESS		read-only
		STATUS			current
		DESCRIPTION		"The Sensor10 of Integrate Unit"
		::= { dsiSnsAvegp 10 }
	
	-- cunitAve11 -> cunitAve64
	
	-- Sensor Bottom
	
	cunitBtm01 			OBJECT-TYPE
		SYNTAX			OCTET STRING ( SIZE (96) )
		MAX-ACCESS		read-only
		STATUS			current
		DESCRIPTION		"The Sensor01 of Integrate Unit"
		::= { dsiSnsBtmgp 1 }
	
	cunitBtm02 			OBJECT-TYPE
		SYNTAX			OCTET STRING ( SIZE (96) )
		MAX-ACCESS		read-only
		STATUS			current
		DESCRIPTION		"The Sensor02 of Integrate Unit"
		::= { dsiSnsBtmgp 2 }
	
	cunitBtm03 			OBJECT-TYPE
		SYNTAX			OCTET STRING ( SIZE (96) )
		MAX-ACCESS		read-only
		STATUS			current
		DESCRIPTION		"The Sensor03 of Integrate Unit"
		::= { dsiSnsBtmgp 3 }
	
	cunitBtm04 			OBJECT-TYPE
		SYNTAX			OCTET STRING ( SIZE (96) )
		MAX-ACCESS		read-only
		STATUS			current
		DESCRIPTION		"The Sensor04 of Integrate Unit"
		::= { dsiSnsBtmgp 4 }
	
	cunitBtm05 			OBJECT-TYPE
		SYNTAX			OCTET STRING ( SIZE (96) )
		MAX-ACCESS		read-only
		STATUS			current
		DESCRIPTION		"The Sensor05 of Integrate Unit"
		::= { dsiSnsBtmgp 5 }
	
	cunitBtm06 			OBJECT-TYPE
		SYNTAX			OCTET STRING ( SIZE (96) )
		MAX-ACCESS		read-only
		STATUS			current
		DESCRIPTION		"The Sensor06 of Integrate Unit"
		::= { dsiSnsBtmgp 6 }
	
	cunitBtm07 			OBJECT-TYPE
		SYNTAX			OCTET STRING ( SIZE (96) )
		MAX-ACCESS		read-only
		STATUS			current
		DESCRIPTION		"The Sensor07 of Integrate Unit"
		::= { dsiSnsBtmgp 7 }
	
	cunitBtm08 			OBJECT-TYPE
		SYNTAX			OCTET STRING ( SIZE (96) )
		MAX-ACCESS		read-only
		STATUS			current
		DESCRIPTION		"The Sensor08 of Integrate Unit"
		::= { dsiSnsBtmgp 8 }
	
	cunitBtm09 			OBJECT-TYPE
		SYNTAX			OCTET STRING ( SIZE (96) )
		MAX-ACCESS		read-only
		STATUS			current
		DESCRIPTION		"The Sensor09 of Integrate Unit"
		::= { dsiSnsBtmgp 9 }
	
	cunitBtm10 			OBJECT-TYPE
		SYNTAX			OCTET STRING ( SIZE (96) )
		MAX-ACCESS		read-only
		STATUS			current
		DESCRIPTION		"The Sensor10 of Integrate Unit"
		::= { dsiSnsBtmgp 10 }
	
	-- cunitBtm11 -> cunitBtm64
	
END
