-- MIB file for Monnit Ethernet Gateway 4, created 10-Apr-2019 by EDR

MONNITEGW4MIB DEFINITIONS ::= BEGIN

IMPORTS
		enterprises
        FROM RFC1155-SMI
		OBJECT-TYPE
        FROM RFC-1212
		TRAP-TYPE
        FROM RFC-1215
		DisplayString
        FROM RFC1213-MIB
		TEXTUAL-CONVENTION
	 			FROM SNMPv2-TC;

monnitManufacturer			OBJECT IDENTIFIER ::= { enterprises 41542 }
-- DESCRIPTION
--    "Devices manufactured by Monnit Corporation.
--    Please visit: www.monnit.com"

monnitEGW4				OBJECT IDENTIFIER ::= { monnitManufacturer 2 }
-- DESCRIPTION
--    "The EGW4 is a product supporting the delivery of data from wireless
--    sensor devices over an Ethernet connection through the SNMP v1 protocol
--     and others. This gateway is major release version 4."

monnitEGW4GatewaySpecificInfo OBJECT IDENTIFIER ::= { monnitEGW4 1 }
-- DESCRIPTION
--    "The EGW4 reports certain information specific to the particular
--    gateway device, which are reported under this hierarchy."

--
-- Gateway-specific section
--

monnitEGW4GatewayID OBJECT-TYPE
    SYNTAX        Unsigned32
    ACCESS    		read-only
    STATUS        mandatory
    DESCRIPTION
				"The serial number identifier of the gateway device assigned and
				programmed by the manufacturer. This will ordinarily be printed
				on a label on the housing of the device."
    ::= {monnitEGW4GatewaySpecificInfo 1}

monnitEGW4GatewayFirmwareVerNo OBJECT-TYPE
    SYNTAX        OCTET STRING
    ACCESS    		read-only
    STATUS        mandatory
    DESCRIPTION
        "The version number of the firmware of the gateway device. Note that
        this can change upon a firmware update."
    ::= {monnitEGW4GatewaySpecificInfo 2}

monnitEGW4GatewaySensorDeviceCount OBJECT-TYPE
    SYNTAX        INTEGER(0..256)
    ACCESS    		read-only
    STATUS        mandatory
    DESCRIPTION
        "The number of sensors registered to the gateway, i.e. on its netlist.
        Note that this can change as sensors are added or removed."
    ::= {monnitEGW4GatewaySpecificInfo 3}

monnitEGW4GatewayTrapIPAddr OBJECT-TYPE
    SYNTAX        IpAddress
    ACCESS    		read-only
    STATUS        mandatory
    DESCRIPTION
        "The configured destination IP address for trap messages from this
        gateway."
    ::= {monnitEGW4GatewaySpecificInfo 4}

monnitEGW4GatewaySensorTrapPort OBJECT-TYPE
    SYNTAX        INTEGER(0..65535)
    ACCESS    		read-only
    STATUS        mandatory
    DESCRIPTION
        "The configured IP port for trap messages from this gateway."
    ::= {monnitEGW4GatewaySpecificInfo 5}

--
-- Definitions of sensor-specific informational types
--

MonnitEGW4SensorID ::= TEXTUAL-CONVENTION
		STATUS        mandatory
		DESCRIPTION
				"The serial number identifier of the sensor device assigned and
				programmed by the manufacturer. This will ordinarily be printed
				on a label on the housing of the device."
		SYNTAX				Unsigned32

MonnitEGW4SensorRegistrationIndex ::= TEXTUAL-CONVENTION
		STATUS        mandatory
		DESCRIPTION
				"The index number of a sensor device in a gateway's sensor
				registration list. This is determined by the order in which a set
				of sensors has been registered, but will not change so long as
				the list remains fixed. This is included for legacy applications:
				please consider using the more convenient
				monnitEGW4SensorInfoTranslatedFormat and
				monnitEGW4SensorInfoBySensorID hierarchies."
		SYNTAX				INTEGER(0..255)

MonnitEGW4DatumNo ::= TEXTUAL-CONVENTION
		STATUS        mandatory
		DESCRIPTION
				"The datum number of a sequence of data readings from a sensor. The
				range of this type depends upon the number of datums reported by
				a sensor device. Thus, a 3-axis accelerometer sensor might report
				three datums for the X, Y and Z axes, and the datums would range
				from 1 to 3. For a simple temperature sensor reporting one
				reading, this value would always be 1."
		SYNTAX				INTEGER(1..8)

MonnitEGW4SensorDeviceType ::= TEXTUAL-CONVENTION
		STATUS        mandatory
		DESCRIPTION
				"The textual description of the type of the sensor device."
		SYNTAX				OCTET STRING

MonnitEGW4DatumNumber ::= TEXTUAL-CONVENTION
		STATUS        mandatory
		DESCRIPTION
				"The number of a datum in a set of datums comprising a sensor reading.
				For sensors reporting one datum, this will always be one. Otherwise
				it will be a number between 1 and the number of datums reported by
				the particular type of sensor."
		SYNTAX				INTEGER

MonnitEGW4SensorDeviceReadingTranslatedValue ::= TEXTUAL-CONVENTION
		STATUS        mandatory
		DESCRIPTION
				"The value of a sensor reading, in textual format, translated
				according to sensor and datum types. These formats can include
				integers, fixed-point, and binary values. In several examples:
				a pulse counter might report '12345', a current sensor might report
				'1.43', and a door closed sensor might report 'Yes'."
		SYNTAX				OCTET STRING

MonnitEGW4SensorDeviceReadingTranslatedUnits ::= TEXTUAL-CONVENTION
		STATUS        mandatory
		DESCRIPTION
				"The units or scale of value of a sensor reading, reported in textual
				format. In several examples: a pulse counter might report 'Count',
				a current sensor might report 'A', and a door sensor might report
				'Closed'."
		SYNTAX				OCTET STRING

MonnitEGW4SensorDeviceReadingValuesAll ::= TEXTUAL-CONVENTION
		STATUS        mandatory
		DESCRIPTION
				"All of the datums for the most recent reading of the sensor device,
				separated by commas, in textual format. For example, a report for a
				temperature and humidity sensor might read '20.3, 35' indicating
				20.3 degrees at 35 percent humidity. If only one datum is reported
				by a sensor device, e.g. for a simple temperature sensor, it will be
				reported singly with no commas."
		SYNTAX				OCTET STRING

MonnitEGW4SensorDeviceReadingUnitsAll ::= TEXTUAL-CONVENTION
		STATUS        mandatory
		DESCRIPTION
				"All of the units corresponding to the datums for the most recent
				reading of the sensor device, separated by commas, in textual
				format. For example, for a sensor reporting temperature and
				humidity this might read 'degrees C, %RH'"
		SYNTAX				OCTET STRING

MonnitEGW4SensorDeviceReadingUntranslated ::= TEXTUAL-CONVENTION
		STATUS        mandatory
		DESCRIPTION
				"The untranslated data block received from a sensor, in hexadecimal
				format. This may be used where a translating function isn't yet
				present, and for development purposes. Most users should use the
				translated values delivered in the format of
				MonnitEGW4SensorDeviceReadingValuesAll."
		SYNTAX				OCTET STRING

MonnitEGW4SensorDeviceReadingU32Value ::= TEXTUAL-CONVENTION
		STATUS        mandatory
		DESCRIPTION
				"Either a single sensor value of up to 32 bits, or half of a
				64-bit value. Thus where a sensor value is reportable in a
				single Unsigned32, one OID is sufficient to gather that value.
				Where more than 32 bits are needed, the value is reported in two
				successive values of type MonnitEGW4SensorDeviceReadingU32Value.
				Where a set of datums is reported, those datums are reported
				beginning with the lowest-numbered OID proceeding sequentially
				through the highest. Thus were a sensor to report a single-bit
				value A followed by 32-bit and a 64 bit ones B and C, and where
				OIDS x.10 through x.17 were used for reporting values, the value A
				would be encoded in x.10, B in x.11 and C in x.12 (low-order bits)
				and x.13 (high-order bits). These values are merely converted
				from sensor-specific internal formats to integers, and not beyond
				to human-readable formats.
				Furthermore, where for a sensor datums extend only part-way through
				the available U32Value OIDs, the ones unused may be filled with 0.
				Where an SNMP walk is performed, the gateway may not traverse these
				unused OIDs."
		SYNTAX				Unsigned32

MonnitEGW4SensorDeviceReadingAge ::= TEXTUAL-CONVENTION
		STATUS        mandatory
		DESCRIPTION
				"The age of the sensor report received most recently from a sensor.
				That time is reported as the number of seconds between the time of
				the sensor report and the time this information is requested."
		SYNTAX				Unsigned32

MonnitEGW4SensorDeviceReadingAlarming ::= TEXTUAL-CONVENTION
		STATUS        mandatory
		DESCRIPTION
				"Either 'Alarming' or 'Not alarming'. A device will report an alarm
				if it is programmed with a threshold found to be exceeded. Examples:
				a temperature sensor for a refrigeration unit can be programmed to
				alarm if the measured temperature rises above a threshold, and
				a door sensor might alarm if a security door is opened."
		SYNTAX				OCTET STRING

--
-- Sensor-specific section, translated format
--

monnitEGW4SensorInfoTranslatedFormatTable OBJECT-TYPE
		SYNTAX				SEQUENCE OF monnitEGW4SensorInfoTranslatedFormatEntry
		ACCESS    		not-accessible
		STATUS        mandatory
		DESCRIPTION
				"The (conceptual) table containing sensor-specific information in an
 				easy-to-use translated string format, indexed by sensor ID is reported
 				under this hierarchy. Sensor data is translated by the gateway from
 				sensor-internal format to human-readable and scriptable values. Use of
 				this format is preferred for most users. The gateway will report the
 				most current information received from sensors, according to their
 				programmed reporting period or heartbeat. When using this section
 				through getRequests or getNextRequests, successive polling is required
 				to keep sensor data current. This table can change as sensors are
 				added or removed. If queried, this OID will return the number of rows
 				in the table, which is the number of sensors registered to this gateway."
		::= { monnitEGW4 2 }

-- Table portion consisting of non-datum-specific info

monnitEGW4SensorInfoTranslatedFormatEntry OBJECT-TYPE
		SYNTAX				MonnitEGW4SensorInfoTranslatedFormatEntry
		ACCESS    		not-accessible
		STATUS        mandatory
		DESCRIPTION
				"An entry (conceptual row) in the Translated Format Table containing
				the latest sensor state for a single sensor."
		INDEX   { monnitEGW4SensorInfoTranslatedFormatSensorDeviceID }
		::= { monnitEGW4SensorInfoTranslatedFormatTable 1 }

MonnitEGW4SensorInfoTranslatedFormatEntry ::= SEQUENCE {
		monnitEGW4SensorInfoTranslatedFormatSensorDeviceID MonnitEGW4SensorID,
		monnitEGW4SensorInfoTranslatedFormatSensorDeviceType MonnitEGW4SensorDeviceType,
		monnitEGW4SensorInfoTranslatedFormatSensorDeviceReadingValuesAll MonnitEGW4SensorDeviceReadingValuesAll,
		monnitEGW4SensorInfoTranslatedFormatSensorDeviceReadingUnitsAll MonnitEGW4SensorDeviceReadingUnitsAll,
		monnitEGW4SensorInfoTranslatedFormatSensorDeviceRptUT MonnitEGW4SensorDeviceReadingUntranslated,
		monnitEGW4SensorInfoTranslatedFormatSensorDeviceReadingTime DisplayString,
		monnitEGW4SensorInfoTranslatedFormatSensorDeviceReadingAge MonnitEGW4SensorDeviceReadingAge,
		monnitEGW4SensorInfoTranslatedFormatSensorDeviceTypeNo DisplayString,
		monnitEGW4SensorInfoTranslatedFormatSensorDeviceRFStrength DisplayString,
		monnitEGW4SensorInfoTranslatedFormatSensorDeviceActive DisplayString,
		monnitEGW4SensorInfoTranslatedFormatSensorDeviceAlarming MonnitEGW4SensorDeviceReadingAlarming,
		monnitEGW4SensorInfoTranslatedFormatSensorDeviceVoltage DisplayString,
		monnitEGW4SensorInfoTranslatedFormatSensorDeviceWDIndexNo DisplayString
}

monnitEGW4SensorInfoTranslatedFormatSensorDeviceID OBJECT-TYPE
    SYNTAX        MonnitEGW4SensorID
    ACCESS    		read-only
    STATUS        mandatory
    DESCRIPTION
				"The serial number identifier of the sensor device assigned and
				programmed by the manufacturer. This will ordinarily be printed
				on a label on the housing of the device."
		::= { monnitEGW4SensorInfoTranslatedFormatEntry 1 }

monnitEGW4SensorInfoTranslatedFormatSensorDeviceType OBJECT-TYPE
    SYNTAX        MonnitEGW4SensorDeviceType
    ACCESS    		read-only
    STATUS        mandatory
    DESCRIPTION
				"The textual description of the type of the sensor device."
		::= {monnitEGW4SensorInfoTranslatedFormatEntry 2 }

monnitEGW4SensorInfoTranslatedFormatSensorDeviceReadingValuesAll OBJECT-TYPE
    SYNTAX        MonnitEGW4SensorDeviceReadingValuesAll
    ACCESS    		read-only
    STATUS        mandatory
    DESCRIPTION
				"All of the datums for the most recent reading of the sensor device,
				separated by commas, in textual format. For example, a report for a
				temperature and humidity sensor might read '20.3, 35' indicating
				20.3 degrees at 35 percent humidity. If only one datum is reported
				by a sensor device, e.g. for a simple temperature sensor, it will be
				reported singly with no commas. The use of this OID is recommended
				for most users, rather than the single value ones, because all values
				can be retrieved atomically from a sensor in one SNMP request."
		::= {monnitEGW4SensorInfoTranslatedFormatEntry 3 }

monnitEGW4SensorInfoTranslatedFormatSensorDeviceReadingUnitsAll OBJECT-TYPE
    SYNTAX        MonnitEGW4SensorDeviceReadingUnitsAll
    ACCESS    		read-only
    STATUS        mandatory
    DESCRIPTION
				"All of the units corresponding to the datums for the most recent
				reading of the sensor device, separated by commas, in textual
				format. For example, for a sensor reporting temperature and
				humidity this might read 'degrees C, %RH'"
		::= {monnitEGW4SensorInfoTranslatedFormatEntry 4 }

monnitEGW4SensorInfoTranslatedFormatSensorDeviceRptUT OBJECT-TYPE
    SYNTAX        MonnitEGW4SensorDeviceReadingUntranslated
    ACCESS    		read-only
    STATUS        mandatory
    DESCRIPTION
				"The untranslated data block received from a sensor, in hexadecimal
				format. This may be used where a translating function isn't yet
				present, and for development purposes. Most users should use the
				translated values delivered in the format of
				MonnitEGW4SensorDeviceReadingValuesAll."
		::= {monnitEGW4SensorInfoTranslatedFormatEntry 5 }

monnitEGW4SensorInfoTranslatedFormatSensorDeviceReadingTime OBJECT-TYPE
    SYNTAX        DisplayString
    ACCESS    		read-only
    STATUS        mandatory
    DESCRIPTION
				"The time of the sensor report received most recently from a sensor.
				That time is reported as the number of seconds elapsed since the epoch
				of the gateway, which is presently Jan. 1, 2010."
		::= {monnitEGW4SensorInfoTranslatedFormatEntry 6 }

monnitEGW4SensorInfoTranslatedFormatSensorDeviceReadingAge OBJECT-TYPE
    SYNTAX        MonnitEGW4SensorDeviceReadingAge
    ACCESS    		read-only
    STATUS        mandatory
    DESCRIPTION
				"The age of the sensor report received most recently from a sensor.
				That time is reported as the number of seconds between the time of
				the sensor report and the time this information is requested."
		::= {monnitEGW4SensorInfoTranslatedFormatEntry 7 }

monnitEGW4SensorInfoTranslatedFormatSensorDeviceTypeNo OBJECT-TYPE
    SYNTAX        DisplayString
    ACCESS    		read-only
    STATUS        mandatory
    DESCRIPTION
				"The manufacturer's type number that identifies the kind of sensor."
		::= {monnitEGW4SensorInfoTranslatedFormatEntry 8 }

monnitEGW4SensorInfoTranslatedFormatSensorDeviceRFStrength OBJECT-TYPE
    SYNTAX        DisplayString
    ACCESS    		read-only
    STATUS        mandatory
    DESCRIPTION
				"The signal strength, in dB, of the radio link between the gateway
				and the particular sensor, as measured at the time of the most recent
				sensor report."
		::= {monnitEGW4SensorInfoTranslatedFormatEntry 9 }

monnitEGW4SensorInfoTranslatedFormatSensorDeviceActive OBJECT-TYPE
    SYNTAX        DisplayString
    ACCESS    		read-only
    STATUS        mandatory
    DESCRIPTION
				"Either 'Active' or '' (an empty string). A sensor will be reported
				active if it has recently communicated with the gateway since the last
				reboot. If a sensor device does not show active, it is likely because
				(1) the sensor lacks a power source, (2) the sensor is not in
				proximity to the gateway, or (3) the gateway has recently been
				powered on, and the sensor hasn't yet communicated."
		::= {monnitEGW4SensorInfoTranslatedFormatEntry 10 }

monnitEGW4SensorInfoTranslatedFormatSensorDeviceAlarming OBJECT-TYPE
    SYNTAX        MonnitEGW4SensorDeviceReadingAlarming
    ACCESS    		read-only
    STATUS        mandatory
    DESCRIPTION
				"Either 'Alarming' or 'Not alarming'. A device will report an alarm
				if it is programmed with a threshold found to be exceeded. Examples:
				a temperature sensor for a refrigeration unit can be programmed to
				alarm if the measured temperature rises above a threshold, and
				a door sensor might alarm if a security door is opened."
		::= {monnitEGW4SensorInfoTranslatedFormatEntry 11 }

monnitEGW4SensorInfoTranslatedFormatSensorDeviceVoltage OBJECT-TYPE
    SYNTAX        DisplayString
    ACCESS    		read-only
    STATUS        mandatory
    DESCRIPTION
				"The value of the voltage of the supply powering a sensor device.
				Ordinarily this will report the voltage at the battery terminals of
				a sensor. It is provided mainly so batteries can be changed when
				depleted."
		::= {monnitEGW4SensorInfoTranslatedFormatEntry 12 }

monnitEGW4SensorInfoTranslatedFormatSensorDeviceWDIndexNo OBJECT-TYPE
    SYNTAX        DisplayString
    ACCESS    		read-only
    STATUS        mandatory
    DESCRIPTION
				"The index number of the sensor in the gateway's sensor registration
				table. This is the number used in referencing the sensor in the
				monnitEGW4SensorInformationBySensorRegisOrder
				hierarchy."
		::= {monnitEGW4SensorInfoTranslatedFormatEntry 13 }

-- Table portion consisting of datum-specific info (single values and units addressed by device ID and datum)

monnitEGW4SensorInfoTranslatedFormatByDatumNumberEntry OBJECT-TYPE
		SYNTAX				MonnitEGW4SensorInfoTranslatedFormatByDatumNumberEntry
		ACCESS    		not-accessible
		STATUS        mandatory
		DESCRIPTION
				"An entry (conceptual row) in the Translated Format Table containing
				the sensor datums, indexed by a sensor ID and datum number."
		INDEX   { monnitEGW4SensorInfoTranslatedFormatSensorDeviceID,
							monnitEGW4SensorInfoTranslatedFormatByDatumNumberDatumNumber }
		::= { monnitEGW4SensorInfoTranslatedFormatTable 2 }

MonnitEGW4SensorInfoTranslatedFormatByDatumNumberEntry ::= SEQUENCE {
		monnitEGW4SensorInfoTranslatedFormatByDatumNumberSensorDeviceID MonnitEGW4SensorID,
		monnitEGW4SensorInfoTranslatedFormatByDatumNumberDatumNumber MonnitEGW4DatumNumber,
		monnitEGW4SensorInfoTranslatedFormatByDatumNumberReadingValue MonnitEGW4SensorDeviceReadingTranslatedValue,
		monnitEGW4SensorInfoTranslatedFormatByDatumNumberReadingUnits MonnitEGW4SensorDeviceReadingTranslatedUnits
}

monnitEGW4SensorInfoTranslatedFormatByDatumNumberSensorDeviceID OBJECT-TYPE
    SYNTAX        MonnitEGW4SensorID
    ACCESS    		read-only
    STATUS        mandatory
    DESCRIPTION
				"The serial number identifier of the sensor device assigned and
				programmed by the manufacturer. This will ordinarily be printed
				on a label on the housing of the device."
		::= { monnitEGW4SensorInfoTranslatedFormatByDatumNumberEntry 1 }

monnitEGW4SensorInfoTranslatedFormatByDatumNumberDatumNumber OBJECT-TYPE
		SYNTAX        MonnitEGW4DatumNumber
   	ACCESS    		read-only
   	STATUS        mandatory
   	DESCRIPTION
				"The number of a datum in a set of datums comprising a sensor reading.
				For sensors reporting one datum, this will always be one. Otherwise
				it will be a number between 1 and the number of datums reported by
				the particular type of sensor."
		::= { monnitEGW4SensorInfoTranslatedFormatByDatumNumberEntry 2 }

monnitEGW4SensorInfoTranslatedFormatByDatumNumberReadingValue OBJECT-TYPE
		SYNTAX        MonnitEGW4SensorDeviceReadingTranslatedValue
   	ACCESS    		read-only
   	STATUS        mandatory
   	DESCRIPTION
				"The value of a sensor reading, in textual format, translated
 				according to sensor and datum types. These formats can include
				integers, fixed-point, and binary values. In several examples:
				a pulse counter might report '12345', a current sensor might report
				'1.43', and a door sensor might report 'closed'."
		::= { monnitEGW4SensorInfoTranslatedFormatByDatumNumberEntry 3 }

monnitEGW4SensorInfoTranslatedFormatByDatumNumberReadingUnits OBJECT-TYPE
		SYNTAX        MonnitEGW4SensorDeviceReadingTranslatedUnits
   	ACCESS    		read-only
   	STATUS        mandatory
   	DESCRIPTION
				"The units or scale of value of a sensor reading, reported in textual
				format. In several examples: a pulse counter might report 'Count',
				a current sensor might report 'A', and a door sensor might report
				'Closed'."
		::= { monnitEGW4SensorInfoTranslatedFormatByDatumNumberEntry 4 }

--
-- Sensor-specific section, untranslated legacy format, by sensor ID
--

monnitEGW4SensorInfoBySensorIDTable OBJECT-TYPE
		SYNTAX				SEQUENCE OF monnitEGW4SensorInfoBySensorIDSensorEntry
		ACCESS    		not-accessible
		STATUS        mandatory
		DESCRIPTION
				"The (conceptual) table containing sensor information in a legacy
 				untranslated numeric format, addressed by sensor ID. This is provided
 				for users who need a precise match of the format of the older EGW1
 				platform. The gateway will report the most current information received
 				from sensors, according to their programmed reporting period or
 				heartbeat. A more convenient format to new users is available under
				the monnitEGW4SensorInfoTranslatedFormat. If queried, this
				OID will return the number of rows in the table, which is the number
				of sensors registered to this gateway."
		::= { monnitEGW4 3 }

monnitEGW4SensorInfoBySensorIDEntry OBJECT-TYPE
		SYNTAX				MonnitEGW4SensorInfoBySensorIDEntry
		ACCESS    		not-accessible
		STATUS        mandatory
		DESCRIPTION
				"An entry (conceptual row) in the untranslated by-sensor-ID-order
 				table containing the latest sensor state for a single sensor."
		INDEX   { monnitEGW4SensorInfoBySensorIDSensorDeviceID }
		::= { monnitEGW4SensorInfoBySensorIDTable 1 }

MonnitEGW4SensorInfoBySensorIDEntry ::= SEQUENCE {
		monnitEGW4SensorInfoBySensorIDSensorDeviceID Unsigned32,
		monnitEGW4SensorInfoBySensorIDSensorDeviceWDIndexNo INTEGER,
		monnitEGW4SensorInfoBySensorIDSensorDeviceTypeNo INTEGER,
		monnitEGW4SensorInfoBySensorIDSensorDeviceReadingAge Unsigned32,
		monnitEGW4SensorInfoBySensorIDSensorDeviceActive INTEGER,
		monnitEGW4SensorInfoBySensorIDSensorDeviceAlarming INTEGER,
		monnitEGW4SensorInfoBySensorIDSensorDeviceVoltage INTEGER,
		monnitEGW4SensorInfoBySensorIDSensorDeviceRFStrength INTEGER,
		monnitEGW4SensorInfoBySensorIDSensorDeviceRptUT DisplayString,
		monnitEGW4SensorInfoBySensorIDSensorDeviceReadingValue1 MonnitEGW4SensorDeviceReadingU32Value,
		monnitEGW4SensorInfoBySensorIDSensorDeviceReadingValue2 MonnitEGW4SensorDeviceReadingU32Value,
		monnitEGW4SensorInfoBySensorIDSensorDeviceReadingValue3 MonnitEGW4SensorDeviceReadingU32Value,
		monnitEGW4SensorInfoBySensorIDSensorDeviceReadingValue4 MonnitEGW4SensorDeviceReadingU32Value,
		monnitEGW4SensorInfoBySensorIDSensorDeviceReadingValue5 MonnitEGW4SensorDeviceReadingU32Value,
		monnitEGW4SensorInfoBySensorIDSensorDeviceReadingValue6 MonnitEGW4SensorDeviceReadingU32Value,
		monnitEGW4SensorInfoBySensorIDSensorDeviceReadingValue7 MonnitEGW4SensorDeviceReadingU32Value,
		monnitEGW4SensorInfoBySensorIDSensorDeviceReadingValue8 MonnitEGW4SensorDeviceReadingU32Value
}

monnitEGW4SensorInfoBySensorIDSensorDeviceID OBJECT-TYPE
     SYNTAX				Unsigned32
     ACCESS    		read-only
     STATUS       mandatory
     DESCRIPTION
 				"The serial number identifier of the sensor device assigned and
 				programmed by the manufacturer. This will ordinarily be printed
 				on a label on the housing of the device."
		INDEX   { MonnitEGW4SensorID }
 		::= {monnitEGW4SensorInfoBySensorIDEntry 1 }

monnitEGW4SensorInfoBySensorIDSensorDeviceWDIndexNo OBJECT-TYPE
    SYNTAX				INTEGER(0..255)
    ACCESS    		read-only
    STATUS       mandatory
    DESCRIPTION
 				"The index number of the sensor in the gateway's sensor registration
 				table. This is the number used in referencing the sensor in the
 				monnitEGW4SensorInfoBySensorRegisOrder
 				hierarchy."
		INDEX   { MonnitEGW4SensorID }
 		::= {monnitEGW4SensorInfoBySensorIDEntry 2 }

monnitEGW4SensorInfoBySensorIDSensorDeviceTypeNo OBJECT-TYPE
     SYNTAX       INTEGER(1..65535)
     ACCESS    		read-only
     STATUS       mandatory
     DESCRIPTION
 				"The manufacturer's type number that identifies the kind of sensor."
		INDEX   { MonnitEGW4SensorID }
 		::= {monnitEGW4SensorInfoBySensorIDEntry 3 }

monnitEGW4SensorInfoBySensorIDSensorDeviceReadingAge OBJECT-TYPE
     SYNTAX       Unsigned32
     ACCESS    		read-only
     STATUS       mandatory
     DESCRIPTION
 				"The age of the sensor report received most recently from a sensor.
 				That time is reported as the number of seconds between the time of
 				the sensor report and the time this information is requested."
		INDEX   { MonnitEGW4SensorID }
 		::= {monnitEGW4SensorInfoBySensorIDEntry 4 }

monnitEGW4SensorInfoBySensorIDSensorDeviceActive OBJECT-TYPE
     SYNTAX       INTEGER(0..1)
     ACCESS    		read-only
     STATUS       mandatory
     DESCRIPTION
 				"Either 1 (active) or 0 (inactive). A sensor will be reported active
				if it has recently communicated with the gateway since the last
 				reboot. If a sensor device does not show active, it is likely because
 				(1) the sensor lacks a power source, (2) the sensor is not in
 				proximity to the gateway, or (3) the gateway has recently been
 				powered on, and the sensor hasn't yet communicated."
		INDEX   { MonnitEGW4SensorID }
 		::= {monnitEGW4SensorInfoBySensorIDEntry 5 }

monnitEGW4SensorInfoBySensorIDSensorDeviceAlarming OBJECT-TYPE
		 SYNTAX       INTEGER(0..1)
     ACCESS    		read-only
     STATUS       mandatory
     DESCRIPTION
 				"Either 1 (alarming) or 0 (not alarming)'. A device will report an
				alarm if it is programmed with a threshold found to be exceeded.
				Examples: a temperature sensor for a refrigeration unit can be
				programmed to alarm if the measured temperature rises above a
				threshold, and a door sensor might alarm if a security door is opened."
		INDEX   { MonnitEGW4SensorID }
 		::= {monnitEGW4SensorInfoBySensorIDEntry 6 }

monnitEGW4SensorInfoBySensorIDSensorDeviceVoltage OBJECT-TYPE
		SYNTAX        INTEGER(0..255)
    ACCESS    		read-only
    STATUS        mandatory
    DESCRIPTION
				"A value representing the voltage of the supply powering a sensor
				device. Ordinarily this will report the voltage at the battery
				terminals of a sensor. It is provided mainly so batteries can be
				changed when depleted. The formula for calculating the voltage from
				this number is: voltage=(150 + v) / 10.0."
		INDEX   { MonnitEGW4SensorID }
 		::= {monnitEGW4SensorInfoBySensorIDEntry 7 }

monnitEGW4SensorInfoBySensorIDSensorDeviceRFStrength OBJECT-TYPE
     SYNTAX       INTEGER(-128..127)
     ACCESS    		read-only
     STATUS       mandatory
     DESCRIPTION
 				"The signal strength, in dB, of the radio link between the gateway
 				and the particular sensor, as measured at the time of the most recent
 				sensor report."
		INDEX   { MonnitEGW4SensorID }
 		::= {monnitEGW4SensorInfoBySensorIDEntry 8 }

monnitEGW4SensorInfoBySensorIDSensorDeviceRptUT OBJECT-TYPE
     SYNTAX       DisplayString
     ACCESS    		read-only
     STATUS       mandatory
     DESCRIPTION
 				"The untranslated data block received from a sensor, in hexadecimal
 				format. This may be used where a translating function isn't yet
 				present, and for development purposes. Most users should use the
				translated values delivered in the format of
				MonnitEGW4SensorDeviceReadingValuesAll."
		INDEX   { MonnitEGW4SensorID }
 		::= {monnitEGW4SensorInfoBySensorIDEntry 9 }

monnitEGW4SensorInfoBySensorIDSensorDeviceReadingValue1 OBJECT-TYPE
    SYNTAX		MonnitEGW4SensorDeviceReadingU32Value
    ACCESS		read-only
    STATUS		mandatory
    DESCRIPTION
				"The value of a single sensor reading, or one half of a 64-bit reading,
				in integer format, not translated to human-readable form. See
				MonnitEGW4SensorDeviceReadingU32Value for further explanation."
		INDEX   { MonnitEGW4SensorID }
 		::= {monnitEGW4SensorInfoBySensorIDEntry 10 }

monnitEGW4SensorInfoBySensorIDSensorDeviceReadingValue2 OBJECT-TYPE
    SYNTAX		MonnitEGW4SensorDeviceReadingU32Value
    ACCESS		read-only
    STATUS		mandatory
    DESCRIPTION
  			"The value of a single sensor reading, or one half of a 64-bit reading,
 				in integer format, not translated to human-readable form. See
 				MonnitEGW4SensorDeviceReadingU32Value for further explanation."
		INDEX   { MonnitEGW4SensorID }
  	::= {monnitEGW4SensorInfoBySensorIDEntry 11 }

monnitEGW4SensorInfoBySensorIDSensorDeviceReadingValue3 OBJECT-TYPE
		SYNTAX		MonnitEGW4SensorDeviceReadingU32Value
	  ACCESS		read-only
	  STATUS		mandatory
		DESCRIPTION
				"The value of a single sensor reading, or one half of a 64-bit reading,
				in integer format, not translated to human-readable form. See
				MonnitEGW4SensorDeviceReadingU32Value for further explanation."
		INDEX   { MonnitEGW4SensorID }
 		::= {monnitEGW4SensorInfoBySensorIDEntry 12 }

monnitEGW4SensorInfoBySensorIDSensorDeviceReadingValue4 OBJECT-TYPE
    SYNTAX		MonnitEGW4SensorDeviceReadingU32Value
    ACCESS		read-only
    STATUS		mandatory
    DESCRIPTION
				"The value of a single sensor reading, or one half of a 64-bit reading,
	 			in integer format, not translated to human-readable form. See
	 			MonnitEGW4SensorDeviceReadingU32Value for further explanation."
		INDEX   { MonnitEGW4SensorID }
	  ::= {monnitEGW4SensorInfoBySensorIDEntry 13 }

monnitEGW4SensorInfoBySensorIDSensorDeviceReadingValue5 OBJECT-TYPE
    SYNTAX		MonnitEGW4SensorDeviceReadingU32Value
    ACCESS		read-only
    STATUS		mandatory
    DESCRIPTION
		 		"The value of a single sensor reading, or one half of a 64-bit reading,
				in integer format, not translated to human-readable form. See
				MonnitEGW4SensorDeviceReadingU32Value for further explanation."
		INDEX   { MonnitEGW4SensorID }
 		::= {monnitEGW4SensorInfoBySensorIDEntry 14 }

monnitEGW4SensorInfoBySensorIDSensorDeviceReadingValue6 OBJECT-TYPE
    SYNTAX		MonnitEGW4SensorDeviceReadingU32Value
    ACCESS		read-only
    STATUS		mandatory
    DESCRIPTION
		  	"The value of a single sensor reading, or one half of a 64-bit reading,
		 		in integer format, not translated to human-readable form. See
		 		MonnitEGW4SensorDeviceReadingU32Value for further explanation."
		INDEX   { MonnitEGW4SensorID }
		::= {monnitEGW4SensorInfoBySensorIDEntry 15 }

monnitEGW4SensorInfoBySensorIDSensorDeviceReadingValue7 OBJECT-TYPE
    SYNTAX		MonnitEGW4SensorDeviceReadingU32Value
    ACCESS		read-only
    STATUS		mandatory
    DESCRIPTION
			 	"The value of a single sensor reading, or one half of a 64-bit reading,
				in integer format, not translated to human-readable form. See
				MonnitEGW4SensorDeviceReadingU32Value for further explanation."
		INDEX   { MonnitEGW4SensorID }
		::= {monnitEGW4SensorInfoBySensorIDEntry 16 }

monnitEGW4SensorInfoBySensorIDSensorDeviceReadingValue8 OBJECT-TYPE
    SYNTAX		MonnitEGW4SensorDeviceReadingU32Value
    ACCESS		read-only
    STATUS		mandatory
    DESCRIPTION
				"The value of a single sensor reading, or one half of a 64-bit reading,
				in integer format, not translated to human-readable form. See
				MonnitEGW4SensorDeviceReadingU32Value for further explanation."
		INDEX   { MonnitEGW4SensorID }
		::= {monnitEGW4SensorInfoBySensorIDEntry 17 }

 --
 -- Sensor-specific section, untranslated legacy format, by registration order
 --

monnitEGW4SensorInfoBySensorRegisOrderTable OBJECT-TYPE
		SYNTAX				SEQUENCE OF monnitEGW4SensorInfoBySensorRegisOrderSensorEntry
		ACCESS    		not-accessible
		STATUS        mandatory
		DESCRIPTION
				"The (conceptual) table containing an untranslated numeric format,
				addressed by sensor registration order starting at 1 and ascending by
				one, in a legacy integer format. This is provided for users who need a
 				precise match of the format and order of the older EGW1 platform.
 				The gateway will report the most current information received from
 				sensors, according to their programmed reporting period or heartbeat.
				A more convenient format to new users is available under
				the monnitEGW4SensorInfoTranslatedFormat. If queried, this
				OID will return the number of rows in the table, which is the number
				of sensors registered to this gateway."
		::= { monnitEGW4 4 }

monnitEGW4SensorInfoBySensorRegisOrderEntry OBJECT-TYPE
		SYNTAX				MonnitEGW4SensorInfoBySensorRegisOrderEntry
		ACCESS    		not-accessible
		STATUS        mandatory
		DESCRIPTION
				"An entry (conceptual row) in the untranslated by-registration-order
 				table containing the latest sensor state for a single sensor."
		INDEX   { monnitEGW4SensorInfoBySensorRegisOrderSensDevID }
		::= { monnitEGW4SensorInfoBySensorRegisOrderTable 1 }

MonnitEGW4SensorInfoBySensorRegisOrderEntry ::= SEQUENCE {
		monnitEGW4SensorInfoBySensorRegisOrderSensorDeviceID Unsigned32,
		monnitEGW4SensorInfoBySensorRegisOrderSensorDeviceWDIndexNo INTEGER,
		monnitEGW4SensorInfoBySensorRegisOrderSensorDeviceTypeNo INTEGER,
		monnitEGW4SensorInfoBySensorRegisOrderSensorDeviceReadingAge Unsigned32,
		monnitEGW4SensorInfoBySensorRegisOrderSensorDeviceActive INTEGER,
		monnitEGW4SensorInfoBySensorRegisOrderSensorDeviceAlarming INTEGER,
		monnitEGW4SensorInfoBySensorRegisOrderSensorDeviceVoltage INTEGER,
		monnitEGW4SensorInfoBySensorRegisOrderSensorDeviceRFStrength INTEGER,
		monnitEGW4SensorInfoBySensorRegisOrderSensorDeviceRptUT DisplayString,
		monnitEGW4SensorInfoBySensorRegisOrderSensorDeviceReadingValue1 MonnitEGW4SensorDeviceReadingU32Value,
		monnitEGW4SensorInfoBySensorRegisOrderSensorDeviceReadingValue2 MonnitEGW4SensorDeviceReadingU32Value,
		monnitEGW4SensorInfoBySensorRegisOrderSensorDeviceReadingValue3 MonnitEGW4SensorDeviceReadingU32Value,
		monnitEGW4SensorInfoBySensorRegisOrderSensorDeviceReadingValue4 MonnitEGW4SensorDeviceReadingU32Value,
		monnitEGW4SensorInfoBySensorRegisOrderSensorDeviceReadingValue5 MonnitEGW4SensorDeviceReadingU32Value,
		monnitEGW4SensorInfoBySensorRegisOrderSensorDeviceReadingValue6 MonnitEGW4SensorDeviceReadingU32Value,
		monnitEGW4SensorInfoBySensorRegisOrderSensorDeviceReadingValue7 MonnitEGW4SensorDeviceReadingU32Value,
		monnitEGW4SensorInfoBySensorRegisOrderSensorDeviceReadingValue8 MonnitEGW4SensorDeviceReadingU32Value
}

monnitEGW4SensorInfoBySensorRegisOrderSensDevID OBJECT-TYPE
    SYNTAX        Unsigned32
    ACCESS    		read-only
    STATUS        mandatory
    DESCRIPTION
  			"The serial number identifier of the sensor device assigned and
  			programmed by the manufacturer. This will ordinarily be printed
  			on a label on the housing of the device."
		INDEX   { MonnitEGW4SensorRegistrationIndex }
  	::= {monnitEGW4SensorInfoBySensorRegisOrderEntry 1 }

monnitEGW4SensorInfoBySensorRegisOrderSensDevWDIndexNo OBJECT-TYPE
    SYNTAX        INTEGER(0..255)
    ACCESS    		read-only
    STATUS        mandatory
    DESCRIPTION
  			"The index number of the sensor in the gateway's sensor registration
  			table. This is the number used in referencing the sensor in the
  			monnitEGW4SensorInfoBySensorRegisOrder hierarchy."
		INDEX   { MonnitEGW4SensorRegistrationIndex }
  	::= {monnitEGW4SensorInfoBySensorRegisOrderEntry 2 }

monnitEGW4SensorInfoBySensorRegisOrderSensDevTypeNo OBJECT-TYPE
    SYNTAX        INTEGER(1..65535)
    ACCESS    		read-only
    STATUS        mandatory
    DESCRIPTION
  			"The manufacturer's type number that identifies the kind of sensor."
		INDEX   { MonnitEGW4SensorRegistrationIndex }
  	::= {monnitEGW4SensorInfoBySensorRegisOrderEntry 3 }

monnitEGW4SensorInfoBySensorRegisOrderSensDevReadingAge OBJECT-TYPE
    SYNTAX        Unsigned32
    ACCESS    		read-only
    STATUS        mandatory
    DESCRIPTION
  			"The age of the sensor report received most recently from a sensor.
  			That time is reported as the number of seconds between the time of
  			the sensor report and the time this information is requested."
		INDEX   { MonnitEGW4SensorRegistrationIndex }
  	::= {monnitEGW4SensorInfoBySensorRegisOrderEntry 4 }

monnitEGW4SensorInfoBySensorRegisOrderSensDevActive OBJECT-TYPE
    SYNTAX        INTEGER(0..1)
    ACCESS    		read-only
    STATUS        mandatory
    DESCRIPTION
  			"Either 1 (active) or 0 (inactive). A sensor will be reported active
 				if it has recently communicated with the gateway since the last
  			reboot. If a sensor device does not show active, it is likely because
  			(1) the sensor lacks a power source, (2) the sensor is not in
  			proximity to the gateway, or (3) the gateway has recently been
  			powered on, and the sensor hasn't yet communicated."
		INDEX   { MonnitEGW4SensorRegistrationIndex }
  	::= {monnitEGW4SensorInfoBySensorRegisOrderEntry 5 }

monnitEGW4SensorInfoBySensorRegisOrderSensDevAlarming OBJECT-TYPE
		SYNTAX        	INTEGER(0..1)
    ACCESS    		read-only
    STATUS        mandatory
    DESCRIPTION
  			"Either 1 (alarming) or 0 (not alarming)'. A device will report an
 				alarm if it is programmed with a threshold found to be exceeded.
 				Examples: a temperature sensor for a refrigeration unit can be
 				programmed to alarm if the measured temperature rises above a
 				threshold, and a door sensor might alarm if a security door is opened."
		INDEX   { MonnitEGW4SensorRegistrationIndex }
  	::= {monnitEGW4SensorInfoBySensorRegisOrderEntry 6 }

monnitEGW4SensorInfoBySensorRegisOrderSensDevVoltage OBJECT-TYPE
		SYNTAX        	INTEGER(0..255)
    ACCESS    			read-only
    STATUS       	mandatory
    DESCRIPTION
 				"A value representing the voltage of the supply powering a sensor
 				device. Ordinarily this will report the voltage at the battery
 				terminals of a sensor. It is provided mainly so batteries can be
 				changed when depleted. The formula for calculating the voltage from
 				this number is: voltage=(150 + v) / 10.0."
		INDEX   { MonnitEGW4SensorRegistrationIndex }
  	::= {monnitEGW4SensorInfoBySensorRegisOrderEntry 7 }

monnitEGW4SensorInfoBySensorRegisOrderSensDevRFStrength OBJECT-TYPE
    SYNTAX        INTEGER(-128..127)
    ACCESS    		read-only
    STATUS        mandatory
    DESCRIPTION
  			"The signal strength, in dB, of the radio link between the gateway
  			and the particular sensor, as measured at the time of the most recent
  			sensor report."
		INDEX   { MonnitEGW4SensorRegistrationIndex }
  	::= {monnitEGW4SensorInfoBySensorRegisOrderEntry 8 }

monnitEGW4SensorInfoBySensorRegisOrderSensDevRptUT OBJECT-TYPE
    SYNTAX        DisplayString
    ACCESS    		read-only
    STATUS        mandatory
    DESCRIPTION
  			"The untranslated data block received from a sensor, in hexadecimal
  			format. This may be used where a translating function isn't yet
  			present, and for development purposes. Most users should use the
				translated values delivered in the format of
				MonnitEGW4SensorDeviceReadingValuesAll."
		INDEX   { MonnitEGW4SensorRegistrationIndex }
  	::= {monnitEGW4SensorInfoBySensorRegisOrderEntry 9 }

monnitEGW4SensorInfoBySensorRegisOrderSensDevReadingVl1 OBJECT-TYPE
    SYNTAX        MonnitEGW4SensorDeviceReadingU32Value
    ACCESS    		read-only
    STATUS        mandatory
    DESCRIPTION
  			"The value of a single sensor reading, or one half of a 64-bit reading,
 				in integer format, not translated to human-readable form. See
 				MonnitEGW4SensorDeviceReadingU32Value for further explanation."
  	::= {monnitEGW4SensorInfoBySensorRegisOrderEntry 10 }

monnitEGW4SensorInfoBySensorRegisOrderSensDevReadingVl2 OBJECT-TYPE
    SYNTAX        MonnitEGW4SensorDeviceReadingU32Value
    ACCESS    		read-only
    STATUS        mandatory
    DESCRIPTION
  			"The value of a single sensor reading, or one half of a 64-bit reading,
 				in integer format, not translated to human-readable form. See
 				MonnitEGW4SensorDeviceReadingU32Value for further explanation."
  	::= {monnitEGW4SensorInfoBySensorRegisOrderEntry 11 }

monnitEGW4SensorInfoBySensorRegisOrderSensDevReadingVl3 OBJECT-TYPE
    SYNTAX        MonnitEGW4SensorDeviceReadingU32Value
    ACCESS    		read-only
    STATUS        mandatory
    DESCRIPTION
  			"The value of a single sensor reading, or one half of a 64-bit reading,
 				in integer format, not translated to human-readable form. See
 				MonnitEGW4SensorDeviceReadingU32Value for further explanation."
  	::= {monnitEGW4SensorInfoBySensorRegisOrderEntry 12 }

monnitEGW4SensorInfoBySensorRegisOrderSensDevReadingVl4 OBJECT-TYPE
    SYNTAX        MonnitEGW4SensorDeviceReadingU32Value
    ACCESS    		read-only
    STATUS        mandatory
    DESCRIPTION
  			"The value of a single sensor reading, or one half of a 64-bit reading,
 				in integer format, not translated to human-readable form. See
 				MonnitEGW4SensorDeviceReadingU32Value for further explanation."
  	::= {monnitEGW4SensorInfoBySensorRegisOrderEntry 13 }

monnitEGW4SensorInfoBySensorRegisOrderSensDevReadingVl5 OBJECT-TYPE
    SYNTAX        MonnitEGW4SensorDeviceReadingU32Value
    ACCESS    		read-only
    STATUS        mandatory
    DESCRIPTION
  			"The value of a single sensor reading, or one half of a 64-bit reading,
 				in integer format, not translated to human-readable form. See
 				MonnitEGW4SensorDeviceReadingU32Value for further explanation."
  	::= {monnitEGW4SensorInfoBySensorRegisOrderEntry 14 }

monnitEGW4SensorInfoBySensorRegisOrderSensDevReadingVl6 OBJECT-TYPE
    SYNTAX        MonnitEGW4SensorDeviceReadingU32Value
    ACCESS    		read-only
    STATUS        mandatory
    DESCRIPTION
  			"The value of a single sensor reading, or one half of a 64-bit reading,
 				in integer format, not translated to human-readable form. See
 				MonnitEGW4SensorDeviceReadingU32Value for further explanation."
  	::= {monnitEGW4SensorInfoBySensorRegisOrderEntry 15 }

monnitEGW4SensorInfoBySensorRegisOrderSensDevReadingVl7 OBJECT-TYPE
    SYNTAX        MonnitEGW4SensorDeviceReadingU32Value
    ACCESS    		read-only
    STATUS        mandatory
    DESCRIPTION
  			"The value of a single sensor reading, or one half of a 64-bit reading,
 				in integer format, not translated to human-readable form. See
 				MonnitEGW4SensorDeviceReadingU32Value for further explanation."
  	::= {monnitEGW4SensorInfoBySensorRegisOrderEntry 16 }

monnitEGW4SensorInfoBySensorRegisOrderSensDevReadingVl8 OBJECT-TYPE
    SYNTAX        MonnitEGW4SensorDeviceReadingU32Value
    ACCESS    		read-only
    STATUS        mandatory
    DESCRIPTION
  			"The value of a single sensor reading, or one half of a 64-bit reading,
 				in integer format, not translated to human-readable form. See
 				MonnitEGW4SensorDeviceReadingU32Value for further explanation."
  	::= {monnitEGW4SensorInfoBySensorRegisOrderEntry 17 }

--
-- Traps
--

--Map of types used in traps to those used in requests
--	Monnit-EGW4-Trap-DevIDReported ::= Monnit-EGW4-GatewayID
--	Monnit-EGW4-Trap-AllValuesReported ::=
-- 		CHOICE {
--							Monnit-EGW4-trap-values-translatable Monnit-EGW4-SensorDeviceReadingValuesAll,
--							Monnit-EGW4-trap-values-unknown Monnit-EGW4-SensorDeviceReadingUntranslated
--					 }
--	Monnit-EGW4-Trap-AllUnitsReported ::= Monnit-EGW4-SensorDeviceReadingUnitsAll
--	Monnit-EGW4-Trap-AgeReported ::= Monnit-EGW4-SensorDeviceReadingUnitsAll
--	Monnit-EGW4-Trap-AlarmingReported ::= Monnit-EGW4-SensorDeviceReadingUnitsAll

MonnitEGW4TrapDevIDReported ::= TEXTUAL-CONVENTION
		STATUS        mandatory
		DESCRIPTION
				"The serial number identifier of the sensor device assigned and
				programmed by the manufacturer. This will ordinarily be printed
				on a label on the housing of the device. MonnitEGW4TrapDevIDReported
				is the same as MonnitEGW4SensorID."
		SYNTAX				Unsigned32(1..2147483631)

MonnitEGW4TrapAllValuesReported ::= TEXTUAL-CONVENTION
		STATUS        mandatory
		DESCRIPTION
				"This will make one of two reports. For the case the sensor type is
				known to the gateway, this will be all of the datums for the most
 				recent reading of the sensor device, separated by commas, in textual
 				format, using the MonnitEGW4SensorDeviceReadingValuesAll format.
				Where the sensor type is not known to the gateway, this will be
				the untranslated data block received from a sensor, in hexadecimal
				format. This MonnitEGW4TrapAllValuesReported is the same as either
				MonnitEGW4SensorDeviceReadingValuesAll or
 				MonnitEGW4SensorDeviceReadingUntranslated."
		SYNTAX				OCTET STRING

MonnitEGW4TrapAllUnitsReported ::= TEXTUAL-CONVENTION
		STATUS        mandatory
		DESCRIPTION
				"All of the units corresponding to the datums for the most recent
				reading of the sensor device, separated by commas, in textual
				format. For example, for a sensor reporting temperature and
				humidity this might read 'degrees C, %RH'.
				MonnitEGW4TrapAllUnitsReported is the same as
 				MonnitEGW4SensorDeviceReadingUnitsAll."
		SYNTAX				OCTET STRING

MonnitEGW4TrapAgeReported ::= TEXTUAL-CONVENTION
		STATUS        mandatory
		DESCRIPTION
				"The age of the sensor report received most recently from a sensor.
				That time is reported as the number of seconds between the time of
				the sensor report and the time this information is requested.
				MonnitEGW4TrapAgeReported is the same as
				MonnitEGW4SensorDeviceReadingAge."
		SYNTAX				OCTET STRING

MonnitEGW4TrapAlarmingReported ::= TEXTUAL-CONVENTION
		STATUS        mandatory
		DESCRIPTION
				"Either 'Alarming' or 'Not alarming'. A device will report an alarm
				if it is programmed with a threshold found to be exceeded. Examples:
				a temperature sensor for a refrigeration unit can be programmed to
				alarm if the measured temperature rises above a threshold, and
				a door sensor might alarm if a security door is opened.
				MonnitEGW4TrapAlarmingReported is the same as
				MonnitEGW4SensorDeviceReadingAlarming."
		SYNTAX				OCTET STRING

monnitEGW4NewSensorTraffic TRAP-TYPE
	ENTERPRISE monnitEGW4
	VARIABLES {
							monnitEGW4SensorInfoTranslatedFormatSensorDeviceID, MonnitEGW4TrapDevIDReported,
							monnitEGW4SensorInfoTranslatedFormatSensorDeviceReadingValuesAll, MonnitEGW4TrapAllValuesReported,
							monnitEGW4SensorInfoTranslatedFormatSensorDeviceReadingUnitsAll, MonnitEGW4TrapAllUnitsReported,
							monnitEGW4SensorInfoTranslatedFormatSensorDeviceReadingAge, MonnitEGW4TrapAgeReported,
							monnitEGW4SensorInfoTranslatedFormatSensorDeviceAlarming, MonnitEGW4TrapAlarmingReported
						}
	DESCRIPTION
			"This trap, when enabled, will generate a report corresponding to new
 			data from any registered sensor as it is received. Included with the
 			trap message are the sensor ID, all values the sensor reports, units for
 			all those values, the age, and whether the sensor is alarming."
	::= 1

monnitEGW4DeviceAlarming TRAP-TYPE
	ENTERPRISE monnitEGW4
	VARIABLES {
							monnitEGW4SensorInfoTranslatedFormatSensorDeviceID, MonnitEGW4TrapDevIDReported,
							monnitEGW4SensorInfoTranslatedFormatSensorDeviceReadingValuesAll, MonnitEGW4TrapAllValuesReported,
							monnitEGW4SensorInfoTranslatedFormatSensorDeviceReadingUnitsAll, MonnitEGW4TrapAllUnitsReported,
							monnitEGW4SensorInfoTranslatedFormatSensorDeviceReadingAge, MonnitEGW4TrapAgeReported,
							monnitEGW4SensorInfoTranslatedFormatSensorDeviceAlarming, MonnitEGW4TrapAlarmingReported
						}
	DESCRIPTION
			"This trap, when enabled, will generate a report corresponding to new
 			data from any registered sensor as it is received, but only if that
			sensor is alarming and the monnitEGW4NewSensorTraffic trap is disabled.
			(That trap will generate the same message, rendering this trap redundant.)
			Included with the trap message are the sensor ID, all values the sensor
 			reports, units for all those values, the age, and whether the sensor
 			is alarming."
	::= 2

END
