--
-- Chatsworth Products Inc.
-- Copyright (c) Chatsworth Products Inc., 1998-2014.
-- Version : 2.0.0
-- ************************************************************************

CPI-UNITY-MIB DEFINITIONS ::= BEGIN

IMPORTS
    MODULE-IDENTITY,
    OBJECT-TYPE,
    NOTIFICATION-TYPE,
    IpAddress,
    Integer32,
    Counter64,
    enterprises
        FROM SNMPv2-SMI
    DisplayString
        FROM SNMPv2-TC
    MacAddress
        FROM SNMPv2-TC
    TruthValue
        FROM SNMPv2-TC
    Unsigned32
        FROM SNMPv2-SMI
    MODULE-COMPLIANCE,
    OBJECT-GROUP,
    NOTIFICATION-GROUP
        FROM SNMPv2-CONF;

products MODULE-IDENTITY
    LAST-UPDATED "201411211508Z" -- 1 August 2014
    ORGANIZATION "Chatsworth Products Inc."
    CONTACT-INFO
        "Chatsworth Products, Inc.
        3004 South Austin Avenue
        Georgetown, TX 78626
        Tel: (800) 834-4969
        Email: techsupport@chatsworth.com"
    DESCRIPTION
     "The MIB module is used to register Chatsworth eConnect related 
      SNMP OIDs for all models.

      Copyright 2014 Chatsworth Products, Inc. All rights reserved.
      Reproduction of this document is authorized on the condition
      that the forgoing copyright notice is included.

      This Specification is supplied 'AS IS' and Chatsworth Products, Inc
      makes no warranty, either express or implied, as to the use,
      operation, condition, or performance of the Specification."
    REVISION "201408011508Z"
    DESCRIPTION
    "Initial version of the Unity SNMP OIDs"
    ::= { cpi 1 }

cpi OBJECT IDENTIFIER ::= { enterprises 30932 }

power OBJECT IDENTIFIER ::= { products 10 }

econnect OBJECT IDENTIFIER ::= { power 1 }

configuration OBJECT IDENTIFIER ::= { econnect 1 }

network OBJECT IDENTIFIER ::= { configuration 1 }

ipv4 OBJECT IDENTIFIER ::= { network 1 }

ipV4Enable OBJECT-TYPE
    SYNTAX INTEGER { disabled(0), enabled(1) }
    MAX-ACCESS read-write
    STATUS current
    DESCRIPTION
        "Controls whether the IPv4 network interface is enabled."
    ::= { ipv4 1 }

pduIP OBJECT-TYPE
    SYNTAX IpAddress
    MAX-ACCESS read-write
    STATUS current
    DESCRIPTION
        "Set or get the IPv4 address of the PDU."
    ::= { ipv4 2 }

autoIP OBJECT-TYPE
    SYNTAX INTEGER { static(0), dynamic(1) }
    MAX-ACCESS read-write
    STATUS current
    DESCRIPTION
        "Controls whether the IPv4 address is retrieved from a 
         DHCP server or is set statically."
    ::= { ipv4 3 }

autoDNS OBJECT-TYPE
    SYNTAX INTEGER { static(0), dynamic(1) }
    MAX-ACCESS read-write
    STATUS current
    DESCRIPTION
        "Controls whether the DNS addresses are retrieved from
        a DHCP server or are set statically."
    ::= { ipv4 4 }

subnetMask OBJECT-TYPE
    SYNTAX IpAddress
    MAX-ACCESS read-write
    STATUS current
    DESCRIPTION
        "The subnet mask associated with the IPv4 address of this 
        entry. The value of the mask is an IPv4 address with all the 
        network bits set to 1 and all the hosts bits set to 0."
    ::= { ipv4 5 }

gateway OBJECT-TYPE
    SYNTAX IpAddress
    MAX-ACCESS read-write
    STATUS current
    DESCRIPTION
        "Set or get the IPv4 address of the gateway router for the PDU."
    ::= { ipv4 6 }

dns1 OBJECT-TYPE
    SYNTAX IpAddress
    MAX-ACCESS read-write
    STATUS current
    DESCRIPTION
        "Set or get the IPv4 address of the first DNS entry for the PDU."
    ::= { ipv4 7 }

dns2 OBJECT-TYPE
    SYNTAX IpAddress
    MAX-ACCESS read-write
    STATUS current
    DESCRIPTION
        "Set or get the IPv4 address of the second DNS entry for the PDU."
    ::= { ipv4 8 }

dns3 OBJECT-TYPE
    SYNTAX IpAddress
    MAX-ACCESS read-write
    STATUS current
    DESCRIPTION
        "Set or get the IPv4 address of the third DNS entry for the PDU."
    ::= { ipv4 9 }

ipv6 OBJECT IDENTIFIER ::= { network 2 }

ipV6Enable OBJECT-TYPE
    SYNTAX INTEGER { disabled(0), enabled(1) }
    MAX-ACCESS read-write
    STATUS current
    DESCRIPTION
        "Controls whether the IPv6 network interface is enabled."
    ::= { ipv6 1 }

linkLocalEnable OBJECT-TYPE
    SYNTAX INTEGER { disabled(0), enabled(1) }
    MAX-ACCESS read-write
    STATUS current
    DESCRIPTION
        "Controls whether the IPv6 link-local address is enabled."
    ::= { ipv6 2 }

globalAddrEnable OBJECT-TYPE
    SYNTAX INTEGER { disabled(0), enabled(1) }
    MAX-ACCESS read-write
    STATUS current
    DESCRIPTION
        "Controls whether the IPv6 global address is enabled."
    ::= { ipv6 3 }

pduIPv6 OBJECT-TYPE
    SYNTAX DisplayString
    MAX-ACCESS read-write
    STATUS current
    DESCRIPTION
        "Set or get the IPv6 address of the PDU."
    ::= { ipv6 4 }

autoIPv6 OBJECT-TYPE
    SYNTAX INTEGER { static(0), dynamic(1) }
    MAX-ACCESS read-write
    STATUS current
    DESCRIPTION
        "Controls whether the IPv6 address is retrieved from a 
         DHCP server or is set statically."
    ::= { ipv6 5 }

autoDNSv6 OBJECT-TYPE
    SYNTAX Integer32 (0..1)
    MAX-ACCESS read-write
    STATUS current
    DESCRIPTION
        "Controls whether the DNS IPv6 address is retrieved from a 
         DHCP server or is set statically."
    ::= { ipv6 6 }

subnetMaskv6 OBJECT-TYPE
    SYNTAX DisplayString
    MAX-ACCESS read-write
    STATUS current
    DESCRIPTION
        "The subnet mask associated with the IPv6 address of this 
        entry. The value of the mask is an IPv6 address with all the 
        network bits set to 1 and all the hosts bits set to 0."
    ::= { ipv6 7 }

gatewayv6 OBJECT-TYPE
    SYNTAX DisplayString
    MAX-ACCESS read-write
    STATUS current
    DESCRIPTION
        "Set or get the IPv6 address of the gateway router for the PDU."
    ::= { ipv6 8 }

dns1v6 OBJECT-TYPE
    SYNTAX DisplayString
    MAX-ACCESS read-write
    STATUS current
    DESCRIPTION
        "Set or get the IPv6 address of the first DNS entry for the PDU."
    ::= { ipv6 9 }

dns2v6 OBJECT-TYPE
    SYNTAX DisplayString
    MAX-ACCESS read-write
    STATUS current
    DESCRIPTION
        "Set or get the IPv6 address of the second DNS entry for the PDU."
    ::= { ipv6 10 }

dns3v6 OBJECT-TYPE
    SYNTAX DisplayString
    MAX-ACCESS read-write
    STATUS current
    DESCRIPTION
        "Set or get the IPv6 address of the third DNS entry for the PDU."
    ::= { ipv6 11 }

time OBJECT IDENTIFIER ::= { network 3 }

rfcTimeServer OBJECT-TYPE
    SYNTAX      DisplayString
    MAX-ACCESS  read-write
    STATUS      current
    DESCRIPTION
        "Set or get the IP address of the RFC Time Server."
    ::= { time 1 }

ntpTimeServer OBJECT-TYPE
    SYNTAX      DisplayString
    MAX-ACCESS  read-write
    STATUS      current
    DESCRIPTION
        "Set or get the IP address of the NTP Time Server."
    ::= { time 2 }

interfaces OBJECT IDENTIFIER ::= { configuration 2 }

snmp OBJECT IDENTIFIER ::= { interfaces 1 }

snmpEnable OBJECT-TYPE
    SYNTAX INTEGER { disabled(0), enabled(1) }
    MAX-ACCESS read-write
    STATUS current
    DESCRIPTION
        "Controls whether the SNMP network service is enabled."
    ::= { snmp 1 }

snmpHosts OBJECT IDENTIFIER ::= { snmp 2 }

snmpHostOnly OBJECT-TYPE
    SYNTAX INTEGER { any(0), listed(1) }
    MAX-ACCESS read-write
    STATUS current
    DESCRIPTION
        "Controls whether access to the SNMP service responsed to
        the listed hosts (snmpHost1, snmpHost2, snmpHost3) or
        to any host requesting data."
    ::= { snmpHosts 1 }

snmpHost1 OBJECT-TYPE
    SYNTAX DisplayString
    MAX-ACCESS read-write
    STATUS current
    DESCRIPTION
        "Set or get the IPv4 address of the first host the SNMP service
        will reply to."
    ::= { snmpHosts 2 }

snmpHost2 OBJECT-TYPE
    SYNTAX DisplayString
    MAX-ACCESS read-write
    STATUS current
    DESCRIPTION
        "Set or get the IPv4 address of the second host the SNMP service
        will reply to."
    ::= { snmpHosts 3 }

snmpHost3 OBJECT-TYPE
    SYNTAX DisplayString
    MAX-ACCESS read-write
    STATUS current
    DESCRIPTION
        "Set or get the IPv4 address of the third host the SNMP service
        will reply to."
    ::= { snmpHosts 4 }
   
snmpHostIPv61 OBJECT-TYPE
    SYNTAX DisplayString
    MAX-ACCESS read-write
    STATUS current
    DESCRIPTION
        "Set or get the IPv6 address of the first host the SNMP service
        will reply to."
    ::= { snmpHosts 5 }

snmpHostIPv62 OBJECT-TYPE
    SYNTAX DisplayString
    MAX-ACCESS read-write
    STATUS current
    DESCRIPTION
        "Set or get the IPv6 address of the first host the SNMP service
        will reply to."
    ::= { snmpHosts 6 }

snmpHostIPV63 OBJECT-TYPE
    SYNTAX DisplayString
    MAX-ACCESS read-write
    STATUS current
    DESCRIPTION
        "Set or get the IPv6 address of the first host the SNMP service
        will reply to."
    ::= { snmpHosts 7 }

snmpQueryPort OBJECT-TYPE
    SYNTAX Integer32 (0..65535)
    MAX-ACCESS read-write
    STATUS current
    DESCRIPTION
        "Set or get the port for SNMP query access."
    ::= { snmp 3 }

snmpTrapPort OBJECT-TYPE
    SYNTAX Integer32 (0..65535)
    MAX-ACCESS read-write
    STATUS current
    DESCRIPTION
        "Set or get the port for SNMP traps."
    ::= { snmp 4 }

snmpReadComm OBJECT-TYPE
    SYNTAX DisplayString
    MAX-ACCESS read-write
    STATUS current
    DESCRIPTION
        "Set or get the SNMP Read Community."
    ::= { snmp 5 }

snmpWriteComm OBJECT-TYPE
    SYNTAX DisplayString
    MAX-ACCESS read-write
    STATUS current
    DESCRIPTION
        "Set or get the SNMP Write Community."
    ::= { snmp 6 }

snmpUSMuserName OBJECT-TYPE
    SYNTAX DisplayString
    MAX-ACCESS read-write
    STATUS current
    DESCRIPTION
        "Set or get the SNMP USM User Name."
    ::= { snmp 7 }

snmpSecurityLevel OBJECT-TYPE
    SYNTAX INTEGER { v1(0), v2c(1), v3(2), v3Auth(3), v3AuthPriv(4) }
    MAX-ACCESS read-write
    STATUS current
    DESCRIPTION
        "Set or get the security Level for SNMP: 0 = v1, 1 = v2c, 2 = v3 no authentication,
        3 = v3 with authentication only, 4 = v3 with authentication and privacy"
    ::= { snmp 8 }

snmpAuthAlgo OBJECT-TYPE
    SYNTAX INTEGER { SHA(0), MD5(1) }
    MAX-ACCESS read-write
    STATUS current
    DESCRIPTION
        "Set or get the Authentication Algorithm for SNMP."
    ::= { snmp 9 }

snmpPrivAlgo OBJECT-TYPE
    SYNTAX INTEGER { DES(0), AES(1) }
    MAX-ACCESS read-write
    STATUS current
    DESCRIPTION
        "Get or get the Privacy Algorithm for SNMP."
    ::= { snmp 10 }

snmpAuthPasswd OBJECT-TYPE
    SYNTAX DisplayString (SIZE (0..64))
    MAX-ACCESS read-write
    STATUS current
    DESCRIPTION
        "Set or Get the SNMP Authentication Password."
    ::= { snmp 11 }

snmpPrivPasswd OBJECT-TYPE
    SYNTAX DisplayString (SIZE (0..64))
    MAX-ACCESS read-write
    STATUS current
    DESCRIPTION
        "Set or get the SNMP Privacy Password."
    ::= { snmp 12 }

snmpContextName OBJECT-TYPE
    SYNTAX DisplayString (SIZE (0..64))
    MAX-ACCESS read-write
    STATUS current
    DESCRIPTION
        "Set or get the SNMP Context Name."
    ::= { snmp 13 }

snmpEngineID OBJECT-TYPE
    SYNTAX DisplayString (SIZE (0..64))
    MAX-ACCESS read-write
    STATUS current
    DESCRIPTION
        "Set or get the SNMP Engine ID."
    ::= { snmp 14 }

snmpLocAuthKey OBJECT-TYPE
    SYNTAX DisplayString (SIZE (0..64))
    MAX-ACCESS read-write
    STATUS current
    DESCRIPTION
        "Set or get the SNMP Local Authentication Key."
    ::= { snmp 15 }

snmpLocPrivKey OBJECT-TYPE
    SYNTAX DisplayString (SIZE (0..64))
    MAX-ACCESS read-write
    STATUS current
    DESCRIPTION
        "Set or get the SNMP Local Privacy Key."
    ::= { snmp 16 }

snmpTrapHosts OBJECT IDENTIFIER ::= { snmp 17 }

snmpTrapHost1 OBJECT-TYPE
    SYNTAX DisplayString
    MAX-ACCESS read-write
    STATUS current
    DESCRIPTION
        "Set or get the IPv4 address of the first SNMP Trap Host."
    ::= { snmpTrapHosts 1 }

snmpTrapHost2 OBJECT-TYPE
    SYNTAX DisplayString
    MAX-ACCESS read-write
    STATUS current
    DESCRIPTION
        "Set or get the IPv4 address of the second SNMP Trap Host."
    ::= { snmpTrapHosts 2 }

snmpTrapHost3 OBJECT-TYPE
    SYNTAX DisplayString
    MAX-ACCESS read-write
    STATUS current
    DESCRIPTION
        "Set or get the IPv4 address of the third SNMP Trap Host."
    ::= { snmpTrapHosts 3 }

snmpTrapHostIPv61 OBJECT-TYPE
    SYNTAX DisplayString
    MAX-ACCESS read-write
    STATUS current
    DESCRIPTION
        "Set or get the IPv6 address of the first SNMP Trap Host."
    ::= { snmpTrapHosts 4 }

snmpTrapHostIPv62 OBJECT-TYPE
    SYNTAX DisplayString
    MAX-ACCESS read-write
    STATUS current
    DESCRIPTION
        "Set or get the IPv6 address of the second SNMP Trap Host."
    ::= { snmpTrapHosts 5 }

snmpTrapHostIPv63 OBJECT-TYPE
    SYNTAX DisplayString
    MAX-ACCESS read-write
    STATUS current
    DESCRIPTION
        "Set or get the IPv6 address of the third SNMP Trap Host."
    ::= { snmpTrapHosts 6 }

http OBJECT IDENTIFIER ::= { interfaces 2 }

enableWeb OBJECT-TYPE
    SYNTAX INTEGER { disabled(0), enabled(1) }
    MAX-ACCESS read-write
    STATUS current
    DESCRIPTION
        "Controls whether the web interface is enabled."
    ::= { http 1 }

httpEnable OBJECT-TYPE
    SYNTAX INTEGER { disabled(0), enabled(1) }
    MAX-ACCESS read-write
    STATUS current
    DESCRIPTION
        "Controls whether the HTTP service is enabled."
    ::= { http 2 }

httpsEnable OBJECT-TYPE
    SYNTAX INTEGER { disabled(0), enabled(1) }
    MAX-ACCESS read-write
    STATUS current
    DESCRIPTION
        "Controls whether the HTTPS service is enabled."
    ::= { http 3 }

httpPort OBJECT-TYPE
    SYNTAX Integer32 (0..65535)
    MAX-ACCESS read-write
    STATUS current
    DESCRIPTION
        "Set or get the port for unsecure HTTP access."
    ::= { http 4 }

httpsPort OBJECT-TYPE
    SYNTAX Integer32 (0..65535)
    MAX-ACCESS read-write
    STATUS current
    DESCRIPTION
        "Set or get the port for secure HTTPS access."
    ::= { http 5 }

ssh OBJECT IDENTIFIER ::= { interfaces 3 }

telnetEnable OBJECT-TYPE
    SYNTAX INTEGER { disabled(0), enabled(1) }
    MAX-ACCESS read-write
    STATUS current
    DESCRIPTION
        "Controls whether the telnet service is enabled."
    ::= { ssh 1 }

sshEnable OBJECT-TYPE
    SYNTAX Integer32 (0..1)
    MAX-ACCESS read-write
    STATUS current
    DESCRIPTION
        "Controls whether the SSH service is enabled."
    ::= { ssh 2 }

sshPort OBJECT-TYPE
    SYNTAX Integer32 (0..65535)
    MAX-ACCESS read-write
    STATUS current
    DESCRIPTION
        "Set or get the port for secure SSH access."
    ::= { ssh 3 }

telnetPort OBJECT-TYPE
    SYNTAX Integer32 (0..65535)
    MAX-ACCESS read-write
    STATUS current
    DESCRIPTION
        "Set or get the port for non secure Telnet access."
    ::= { ssh 4 }

smtp OBJECT IDENTIFIER ::= { interfaces 4 }

enableSMTP OBJECT-TYPE
    SYNTAX INTEGER { disabled(0), enabled(1) }
    MAX-ACCESS read-write
    STATUS current
    DESCRIPTION
        "Controls whether the mail notification service is enabled.."
    ::= { smtp 1 }

smtpSendPort OBJECT-TYPE
    SYNTAX Integer32 (0..65535)
    MAX-ACCESS read-write
    STATUS current
    DESCRIPTION
        "Set or get the port for SMTP send."
    ::= { smtp 2 }

smtpReceivePort OBJECT-TYPE
    SYNTAX Integer32 (0..65535)
    MAX-ACCESS read-write
    STATUS current
    DESCRIPTION
        "Set or get the port for SMTP Receive."
    ::= { smtp 3 }

smtpServer OBJECT-TYPE
    SYNTAX DisplayString
    MAX-ACCESS read-write
    STATUS current
    DESCRIPTION
        "Set or get the IP address of the e-mail server."
    ::= { smtp 4 }

smtpUserName OBJECT-TYPE
    SYNTAX DisplayString
    MAX-ACCESS read-write
    STATUS current
    DESCRIPTION
        "Set or get the PDU e-mail user login name."
    ::= { smtp 5 }

smtpUserPasswd OBJECT-TYPE
    SYNTAX DisplayString
    MAX-ACCESS read-write
    STATUS current
    DESCRIPTION
        "Set or get the PDU e-mail user login password."
    ::= { smtp 6 }

smtpEmailAddr OBJECT-TYPE
    SYNTAX DisplayString
    MAX-ACCESS read-write
    STATUS current
    DESCRIPTION
        "Set or get the PDU e-mail address."
    ::= { smtp 7 }

smtpEmailDestination1 OBJECT-TYPE
    SYNTAX DisplayString (SIZE (0..64))
    MAX-ACCESS read-write
    STATUS current
    DESCRIPTION
        "Set or get the e-mail address of the first recipient."
    ::= { smtp 8 }

smtpEmailDestination2 OBJECT-TYPE
    SYNTAX DisplayString (SIZE (0..64))
    MAX-ACCESS read-write
    STATUS current
    DESCRIPTION
        "Set or get the e-mail address of the second recipient."
    ::= { smtp 9 }

smtpEmailDestination3 OBJECT-TYPE
    SYNTAX DisplayString (SIZE (0..64))
    MAX-ACCESS read-write
    STATUS current
    DESCRIPTION
        "Set or get the e-mail address of the third recipient."
    ::= { smtp 10 }

smtpServOptions OBJECT-TYPE
    SYNTAX Integer32 (0..2)
    MAX-ACCESS read-write
    STATUS current
    DESCRIPTION
        "Set or get the SMTP server options."
    ::= { smtp 11 }

logging OBJECT IDENTIFIER ::= { configuration 3 }

logEnable OBJECT-TYPE
    SYNTAX INTEGER { disabled(0), enabled(1) }
    MAX-ACCESS read-write
    STATUS current
    DESCRIPTION
        "Controls whether the data logging feature is enabled."
    ::= { logging 1 }

logInterval OBJECT-TYPE
    SYNTAX Integer32 (0..65535)
    MAX-ACCESS read-write
    STATUS current
    DESCRIPTION
        "Set or get the time interval in seconds for logging metrics (disabled if < 10)."
    ::= { logging 2 }

logDifference OBJECT-TYPE
    SYNTAX Integer32 (0..2000)
    MAX-ACCESS read-write
    STATUS current
    DESCRIPTION
        "Set or get the current difference in 1/100 Amps that triggers logging metrics."
    ::= { logging 3 }

netservdLog OBJECT-TYPE
    SYNTAX INTEGER { disabled(0), enabled(1) }
    MAX-ACCESS read-write
    STATUS current
    DESCRIPTION
        "Controls sending the data logs to log server over network."
    ::= { logging 4 }

autonetLog OBJECT-TYPE
    SYNTAX INTEGER { disabled(0), enabled(1) }
    MAX-ACCESS read-write
    STATUS current
    DESCRIPTION
        "Controls whether automatic transfer to log server every 6 hours is enabled."
    ::= { logging 5 }

stdmeterdLog OBJECT-TYPE
    SYNTAX INTEGER { disabled(0), enabled(1) }
    MAX-ACCESS read-write
    STATUS current
    DESCRIPTION
        "Controls whether logging of branch, receptacle and environmental metrics is enabled."
    ::= { logging 6 }

groupmeterdLog OBJECT-TYPE
    SYNTAX INTEGER { disabled(0), enabled(1) }
    MAX-ACCESS read-write
    STATUS current
    DESCRIPTION
        "Controls whether logging of grouped receptacle metrics is enabled."
    ::= { logging 7 }

alarmdLog OBJECT-TYPE
    SYNTAX INTEGER { disabled(0), enabled(1) }
    MAX-ACCESS read-write
    STATUS current
    DESCRIPTION
        "Controls whether logging of alarm events is enabled."
    ::= { logging 8 }

userlogindLog OBJECT-TYPE
    SYNTAX INTEGER { disabled(0), enabled(1) }
    MAX-ACCESS read-write
    STATUS current
    DESCRIPTION
        "Control whether logging of user login events is enabled."
    ::= { logging 9 }

usersetupdLog OBJECT-TYPE
    SYNTAX INTEGER { disabled(0), enabled(1) }
    MAX-ACCESS read-write
    STATUS current
    DESCRIPTION
        "Control whether logging of user setup change events is enabled."
    ::= { logging 10 }

fwupdatedLog OBJECT-TYPE
    SYNTAX INTEGER { disabled(0), enabled(1) }
    MAX-ACCESS read-write
    STATUS current
    DESCRIPTION
        "Control whether the logging of firmware updates is enabled."
    ::= { logging 11 }

setupchangedLog OBJECT-TYPE
    SYNTAX INTEGER { disabled(0), enabled(1) }
    MAX-ACCESS read-write
    STATUS current
    DESCRIPTION
        "Control whether the logging of setup change events is enabled."
    ::= { logging 12 }

recepchangedLog OBJECT-TYPE
    SYNTAX INTEGER { disabled(0), enabled(1) }
    MAX-ACCESS read-write
    STATUS current
    DESCRIPTION
        "Control whether logging of receptacle state changes is enabled."
    ::= { logging 13 }

pduopchangedLog OBJECT-TYPE
    SYNTAX INTEGER { disabled(0), enabled(1) }
    MAX-ACCESS read-write
    STATUS current
    DESCRIPTION
        "Control whether logging of PDU operation and state changes is enabled."
    ::= { logging 14 }

dLogCycle OBJECT-TYPE
    SYNTAX Integer32 (0..65535)
    MAX-ACCESS read-write
    STATUS current
    DESCRIPTION
        "Set or get the time interval in minutes for internal data logging to occur."
    ::= { logging 15 }

dLogFullWarnLevel OBJECT-TYPE
    SYNTAX Integer32 (50..100)
    MAX-ACCESS read-write
    STATUS current
    DESCRIPTION
        "Set or get the warning threshold for percentage of storage full (min=50, max=100)."
    ::= { logging 16 }

netdLogServer OBJECT-TYPE
    SYNTAX DisplayString (SIZE (0..64))
    MAX-ACCESS read-write
    STATUS current
    DESCRIPTION
        "Set or get the network address for the data log server."
    ::= { logging 17 }

netdLogPort OBJECT-TYPE
    SYNTAX Integer32 (0..65535)
    MAX-ACCESS read-write
    STATUS current
    DESCRIPTION
        "Set or get the port used by the data log server."
    ::= { logging 18 }

netdLogUser OBJECT-TYPE
    SYNTAX DisplayString (SIZE (0..64))
    MAX-ACCESS read-write
    STATUS current
    DESCRIPTION
        "Set or get the user name to access the data log server."
    ::= { logging 19 }

netdLogPasswd OBJECT-TYPE
    SYNTAX DisplayString (SIZE (0..64))
    MAX-ACCESS read-write
    STATUS current
    DESCRIPTION
        "Set or get the user password to access the data log server."
    ::= { logging 20 }

netdLogDestdir OBJECT-TYPE
    SYNTAX DisplayString (SIZE (0..64))
    MAX-ACCESS read-write
    STATUS current
    DESCRIPTION
        "Get or get the destination directory in the data log server."
    ::= { logging 21 }

netdLogOptions OBJECT-TYPE
    SYNTAX DisplayString (SIZE (0..64))
    MAX-ACCESS read-write
    STATUS current
    DESCRIPTION
        "Get or set the options string when accessing the data log server."
    ::= { logging 22 }

accesscontrol OBJECT IDENTIFIER ::= { configuration 4 }

ldap OBJECT IDENTIFIER ::= { accesscontrol 1 }

enableADAuth OBJECT-TYPE
    SYNTAX INTEGER { disabled(0), enabled(1) }
    MAX-ACCESS read-write
    STATUS current
    DESCRIPTION
        "Controls whether the Active Directory authentication is enabled."
    ::= { ldap 1 }

adServer OBJECT-TYPE
    SYNTAX DisplayString
    MAX-ACCESS read-write
    STATUS current
    DESCRIPTION
        "Set or get the IP address of the Active Directory Server."
    ::= { ldap 2 }

adDomain OBJECT-TYPE
    SYNTAX DisplayString
    MAX-ACCESS read-write
    STATUS current
    DESCRIPTION
        "Set or get the Active Directory Domain."
    ::= { ldap 3 }
    
adPort OBJECT-TYPE
    SYNTAX Integer32 (0..65535)
    MAX-ACCESS read-write
    STATUS current
    DESCRIPTION
        "Set or get the port for Active Directory authentication."
    ::= { ldap 4 }

adResvPort OBJECT-TYPE
    SYNTAX Integer32 (0..65535)
    MAX-ACCESS read-write
    STATUS current
    DESCRIPTION
        "Set or get the alternate or reserved port for Active Directory Authentication."
    ::= { ldap 5 }

radius OBJECT IDENTIFIER ::= { accesscontrol 2 }

enableRadiusAuth OBJECT-TYPE
    SYNTAX INTEGER { disabled(0), enabled(1) }
    MAX-ACCESS read-write
    STATUS current
    DESCRIPTION
        "Controls whether radius authentication is enabled."
    ::= { radius 1 }

radiusServer OBJECT-TYPE
    SYNTAX DisplayString
    MAX-ACCESS read-write
    STATUS current
    DESCRIPTION
        "Set or get the IP address of the Radius Authentication Server."
    ::= { radius 2 }

radiusSHSecret OBJECT-TYPE
    SYNTAX DisplayString
    MAX-ACCESS read-write
    STATUS current
    DESCRIPTION
        "Set or get the Radius Shared Secret."
    ::= { radius 3 }

radiusNASServer OBJECT-TYPE
    SYNTAX DisplayString
    MAX-ACCESS read-write
    STATUS current
    DESCRIPTION
        "Set or get the Radius Network Access Service."
    ::= { radius 4 }

radiusPort OBJECT-TYPE
    SYNTAX Integer32 (0..65535)
    MAX-ACCESS read-write
    STATUS current
    DESCRIPTION
        "Set or get the port for radius authentication."
    ::= { radius 5 }

nasPort OBJECT-TYPE
    SYNTAX Integer32 (0..65535)
    MAX-ACCESS read-write
    STATUS current
    DESCRIPTION
        "Set or get the port for Radius Network Access Service."
    ::= { radius 6 }

pdu OBJECT IDENTIFIER ::= { configuration 6 }

inputTop OBJECT-TYPE
    SYNTAX INTEGER { bottom(0), top(1) }
    MAX-ACCESS read-write
    STATUS current
    DESCRIPTION
        "Set or get the input cord entry orientation."
    ::= { pdu 1 }

celsiusTemp OBJECT-TYPE
    SYNTAX INTEGER { Fahrenheit(0), Celsius(1) }
    MAX-ACCESS read-write
    STATUS current
    DESCRIPTION
        "Set or get the temperature units."
    ::= { pdu 2 }

shareRole OBJECT-TYPE
    SYNTAX INTEGER { Backup(0), Shared(1) }
    MAX-ACCESS read-write
    STATUS current
    DESCRIPTION
        "Controls whether to allow sharing of PDU Primary and Alternate Roles."
    ::= { pdu 3 }

missingPDUNotify OBJECT-TYPE
    SYNTAX INTEGER { disabled(0), enabled(1) }
    MAX-ACCESS read-write
    STATUS current
    DESCRIPTION
        "Controls whether to notify when a PDU is missing from the link."
    ::= { pdu 4 }

roleChangeNotify OBJECT-TYPE
    SYNTAX INTEGER { disabled(0), enabled(1) }
    MAX-ACCESS read-write
    STATUS current
    DESCRIPTION
        "Control whether to notify when a PDU changes role in the link."
    ::= { pdu 5 }

dispTimeout OBJECT-TYPE
    SYNTAX Integer32 (1..90)
    MAX-ACCESS read-write
    STATUS current
    DESCRIPTION
        "Set or get the inactivity timeout in minutes to blank the local display (minimum is 1 minute)."
    ::= { pdu 6 }

loginTimeout OBJECT-TYPE
    SYNTAX Integer32 (1..60)
    MAX-ACCESS read-write
    STATUS current
    DESCRIPTION
        "Set or get the inactivity timeout in minutes to terminate a logged in session (minimum is 1 minute)."
    ::= { pdu 7 }

dispBrightness OBJECT-TYPE
    SYNTAX Integer32 (0..9)
    MAX-ACCESS read-write
    STATUS current
    DESCRIPTION
        "Set or get the relative brightness of the local display (0 in min, 9 is max)."
    ::= { pdu 8 }

sumAmps OBJECT-TYPE
    SYNTAX INTEGER { disabled(0), enabled(1) }
    MAX-ACCESS read-write
    STATUS current
    DESCRIPTION
        "Control whether the PDU displays the amperage sum of all branchs."
    ::= { pdu 9 }

alerts OBJECT IDENTIFIER ::= { configuration 7 }

alarmInterval OBJECT-TYPE
    SYNTAX Integer32 (0..65535)
    MAX-ACCESS read-write
    STATUS current
    DESCRIPTION
        "Set or get the time interval in seconds for alarm cycle (disabled if < 10)."
    ::= { alerts 1 }

systeminfo OBJECT IDENTIFIER ::= { econnect 2 }

cpiPduTableCount OBJECT-TYPE
    SYNTAX      Unsigned32
    UNITS       "Count"
    MAX-ACCESS  read-only
    STATUS      current
    DESCRIPTION
        "Get the number of PDUs being monitored by this PDU.  This is the 
         number of entries in the cpiPduTable."
    ::= { systeminfo 1 }

cpiPduTable OBJECT-TYPE
    SYNTAX      SEQUENCE OF CpiPduEntry
    MAX-ACCESS  not-accessible
    STATUS      current
    DESCRIPTION
        "This table contains a list of PDU entries that are being monitored
        by the PDU. 
        
        The table contains one, or many rows, depending upon the 
        number of PDUs being monitored. Each row in the table represents a PDU 
        in the daisy chain.
        
        This table always contains at least one entry and a maximum of 32 entries.
        The MAC address is used as an index on the table to allow data collectors
        to ensure that information can be retrieved for a specific PDU."
    ::= { systeminfo 10 }

    cpiPduEntry OBJECT-TYPE
        SYNTAX      CpiPduEntry
        MAX-ACCESS  not-accessible
        STATUS      current
        DESCRIPTION
            "This entry defines the columns to be populated in the
             'cpiPduTable'.  Each column represents an attribute of a PDU.
             This table is indexed by the PDU MAC that is globally unique."

        INDEX
        { 
            cpiPduMac 
        }
        ::= { cpiPduTable 1 }

    CpiPduEntry ::= SEQUENCE 
    {
        cpiPduMac			    MacAddress,
        cpiPduModel			    DisplayString,	
        cpiPduName			    DisplayString,
        cpiPduDescription		DisplayString,
        cpiPduHasBranchMonitor	Integer32,
        cpiPduHasOutletMonitor	Integer32,
        cpiPduHasOutletControl	Integer32,
        cpiPduNumberBranches    Integer32,
        cpiPduNumberOutlets		Integer32,
        cpiPduVersion			DisplayString,
        cpiPduUpgrade			Integer32,
        cpiPduChainRole			Integer32,
        cpiPduOutOfService		Integer32,
        cpiPduIp			    IpAddress,
        cpiPduIpv6			    DisplayString
    }

    cpiPduMac OBJECT-TYPE
        SYNTAX      MacAddress
        MAX-ACCESS  not-accessible
        STATUS      current
        DESCRIPTION
            "Get the MAC address of the PDU."
        ::= { cpiPduEntry 1 }

    cpiPduModel OBJECT-TYPE
        SYNTAX      DisplayString
        MAX-ACCESS  not-accessible
        STATUS      current
        DESCRIPTION
            "Get the model number of the PDU."
        ::= { cpiPduEntry 2 }

    cpiPduName OBJECT-TYPE
        SYNTAX      DisplayString
        MAX-ACCESS  read-write
        STATUS      current
        DESCRIPTION
            "Set or get the user assigned name of the PDU."
        ::= { cpiPduEntry 3 }

    cpiPduDescription OBJECT-TYPE
        SYNTAX      DisplayString
        MAX-ACCESS  read-write
        STATUS      current
        DESCRIPTION
            "Set or get the user assigned description of the PDU."
        ::= { cpiPduEntry 4 }

    cpiPduHasBranchMonitor OBJECT-TYPE
        SYNTAX      INTEGER { NotSupported(0), Supported(1) }
        MAX-ACCESS  not-accessible
        STATUS      current
        DESCRIPTION
            "An indicator if the PDU supports monitoring voltage, and current on branches in the PDU."
        ::= { cpiPduEntry 5 }

    cpiPduHasOutletMonitor OBJECT-TYPE
        SYNTAX      INTEGER { NotSupported(0), Supported(1) }
        MAX-ACCESS  not-accessible
        STATUS      current
        DESCRIPTION
            "An indicator if the PDU supports monitoring current on the individual outlets in the PDU."
        ::= { cpiPduEntry 6 }

    cpiPduHasOutletControl OBJECT-TYPE
        SYNTAX      INTEGER { NotSupported(0), Supported(1) }
        MAX-ACCESS  not-accessible
        STATUS      current
        DESCRIPTION
            "An indicator if the PDU supports control (turn on/off) individual outlets in the PDU."
        ::= { cpiPduEntry 7 }

    cpiPduNumberBranches OBJECT-TYPE
        SYNTAX      Integer32 (0..6)
        MAX-ACCESS  not-accessible
        STATUS      current
        DESCRIPTION
            "Get the number of branches (breakers) in the PDU."
        ::= { cpiPduEntry 8 }

    cpiPduNumberOutlets OBJECT-TYPE
        SYNTAX      Integer32 (0..48)
        MAX-ACCESS  not-accessible
        STATUS      current
        DESCRIPTION
            "Get the number of outlets in the PDU."
        ::= { cpiPduEntry 9 }

    cpiPduOutOfService OBJECT-TYPE
        SYNTAX      INTEGER { InService(0), OutOfService(1) }
        MAX-ACCESS  read-write
        STATUS      current
        DESCRIPTION
            "Set or get whether the PDU is in-service."
        ::= { cpiPduEntry 10 }

    cpiPduVersion OBJECT-TYPE
        SYNTAX      DisplayString
        MAX-ACCESS  not-accessible
        STATUS      current
        DESCRIPTION
            "Get the firmware version number of the PDU."
        ::= { cpiPduEntry 11 }

    cpiPduUpgrade OBJECT-TYPE
        SYNTAX      INTEGER { No(0), Yes(1) }
        MAX-ACCESS  not-accessible
        STATUS      current
        DESCRIPTION
            "An indicator if the PDU firmware is being upgraded."
        ::= { cpiPduEntry 12 }

    cpiPduChainRole OBJECT-TYPE
        SYNTAX      INTEGER { Secondary(0), Primary(1), Alternate(2) }
        MAX-ACCESS  read-write
        STATUS      current
        DESCRIPTION
            "Get the role of the PDU in a daisy chain."
        ::= { cpiPduEntry 13 }

    cpiPduIp OBJECT-TYPE
        SYNTAX      IpAddress
        MAX-ACCESS  not-accessible
        STATUS      current
        DESCRIPTION
            "Get IP address of the PDU."
        ::= { cpiPduEntry 14 }

    cpiPduIpv6 OBJECT-TYPE
        SYNTAX      DisplayString
        MAX-ACCESS  not-accessible
        STATUS      current
        DESCRIPTION
            "Get the IPv6 address of the PDU."
        ::= { cpiPduEntry 15 }

branch OBJECT IDENTIFIER ::= { econnect 3 }

cpiLineTableCount OBJECT-TYPE
    SYNTAX      Unsigned32
    UNITS       "Count"
    MAX-ACCESS  read-only
    STATUS      current
    DESCRIPTION
        "Get the number of PDU input lines being monitored by this PDU.  
         This is the number of entries in the cpiLineTable and accounts
         for all input lines in a daisy chain."
    ::= { branch 1 }

cpiPduLineTable OBJECT-TYPE
    SYNTAX      SEQUENCE OF CpiPduLineEntry
    MAX-ACCESS  not-accessible
    STATUS      current
    DESCRIPTION
        "This table contains a list of PDU line entries that are being
         monitored by the PDU.

         The table contains one, or many rows, depending upon the number
         of PDUs being monitored and the number of input lines. Each row 
         in the table represents a PDU line in the daisy chain.
         
         The table is indexed based on the corresponding Line Input ID and
         the source PDU MAC."
    ::= { branch 10 }

    cpiPduLineEntry OBJECT-TYPE
        SYNTAX      CpiPduLineEntry
        MAX-ACCESS  not-accessible
        STATUS      current
        DESCRIPTION
            "This entry defines the columns to be populated in the
             'cpiPduLineTable'.  Each column represents an attribute of a PDU.
             This table is indexed by the PDU Line identifier that is unique 
             within the PDU."

        INDEX
        { 
            cpiPduLineId,
            cpiPduLineMac 
        }
        ::= { cpiPduLineTable 1 }

    CpiPduLineEntry ::= SEQUENCE 
    {
        cpiPduLineMac			DisplayString,
        cpiPduLineId			DisplayString,	
        cpiPduLineCurrent		Integer32
    }

    cpiPduLineMac OBJECT-TYPE
        SYNTAX      MacAddress
        MAX-ACCESS  not-accessible
        STATUS      current
        DESCRIPTION
            "Get the MAC address of the PDU that owns the input line."
        ::= { cpiPduLineEntry 1 }

    cpiPduLineId OBJECT-TYPE
        SYNTAX      Integer32
        MAX-ACCESS  not-accessible
        STATUS      current
        DESCRIPTION
            "Get the ID of the input line on the PDU."
        ::= { cpiPduLineEntry 2 }

    cpiPduLineCurrent OBJECT-TYPE
        SYNTAX      Integer32
        MAX-ACCESS  not-accessible
        STATUS      current
        DESCRIPTION
            "Get current draw in 1/100 amp of the line on the PDU.  Convert the value by dividing by 100."
        ::= { cpiPduLineEntry 3 }

cpiBranchTableCount OBJECT-TYPE
    SYNTAX      Unsigned32
    UNITS       "Count"
    MAX-ACCESS  read-only
    STATUS      current
    DESCRIPTION
        "Get the number of PDU branches being monitored by this PDU.  This is the 
         number of entries in the cpiPduBranchTable."
    ::= { branch 100 }

cpiPduBranchTable OBJECT-TYPE
    SYNTAX      SEQUENCE OF CpiPduBranchEntry
    MAX-ACCESS  not-accessible
    STATUS      current
    DESCRIPTION
        "This table contains a list of PDU branch entries that are being
         monitored by the PDU.
         
         The table contains one, or many rows, depending upon the number
         of PDUs being monitored and the number of branches per PDU. Each row 
         in the table represents a PDU branch in the daisy chain.
         
         The table is indexed based on the corresponding Branch ID and
         the source PDU MAC."
    ::= { branch 110 }

    cpiPduBranchEntry OBJECT-TYPE
        SYNTAX      CpiPduBranchEntry
        MAX-ACCESS  not-accessible
        STATUS      current
        DESCRIPTION
            "This entry defines the columns to be populated in the
             'cpiPduBranchTable'.  Each column represents an attribute of a PDU.
             This table is indexed by the PDU Line identifier that is unique 
             within the PDU."

        INDEX
        { 
            cpiPduBranchId,
            cpiPduBranchMac
        }
        ::= { cpiPduBranchTable 1 }

    CpiPduBranchEntry ::= SEQUENCE 
    {
        cpiPduBranchMac			    DisplayString,
        cpiPduBranchId			    DisplayString,	
        cpiPduBranchCurrent		    Integer32,
        cpiPduBranchMaxCurrent		Integer32,
        cpiPduBranchVoltage		    Integer32,
        cpiPduBranchPower 		    Integer32,
        cpiPduBranchPowerFactor		Integer32,
        cpiPduBranchStatus		    Integer32,
        cpiPduBranchEnergy		    Counter64
    }

    cpiPduBranchMac OBJECT-TYPE
        SYNTAX      MacAddress
        MAX-ACCESS  not-accessible
        STATUS      current
        DESCRIPTION
            "Get the MAC address of the PDU that owns the branch."
        ::= { cpiPduBranchEntry 1 }

    cpiPduBranchId OBJECT-TYPE
        SYNTAX      Integer32
        MAX-ACCESS  not-accessible
        STATUS      current
        DESCRIPTION
            "Get the ID of the branch on the owning PDU."
        ::= { cpiPduBranchEntry 2 }

    cpiPduBranchCurrent OBJECT-TYPE
        SYNTAX      Integer32
        MAX-ACCESS  not-accessible
        STATUS      current
        DESCRIPTION
            "Get the current draw in 1/100 amp of the branch on the PDU.  Convert the value by dividing by 100."
        ::= { cpiPduBranchEntry 3 }

    cpiPduBranchMaxCurrent OBJECT-TYPE
        SYNTAX      Integer32
        MAX-ACCESS  not-accessible
        STATUS      current
        DESCRIPTION
            "Get the maximum current draw in 1/100 amp of the branch on the PDU.  Convert the value by dividing by 100."
        ::= { cpiPduBranchEntry 4 }

    cpiPduBranchVoltage OBJECT-TYPE
        SYNTAX      Integer32
        MAX-ACCESS  not-accessible
        STATUS      current
        DESCRIPTION
            "Get the voltage in 1/10 volts of the branch on the PDU.  Convert the value by dividing by 10."
        ::= { cpiPduBranchEntry 5 }

    cpiPduBranchPower OBJECT-TYPE
        SYNTAX      Integer32
        MAX-ACCESS  not-accessible
        STATUS      current
        DESCRIPTION
            "Get the power in volt-amps for the branch."
        ::= { cpiPduBranchEntry 6 }

    cpiPduBranchPowerFactor OBJECT-TYPE
        SYNTAX      Integer32
        MAX-ACCESS  not-accessible
        STATUS      current
        DESCRIPTION
            "Get the power factor for the branch."
        ::= { cpiPduBranchEntry 7 }

    cpiPduBranchStatus OBJECT-TYPE
        SYNTAX      INTEGER { NoAlarm(0), Warning(1), Alarm(2) }
        MAX-ACCESS  not-accessible
        STATUS      current
        DESCRIPTION
            "Get the alarm status of the branch."
        ::= { cpiPduBranchEntry 8 }

    cpiPduBranchEnergy OBJECT-TYPE
        SYNTAX      Counter64
        MAX-ACCESS  not-accessible
        STATUS      current
        DESCRIPTION
            "Get the branch energy accumulated in decaVA-secs, divide by 360 to obtain VA-hr."
        ::= { cpiPduBranchEntry 9 }

cpiPduBranchAlertTable OBJECT-TYPE
    SYNTAX      SEQUENCE OF CpiPduBranchAlertEntry
    MAX-ACCESS  not-accessible
    STATUS      current
    DESCRIPTION
        "This table contains a list of PDU branch alert entries that are
         being monitored by the PDU.

         The table contains one, or many rows, depending upon the number
         of PDUs being monitored and the number of branches per PDU. Each row 
         in the table represents a PDU branch in the daisy chain.
         
         The table is indexed based on the corresponding Branch ID and the
         source PDU MAC."
    ::= { branch 210 }

    cpiPduBranchAlertEntry OBJECT-TYPE
        SYNTAX      CpiPduBranchAlertEntry
        MAX-ACCESS  not-accessible
        STATUS      current
        DESCRIPTION
            "This entry defines the columns to be populated in the
             'cpiPduBranchAlertTable'.  Each column represents an alert attribute of a PDU.
             This table is indexed by the PDU Line identifier that is unique 
             within the PDU."

        INDEX
        { 
            cpiPduBranchAlertIndex 
        }
        ::= { cpiPduBranchAlertTable 1 }

    CpiPduBranchAlertEntry ::= SEQUENCE 
    {
        cpiPduBranchAlertIndex              Unsigned32,
        cpiPduBranchAlertMac		        MacAddress,
        cpiPduBranchAlertBranchId		    Integer32,
        cpiPduBranchAlertWarnLoCurrent      Integer32,
        cpiPduBranchAlertWarnHiCurrent      Integer32,
        cpiPduBranchAlertLoCurrent          Integer32,
        cpiPduBranchAlertHiCurrent          Integer32,
        cpiPduBranchAlertCriticalCurrent    Integer32,
        cpiPduBranchAlertWarnLoVolt         Integer32,
        cpiPduBranchAlertWarnHiVolt         Integer32,
        cpiPduBranchAlertLoVolt             Integer32,
        cpiPduBranchAlertHiVolt             Integer32
    }

    cpiPduBranchAlertMac OBJECT-TYPE
        SYNTAX      MacAddress
        MAX-ACCESS  not-accessible
        STATUS      current
        DESCRIPTION
            "Get the MAC address of the PDU."
        ::= { cpiPduBranchAlertEntry 1 }

    cpiPduBranchAlertBranchId OBJECT-TYPE
        SYNTAX      Integer32
        MAX-ACCESS  not-accessible
        STATUS      current
        DESCRIPTION
            "Get the branch ID on the PDU."
        ::= { cpiPduBranchAlertEntry 2 }

    cpiPduBranchAlertWarnLoCurrent OBJECT-TYPE
        SYNTAX      Integer32
        MAX-ACCESS  read-write
        STATUS      current
        DESCRIPTION
            "Set or get the current draw in 1/100 amp of the branch on 
            the PDU that triggers a warning condition.  Convert the 
            value by dividing by 100."
        ::= { cpiPduBranchAlertEntry 3 }

    cpiPduBranchAlertWarnHiCurrent OBJECT-TYPE
        SYNTAX      Integer32
        MAX-ACCESS  read-write
        STATUS      current
        DESCRIPTION
            "Set or get the current draw in 1/100 amp of the branch on 
            the PDU that triggers a warning condition.  Convert the 
            value by dividing by 100."
        ::= { cpiPduBranchAlertEntry 4 }

    cpiPduBranchAlertLoCurrent OBJECT-TYPE
        SYNTAX      Integer32
        MAX-ACCESS  read-write
        STATUS      current
        DESCRIPTION
            "Set or get the current draw in 1/100 amp of the branch on 
            the PDU that triggers an alarm condition.  Convert the 
            value by dividing by 100."
        ::= { cpiPduBranchAlertEntry 5 }

    cpiPduBranchAlertHiCurrent OBJECT-TYPE
        SYNTAX      Integer32
        MAX-ACCESS  read-write
        STATUS      current
        DESCRIPTION
            "Set or get the current draw in 1/100 amp of the branch on 
            the PDU, that triggers an alarm condition.  Convert the 
            value by dividing by 100."
        ::= { cpiPduBranchAlertEntry 6 }

    cpiPduBranchAlertCriticalCurrent OBJECT-TYPE
        SYNTAX      Integer32
        MAX-ACCESS  read-write
        STATUS      current
        DESCRIPTION
            "Set or get the critical current draw in 1/100 amp of the 
            branch on the PDU.  Convert the value by dividing by 100."
        ::= { cpiPduBranchAlertEntry 7 }

    cpiPduBranchAlertWarnLoVolt OBJECT-TYPE
        SYNTAX      Integer32
        MAX-ACCESS  read-write
        STATUS      current
        DESCRIPTION
            "Set or get the minimum voltage that the branch can reach 
            up to in 1/10th volts, 0=ignore.  Convert the value by 
            dividing by 10."
        ::= { cpiPduBranchAlertEntry 8 }

    cpiPduBranchAlertWarnHiVolt OBJECT-TYPE
        SYNTAX      Integer32
        MAX-ACCESS  read-write
        STATUS      current
        DESCRIPTION
            "Set or get the maximum voltage that the branch can reach 
            up to in 1/10th volts, 0=ignore.  Convert the value by 
            dividing by 10."
        ::= { cpiPduBranchAlertEntry 9 }

    cpiPduBranchAlertLoVolt OBJECT-TYPE
        SYNTAX      Integer32
        MAX-ACCESS  read-write
        STATUS      current
        DESCRIPTION
            "Set or get the minimum voltage that the branch can reach 
            up to in 1/10th volts, 0=ignore.  Convert the value by 
            dividing by 10."
        ::= { cpiPduBranchAlertEntry 10 }

    cpiPduBranchAlertHiVolt OBJECT-TYPE
        SYNTAX      Integer32
        MAX-ACCESS  read-write
        STATUS      current
        DESCRIPTION
            "Set or get the maximum voltage that the branch can reach 
            up to in 1/10th volts, 0=ignore.  Convert the value by 
            dividing by 10."
        ::= { cpiPduBranchAlertEntry 11 }

outlet OBJECT IDENTIFIER ::= { econnect 4 }

cpiOutletTableCount OBJECT-TYPE
    SYNTAX      Unsigned32
    UNITS       "Count"
    MAX-ACCESS  read-only
    STATUS      current
    DESCRIPTION
        "Get the number of PDU outlets being monitored by this PDU. This 
         is the number of entries in the cpiPduOutletTable."
    ::= { outlet 1 }

cpiPduOutletTable OBJECT-TYPE
    SYNTAX      SEQUENCE OF CpiPduOutletEntry
    MAX-ACCESS  not-accessible
    STATUS      current
    DESCRIPTION
        "This table contains a list of PDU outlet entries that are being
         monitored by the PDU.

         The table contains one, or many rows, depending upon the number
         of PDUs being monitored and the number of outlets on each PDU. 
         Each row in the table represents a PDU outlet in the daisy chain.
         
         The table is indexed based on the corresponding Outlet ID and
         the source PDU MAC."
    ::= { outlet 10 }

    cpiPduOutletEntry OBJECT-TYPE
        SYNTAX      CpiPduOutletEntry
        MAX-ACCESS  not-accessible
        STATUS      current
        DESCRIPTION
            "This entry defines the columns to be populated in the
             'cpiPduOutletTable'.  Each column represents an outlet of a PDU.
             This table is indexed by the PDU Outlet identifier that is unique 
             within the PDU."

        INDEX
        { 
            cpiPduOutletId, 
            cpiPduOutletMac
        }
        ::= { cpiPduOutletTable 1 }

    CpiPduOutletEntry ::= SEQUENCE 
    {
        cpiPduOutletMac		    	DisplayString,
        cpiPduOutletId		    	Integer32,
        cpiPduOutletBranchId    	Integer32,
        cpiPduOutletName	    	DisplayString,
        cpiPduOutletDescription    	DisplayString,
        cpiPduOutletCurrent		    Integer32,	    
        cpiPduOutletVoltage		    Integer32,
        cpiPduOutletPower		    Integer32,	    
        cpiPduOutletStatus		    Integer32,
        cpiPduOutletEnergy		    Counter64,
        cpiPduOutletControl		    Integer32,
        cpiPduOutletReset		    Integer32
    }

    cpiPduOutletMac OBJECT-TYPE
        SYNTAX      MacAddress
        MAX-ACCESS  not-accessible
        STATUS      current
        DESCRIPTION
            "Get the MAC address of the source PDU."
        ::= { cpiPduOutletEntry 1 }

    cpiPduOutletId OBJECT-TYPE
        SYNTAX      Integer32
        MAX-ACCESS  not-accessible
        STATUS      current
        DESCRIPTION
            "Get the ID of the outlet on the PDU."
        ::= { cpiPduOutletEntry 2 }

    cpiPduOutletBranchId OBJECT-TYPE
        SYNTAX      Integer32
        MAX-ACCESS  not-accessible
        STATUS      current
        DESCRIPTION
            "Get the ID of the branch the outlet is associated with on the PDU."
        ::= { cpiPduOutletEntry 3 }

    cpiPduOutletName OBJECT-TYPE
        SYNTAX      DisplayString
        MAX-ACCESS  read-write
        STATUS      current
        DESCRIPTION
            "Set or get the user supplied name of the outlet on the PDU."
        ::= { cpiPduOutletEntry 4 }

    cpiPduOutletDescription OBJECT-TYPE
        SYNTAX      DisplayString
        MAX-ACCESS  read-write
        STATUS      current
        DESCRIPTION
            "Set or get the user supplied description of the outlet on the PDU."
        ::= { cpiPduOutletEntry 5 }

    cpiPduOutletCurrent OBJECT-TYPE
        SYNTAX      Integer32
        MAX-ACCESS  not-accessible
        STATUS      current
        DESCRIPTION
            "Get the current draw in 1/100 amp of the outlet on the PDU.  Convert 
            the value by dividing by 100."
        ::= { cpiPduOutletEntry 6 }

    cpiPduOutletVoltage OBJECT-TYPE
        SYNTAX      Integer32
        MAX-ACCESS  not-accessible
        STATUS      current
        DESCRIPTION
            "Get the voltage in 1/10 volts of the outlet on the PDU.  Convert the 
            value by dividing by 10."
        ::= { cpiPduOutletEntry 7 }

    cpiPduOutletPower OBJECT-TYPE
        SYNTAX      Integer32
        MAX-ACCESS  not-accessible
        STATUS      current
        DESCRIPTION
            "The power in 1/10 wat of the outlet on the PDU.  Convert the value by dividing by 10."
        ::= { cpiPduOutletEntry 8 }

    cpiPduOutletStatus OBJECT-TYPE
        SYNTAX      INTEGER { NoAlarm(0), Warning(1), Alarm(2) }
        MAX-ACCESS  not-accessible
        STATUS      current
        DESCRIPTION
            "Get the alarm status of the outlet."
        ::= { cpiPduOutletEntry 9 }

    cpiPduOutletEnergy OBJECT-TYPE
        SYNTAX      Counter64
        MAX-ACCESS  not-accessible
        STATUS      current
        DESCRIPTION
            "Get the outlet energy accumulated in decaWatt-secs, divide by 360 to obtain Watt-hr."
        ::= { cpiPduOutletEntry 10 }

    cpiPduOutletControl OBJECT-TYPE
        SYNTAX      INTEGER { OFF(0), ON(1) }
        MAX-ACCESS  read-write
        STATUS      current
        DESCRIPTION
            "Set or get power control to the outlet."
        ::= { cpiPduOutletEntry 11 }

    cpiPduOutletReset OBJECT-TYPE
        SYNTAX      INTEGER { NOMINAL(0), RESET(1) }
        MAX-ACCESS  read-write
        STATUS      current
        DESCRIPTION
            "Set or get reset power to the outlet."
        ::= { cpiPduOutletEntry 12 }

cpiPduOutletConfigTable OBJECT-TYPE
    SYNTAX      SEQUENCE OF CpiPduOutletConfigEntry
    MAX-ACCESS  not-accessible
    STATUS      current
    DESCRIPTION
        "This table contains a list of PDU outlet configuration entries
        that are being monitored by the PDU.

         The table contains one, or many rows, depending upon the number
         of PDUs being monitored and the number of outlets per PDU. Each row 
         in the table represents a PDU outlet in the daisy chain.
         
         The table is indexed based on the corresponding Outlet ID and
         the source PDU MAC."
    ::= { outlet 210 }

    cpiPduOutletConfigEntry OBJECT-TYPE
        SYNTAX      CpiPduOutletConfigEntry
        MAX-ACCESS  not-accessible
        STATUS      current
        DESCRIPTION
            "This entry defines the columns to be populated in the
             'cpiPduOutletConfigTable'.  Each column represents an 
             configurable attribute of an outlet in the PDU. This 
             table is indexed by the PDU Line identifier that is 
             unique within the PDU."

        INDEX
        { 
            cpiPduOutletConfigOutletId,
            cpiPduOutletConfigMac
        }
        ::= { cpiPduOutletConfigTable 1 }

    CpiPduOutletConfigEntry ::= SEQUENCE 
    {
        cpiPduOutletConfigMac		        DisplayString,
        cpiPduOutletConfigOutletId		    Integer32,
        cpiPduOutletConfigOnDelay           Integer32,
        cpiPduOutletConfigResetDelay        Integer32
    }

    cpiPduOutletConfigMac OBJECT-TYPE
        SYNTAX      MacAddress
        MAX-ACCESS  not-accessible
        STATUS      current
        DESCRIPTION
            "Get the MAC address of the PDU."
        ::= { cpiPduOutletConfigEntry 1 }

    cpiPduOutletConfigOutletId OBJECT-TYPE
        SYNTAX      Integer32
        MAX-ACCESS  not-accessible
        STATUS      current
        DESCRIPTION
            "Get the ID of the outlet on the PDU."
        ::= { cpiPduOutletConfigEntry 2 }

    cpiPduOutletConfigOnDelay OBJECT-TYPE
        SYNTAX Integer32 (0..255)
        MAX-ACCESS read-write
        STATUS current
        DESCRIPTION
            "Set or get the outlet power-on delay in seconds."
        ::= { cpiPduOutletConfigEntry 3 }

    cpiPduOutletConfigResetDelay OBJECT-TYPE
        SYNTAX Integer32 (0..255)
        MAX-ACCESS read-write
        STATUS current
        DESCRIPTION
            "Set or get the outlet reset delay in seconds."
        ::= { cpiPduOutletConfigEntry 4 }

cpiPduOutletAlertTable OBJECT-TYPE
    SYNTAX      SEQUENCE OF CpiPduOutletAlertEntry
    MAX-ACCESS  not-accessible
    STATUS      current
    DESCRIPTION
        "This table contains a list of PDU outlet alert entries that are
        being monitored by the PDU.

         The table contains one, or many rows, depending upon the number
         of PDUs being monitored and the number of outlets per PDU. Each row 
         in the table represents a PDU outlet in the daisy chain.
         
         The table is indexed based on the corresponding Outlet ID and the
         source PDU MAC."
    ::= { outlet 310 }

    cpiPduOutletAlertEntry OBJECT-TYPE
        SYNTAX      CpiPduOutletAlertEntry
        MAX-ACCESS  not-accessible
        STATUS      current
        DESCRIPTION
            "This entry defines the columns to be populated in the
             'cpiPduOutletAlertTable'.  Each column represents an alert attribute of a PDU.
             This table is indexed by the PDU Line identifier that is unique 
             within the PDU."

        INDEX
        { 
            cpiPduOutletAlertOutletId,
            cpiPduOutletAlertMac
        }
        ::= { cpiPduOutletAlertTable 1 }

    CpiPduOutletAlertEntry ::= SEQUENCE 
    {
        cpiPduOutletAlertMac		        DisplayString,
        cpiPduOutletAlertOutletId	        Integer32,
        cpiPduOutletAlertWarnLoCurrent      Integer32,
        cpiPduOutletAlertWarnHiCurrent      Integer32,
        cpiPduOutletAlertLoCurrent          Integer32,
        cpiPduOutletAlertHiCurrent          Integer32,
        cpiPduOutletAlertCriticalCurrent    Integer32
    }

    cpiPduOutletAlertMac OBJECT-TYPE
        SYNTAX      MacAddress
        MAX-ACCESS  not-accessible
        STATUS      current
        DESCRIPTION
            "Get the MAC address of the PDU."
        ::= { cpiPduOutletAlertEntry 1 }

    cpiPduOutletAlertId OBJECT-TYPE
        SYNTAX      DisplayString
        MAX-ACCESS  not-accessible
        STATUS      current
        DESCRIPTION
            "Get the outlet ID on the PDU."
        ::= { cpiPduOutletAlertEntry 2 }

    cpiPduOutletAlertWarnLoCurrent OBJECT-TYPE
        SYNTAX      Integer32
        MAX-ACCESS  read-write
        STATUS      current
        DESCRIPTION
            "Set or get the current draw in 1/100 amp of the branch on 
            the PDU that triggers a warning condition.  Convert the 
            value by dividing by 100."
        ::= { cpiPduOutletAlertEntry 3 }

    cpiPduOutletAlertWarnHiCurrent OBJECT-TYPE
        SYNTAX      Integer32
        MAX-ACCESS  read-write
        STATUS      current
        DESCRIPTION
            "Set or get the current draw in 1/100 amp of the branch on 
            the PDU that triggers a warning condition.  Convert the 
            value by dividing by 100."
        ::= { cpiPduOutletAlertEntry 4 }

    cpiPduOutletAlertLoCurrent OBJECT-TYPE
        SYNTAX      Integer32
        MAX-ACCESS  read-write
        STATUS      current
        DESCRIPTION
            "Set or get the current draw in 1/100 amp of the branch on 
            the PDU that triggers an alarm condition.  Convert the 
            value by dividing by 100."
        ::= { cpiPduOutletAlertEntry 5 }

    cpiPduOutletAlertHiCurrent OBJECT-TYPE
        SYNTAX      Integer32
        MAX-ACCESS  read-write
        STATUS      current
        DESCRIPTION
            "Set or get the current draw in 1/100 amp of the branch on 
            the PDU, that triggers an alarm condition.  Convert the 
            value by dividing by 100."
        ::= { cpiPduOutletAlertEntry 6 }

    cpiPduOutletAlertCriticalCurrent OBJECT-TYPE
        SYNTAX      Integer32
        MAX-ACCESS  read-write
        STATUS      current
        DESCRIPTION
            "Set or get the critical current draw in 1/100 amp of the 
            outlet on the PDU.  Convert the value by dividing by 100."
        ::= { cpiPduOutletAlertEntry 7 }

sensors OBJECT IDENTIFIER ::= { econnect 5 }

cpiPduSensorCount OBJECT-TYPE
    SYNTAX      Unsigned32
    UNITS       "Count"
    MAX-ACCESS  read-only
    STATUS      current
    DESCRIPTION
        "Get the number of PDU sensors being monitored by this PDU.  This is the 
         number of entries in the cpiPduSensorTable."
    ::= { sensors 1 }

cpiPduSensorTable OBJECT-TYPE
    SYNTAX      SEQUENCE OF CpiPduSensorEntry
    MAX-ACCESS  not-accessible
    STATUS      current
    DESCRIPTION
        "This table contains a list of PDU sensor entries that are being monitored
         by the PDU.

         The table contains zero, one, or many rows, depending upon the number
         of PDUs being monitored and the number of sensors attached to the PDUs in
         the daisy chain. Each row in the table represents a sensor in the daisy chain.
         
         The table is index based on the corresponding Sensor ID and the source
         PDU MAC."
    ::= { sensors 10 }

    cpiPduSensorEntry OBJECT-TYPE
        SYNTAX      CpiPduSensorEntry
        MAX-ACCESS  not-accessible
        STATUS      current
        DESCRIPTION
            "This entry defines the columns to be populated in the
             'cpiPduTable'.  Each column represents an attribute of a PDU.
             This table is indexed by the PDU identifier that is unique 
             within the PDU."

        INDEX
        { 
            cpiPduSensorId, 
            cpiPduSensorMac
        }
        ::= { cpiPduSensorTable 1 }

    CpiPduSensorEntry ::= SEQUENCE 
    {
        cpiPduSensorMac		DisplayString,
        cpiPduSensorId		Integer32,
        cpiPduSensorName	DisplayString,
        cpiPduSensorType	Integer32,
        cpiPduSensorValue	Integer32
    }

    cpiPduSensorMac OBJECT-TYPE
        SYNTAX      MacAddress
        MAX-ACCESS  not-accessible
        STATUS      current
        DESCRIPTION
            "Get the MAC address of the PDU."
        ::= { cpiPduSensorEntry 1 }

    cpiPduSensorId OBJECT-TYPE
        SYNTAX      Integer32
        MAX-ACCESS  not-accessible
        STATUS      current
        DESCRIPTION
            "Get the sensor ID on the PDU."
        ::= { cpiPduSensorEntry 2 }

    cpiPduSensorName OBJECT-TYPE
        SYNTAX      DisplayString
        MAX-ACCESS  not-accessible
        STATUS      current
        DESCRIPTION
            "Set or tet the user defined name of the sensor."
        ::= { cpiPduSensorEntry 3 }

    cpiPduSensorType OBJECT-TYPE
        SYNTAX      INTEGER { Temperature(1), Humidity(2) }
        MAX-ACCESS  not-accessible
        STATUS      current
        DESCRIPTION
            "Get the type of sensor for the entry."
        ::= { cpiPduSensorEntry 4 }

    cpiPduSensorValue OBJECT-TYPE
        SYNTAX      Integer32
        MAX-ACCESS  not-accessible
        STATUS      current
        DESCRIPTION
            "Get the value of the sensor."
        ::= { cpiPduSensorEntry 5 }

cpiPduSensorAlertTable OBJECT-TYPE
    SYNTAX      SEQUENCE OF CpiPduSensorAlertEntry
    MAX-ACCESS  not-accessible
    STATUS      current
    DESCRIPTION
        "This table contains a list of PDU sensor alert entries that are
         being monitored by the PDU.

         The table contains zero, one, or many rows, depending upon the number
         of PDUs being monitored and the number of sensors attached to the PDUs in
         the daisy chain. Each row in the table represents a sensor in the daisy chain.
         
         The table is index based on the corresponding Sonsor ID and the source
         PDU MAC."
    ::= { sensors 110 }

    cpiPduSensorAlertEntry OBJECT-TYPE
        SYNTAX      CpiPduSensorAlertEntry
        MAX-ACCESS  not-accessible
        STATUS      current
        DESCRIPTION
            "This entry defines the columns to be populated in the
             'cpiPduTable'.  Each column represents an attribute of a PDU.
             This table is indexed by the PDU identifier that is unique 
             within the PDU."

        INDEX
        { 
            cpiPduSensorAlertSensorId,
            cpiPduSensorAlertMac
        }
        ::= { cpiPduSensorAlertTable 1 }

    CpiPduSensorAlertEntry ::= SEQUENCE 
    {
        cpiPduSensorAlertMac		        DisplayString,		
        cpiPduSensorAlertSensorId	        Integer32,
        cpiPduSensorAlertWarnMin	        Integer32,
        cpiPduSensorAlertWarnMax	        Integer32,
        cpiPduSensorAlertMin	            Integer32,
        cpiPduSensorAlertMax	            Integer32
    }

    cpiPduSensorAlertMac OBJECT-TYPE
        SYNTAX      MacAddress
        MAX-ACCESS  not-accessible
        STATUS      current
        DESCRIPTION
            "Get the MAC address of the PDU."
        ::= { cpiPduSensorAlertEntry 1 }

    cpiPduSensorAlertId OBJECT-TYPE
        SYNTAX      Integer32
        MAX-ACCESS  not-accessible
        STATUS      current
        DESCRIPTION
            "Get the id of the sensor."
        ::= { cpiPduSensorAlertEntry 2 }

    cpiPduSensorAlertWarnMin OBJECT-TYPE
        SYNTAX      Integer32
        MAX-ACCESS  read-write
        STATUS      current
        DESCRIPTION
            "Set or get the minimum warning value of the sensor."
        ::= { cpiPduSensorAlertEntry 3 }

    cpiPduSensorAlertWarnMax OBJECT-TYPE
        SYNTAX      Integer32
        MAX-ACCESS  read-write
        STATUS      current
        DESCRIPTION
            "Set or get the maximum warning value of the sensor."
        ::= { cpiPduSensorAlertEntry 4 }

    cpiPduSensorAlertMin OBJECT-TYPE
        SYNTAX      Integer32
        MAX-ACCESS  read-write
        STATUS      current
        DESCRIPTION
            "Set or get the minimum alarm value of the sensor."
        ::= { cpiPduSensorAlertEntry 5 }

    cpiPduSensorAlertMax OBJECT-TYPE
        SYNTAX      Integer32
        MAX-ACCESS  read-write
        STATUS      current
        DESCRIPTION
            "Set or get the maximum alarm value of the sensor."
        ::= { cpiPduSensorAlertEntry 6 }

group OBJECT IDENTIFIER ::= { econnect 6 }

cpiPduGroupCount OBJECT-TYPE
    SYNTAX      Unsigned32
    UNITS       "Count"
    MAX-ACCESS  read-only
    STATUS      current
    DESCRIPTION
        "Get the number of supported groups by the PDU. Value from 0 to 16."
    ::= { group 1 }

cpiPduGroupOutletCount OBJECT-TYPE
    SYNTAX      Unsigned32
    UNITS       "Count"
    MAX-ACCESS  read-only
    STATUS      current
    DESCRIPTION
        "Get the number of outlets in the Group Outlet Table."
    ::= { group 2 }

cpiGroupTable OBJECT-TYPE
    SYNTAX      SEQUENCE OF CpiGroupEntry
    MAX-ACCESS  not-accessible
    STATUS      current
    DESCRIPTION
        "This table contains a list of PDU group entries that are being monitored
        by the PDU.
         
         The table contains one, or many rows, depending upon the number
         of groups that have been configured. Each row in the table represents a
         group."
    ::= { group 10 }

    cpiGroupEntry OBJECT-TYPE
        SYNTAX      CpiGroupEntry
        MAX-ACCESS  not-accessible
        STATUS      current
        DESCRIPTION
            "This entry defines the columns to be populated in the
             'cpiGroupTable'.  This table is indexed by the group identifier that 
             is unique within the PDU."

        INDEX
        { 
            cpiGroupEntryIndex 
        }
        ::= { cpiGroupTable 1 }

    CpiGroupEntry ::= SEQUENCE 
    {
        cpiGroupEntryIndex      Unsigned32,
        cpiGroupName		    DisplayString,
        cpiGroupMap		        OCTET STRING
    }

    cpiGroupEntryIndex OBJECT-TYPE
        SYNTAX      Unsigned32
        MAX-ACCESS  not-accessible
        STATUS      current
        DESCRIPTION
            "This is the index that indicates the row of the 'cpiPduTable'."
        ::= { cpiGroupEntry 1 }

    cpiGroupName OBJECT-TYPE
        SYNTAX      DisplayString
        MAX-ACCESS  read-write
        STATUS      current
        DESCRIPTION
            "Name for GROUP 1 of receptacles."
        ::= { cpiGroupEntry 2 }

cpiGroupOutletTable OBJECT-TYPE
    SYNTAX      SEQUENCE OF CpiGroupOutletEntry
    MAX-ACCESS  not-accessible
    STATUS      current
    DESCRIPTION
        "This table contains a list of PDU group entries.
         The table contains zero, one, or many rows, depending upon the number
         of groups that have been configured. Each row in the table represents a
         group."
    ::= { group 20 }

    cpiGroupOutletEntry OBJECT-TYPE
        SYNTAX      CpiGroupOutletEntry
        MAX-ACCESS  not-accessible
        STATUS      current
        DESCRIPTION
            "This entry defines the columns to be populated in the
             'cpiGroupTable'.  This table is indexed by the group identifier that 
             is unique within the PDU."

        INDEX
        { 
            cpiGroupOutletEntryIndex 
        }
        ::= { cpiGroupOutletTable 1 }
        
    CpiGroupOutletEntry ::= SEQUENCE 
    {
        cpiGroupOutletEntryIndex    Unsigned32,
        cpiGroupOutletGroupID		Unsigned32,
        cpiGroupOutletPDUMac        OCTET STRING,
        cpiGroupOutletOutletId		Integer32,
    }

    cpiGroupOutletEntryIndex OBJECT-TYPE
        SYNTAX      Unsigned32
        MAX-ACCESS  not-accessible
        STATUS      current
        DESCRIPTION
            "This is the index that indicates the row of the 'cpiGroupOutletTable'."
        ::= { cpiGroupOutletEntry 1 }

    cpiGroupOutletGroupID OBJECT-TYPE
        SYNTAX      Unsigned32
        MAX-ACCESS  not-accessible
        STATUS      current
        DESCRIPTION
            "Name for GROUP 1 of receptacles."
        ::= { cpiGroupOutletEntry 2 }

    cpiGroupOutletPDUMac OBJECT-TYPE
        SYNTAX		MacAddress
        MAX-ACCESS	read-write
        STATUS		current
        DESCRIPTION
            "MAC of PDU the outlet is on."
        ::= { cpiGroupOutletEntry 3 }
        
    cpiGroupOutletOutletId OBJECT-TYPE
        SYNTAX		Integer32
        MAX-ACCESS	read-write
        STATUS		current
        DESCRIPTION
            "The ID of the outlet on the PDU."
        ::= { cpiGroupOutletEntry 4 }

traps OBJECT IDENTIFIER ::= { econnect 7 }

mibconformance OBJECT IDENTIFIER ::= { econnect 8 }

END
