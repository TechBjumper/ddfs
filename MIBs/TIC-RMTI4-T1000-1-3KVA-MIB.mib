-- Toshiba MIB
-- UPS MIB for Toshiba T1000 Uninterruptible Power Systems with RemotEye 4
--
--{iso(1) org(3) dod(6) internet(1) private(4) enterprises(1) toshiba(186) 
-- equ(1) equups(19) ticups(2) rmti4 (5) upsT1000-1-3kva (7)}
--=============================================================================

TIC-RMTI4-T1000-1-3KVA-MIB DEFINITIONS ::= BEGIN

--=============================================================================
-- Update : October 4, 2016
-- By     : Edwin Rubio, Toshiba International Corp. 
-- Revised: renamed MIB file from upsT1000_1-3kva to upsT1000-1-3kva
--=============================================================================
-- Update : March 7, 2016
-- By     : Edwin Rubio, Toshiba International Corp.
-- Revised: T1000 (1-3KVA) First Draft 
--=============================================================================

IMPORTS
  DisplayString, TimeStamp, TimeInterval, TestAndIncr, AutonomousType
    FROM SNMPv2-TC
  enterprises
    FROM RFC1155-SMI
  OBJECT-TYPE
    FROM RFC-1212
  TRAP-TYPE
    FROM RFC-1215;

PositiveInteger    ::= INTEGER (0..2147483647)
NonNegativeInteger ::= INTEGER (0..2147483647)

toshiba      OBJECT IDENTIFIER ::= { enterprises 186 }
equ          OBJECT IDENTIFIER ::= { toshiba 1 }
equUPS       OBJECT IDENTIFIER ::= { equ 19 }
ticUPS       OBJECT IDENTIFIER ::= { equUPS 2 }
rmti4        OBJECT IDENTIFIER ::= { ticUPS 5 }
upsT1000-1-3kva    OBJECT IDENTIFIER ::= { rmti4 7 }


upsIdent     OBJECT IDENTIFIER ::= { upsT1000-1-3kva 1 }
upsInput     OBJECT IDENTIFIER ::= { upsT1000-1-3kva 2 }
upsOutput    OBJECT IDENTIFIER ::= { upsT1000-1-3kva 3 }
upsBattery   OBJECT IDENTIFIER ::= { upsT1000-1-3kva 4 }
upsStsCtlCfg OBJECT IDENTIFIER ::= { upsT1000-1-3kva 5 }
upsAlarm     OBJECT IDENTIFIER ::= { upsT1000-1-3kva 6 }
upsTrap      OBJECT IDENTIFIER ::= { upsT1000-1-3kva 7 }

-- ===========================================================================
-- upsIdent - upsT1000-1-3kva Group 1
-- The UPS Identification Group
-- ===========================================================================

upsIdentManufacturer OBJECT-TYPE
    SYNTAX DisplayString (SIZE (0..31))
    ACCESS read-only
    STATUS mandatory
    DESCRIPTION
        "The name of the UPS manufacturer."
    ::= { upsIdent 1 }

upsIdentTypeform OBJECT-TYPE
    SYNTAX DisplayString (SIZE(0..16))
    ACCESS read-only
    STATUS mandatory
    DESCRIPTION
        "The UPS Typeform."
    ::= { upsIdent 2 }

upsIdentSerialNumber OBJECT-TYPE
    SYNTAX DisplayString (SIZE(0..16))
    ACCESS read-only
    STATUS mandatory
    DESCRIPTION
        "The UPS Serial Number."
    ::= { upsIdent 3 }

upsIdentMainFirmwareVersion OBJECT-TYPE
    SYNTAX DisplayString (SIZE(0..16))
    ACCESS read-only
    STATUS mandatory
    DESCRIPTION
        "The UPS firmware version of the main controller."
    ::= { upsIdent 4 }

upsIdentSysName OBJECT-TYPE
    SYNTAX DisplayString (SIZE(0..16))
    ACCESS read-write
    STATUS mandatory
    DESCRIPTION
        "A string identifying the UPS. This object should be set by the administrator."
    ::= { upsIdent 5 }

upsIdentAttachedDevices OBJECT-TYPE
    SYNTAX DisplayString (SIZE(0..16))
    ACCESS read-write
    STATUS mandatory
    DESCRIPTION
        "A string identifying the devices attached to the output(s) of the UPS. This object should be set by the administrator."
    ::= { upsIdent 6 }

upsIdentInstallationDate OBJECT-TYPE
    SYNTAX DisplayString (SIZE(8))
    ACCESS read-write
    STATUS mandatory
    DESCRIPTION
        "The UPS installation date in YYYYMMDD format."
    ::= { upsIdent 7 }

-- ===========================================================================
-- upsInput - upsT1000-1-3kva Group 2
-- The UPS Input Data Group 
-- ===========================================================================
upsInputTable OBJECT-TYPE
    SYNTAX SEQUENCE OF UpsInputEntry
    ACCESS not-accessible
    STATUS mandatory
    DESCRIPTION
        "A list of input table entries. The number of entries is given by the value of upsInputNumOfPhases."
    ::= { upsInput  1 }

upsInputEntry OBJECT-TYPE
    SYNTAX UpsInputEntry
    ACCESS not-accessible
    STATUS mandatory
    DESCRIPTION
        "An entry containing information applicable to a particular input line."
    INDEX { upsInputIndex }
    ::= { upsInputTable  1 }

UpsInputEntry ::=
    SEQUENCE {
        upsInputIndex      PositiveInteger,
        upsInputFrequency  INTEGER,
        upsInputVoltage    INTEGER,
		upsInputVoltagePercent INTEGER,
        upsInputRatedVoltage    INTEGER
    }

-- ===========================================================================
-- upsInputTable/upsInputEntry/upsInputIndex
-- ===========================================================================
upsInputIndex OBJECT-TYPE
    SYNTAX PositiveInteger 
    ACCESS not-accessible
    STATUS mandatory
    DESCRIPTION
        "The input line identifier"
    ::= { upsInputEntry 1 }

upsInputFrequency OBJECT-TYPE
    SYNTAX INTEGER
    UNITS  "0.1 Hertz"
    ACCESS read-only
    STATUS mandatory
    DESCRIPTION
        "The present input frequency to the UPS system in 1/10 of Hz."
    ::= { upsInputEntry 2 }

upsInputVoltage OBJECT-TYPE
    SYNTAX INTEGER
    UNITS  "RMS Volts"
    ACCESS read-only
    STATUS mandatory
    DESCRIPTION
        "The input utility line voltage in RMS volts."
    ::= { upsInputEntry 3 }
	
upsInputVoltagePercent OBJECT-TYPE
    SYNTAX INTEGER
    UNITS  "Percent"
    ACCESS read-only
    STATUS mandatory
    DESCRIPTION
        "The input utility line voltage in percent."
    ::= { upsInputEntry 4 }

upsInputRatedVoltage OBJECT-TYPE
    SYNTAX INTEGER
    UNITS  "RMS Volts"
    ACCESS read-only
    STATUS mandatory
    DESCRIPTION
        "The magnitude of the rated input voltage in RMS volts."
    ::= { upsInputEntry 5 }

-- ===========================================================================
-- upsOutput - upsT1000-1-3kva Group 3
-- The UPS Output Data Group
-- ===========================================================================
upsOutputVoltage OBJECT-TYPE
    SYNTAX INTEGER
    UNITS  "RMS Volts"
    ACCESS read-only
    STATUS mandatory
    DESCRIPTION
        "The output utility line voltage in RMS volts."
    ::= { upsOutput 1 }
	
upsOutputLoadPercentage OBJECT-TYPE
    SYNTAX INTEGER
    UNITS  "Percent"
    ACCESS read-only
    STATUS mandatory
    DESCRIPTION
        "The present UPS output load percentage which is current percent."
    ::= { upsOutput 2 }

upsOutputRatedTable OBJECT-TYPE
    SYNTAX SEQUENCE OF UpsOutputRatedEntry
    ACCESS not-accessible
    STATUS mandatory
    DESCRIPTION
        "A list of Output table entries. The number of entries is given by the value of upsOutputNumOfPhases."
    ::= { upsOutput  3 }

upsOutputRatedEntry OBJECT-TYPE
    SYNTAX UpsOutputRatedEntry
    ACCESS not-accessible
    STATUS mandatory
    DESCRIPTION
        "An entry containing information applicable to a particular Output line."
    INDEX { upsOutputSlotIndex }
    ::= { upsOutputRatedTable 1 }

UpsOutputRatedEntry ::=
    SEQUENCE {
        upsOutputSlotIndex         PositiveInteger,
        upsOutputRatedFrequency     INTEGER,
        upsOutputRatedVoltage       INTEGER,
        upsOutputRatedActivePower   INTEGER,
        upsOutputRatedApparentPower INTEGER
    }

-- ===========================================================================
-- upsOutputRatedTable/upsOutputRatedEntry/upsOutputSlotIndex
-- ===========================================================================
upsOutputSlotIndex OBJECT-TYPE
    SYNTAX PositiveInteger 
    ACCESS not-accessible
    STATUS mandatory
    DESCRIPTION
        "The Output line identifier."
    ::= { upsOutputRatedEntry 1 }

upsOutputRatedFrequency OBJECT-TYPE
    SYNTAX INTEGER
    UNITS  "0.1 Hertz"
    ACCESS read-only
    STATUS mandatory
    DESCRIPTION
        "The rated output frequency of the UPS system in 1/10 of Hz."
    ::= { upsOutputRatedEntry 2 }

upsOutputRatedVoltage OBJECT-TYPE
    SYNTAX INTEGER
    UNITS  "RMS Volts"
    ACCESS read-only
    STATUS mandatory
    DESCRIPTION
        "The rated Output voltage in RMS volts."
    ::= { upsOutputRatedEntry 3 }


upsOutputRatedActivePower OBJECT-TYPE
    SYNTAX INTEGER
    UNITS  "Watts"
    ACCESS read-only
    STATUS mandatory
    DESCRIPTION
        "The rated output active power in Watt."
    ::= { upsOutputRatedEntry 4 }

upsOutputRatedApparentPower OBJECT-TYPE
    SYNTAX INTEGER
    UNITS  "Volt-Amp"
    ACCESS read-only
    STATUS mandatory
    DESCRIPTION
        "The rated output apparent power in Volt-Amp."
    ::= { upsOutputRatedEntry 5 }

upsOutputRatedPowerFactor OBJECT-TYPE
    SYNTAX INTEGER
    UNITS  "0.01"
    ACCESS read-only
    STATUS mandatory
    DESCRIPTION
        "The rated output power factor."
    ::= { upsOutput 4 }

-- ===========================================================================
-- upsBattery upsT1000-1-3kva Group 4
-- The UPS Battery Data Group
-- ===========================================================================

upsBatteryStatus OBJECT-TYPE
    SYNTAX INTEGER {
         unknown(1),
         batteryNormal(2),
         batteryLow(3),
         batteryDepleted(4),
         batteryDischarging(5),
         batteryFailure(6)
    }
    ACCESS read-only
    STATUS mandatory
    DESCRIPTION
        "The indication of the capacity remaining in the UPS system's batteries. A value of batteryNormal indicates that the remaining run-time sufficient to handle the load. A value of batteryLow indicates the battery level is low. Continued operation in battery mode will deplate batteries. A value of batteryDepleted indicates that the UPS will be unable to sustain the present load when and if the utility power is lost (including the possibility that the utility power is currently absent and the UPS is unable to sustain the output). A value of batteryDischarging indicates UPS system is in Battery power."
    ::= { upsBattery 1 }

upsBatteryElapsedTimeOnBatteryPower OBJECT-TYPE
    SYNTAX NonNegativeInteger
    UNITS   "Second"
    ACCESS read-only
    STATUS mandatory
    DESCRIPTION
        "If the unit is on battery power, the elapsed time since the UPS on battery power, or the time since the network management subsystem was last restarted, whichever is less. Zero shall be returned if the unit is not on battery power."
    ::= { upsBattery 2 }

upsBatteryEstimatedBatteryRuntime OBJECT-TYPE
     SYNTAX PositiveInteger
     UNITS "minutes"
     ACCESS read-only
     STATUS mandatory
     DESCRIPTION
         "An estimate of the time to battery charge depletion under the present load conditions if the utility power is off and remains off, or if it were to be lost and remain off."
     ::= { upsBattery 3 }

upsBatteryVoltage OBJECT-TYPE
    SYNTAX INTEGER
    UNITS  "DC Volt"
    ACCESS read-only
    STATUS mandatory
    DESCRIPTION
        "The magnitude of the present battery voltage in DC Volt."
    ::= { upsBattery 4 }

upsBatteryRatedAmpereHour OBJECT-TYPE
    SYNTAX INTEGER
    UNITS  "Amp-Hour"
    ACCESS read-only
    STATUS mandatory
    DESCRIPTION
        "The battery capacity in Amp-Hour."
    ::= { upsBattery 5 }

upsBatteryInstallationDate OBJECT-TYPE
    SYNTAX DisplayString (SIZE(8))
    ACCESS read-write
    STATUS mandatory
    DESCRIPTION
        "The battery installation date in YYYYMMDD format."
    ::= { upsBattery 6 }

upsBatteryCapacity OBJECT-TYPE
    SYNTAX INTEGER
    UNITS  "Percent"
    ACCESS read-only
    STATUS mandatory
    DESCRIPTION
        "The UPS battery capacity in percent."
    ::= { upsBattery 7 }

-- ===========================================================================
-- upsStsCtlCfg upsT1000-1-3kva Group 5
-- The UPS status, control and configuration
-- ===========================================================================
upsStsCtlCfgSystemTemperature OBJECT-TYPE
    SYNTAX INTEGER 
    UNITS  "Celsius"
    ACCESS read-only
    STATUS mandatory
    DESCRIPTION
        "The UPS system temperature in Celsius."
    ::= { upsStsCtlCfg 1 }

upsStsCtlCfgPresentMode OBJECT-TYPE
    SYNTAX INTEGER {
        online(1),
        bypass(2),
        backup(3),
        shutdown(4)
    }
    ACCESS read-only
    STATUS mandatory
    DESCRIPTION
        "The present mode of the UPS system."
    ::= { upsStsCtlCfg 2 }

upsStsCtlCfgModeChangeDelay OBJECT-TYPE
    SYNTAX NonNegativeInteger
    UNITS  "Second"
    ACCESS read-write
    STATUS mandatory
    DESCRIPTION
        "The timer upon whose expiration a mode transition will be attempted by the system."
    ::= { upsStsCtlCfg 3 }
	
upsStsCtlCfgModeRequest OBJECT-TYPE
    SYNTAX INTEGER {
        none(1),
		shutdown(2),
        online (3)
    }
    ACCESS read-write
    STATUS mandatory
    DESCRIPTION
        "The mode of the UPS system requested by the user."
    ::= { upsStsCtlCfg 4 }

upsStsCtlCfgPresentDate OBJECT-TYPE
    SYNTAX DisplayString (SIZE(10))
    ACCESS read-write
    STATUS mandatory
    DESCRIPTION 
        "The present date on the UPS. This is configurable by Administrator.The Present date in MM/DD/YYY format."
    ::= { upsStsCtlCfg 5 }

upsStsCtlCfgPresentTime OBJECT-TYPE
    SYNTAX DisplayString (SIZE(8))
    ACCESS read-write
    STATUS mandatory
    DESCRIPTION 
        "The present time of the UPS. This is configurable by Administrator. 24 Hour format. SET: hh:mm:ss"
    ::= { upsStsCtlCfg 6 }
	
upsStsCtlCfgUserDefinedOverloadSetPoint OBJECT-TYPE
    SYNTAX INTEGER
	UNITS "%"
    ACCESS read-write
    STATUS mandatory
    DESCRIPTION 
        "The maximum output load % defined by the user."
    ::= { upsStsCtlCfg 7 }
	
upsStsCtlCfgRMTIInstallationDate OBJECT-TYPE
    SYNTAX DisplayString(SIZE(8))
    ACCESS read-write
    STATUS mandatory
    DESCRIPTION
        "The RemotEye installation date."
    ::= { upsStsCtlCfg 8 }
	
upsStsCtlCfgRMTIVersion OBJECT-TYPE
    SYNTAX DisplayString(SIZE(0..15))
    ACCESS read-only
    STATUS mandatory
    DESCRIPTION
        "The RemotEye Firmware Version."
    ::= { upsStsCtlCfg 9 }
	
upsStsCtlCfgRMTIInstallationStatus OBJECT-TYPE
    SYNTAX INTEGER {
        uninstalled(1),
        installed(2)
    }          
    ACCESS read-only
    STATUS mandatory
    DESCRIPTION
        "Shows the installation status of the RemotEye."
    ::= { upsStsCtlCfg 10 }
	
upsStsCtlCfgRMTIBaudRate OBJECT-TYPE
    SYNTAX INTEGER {
        bd9600(1),
        bd19200(2),
        bd38400(3),
        bd57600(4)
    }          
    ACCESS read-only
    STATUS mandatory
    DESCRIPTION
        "Configures the baud rate."
    ::= { upsStsCtlCfg 11 }
	
upsStsCtlCfgRMTIDataLink OBJECT-TYPE
    SYNTAX INTEGER {
        unknown(1),
        link-down(2),
        link-up(3)
    }          
    ACCESS read-only
    STATUS mandatory
    DESCRIPTION
        "Shows the data status of the RemotEye."
    ::= { upsStsCtlCfg 12 }
	
upsStsCtlCfgRMTINetworkLink OBJECT-TYPE
    SYNTAX INTEGER {
        unknown(1),
        link-down(2),
        link-up(3)
    }          
    ACCESS read-only
    STATUS mandatory
    DESCRIPTION
        "Shows the network status of the RemotEye."
    ::= { upsStsCtlCfg 13 }

-- ===========================================================================
-- upsAlarm upsT1000-1-3kva Group 6
-- The UPS Alarm List
-- ===========================================================================
upsAlarmsPresent OBJECT-TYPE
    SYNTAX Gauge32
    ACCESS read-only
    STATUS mandatory
    DESCRIPTION
        "One or more alarms reported."
    ::= { upsAlarm 1 }

upsAlarmTable OBJECT-TYPE
    SYNTAX SEQUENCE OF UpsAlarmEntry
    ACCESS not-accessible
    STATUS mandatory
    DESCRIPTION
        "A list of alarm table entries. The table contains
         zero, one, or many rows at any moment, depending upon
         the number of alarm conditions in effect. The table
         is initially empty at agent start up. The agent
         creates a row in the table each time a condition is
         detected and deletes that row when that condition no
         longer pertains. The agent creates the first row with
         upsAlarmId equal to 1, and increments the value of
         upsAlarmId each time a new row is created, wrapping to
         the first free value greater than or equal to 1 when
         the maximum value of upsAlarmId would otherwise be
         exceeded. Consequently, after multiple operations,
         the table may become sparse, e.g., containing entries
         for rows 95, 100, 101, and 203 and the entries should
         not be assumed to be in chronological order because
         upsAlarmId might have wrapped.

         Alarms are named by an OBJECT IDENTIFIER,
         upsAlarmDescr, to allow a single table to
         reflect well known alarms plus alarms defined by a
         particular implementation, i.e., as documented in the
         private enterprise MIB definition for the device. No
         two rows will have the same value of upsAlarmDescr,
         since alarms define conditions. In order to meet this
         requirement, care should be taken in the definition of
         alarm conditions to insure that a system cannot enter
         the same condition multiple times simultaneously.

         The number of rows in the table at any given time is
         reflected by the value of upsAlarmsPresent."
    ::= { upsAlarm  2 }

upsAlarmEntry OBJECT-TYPE
    SYNTAX UpsAlarmEntry
    ACCESS not-accessible
    STATUS mandatory
    DESCRIPTION
        "An entry containing information applicable to a
         particular alarm."
    INDEX { upsAlarmId }
    ::= { upsAlarmTable  1 }

UpsAlarmEntry ::=
    SEQUENCE {
        upsAlarmId              PositiveInteger,
        upsAlarmDescr           AutonomousType,
        upsAlarmTime            TimeStamp
    }

-- ===========================================================================
-- upsAlarmTable/upsAlarmEntry/upsAlarmId
-- ===========================================================================
upsAlarmId OBJECT-TYPE
    SYNTAX PositiveInteger
    ACCESS not-accessible
    STATUS mandatory
    DESCRIPTION
        "An unique identifier for an alarm condition. This
         value must remain constant."
    ::= { upsAlarmEntry 1 }

upsAlarmDescr OBJECT-TYPE
    SYNTAX AutonomousType
    ACCESS read-only
    STATUS mandatory
    DESCRIPTION
        "A reference to an alarm description object. The
         object referenced should not be accessible, but rather
         be used to provide a unique description of the alarm
         condition."
    ::= { upsAlarmEntry 2 }

-- ===========================================================================
-- .../upsAlarmTime
-- ===========================================================================
upsAlarmTime OBJECT-TYPE
    SYNTAX TimeStamp
    ACCESS read-only
    STATUS mandatory
    DESCRIPTION
        "The value of upsConfigSystemTime when the alarm condition was
          detected. If the alarm condition was detected at the
          time of agent start up and presumably existed before
          agent start up, the value of upsAlarmTime shall equal 0."
    ::= { upsAlarmEntry 3 }

upsWellKnownAlarms OBJECT IDENTIFIER ::= { upsAlarm  3 }

upsAlarmOnBattery OBJECT-TYPE
    SYNTAX INTEGER
    ACCESS read-only
    STATUS mandatory
    DESCRIPTION
        "Info: The UPS is on Battery mode; it is supplying output power from its batteries."
    ::= { upsWellKnownAlarms 1 }
	
upsAlarmLowBattery OBJECT-TYPE
    SYNTAX INTEGER
    ACCESS read-only
    STATUS mandatory
    DESCRIPTION
        "Warning: A Low battery reported."
    ::= { upsWellKnownAlarms 2 }
	
upsAlarmDepletedBattery OBJECT-TYPE
    SYNTAX INTEGER
    ACCESS read-only
    STATUS mandatory
    DESCRIPTION
        "Warning: A battery depleted event reported. It will not be able to support critical loads."
    ::= { upsWellKnownAlarms 3 }

upsAlarmTempBad OBJECT-TYPE 
     SYNTAX INTEGER
     ACCESS read-only
     STATUS mandatory
     DESCRIPTION
         "Warning: The UPS is overheating. Check to see if the ambient temperature is abnormally high. If so, turn on air conditioning. Also, check ventilation fan at the back of the UPS for operation or obstructions. Otherwise, shut down the UPS and contact your Toshiba authorized service center."
     ::= { upsWellKnownAlarms 4 }

upsAlarmInputBad OBJECT-TYPE 
     SYNTAX INTEGER
     ACCESS read-only
     STATUS mandatory
     DESCRIPTION
         "Warning: An input condition is out of tolerance.  Check the input voltage."
     ::= { upsWellKnownAlarms 5 }
	 
upsAlarmOutputBad OBJECT-TYPE 
     SYNTAX INTEGER
     ACCESS read-only
     STATUS mandatory
     DESCRIPTION
         "Fault: An output condition (other than output overload) is out of tolerance. Check the output voltage."
     ::= { upsWellKnownAlarms 6 }
	 
upsAlarmOutputOverload OBJECT-TYPE 
    SYNTAX INTEGER
    ACCESS read-only
    STATUS mandatory
    DESCRIPTION
        "Warning: An inverter output overload reported. UPS will switch to bypass operation or shut down if no action is taken. Shut down excess equipment to reduce Load."
    ::= { upsWellKnownAlarms 7 }
	
upsAlarmOnBypass OBJECT-TYPE 
    SYNTAX INTEGER
    ACCESS read-only
    STATUS mandatory
    DESCRIPTION
        "Warning: The UPS is in Stop (Bypass) mode"
    ::= { upsWellKnownAlarms 8 }

upsAlarmOutputOffAsRequested OBJECT-TYPE 
    SYNTAX INTEGER
    ACCESS read-only
    STATUS mandatory
    DESCRIPTION
        "Info: An output shut down mode requested."
    ::= { upsWellKnownAlarms 9 }
	
upsAlarmUpsOutputOff OBJECT-TYPE 
    SYNTAX INTEGER
    ACCESS read-only
    STATUS mandatory
    DESCRIPTION
        "Info: An output off reported."
    ::= { upsWellKnownAlarms 10 }
	
upsAlarmCommunicationLost OBJECT-TYPE 
 SYNTAX INTEGER
     ACCESS read-only
     STATUS mandatory
     DESCRIPTION
         "Communication lost between the RemotEye and the UPS."
     ::= { upsWellKnownAlarms 11 }
	 
upsAlarmShutdownPending OBJECT-TYPE 
    SYNTAX INTEGER
    ACCESS read-only
    STATUS mandatory
    DESCRIPTION
        "Info: An output shut down in progress reported. Output will turn off after delay."
    ::= { upsWellKnownAlarms 12 }
	
upsAlarmBatteryTestInProgress OBJECT-TYPE 
    SYNTAX INTEGER
    ACCESS read-only
    STATUS mandatory
    DESCRIPTION
        "Info: A battery test in progress reported."
    ::= { upsWellKnownAlarms 13 }
	
upsAlarmOutputUnderVoltage OBJECT-TYPE 
    SYNTAX INTEGER
    ACCESS read-only
    STATUS mandatory
    DESCRIPTION
        "Fault: An inverter output under voltage reported."
    ::= { upsWellKnownAlarms 14 }
	
upsAlarmOutputOverVoltage OBJECT-TYPE 
    SYNTAX INTEGER
    ACCESS read-only
    STATUS mandatory
    DESCRIPTION
        "Fault: An inverter output over voltage reported."
    ::= { upsWellKnownAlarms 15 }
	
upsAlarmUserDefinedOverloadWarning OBJECT-TYPE 
    SYNTAX INTEGER
    ACCESS read-only
    STATUS mandatory
    DESCRIPTION
        "Warning: The inverter output load % is greater than the user defined overload set point (default: 110%)."
    ::= { upsWellKnownAlarms 16 }
	
upsAlarmRemotEyeCommError OBJECT-TYPE 
    SYNTAX INTEGER
    ACCESS read-only
    STATUS mandatory
    DESCRIPTION
        "Warning: A Communication error between the main control and the RemotEye reported."
    ::= { upsWellKnownAlarms 17 }
	
--upsAlarmRemotEyeUplinkCommError OBJECT-TYPE 
--    SYNTAX INTEGER
--    ACCESS read-only
--    STATUS mandatory
--    DESCRIPTION
--        "Warning: A communication error between the RemotEye 4 and the network reported."
--    ::= { upsWellKnownAlarms 18 }
	
upsAlarmPowerFailure OBJECT-TYPE 
    SYNTAX INTEGER
    ACCESS read-only
    STATUS mandatory
    DESCRIPTION
        "Info: A power failure reported."
    ::= { upsWellKnownAlarms 19 }
	
--upsAlarmLogInError OBJECT-TYPE
--    SYNTAX INTEGER
--    ACCESS read-only
--    STATUS mandatory
--    DESCRIPTION
--        "Info: The UPS Admin Password is incorrect."
--    ::= { upsWellKnownAlarms 20 }

-- ===========================================================================
-- upsTraps - upsT1000-1-3kva Group 7
-- Traps group
-- ===========================================================================
upsTrapOnBattery TRAP-TYPE
    ENTERPRISE upsT1000-1-3kva 
    DESCRIPTION
        "Info: The UPS is on Battery mode; it is supplying output power from its batteries."
   --#TYPE "Info: The UPS is on Battery mode; it is supplying output power from its batteries."
   --#SUMMARY "Info: The UPS is on Battery mode; it is supplying output power from its batteries."
   --#SEVERITY INFORMATIONAL
   --#TIMEINDEX 1
   --#HELP ""
   --#HELPTAG 0
   --#STATE OPERATIONAL
    ::= 1

upsTrapOnBatteryClear TRAP-TYPE
    ENTERPRISE upsT1000-1-3kva 
    DESCRIPTION
        "Info Clear: The UPS is on Battery mode; it is supplying output power from its batteries."
   --#TYPE "Info Clear: The UPS is on Battery mode; it is supplying output power from its batteries."
   --#SUMMARY "Info Clear: The UPS is on Battery mode; it is supplying output power from its batteries."
   --#SEVERITY INFORMATIONAL
   --#TIMEINDEX 1
   --#HELP ""
   --#HELPTAG 0
   --#STATE OPERATIONAL
    ::= 2

upsTrapLowBattery TRAP-TYPE 
    ENTERPRISE upsT1000-1-3kva
    DESCRIPTION
        "Warning: A Low battery reported."
   --#TYPE "Warning: A Low battery reported."
   --#SUMMARY "Warning: A Low battery reported."
   --#SEVERITY INFORMATIONAL
   --#TIMEINDEX 1
   --#HELP ""
   --#HELPTAG 0
   --#STATE OPERATIONAL
    ::= 3
	
upsTrapLowBatteryClear TRAP-TYPE 
    ENTERPRISE upsT1000-1-3kva
    DESCRIPTION
        "Warning Clear: A Low battery reported."
   --#TYPE "Warning Clear: A Low battery reported."
   --#SUMMARY "Warning Clear: A Low battery reported."
   --#SEVERITY INFORMATIONAL
   --#TIMEINDEX 1
   --#HELP ""
   --#HELPTAG 0
   --#STATE OPERATIONAL
    ::= 4

upsTrapDepletedBattery TRAP-TYPE 
    ENTERPRISE upsT1000-1-3kva
    DESCRIPTION
        "Warning: A battery depleted event reported. It will not be able to support critical loads."
   --#TYPE "Warning: A battery depleted event reported. It will not be able to support critical loads."
   --#SUMMARY "Warning: A battery depleted event reported. It will not be able to support critical loads."
   --#SEVERITY INFORMATIONAL
   --#TIMEINDEX 1
   --#HELP ""
   --#HELPTAG 0
   --#STATE OPERATIONAL
    ::= 5
	
upsTrapDepletedBatteryClear TRAP-TYPE 
    ENTERPRISE upsT1000-1-3kva
    DESCRIPTION
        "Warning Clear: A battery depleted event reported. It will not be able to support critical loads."
   --#TYPE "Warning Clear: A battery depleted event reported. It will not be able to support critical loads."
   --#SUMMARY "Warning Clear: A battery depleted event reported. It will not be able to support critical loads."
   --#SEVERITY INFORMATIONAL
   --#TIMEINDEX 1
   --#HELP ""
   --#HELPTAG 0
   --#STATE OPERATIONAL
    ::= 6

upsTrapTempBad TRAP-TYPE
    ENTERPRISE upsT1000-1-3kva
    DESCRIPTION
        "Warning: The UPS is overheating. Check to see if the ambient temperature is abnormally high. If so, turn on air conditioning. Also, check ventilation fan at the back of the UPS for operation or obstructions. Otherwise, shut down the UPS and contact your Toshiba authorized service center."
   --#TYPE "Warning: The UPS is overheating. Check to see if the ambient temperature is abnormally high. If so, turn on air conditioning. Also, check ventilation fan at the back of the UPS for operation or obstructions. Otherwise, shut down the UPS and contact your Toshiba authorized service center."
   --#SUMMARY "Warning: The UPS is overheating. Check to see if the ambient temperature is abnormally high. If so, turn on air conditioning. Also, check ventilation fan at the back of the UPS for operation or obstructions. Otherwise, shut down the UPS and contact your Toshiba authorized service center."
   --#SEVERITY INFORMATIONAL
   --#TIMEINDEX 1
   --#HELP ""
   --#HELPTAG 0
   --#STATE OPERATIONAL
    ::= 7
	
upsTrapTempBadClear TRAP-TYPE
    ENTERPRISE upsT1000-1-3kva
    DESCRIPTION
        "Warning Clear: The UPS is overheating. Check to see if the ambient temperature is abnormally high. If so, turn on air conditioning. Also, check ventilation fan at the back of the UPS for operation or obstructions. Otherwise, shut down the UPS and contact your Toshiba authorized service center."
   --#TYPE "Warning Clear: The UPS is overheating. Check to see if the ambient temperature is abnormally high. If so, turn on air conditioning. Also, check ventilation fan at the back of the UPS for operation or obstructions. Otherwise, shut down the UPS and contact your Toshiba authorized service center."
   --#SUMMARY "Warning Clear: The UPS is overheating. Check to see if the ambient temperature is abnormally high. If so, turn on air conditioning. Also, check ventilation fan at the back of the UPS for operation or obstructions. Otherwise, shut down the UPS and contact your Toshiba authorized service center."
   --#SEVERITY INFORMATIONAL
   --#TIMEINDEX 1
   --#HELP ""
   --#HELPTAG 0
   --#STATE OPERATIONAL
    ::= 8

upsTrapInputBad TRAP-TYPE
    ENTERPRISE upsT1000-1-3kva
    DESCRIPTION
        "Warning: An input condition is out of tolerance.  Check the input voltage."
   --#TYPE "Warning: An input condition is out of tolerance.  Check the input voltage."
   --#SUMMARY "Warning: An input condition is out of tolerance.  Check the input voltage."
   --#SEVERITY INFORMATIONAL
   --#TIMEINDEX 1
   --#HELP ""
   --#HELPTAG 0
   --#STATE OPERATIONAL
    ::= 9
	
upsTrapInputBadClear TRAP-TYPE
    ENTERPRISE upsT1000-1-3kva
    DESCRIPTION
        "Warning Clear: An input condition is out of tolerance.  Check the input voltage."
   --#TYPE "Warning Clear: An input condition is out of tolerance.  Check the input voltage."
   --#SUMMARY "Warning Clear: An input condition is out of tolerance.  Check the input voltage."
   --#SEVERITY INFORMATIONAL
   --#TIMEINDEX 1
   --#HELP ""
   --#HELPTAG 0
   --#STATE OPERATIONAL
    ::= 10

upsTrapOutputBad TRAP-TYPE 
    ENTERPRISE upsT1000-1-3kva
    DESCRIPTION
        "Fault: An output condition (other than output overload) is out of tolerance. Check the output voltage."
   --#TYPE "Fault: An output condition (other than output overload) is out of tolerance. Check the output voltage."
   --#SUMMARY "Fault: An output condition (other than output overload) is out of tolerance. Check the output voltage."
   --#SEVERITY INFORMATIONAL
   --#TIMEINDEX 1
   --#HELP ""
   --#HELPTAG 0
   --#STATE OPERATIONAL
    ::= 11
	
upsTrapOutputBadClear TRAP-TYPE 
    ENTERPRISE upsT1000-1-3kva
    DESCRIPTION
        "Fault Clear: An output condition (other than output overload) is out of tolerance. Check the output voltage."
   --#TYPE "Fault Clear: An output condition (other than output overload) is out of tolerance. Check the output voltage."
   --#SUMMARY "Fault Clear: An output condition (other than output overload) is out of tolerance. Check the output voltage."
   --#SEVERITY INFORMATIONAL
   --#TIMEINDEX 1
   --#HELP ""
   --#HELPTAG 0
   --#STATE OPERATIONAL
    ::= 12

upsTrapOutputOverload TRAP-TYPE 
    ENTERPRISE upsT1000-1-3kva
    DESCRIPTION
        "Warning: An inverter output overload reported. UPS will switch to bypass operation or shut down if no action is taken. Shut down excess equipment to reduce Load."
   --#TYPE "Warning: An inverter output overload reported. UPS will switch to bypass operation or shut down if no action is taken. Shut down excess equipment to reduce Load."
   --#SUMMARY "Warning: An inverter output overload reported. UPS will switch to bypass operation or shut down if no action is taken. Shut down excess equipment to reduce Load."
   --#SEVERITY INFORMATIONAL
   --#TIMEINDEX 1
   --#HELP ""
   --#HELPTAG 0
   --#STATE OPERATIONAL
    ::= 13
	
upsTrapOutputOverloadClear TRAP-TYPE 
    ENTERPRISE upsT1000-1-3kva
    DESCRIPTION
        "Warning Clear: An inverter output overload reported. UPS will switch to bypass operation or shut down if no action is taken. Shut down excess equipment to reduce Load."
   --#TYPE "Warning Clear: An inverter output overload reported. UPS will switch to bypass operation or shut down if no action is taken. Shut down excess equipment to reduce Load."
   --#SUMMARY "Warning Clear: An inverter output overload reported. UPS will switch to bypass operation or shut down if no action is taken. Shut down excess equipment to reduce Load."
   --#SEVERITY INFORMATIONAL
   --#TIMEINDEX 1
   --#HELP ""
   --#HELPTAG 0
   --#STATE OPERATIONAL
    ::= 14
	
upsTrapOnBypass TRAP-TYPE 
    ENTERPRISE upsT1000-1-3kva
    DESCRIPTION
        "Warning: The UPS is in Stop (Bypass) mode"
   --#TYPE "Warning: The UPS is in Stop (Bypass) mode"
   --#SUMMARY "Warning: The UPS is in Stop (Bypass) mode"
   --#SEVERITY INFORMATIONAL
   --#TIMEINDEX 1
   --#HELP ""
   --#HELPTAG 0
   --#STATE OPERATIONAL
    ::= 15
	
upsTrapOnBypassClear TRAP-TYPE 
    ENTERPRISE upsT1000-1-3kva
    DESCRIPTION
        "Warning Clear: The UPS is in Stop (Bypass) mode"
   --#TYPE "Warning Clear: The UPS is in Stop (Bypass) mode"
   --#SUMMARY "Warning Clear: The UPS is in Stop (Bypass) mode"
   --#SEVERITY INFORMATIONAL
   --#TIMEINDEX 1
   --#HELP ""
   --#HELPTAG 0
   --#STATE OPERATIONAL
    ::= 16
	
upsTrapOutputOffAsRequested TRAP-TYPE
    ENTERPRISE upsT1000-1-3kva
    DESCRIPTION
        "Info: An output shut down mode requested."
   --#TYPE "Info: An output shut down mode requested."
   --#SUMMARY "Info: An output shut down mode requested."
   --#SEVERITY INFORMATIONAL
   --#TIMEINDEX 1
   --#HELP ""
   --#HELPTAG 0
   --#STATE OPERATIONAL	
    ::= 17
	
upsTrapOutputOffAsRequestedClear TRAP-TYPE
    ENTERPRISE upsT1000-1-3kva
    DESCRIPTION
        "Info Clear: An output shut down mode requested."
   --#TYPE "Info Clear: An output shut down mode requested."
   --#SUMMARY "Info Clear: An output shut down mode requested."
   --#SEVERITY INFORMATIONAL
   --#TIMEINDEX 1
   --#HELP ""
   --#HELPTAG 0
   --#STATE OPERATIONAL	
    ::= 18
	
upsTrapUpsOutputOff TRAP-TYPE
    ENTERPRISE upsT1000-1-3kva
    DESCRIPTION
        "Info: An output off reported."
   --#TYPE "Info: An output off reported."
   --#SUMMARY "Info: An output off reported."
   --#SEVERITY INFORMATIONAL
   --#TIMEINDEX 1
   --#HELP ""
   --#HELPTAG 0
   --#STATE OPERATIONAL	
    ::= 19

upsTrapUpsOutputOffClear TRAP-TYPE
    ENTERPRISE upsT1000-1-3kva
    DESCRIPTION
        "Info: An output off reported."
   --#TYPE "Info: An output off reported."
   --#SUMMARY "Info: An output off reported."
   --#SEVERITY INFORMATIONAL
   --#TIMEINDEX 1
   --#HELP ""
   --#HELPTAG 0
   --#STATE OPERATIONAL	
    ::= 20

upsTrapCommunicationLost TRAP-TYPE 
    ENTERPRISE upsT1000-1-3kva
    DESCRIPTION
        "Info: Communication lost between the RemotEye and the UPS."
   --#TYPE "Info: Communication lost between the RemotEye and the UPS."
   --#SUMMARY "Info: Communication lost between the RemotEye and the UPS."
   --#SEVERITY INFORMATIONAL
   --#TIMEINDEX 1
   --#HELP ""
   --#HELPTAG 0
   --#STATE OPERATIONAL
    ::= 21
	
upsTrapCommunicationLostClear TRAP-TYPE 
    ENTERPRISE upsT1000-1-3kva
    DESCRIPTION
        "Info Clear: Communication lost between the RemotEye and the UPS."
   --#TYPE "Info Clear: Communication lost between the RemotEye and the UPS."
   --#SUMMARY "Info Clear: Communication lost between the RemotEye and the UPS."
   --#SEVERITY INFORMATIONAL
   --#TIMEINDEX 1
   --#HELP ""
   --#HELPTAG 0
   --#STATE OPERATIONAL
    ::= 22

upsTrapShutdownPending TRAP-TYPE
    ENTERPRISE upsT1000-1-3kva
    DESCRIPTION
        "Info: A output shut down in progress reported. Output will turn off after delay."
   --#TYPE "Info: A output shut down in progress reported. Output will turn off after delay."
   --#SUMMARY "Info: A output shut down in progress reported. Output will turn off after delay."
   --#SEVERITY INFORMATIONAL
   --#TIMEINDEX 1
   --#HELP ""
   --#HELPTAG 0
   --#STATE OPERATIONAL	
    ::= 23
	
upsTrapShutdownPendingClear TRAP-TYPE
    ENTERPRISE upsT1000-1-3kva
    DESCRIPTION
        "Info Clear: A output show down in progress reported. Output will turn off after delay."
   --#TYPE "Info Clear: A output shut down in progress reported. Output will turn off after delay."
   --#SUMMARY "Info Clear: A output shut down in progress reported. Output will turn off after delay."
   --#SEVERITY INFORMATIONAL
   --#TIMEINDEX 1
   --#HELP ""
   --#HELPTAG 0
   --#STATE OPERATIONAL	
    ::= 24

upsTrapBatteryTestInProgress TRAP-TYPE
    ENTERPRISE upsT1000-1-3kva
    DESCRIPTION
        "Info: A battery test in progress reported."
   --#TYPE "Info: A battery test in progress reported."
   --#SUMMARY "Info: A battery test in progress reported."
   --#SEVERITY INFORMATIONAL
   --#TIMEINDEX 1
   --#HELP ""
   --#HELPTAG 0
   --#STATE OPERATIONAL	
    ::= 25

upsTrapBatteryTestInProgressClear TRAP-TYPE
    ENTERPRISE upsT1000-1-3kva
    DESCRIPTION
        "Info Clear: A battery test in progress reported."
   --#TYPE "Info Clear: A battery test in progress reported."
   --#SUMMARY "Info Clear: A battery test in progress reported."
   --#SEVERITY INFORMATIONAL
   --#TIMEINDEX 1
   --#HELP ""
   --#HELPTAG 0
   --#STATE OPERATIONAL	
    ::= 26
	
upsTrapOutputUnderVoltage TRAP-TYPE 
    ENTERPRISE upsT1000-1-3kva
    DESCRIPTION
        "Fault: An output under voltage reported. Contact your Toshiba authorized service center for examination."
   --#TYPE "Fault: An output under voltage reported. Contact your Toshiba authorized service center for examination."
   --#SUMMARY "Fault: An output under voltage reported. Contact your Toshiba authorized service center for examination."
   --#SEVERITY INFORMATIONAL
   --#TIMEINDEX 1
   --#HELP ""
   --#HELPTAG 0
   --#STATE OPERATIONAL
    ::= 27

upsTrapOutputUnderVoltageClear TRAP-TYPE 
    ENTERPRISE upsT1000-1-3kva
    DESCRIPTION
        "Fault Clear: An output under voltage reported. Contact your Toshiba authorized service center for examination."
   --#TYPE "Fault Clear: An output under voltage reported. Contact your Toshiba authorized service center for examination."
   --#SUMMARY "Fault Clear: An output under voltage reported. Contact your Toshiba authorized service center for examination."
   --#SEVERITY INFORMATIONAL
   --#TIMEINDEX 1
   --#HELP ""
   --#HELPTAG 0
   --#STATE OPERATIONAL
    ::= 28
	
upsTrapOutputOverVoltage TRAP-TYPE 
    ENTERPRISE upsT1000-1-3kva
    DESCRIPTION
        "Fault: An output over voltage reported. Contact your Toshiba authorized service center for examination."
   --#TYPE "Fault: An output over voltage reported. Contact your Toshiba authorized service center for examination."
   --#SUMMARY "Fault: An output over voltage reported. Contact your Toshiba authorized service center for examination."
   --#SEVERITY INFORMATIONAL
   --#TIMEINDEX 1
   --#HELP ""
   --#HELPTAG 0
   --#STATE OPERATIONAL
    ::= 29

upsTrapOutputOverVoltageClear TRAP-TYPE 
    ENTERPRISE upsT1000-1-3kva
    DESCRIPTION
        "Fault Clear: An output over voltage reported. Contact your Toshiba authorized service center for examination."
   --#TYPE "Fault Clear: An output over voltage reported. Contact your Toshiba service center for examination."
   --#SUMMARY "Fault Clear: An output over voltage reported. Contact your Toshiba authorized service center for examination."
   --#SEVERITY INFORMATIONAL
   --#TIMEINDEX 1
   --#HELP ""
   --#HELPTAG 0
   --#STATE OPERATIONAL
    ::= 30
	
upsTrapUserDefinedOverloadWarning TRAP-TYPE 
    ENTERPRISE upsT1000-1-3kva
    DESCRIPTION
        "Warning: The inverter output load % is greater than the user defined overload set point (default: 110%)."
   --#TYPE "Warning: The inverter output load % is greater than the user defined overload set point (default: 110%)."
   --#SUMMARY "Warning: The inverter output load % is greater than the user defined overload set point (default: 110%)."
   --#SEVERITY INFORMATIONAL
   --#TIMEINDEX 1
   --#HELP ""
   --#HELPTAG 0
   --#STATE OPERATIONAL
    ::= 31
	
upsTrapUserDefinedOverloadWarningClear TRAP-TYPE 
    ENTERPRISE upsT1000-1-3kva
    DESCRIPTION
        "Warning Clear: The inverter output load % is greater than the user defined overload set point (default: 110%)."
   --#TYPE "Warning Clear: The inverter output load % is greater than the user defined overload set point (default: 110%)."
   --#SUMMARY "Warning Clear: The inverter output load % is greater than the user defined overload set point (default: 110%)."
   --#SEVERITY INFORMATIONAL
   --#TIMEINDEX 1
   --#HELP ""
   --#HELPTAG 0
   --#STATE OPERATIONAL
    ::= 32
	
upsTrapRemotEyeCommError TRAP-TYPE
    ENTERPRISE upsT1000-1-3kva
    DESCRIPTION
        "Warning: A communication error between the main control and the RemotEye 4 reported."
   --#TYPE "Warning: A communication error between the main control and the RemotEye 4 reported."
   --#SUMMARY "Warning: A communication error between the main control and the RemotEye 4 reported."
   --#SEVERITY INFORMATIONAL
   --#TIMEINDEX 1
   --#HELP ""
   --#HELPTAG 0
   --#STATE OPERATIONAL
    ::= 33

upsTrapRemotEyeCommErrorClear TRAP-TYPE
    ENTERPRISE upsT1000-1-3kva
    DESCRIPTION
        "Warning Clear: A communication error between the main control and the RemotEye 4 reported."
   --#TYPE "Warning Clear: A communication error between the main control and the RemotEye 4 reported."
   --#SUMMARY "Warning Clear: A communication error between the main control and the RemotEye 4 reported."
   --#SEVERITY INFORMATIONAL
   --#TIMEINDEX 1
   --#HELP ""
   --#HELPTAG 0
   --#STATE OPERATIONAL
    ::= 34
	
--upsTrapRemotEyeUplinkCommError TRAP-TYPE 
--    ENTERPRISE upsT1000-1-3kva
--    DESCRIPTION
--        "Warning: A communication error between the RemotEye 4 and the network reported."
   --#TYPE "Warning: A communication error between the RemotEye 4 and the network reported."
   --#SUMMARY "Warning: A communication error between the RemotEye 4 and the network reported."
   --#SEVERITY INFORMATIONAL
   --#TIMEINDEX 1
   --#HELP ""
   --#HELPTAG 0
   --#STATE OPERATIONAL
--    ::= 35

--upsTrapRemotEyeUplinkCommErrorClear TRAP-TYPE 
--    ENTERPRISE upsT1000-1-3kva
--    DESCRIPTION
--        "Warning Clear: A communication error between the RemotEye 4 and the network reported."
   --#TYPE "Warning Clear: A communication error between the RemotEye 4 and the network reported."
   --#SUMMARY "Warning Clear: A communication error between the RemotEye 4 and the network reported."
   --#SEVERITY INFORMATIONAL
   --#TIMEINDEX 1
   --#HELP ""
   --#HELPTAG 0
   --#STATE OPERATIONAL
--    ::= 36
	
upsTrapPowerFailure TRAP-TYPE 
    ENTERPRISE upsT1000-1-3kva
    DESCRIPTION
        "Info: A power failure reported."
   --#TYPE "Info: A power failure reported."
   --#SUMMARY "Info: A power failure reported."
   --#SEVERITY INFORMATIONAL
   --#TIMEINDEX 1
   --#HELP ""
   --#HELPTAG 0
   --#STATE OPERATIONAL	
    ::= 37

upsTrapPowerFailureClear TRAP-TYPE 
    ENTERPRISE upsT1000-1-3kva
    DESCRIPTION
        "Info Clear: A power failure reported."
   --#TYPE "Info Clear: A power failure reported."
   --#SUMMARY "Info Clear: A power failure reported."
   --#SEVERITY INFORMATIONAL
   --#TIMEINDEX 1
   --#HELP ""
   --#HELPTAG 0
   --#STATE OPERATIONAL	
    ::= 38
	
--upsTrapLogInError TRAP-TYPE 
--    ENTERPRISE upsT1000-1-3kva
--    DESCRIPTION
--        "Info: UPS Password is incorrect."
   --#TYPE "Info: UPS Password is incorrect."
   --#SUMMARY "Info: UPS Password is incorrect."
   --#SEVERITY INFORMATIONAL
   --#TIMEINDEX 1
   --#HELP ""
   --#HELPTAG 0
   --#STATE OPERATIONAL		
--    ::= 39

--upsTrapLogInErrorClear TRAP-TYPE 
--    ENTERPRISE upsT1000-1-3kva
--    DESCRIPTION
--        "Info Clear: UPS Password is incorrect."
   --#TYPE "Info Clear: UPS Password is incorrect."
   --#SUMMARY "Info Clear: UPS Password is incorrect."
   --#SEVERITY INFORMATIONAL
   --#TIMEINDEX 1
   --#HELP ""
   --#HELPTAG 0
   --#STATE OPERATIONAL		
--    ::= 40

END
