-- These MIBs were created on 1/7/2003
-- This module defines enterprise MIBs for NS OSPF
-- 
-- Copyright (c) 1999-2004, Juniper Networks, Inc.
-- All rights reserved.
-- 

-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Descr
--    This module defines the object that are used to monitor
--    NS's OSPF configuration 
--
--  Last modified date: 06/20/2005
--  Created from NS-OSPF.MIB  with modified VR table index
--    

NETSCREEN-VR-OSPF-MIB DEFINITIONS ::= BEGIN

    IMPORTS
            MODULE-IDENTITY, OBJECT-TYPE, Counter32, Gauge32,
            Integer32, IpAddress
                FROM SNMPv2-SMI
            TEXTUAL-CONVENTION, TruthValue, RowStatus
                FROM SNMPv2-TC
            MODULE-COMPLIANCE, OBJECT-GROUP          FROM SNMPv2-CONF
            mib-2                                    FROM RFC1213-MIB
			netscreenVR								 FROM NETSCREEN-SMI;

--  This MIB module uses the extended OBJECT-TYPE macro as
--  defined in [9].

nsVrOspf MODULE-IDENTITY
        LAST-UPDATED "0301170000Z" 
        ORGANIZATION "NS OSPF Working Group"
        CONTACT-INFO
       "   Customer Support
       Postal: NetScreen
	       350 Oakmead Parkway
           Sunnyvale, CA  94085
           USA

       Tel: 1.877.NETSCREEN
       E-mail: support@netscreen.com
       Http://www.netscreen.com"
    DESCRIPTION
       "The MIB module to describe the NS-OSPF Version 2
       Protocol"
    ::= { netscreenVR 5 }

--  The Area ID, in OSPF, has the same format as an IP Address,
--  but has the function of defining a summarization point for
--  Link State Advertisements

AreaID ::= TEXTUAL-CONVENTION
    STATUS      current
    DESCRIPTION
       "An OSPF Area Identifier."
    SYNTAX      IpAddress

--  The Router ID, in OSPF, has the same format as an IP Address,

--  but identifies the router independent of its IP Address.

RouterID ::= TEXTUAL-CONVENTION
    STATUS      current
    DESCRIPTION
       "A OSPF Router Identifier."
    SYNTAX      IpAddress

--  The OSPF Metric is defined as an unsigned value in the range

Metric ::= TEXTUAL-CONVENTION
    STATUS      current
    DESCRIPTION
       "The OSPF Internal Metric."
    SYNTAX      Integer32 (0..'FFFF'H)

BigMetric ::= TEXTUAL-CONVENTION
    STATUS      current
    DESCRIPTION
       "The OSPF External Metric."
    SYNTAX      Integer32 (0..'FFFFFF'H)

--  Status Values

Status ::= TEXTUAL-CONVENTION
    STATUS      current
    DESCRIPTION
       "The status of an interface: 'enabled' indicates that
       it is willing to communicate with other OSPF Routers,
       while 'disabled' indicates that it is not."
    SYNTAX      INTEGER { enabled (1), disabled (2) }

--  Time Durations measured in seconds

PositiveInteger ::= TEXTUAL-CONVENTION
    STATUS      current
    DESCRIPTION
       "A positive integer. Values in excess are precluded as
       unnecessary and prone to interoperability issues."
    SYNTAX      Integer32 (0..'7FFFFFFF'H)

HelloRange ::= TEXTUAL-CONVENTION
    STATUS      current
    DESCRIPTION
       "The range of intervals on which hello messages are
       exchanged."
    SYNTAX      Integer32 (1..'FFFF'H)

UpToMaxAge ::= TEXTUAL-CONVENTION
    STATUS      current
    DESCRIPTION
       "The values that one might find or configure for
       variables bounded by the maximum age of an LSA."
    SYNTAX      Integer32 (0..3600)

--  The range of ifIndex

InterfaceIndex ::= TEXTUAL-CONVENTION
    STATUS      current
    DESCRIPTION
       "The range of ifIndex."
    SYNTAX      Integer32

--  Potential Priorities for the Designated Router Election

DesignatedRouterPriority ::= TEXTUAL-CONVENTION
    STATUS      current
    DESCRIPTION
       "The values defined for the priority of a system for
       becoming the designated router."
    SYNTAX      Integer32 (0..'FF'H)

TOSType ::= TEXTUAL-CONVENTION
    STATUS      current
    DESCRIPTION
       "Type of Service is defined as a mapping to the IP Type of
       Service Flags as defined in the IP Forwarding Table MIB

       +-----+-----+-----+-----+-----+-----+-----+-----+
       |                 |                       |     |
       |   PRECEDENCE    |    TYPE OF SERVICE    |  0  |
       |                 |                       |     |
       +-----+-----+-----+-----+-----+-----+-----+-----+

                IP TOS                IP TOS
           Field     Policy      Field     Policy

           Contents    Code      Contents    Code
           0 0 0 0  ==>   0      0 0 0 1  ==>   2
           0 0 1 0  ==>   4      0 0 1 1  ==>   6
           0 1 0 0  ==>   8      0 1 0 1  ==>  10
           0 1 1 0  ==>  12      0 1 1 1  ==>  14
           1 0 0 0  ==>  16      1 0 0 1  ==>  18
           1 0 1 0  ==>  20      1 0 1 1  ==>  22

           1 1 0 0  ==>  24      1 1 0 1  ==>  26
           1 1 1 0  ==>  28      1 1 1 1  ==>  30

       The remaining values are left for future definition."
    SYNTAX      Integer32 (0..30)

--  OSPF General Variables

--      These parameters apply globally to the Router's
--      OSPF Process.

    nsVrOspfGeneralTable OBJECT-TYPE
        SYNTAX   SEQUENCE OF  NsVrOspfGeneralEntry
        MAX-ACCESS   not-accessible
        STATUS   current
        DESCRIPTION
           "Ospf general information table per VR"
      ::= { nsVrOspf 1 }

    nsVrOspfGeneralEntry OBJECT-TYPE
        SYNTAX    NsVrOspfGeneralEntry
        MAX-ACCESS   not-accessible
        STATUS   current
        DESCRIPTION
           "Ospf general information table per VR"
       INDEX { nsVrOspfGeneralVRID }
       ::= { nsVrOspfGeneralTable 1 }

 NsVrOspfGeneralEntry ::=
    SEQUENCE {
        nsVrOspfRouterId
            RouterID,
        nsVrOspfAdminStat
            Status,
        nsVrOspfVersionNumber
            INTEGER,
        nsVrOspfAreaBdrRtrStatus
            TruthValue,
        nsVrOspfASBdrRtrStatus
            TruthValue,
        nsVrOspfExternLsaCount
            Gauge32,
        nsVrOspfAreaLsaCount
            Gauge32,
        nsVrOspfExternLsaCksumSum
            Integer32,
        nsVrOspfTOSSupport
            TruthValue,
        nsVrOspfOriginateNewLsas
            Counter32,
        nsVrOspfRxNewLsas
            Counter32,
        nsVrOspfExtLsdbLimit
            Integer32,
        nsVrOspfMulticastExtensions
            Integer32,
        nsVrOspfExitOverflowInterval
            PositiveInteger,
        nsVrOspfDemandExtensions
            TruthValue,
        nsVrOspfGeneralVRID
            INTEGER
              }

    nsVrOspfRouterId OBJECT-TYPE
        SYNTAX   RouterID
        MAX-ACCESS   read-only
        STATUS   current
        DESCRIPTION
           "A  32-bit  integer  uniquely  identifying  the
           router in the Autonomous System.

           By  convention,  to  ensure  uniqueness,   this
           should  default  to  the  value  of  one of the
           router's IP interface addresses."
       REFERENCE
          "OSPF Version 2, C.1 Global parameters"
      ::= { nsVrOspfGeneralEntry 1 }

    nsVrOspfAdminStat OBJECT-TYPE
        SYNTAX   Status
        MAX-ACCESS   read-only
        STATUS   current
        DESCRIPTION
           "The  administrative  status  of  OSPF  in  the
           router.   The  value 'enabled' denotes that the
           OSPF Process is active on at least  one  inter-
           face;  'disabled'  disables  it  on  all inter-
           faces."
       ::= { nsVrOspfGeneralEntry 2 }

    nsVrOspfVersionNumber OBJECT-TYPE
        SYNTAX   INTEGER    { version2 (2) }
        MAX-ACCESS   read-only
        STATUS   current
        DESCRIPTION

           "The current version number of the OSPF  proto-
           col is 2."
       REFERENCE
          "OSPF Version 2, Title"
      ::= { nsVrOspfGeneralEntry 3 }

    nsVrOspfAreaBdrRtrStatus OBJECT-TYPE
        SYNTAX   TruthValue
        MAX-ACCESS   read-only
        STATUS   current
        DESCRIPTION
           "A flag to note whether this router is an  area
           border router."
       REFERENCE
          "OSPF Version 2, Section 3 Splitting the AS into
          Areas"
      ::= { nsVrOspfGeneralEntry 4 }

    nsVrOspfASBdrRtrStatus OBJECT-TYPE
        SYNTAX   TruthValue
        MAX-ACCESS   read-only
        STATUS   current
        DESCRIPTION
           "A flag to note whether this router is  config-
           ured as an Autonomous System border router."
       REFERENCE
          "OSPF Version 2, Section 3.3  Classification  of
          routers"
      ::= { nsVrOspfGeneralEntry 5 }

    nsVrOspfExternLsaCount OBJECT-TYPE
        SYNTAX   Gauge32
        MAX-ACCESS   read-only
        STATUS   current
        DESCRIPTION
           "The number of external (LS type 5)  link-state
           advertisements in the link-state database."
       REFERENCE
          "OSPF Version 2, Appendix A.4.5 AS external link
          advertisements"
      ::= { nsVrOspfGeneralEntry 6 }

    nsVrOspfExternLsaCksumSum OBJECT-TYPE
        SYNTAX   Integer32
        MAX-ACCESS   read-only

        STATUS   current
        DESCRIPTION
           "The 32-bit unsigned sum of the LS checksums of
           the  external  link-state  advertisements  con-
           tained in the link-state  database.   This  sum
           can  be  used  to determine if there has been a
           change in a router's link state  database,  and
           to  compare  the  link-state  database  of  two
           routers."
       ::= { nsVrOspfGeneralEntry 7 }

    nsVrOspfTOSSupport OBJECT-TYPE
        SYNTAX   TruthValue
        MAX-ACCESS   read-only
        STATUS   current
        DESCRIPTION
           "The router's support for type-of-service rout-
           ing."
       REFERENCE
          "OSPF Version 2,  Appendix  F.1.2  Optional  TOS
          support"
      ::= { nsVrOspfGeneralEntry 8 }

    nsVrOspfOriginateNewLsas OBJECT-TYPE
        SYNTAX   Counter32
        MAX-ACCESS   read-only
        STATUS   current
        DESCRIPTION
           "The number of  new  link-state  advertisements
           that  have been originated.  This number is in-
           cremented each time the router originates a new
           LSA."
       ::= { nsVrOspfGeneralEntry 9 }

    nsVrOspfRxNewLsas OBJECT-TYPE
        SYNTAX   Counter32
        MAX-ACCESS   read-only
        STATUS   current
        DESCRIPTION
           "The number of  link-state  advertisements  re-
           ceived  determined  to  be  new instantiations.
           This number does not include  newer  instantia-
           tions  of self-originated link-state advertise-
           ments."
       ::= { nsVrOspfGeneralEntry 10 }

    nsVrOspfExtLsdbLimit OBJECT-TYPE
        SYNTAX   Integer32 (-1..'7FFFFFFF'H)
        MAX-ACCESS   read-only
        STATUS   current
        DESCRIPTION
           "The  maximum   number   of   non-default   AS-
           external-LSAs entries that can be stored in the
           link-state database.  If the value is -1,  then
           there is no limit.

           When the number of non-default AS-external-LSAs
           in   a  router's  link-state  database  reaches
           nsVrOspfExtLsdbLimit, the router  enters  Overflow-
           State.   The   router  never  holds  more  than
           nsVrOspfExtLsdbLimit  non-default  AS-external-LSAs
           in  its  database.  OspfExtLsdbLimit MUST be set
           identically in all routers attached to the OSPF
           backbone  and/or  any regular OSPF area. (i.e.,
           OSPF stub areas and NSSAs are excluded)."
       DEFVAL { -1 }
       ::= { nsVrOspfGeneralEntry 11 }

    nsVrOspfMulticastExtensions OBJECT-TYPE
        SYNTAX   Integer32
        MAX-ACCESS   read-only
        STATUS   current
        DESCRIPTION
           "A Bit Mask indicating whether  the  router  is
           forwarding  IP  multicast  (Class  D) datagrams
           based on the algorithms defined in  the  Multi-
           cast Extensions to OSPF.

           Bit 0, if set, indicates that  the  router  can
           forward  IP multicast datagrams in the router's
           directly attached areas (called intra-area mul-
           ticast routing).

           Bit 1, if set, indicates that  the  router  can
           forward  IP  multicast  datagrams  between OSPF
           areas (called inter-area multicast routing).

           Bit 2, if set, indicates that  the  router  can
           forward  IP  multicast  datagrams between Auto-
           nomous Systems (called inter-AS multicast rout-
           ing).

           Only certain combinations of bit  settings  are
           allowed,  namely: 0 (no multicast forwarding is

           enabled), 1 (intra-area multicasting  only),  3
           (intra-area  and  inter-area  multicasting),  5
           (intra-area and inter-AS  multicasting)  and  7
           (multicasting  everywhere). By default, no mul-
           ticast forwarding is enabled."
       DEFVAL { 0 }
       ::= { nsVrOspfGeneralEntry 12 }

    nsVrOspfExitOverflowInterval OBJECT-TYPE
        SYNTAX   PositiveInteger
        MAX-ACCESS   read-only
        STATUS   current
        DESCRIPTION
           "The number of  seconds  that,  after  entering
           OverflowState,  a  router will attempt to leave
           OverflowState. This allows the router to  again
           originate  non-default  AS-external-LSAs.  When
           set to 0, the router will not  leave  Overflow-
           State until restarted."
       DEFVAL { 0 }
       ::= { nsVrOspfGeneralEntry 13 }

    nsVrOspfDemandExtensions OBJECT-TYPE
        SYNTAX   TruthValue
        MAX-ACCESS   read-only
        STATUS   current
        DESCRIPTION
           "The router's support for demand routing."
       REFERENCE
          "OSPF Version 2, Appendix on Demand Routing"
      ::= { nsVrOspfGeneralEntry 14 }

    nsVrOspfGeneralVRID OBJECT-TYPE
        SYNTAX   INTEGER (0..65535)
        MAX-ACCESS   read-only
        STATUS   current
        DESCRIPTION
            "Virtual Router ID. VRID range for system created 
            VRs: [1-1024] and for user created VRs: [1025-2048]"
       ::= { nsVrOspfGeneralEntry 15 }

--      The OSPF Area Data Structure contains information
--      regarding the various areas. The interfaces and
--      virtual links are configured as part of these areas.
--      Area 0.0.0.0, by definition, is the Backbone Area

    nsVrOspfAreaTable OBJECT-TYPE
        SYNTAX   SEQUENCE OF  NsVrOspfAreaEntry
        MAX-ACCESS   not-accessible
        STATUS   current
        DESCRIPTION
           "Information describing the configured  parame-
           ters  and cumulative statistics of the router's
           attached areas."

       REFERENCE
          "OSPF Version 2, Section 6  The Area Data Struc-
          ture"
      ::= { nsVrOspf 2 }

    nsVrOspfAreaEntry OBJECT-TYPE
        SYNTAX    NsVrOspfAreaEntry
        MAX-ACCESS   not-accessible
        STATUS   current
        DESCRIPTION
           "Information describing the configured  parame-
           ters  and  cumulative  statistics of one of the
           router's attached areas."
       INDEX { nsVrOspfAreaVRID, nsVrOspfAreaId}
       ::= { nsVrOspfAreaTable 1 }

 NsVrOspfAreaEntry ::=
    SEQUENCE {
        nsVrOspfAreaId
            AreaID,
        nsVrOspfImportAsExtern
            INTEGER,
        nsVrOspfSpfRuns
            Counter32,
        nsVrOspfAreaBdrRtrCount
            Gauge32,
        nsVrOspfAsBdrRtrCount
            Gauge32,
        nsVrOspfAreaLsaCount
            Gauge32,
        nsVrOspfAreaLsaCksumSum
            Integer32,
        nsVrOspfAreaSummary
            INTEGER,
        nsVrOspfAreaStatus
            RowStatus,
        nsVrOspfAreaVRID
            INTEGER
              }

    nsVrOspfAreaId OBJECT-TYPE
        SYNTAX   AreaID
        MAX-ACCESS   read-only
        STATUS   current
        DESCRIPTION
           "A 32-bit integer uniquely identifying an area.
           Area ID 0.0.0.0 is used for the OSPF backbone."

       REFERENCE
          "OSPF Version 2, Appendix C.2 Area parameters"
      ::= { nsVrOspfAreaEntry 1 }

    nsVrOspfImportAsExtern OBJECT-TYPE
        SYNTAX   INTEGER    {
                    importExternal (1),
                    importNoExternal (2),
                    importNssa (3)
                  }
        MAX-ACCESS   read-create
        STATUS   current
        DESCRIPTION
           "The area's support for importing  AS  external
           link- state advertisements."
       REFERENCE
          "OSPF Version 2, Appendix C.2 Area parameters"
      DEFVAL { importExternal }
      ::= { nsVrOspfAreaEntry 3 }

    nsVrOspfSpfRuns OBJECT-TYPE
        SYNTAX   Counter32
        MAX-ACCESS   read-only
        STATUS   current
        DESCRIPTION
           "The number of times that the intra-area  route
           table  has  been  calculated  using this area's
           link-state database.  This  is  typically  done
           using Dijkstra's algorithm."

       ::= { nsVrOspfAreaEntry 4 }

    nsVrOspfAreaBdrRtrCount OBJECT-TYPE
        SYNTAX   Gauge32
        MAX-ACCESS   read-only
        STATUS   current
        DESCRIPTION
           "The total number of area border routers reach-
           able within this area.  This is initially zero,
           and is calculated in each SPF Pass."
       ::= { nsVrOspfAreaEntry 5 }

    nsVrOspfAsBdrRtrCount OBJECT-TYPE
        SYNTAX   Gauge32
        MAX-ACCESS   read-only
        STATUS   current
        DESCRIPTION
           "The total number of Autonomous  System  border
           routers  reachable  within  this area.  This is
           initially zero, and is calculated in  each  SPF
           Pass."
       ::= { nsVrOspfAreaEntry 6 }

    nsVrOspfAreaLsaCount OBJECT-TYPE
        SYNTAX   Gauge32
        MAX-ACCESS   read-only
        STATUS   current
        DESCRIPTION
           "The total number of link-state  advertisements
           in  this  area's link-state database, excluding
           AS External LSA's."
       ::= { nsVrOspfAreaEntry 7 }

    nsVrOspfAreaLsaCksumSum OBJECT-TYPE
        SYNTAX   Integer32
        MAX-ACCESS   read-only
        STATUS   current
        DESCRIPTION
           "The 32-bit unsigned sum of the link-state  ad-
           vertisements'  LS  checksums  contained in this
           area's link-state database.  This sum  excludes
           external (LS type 5) link-state advertisements.
           The sum can be used to determine if  there  has
           been  a  change  in a router's link state data-
           base, and to compare the link-state database of

           two routers."
       DEFVAL   { 0 }
       ::= { nsVrOspfAreaEntry 8 }

    nsVrOspfAreaSummary OBJECT-TYPE
        SYNTAX   INTEGER    {
                    noAreaSummary (1),
                    sendAreaSummary (2)
                  }
        MAX-ACCESS   read-create
        STATUS   current
        DESCRIPTION
           "The variable nsVrOspfAreaSummary controls the  im-
           port  of  summary LSAs into stub areas.  It has
           no effect on other areas.

           If it is noAreaSummary, the router will neither
           originate  nor  propagate summary LSAs into the
           stub area.  It will rely entirely  on  its  de-
           fault route.

           If it is sendAreaSummary, the router will  both
           summarize and propagate summary LSAs."
       DEFVAL   { noAreaSummary }
       ::= { nsVrOspfAreaEntry 9 }

    nsVrOspfAreaStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
       ::= { nsVrOspfAreaEntry 10 }

    nsVrOspfAreaVRID OBJECT-TYPE
        SYNTAX   INTEGER (0..65535)
        MAX-ACCESS   read-only
        STATUS   current
        DESCRIPTION
           "Virtual Router ID. VRID range for system created 
           VRs: [1-1024] and for user created VRs: [1025-2048]"
       ::= { nsVrOspfAreaEntry 11 }

--  OSPF Area Default Metric Table

--      The OSPF Area Default Metric Table describes the metrics
--      that a default Area Border Router will advertise into a
--      Stub area.

    nsVrOspfStubAreaTable OBJECT-TYPE
        SYNTAX   SEQUENCE OF  NsVrOspfStubAreaEntry

        MAX-ACCESS   not-accessible
        STATUS   current
        DESCRIPTION
           "The set of metrics that will be advertised  by
           a default Area Border Router into a stub area."
       REFERENCE
          "OSPF Version 2, Appendix C.2, Area Parameters"
      ::= { nsVrOspf 3 }

    nsVrOspfStubAreaEntry OBJECT-TYPE
        SYNTAX    NsVrOspfStubAreaEntry
        MAX-ACCESS   not-accessible
        STATUS   current
        DESCRIPTION
           "The metric for a given Type  of  Service  that
           will  be  advertised  by  a default Area Border
           Router into a stub area."
       REFERENCE
          "OSPF Version 2, Appendix C.2, Area Parameters"
      INDEX { nsVrOspfStubVRID, nsVrOspfStubAreaId, nsVrOspfStubTOS}
      ::= { nsVrOspfStubAreaTable 1 }

 NsVrOspfStubAreaEntry ::=
    SEQUENCE {
        nsVrOspfStubAreaId
            AreaID,
        nsVrOspfStubTOS
            TOSType,
        nsVrOspfStubMetric
            BigMetric,
        nsVrOspfStubStatus
            RowStatus,
        nsVrOspfStubMetricType
            INTEGER,
        nsVrOspfStubVRID
            INTEGER
              }

    nsVrOspfStubAreaId OBJECT-TYPE
        SYNTAX   AreaID
        MAX-ACCESS   read-only
        STATUS   current
        DESCRIPTION
           "The 32 bit identifier for the Stub  Area.   On
           creation,  this  can  be  derived  from the in-
           stance."
       ::= { nsVrOspfStubAreaEntry 1 }

    nsVrOspfStubTOS OBJECT-TYPE
        SYNTAX   TOSType
        MAX-ACCESS   read-only
        STATUS   current
        DESCRIPTION
           "The  Type  of  Service  associated  with   the
           metric.   On creation, this can be derived from
           the instance."
       ::= { nsVrOspfStubAreaEntry 2 }

    nsVrOspfStubMetric OBJECT-TYPE
        SYNTAX   BigMetric
        MAX-ACCESS   read-create
        STATUS   current
        DESCRIPTION
           "The metric value applied at the indicated type
           of  service.  By default, this equals the least
           metric at the type of service among the  inter-
           faces to other areas."
       ::= { nsVrOspfStubAreaEntry 3 }

    nsVrOspfStubStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
       ::= { nsVrOspfStubAreaEntry 4 }

    nsVrOspfStubMetricType OBJECT-TYPE
        SYNTAX   INTEGER    {
                    nsVrOspfMetric (1),                -- OSPF Metric
                    comparableCost (2),        -- external type 1
                    nonComparable  (3)        -- external type 2
                  }
        MAX-ACCESS   read-create
        STATUS   current
        DESCRIPTION
           "This variable displays the type of metric  ad-
           vertised as a default route."
       DEFVAL   { nsVrOspfMetric }
       ::= { nsVrOspfStubAreaEntry 5 }

    nsVrOspfStubVRID OBJECT-TYPE
        SYNTAX   INTEGER (0..65535)
        MAX-ACCESS   read-only
        STATUS   current
        DESCRIPTION
           "Virtual Router ID. VRID range for system created 
           VRs: [1-1024] and for user created VRs: [1025-2048]"
       ::= { nsVrOspfStubAreaEntry 6 }

--  OSPF Link State Database

--      The Link State Database contains the Link State
--      Advertisements from throughout the areas that the
--      device is attached to.

    nsVrOspfLsdbTable OBJECT-TYPE
        SYNTAX   SEQUENCE OF  NsVrOspfLsdbEntry
        MAX-ACCESS   not-accessible
        STATUS   current
        DESCRIPTION
           "The OSPF Process's Link State Database."
       REFERENCE
          "OSPF Version 2, Section 12  Link  State  Adver-
          tisements"
      ::= { nsVrOspf 4 }

    nsVrOspfLsdbEntry OBJECT-TYPE
        SYNTAX    NsVrOspfLsdbEntry
        MAX-ACCESS   not-accessible
        STATUS   current
        DESCRIPTION
           "A single Link State Advertisement."
       INDEX { nsVrOspfLsdbVRID, nsVrOspfLsdbAreaId, nsVrOspfLsdbType,
               nsVrOspfLsdbLsid, nsVrOspfLsdbRouterId}
       ::= { nsVrOspfLsdbTable 1 }

 NsVrOspfLsdbEntry ::=
    SEQUENCE {
        nsVrOspfLsdbAreaId
            AreaID,
        nsVrOspfLsdbType
            INTEGER,
        nsVrOspfLsdbLsid
            IpAddress,
        nsVrOspfLsdbRouterId
            RouterID,
        nsVrOspfLsdbSequence
            Integer32,
        nsVrOspfLsdbAge
            Integer32,
        nsVrOspfLsdbChecksum
            Integer32,
        nsVrOspfLsdbAdvertisement
            OCTET STRING,
        nsVrOspfLsdbVRID
            INTEGER
              }

    nsVrOspfLsdbAreaId OBJECT-TYPE
        SYNTAX   AreaID
        MAX-ACCESS   read-only
        STATUS   current
        DESCRIPTION
           "The 32 bit identifier of the Area  from  which
           the LSA was received."
       REFERENCE
          "OSPF Version 2, Appendix C.2 Area parameters"
      ::= { nsVrOspfLsdbEntry 1 }

-- External Link State Advertisements are permitted
-- for backward compatibility, but should be displayed in
-- the nsVrOspfExtLsdbTable rather than here.

    nsVrOspfLsdbType OBJECT-TYPE
        SYNTAX   INTEGER    {
                    routerLink (1),
                    networkLink (2),
                    summaryLink (3),
                    asSummaryLink (4),
                    asExternalLink (5), -- but see nsVrOspfExtLsdbTable
                    multicastLink (6),
                    nssaExternalLink (7)
                  }
        MAX-ACCESS   read-only
        STATUS   current
        DESCRIPTION
           "The type  of  the  link  state  advertisement.
           Each  link state type has a separate advertise-
           ment format."
       REFERENCE
          "OSPF Version 2, Appendix A.4.1 The  Link  State
          Advertisement header"
      ::= { nsVrOspfLsdbEntry 2 }

    nsVrOspfLsdbLsid OBJECT-TYPE
        SYNTAX   IpAddress
        MAX-ACCESS   read-only
        STATUS   current
        DESCRIPTION
           "The Link State ID is an LS Type Specific field
           containing either a Router ID or an IP Address;
           it identifies the piece of the  routing  domain
           that is being described by the advertisement."
       REFERENCE
          "OSPF Version 2, Section 12.1.4 Link State ID"
      ::= { nsVrOspfLsdbEntry 3 }

    nsVrOspfLsdbRouterId OBJECT-TYPE
        SYNTAX   RouterID
        MAX-ACCESS   read-only
        STATUS   current
        DESCRIPTION
           "The 32 bit number that uniquely identifies the
           originating router in the Autonomous System."
       REFERENCE
          "OSPF Version 2, Appendix C.1 Global parameters"
      ::= { nsVrOspfLsdbEntry 4 }

--  Note that the OSPF Sequence Number is a 32 bit signed
--  integer.  It starts with the value '80000001'h,
--  or -'7FFFFFFF'h, and increments until '7FFFFFFF'h
--  Thus, a typical sequence number will be very negative.

    nsVrOspfLsdbSequence OBJECT-TYPE
        SYNTAX   Integer32
        MAX-ACCESS   read-only
        STATUS   current
        DESCRIPTION
           "The sequence number field is a  signed  32-bit
           integer.   It  is used to detect old and dupli-
           cate link state advertisements.  The  space  of
           sequence  numbers  is  linearly  ordered.   The
           larger the sequence number the more recent  the
           advertisement."
       REFERENCE
          "OSPF Version  2,  Section  12.1.6  LS  sequence
          number"
      ::= { nsVrOspfLsdbEntry 5 }

    nsVrOspfLsdbAge OBJECT-TYPE
        SYNTAX   Integer32    -- Should be 0..MaxAge
        MAX-ACCESS   read-only
        STATUS   current
        DESCRIPTION
           "This field is the age of the link state adver-
           tisement in seconds."
       REFERENCE
          "OSPF Version 2, Section 12.1.1 LS age"
      ::= { nsVrOspfLsdbEntry 6 }

    nsVrOspfLsdbChecksum OBJECT-TYPE
        SYNTAX   Integer32
        MAX-ACCESS   read-only
        STATUS   current

        DESCRIPTION
           "This field is the  checksum  of  the  complete
           contents  of  the  advertisement, excepting the
           age field.  The age field is excepted  so  that
           an   advertisement's  age  can  be  incremented
           without updating the  checksum.   The  checksum
           used  is  the same that is used for ISO connec-
           tionless datagrams; it is commonly referred  to
           as the Fletcher checksum."
       REFERENCE
          "OSPF Version 2, Section 12.1.7 LS checksum"
      ::= { nsVrOspfLsdbEntry 7 }

    nsVrOspfLsdbAdvertisement OBJECT-TYPE
        SYNTAX   OCTET STRING (SIZE (1..65535))
        MAX-ACCESS   read-only
        STATUS   current
        DESCRIPTION
           "The entire Link State Advertisement, including
           its header."
       REFERENCE
          "OSPF Version 2, Section 12  Link  State  Adver-
          tisements"
      ::= { nsVrOspfLsdbEntry 8 }

    nsVrOspfLsdbVRID OBJECT-TYPE
        SYNTAX   INTEGER (0..65535)
        MAX-ACCESS   read-only
        STATUS   current
        DESCRIPTION
           "Virtual Router ID. VRID range for system created 
           VRs: [1-1024] and for user created VRs: [1025-2048]"
       ::= { nsVrOspfLsdbEntry 9 }

--  OSPF Host Table

--      The Host/Metric Table indicates what hosts are directly

--      attached to the Router, and what metrics and types of
--      service should be advertised for them.

    nsVrOspfHostTable OBJECT-TYPE
        SYNTAX   SEQUENCE OF  NsVrOspfHostEntry
        MAX-ACCESS   not-accessible
        STATUS   current
        DESCRIPTION
           "The list of Hosts, and their metrics, that the
           router will advertise as host routes."
       REFERENCE
          "OSPF Version 2, Appendix C.6  Host route param-
          eters"
      ::= { nsVrOspf 6 }

    nsVrOspfHostEntry OBJECT-TYPE
        SYNTAX    NsVrOspfHostEntry
        MAX-ACCESS   not-accessible
        STATUS   current
        DESCRIPTION
           "A metric to be advertised, for a given type of
           service, when a given host is reachable."
       INDEX { nsVrOspfHostVRID, nsVrOspfHostIpAddress, nsVrOspfHostTOS}
       ::= { nsVrOspfHostTable 1 }

 NsVrOspfHostEntry ::=
    SEQUENCE {
        nsVrOspfHostIpAddress
            IpAddress,
        nsVrOspfHostTOS
            TOSType,
        nsVrOspfHostMetric
            Metric,
        nsVrOspfHostStatus
            RowStatus,
        nsVrOspfHostAreaID
            AreaID,
        nsVrOspfHostVRID
            INTEGER
              }

    nsVrOspfHostIpAddress OBJECT-TYPE
        SYNTAX   IpAddress
        MAX-ACCESS   read-only
        STATUS   current
        DESCRIPTION
           "The IP Address of the Host."
       REFERENCE
          "OSPF Version 2, Appendix C.6 Host route parame-

          ters"
      ::= { nsVrOspfHostEntry 1 }

    nsVrOspfHostTOS OBJECT-TYPE
        SYNTAX   TOSType
        MAX-ACCESS   read-only
        STATUS   current
        DESCRIPTION
           "The Type of Service of the route being config-
           ured."
       REFERENCE
          "OSPF Version 2, Appendix C.6 Host route parame-
          ters"
      ::= { nsVrOspfHostEntry 2 }

    nsVrOspfHostMetric OBJECT-TYPE
        SYNTAX   Metric
        MAX-ACCESS   read-create
        STATUS   current
        DESCRIPTION
           "The Metric to be advertised."
       REFERENCE
          "OSPF Version 2, Appendix C.6 Host route parame-
          ters"
      ::= { nsVrOspfHostEntry 3 }

    nsVrOspfHostStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
       ::= { nsVrOspfHostEntry 4 }

    nsVrOspfHostAreaID OBJECT-TYPE
        SYNTAX   AreaID
        MAX-ACCESS   read-only
        STATUS   current
        DESCRIPTION
           "The Area the Host Entry is to be found within.
           By  default, the area that a subsuming OSPF in-
           terface is in, or 0.0.0.0"

       REFERENCE
          "OSPF Version 2, Appendix C.2 Area parameters"
      ::= { nsVrOspfHostEntry 5 }

    nsVrOspfHostVRID OBJECT-TYPE
        SYNTAX   INTEGER (0..65535)
        MAX-ACCESS   read-only
        STATUS   current
        DESCRIPTION
           "Virtual Router ID. VRID range for system created 
           VRs: [1-1024] and for user created VRs: [1025-2048]"
       ::= { nsVrOspfHostEntry 6 }

--  OSPF Interface Table

--      The OSPF Interface Table augments the ipAddrTable
--             with OSPF specific information.

    nsVrOspfIfTable OBJECT-TYPE
        SYNTAX   SEQUENCE OF  NsVrOspfIfEntry
        MAX-ACCESS   not-accessible
        STATUS   current
        DESCRIPTION
           "The OSPF Interface Table describes the  inter-
           faces from the viewpoint of OSPF."
       REFERENCE
          "OSPF Version 2, Appendix C.3  Router  interface
          parameters"
      ::= { nsVrOspf 7 }

    nsVrOspfIfEntry OBJECT-TYPE
        SYNTAX    NsVrOspfIfEntry
        MAX-ACCESS   not-accessible
        STATUS   current
        DESCRIPTION
           "The OSPF Interface Entry describes one  inter-
           face from the viewpoint of OSPF."
       INDEX { nsVrOspfIfVRID, nsVrOspfIfIpAddress, nsVrOspfAddressLessIf}
       ::= { nsVrOspfIfTable 1 }

 NsVrOspfIfEntry ::=
    SEQUENCE {
        nsVrOspfIfIpAddress
            IpAddress,
        nsVrOspfAddressLessIf
            Integer32,
        nsVrOspfIfAreaId
            AreaID,
        nsVrOspfIfType
            INTEGER,
        nsVrOspfIfAdminStat
            Status,
        nsVrOspfIfRtrPriority
            DesignatedRouterPriority,
        nsVrOspfIfTransitDelay

            UpToMaxAge,
        nsVrOspfIfRetransInterval
            UpToMaxAge,
        nsVrOspfIfHelloInterval
            HelloRange,
        nsVrOspfIfRtrDeadInterval
            PositiveInteger,
        nsVrOspfIfPollInterval
            PositiveInteger,
        nsVrOspfIfState
            INTEGER,
        nsVrOspfIfDesignatedRouter
            IpAddress,
        nsVrOspfIfBackupDesignatedRouter
            IpAddress,
        nsVrOspfIfEvents
            Counter32,
        nsVrOspfIfAuthType
            INTEGER,
        nsVrOspfIfAuthKey
            OCTET STRING,
        nsVrOspfIfStatus
            RowStatus,
        nsVrOspfIfMulticastForwarding
            INTEGER,
        nsVrOspfIfDemand
            TruthValue,
        nsVrOspfIfVRID
            INTEGER
              }

    nsVrOspfIfIpAddress OBJECT-TYPE
        SYNTAX   IpAddress
        MAX-ACCESS   read-only
        STATUS   current
        DESCRIPTION
           "The IP address of this OSPF interface."
       ::= { nsVrOspfIfEntry 1 }

    nsVrOspfAddressLessIf OBJECT-TYPE
        SYNTAX   Integer32
        MAX-ACCESS   read-only
        STATUS   current
        DESCRIPTION
           "For the purpose of easing  the  instancing  of
           addressed   and  addressless  interfaces;  This
           variable takes the value 0 on  interfaces  with
           IP  Addresses,  and  the corresponding value of
           ifIndex for interfaces having no IP Address."
       ::= { nsVrOspfIfEntry 2 }

    nsVrOspfIfAreaId OBJECT-TYPE
        SYNTAX   AreaID
        MAX-ACCESS   read-create
        STATUS   current
        DESCRIPTION
           "A 32-bit integer uniquely identifying the area
           to  which  the  interface  connects.   Area  ID
           0.0.0.0 is used for the OSPF backbone."
       DEFVAL   { '00000000'H }    -- 0.0.0.0
       ::= { nsVrOspfIfEntry 3 }

    nsVrOspfIfType OBJECT-TYPE
        SYNTAX   INTEGER    {
                    broadcast (1),
                    nbma (2),
                    pointToPoint (3),
                    pointToMultipoint (5)
                  }
        MAX-ACCESS   read-create
        STATUS   current
        DESCRIPTION
           "The OSPF interface type.

           By way of a default, this field may be intuited
           from the corresponding value of ifType.  Broad-
           cast LANs, such as  Ethernet  and  IEEE  802.5,
           take  the  value  'broadcast', X.25 and similar
           technologies take the value 'nbma',  and  links
           that  are  definitively point to point take the
           value 'pointToPoint'."
       ::= { nsVrOspfIfEntry 4 }

    nsVrOspfIfAdminStat OBJECT-TYPE
        SYNTAX   Status
        MAX-ACCESS   read-create
        STATUS   current
        DESCRIPTION
           "The OSPF  interface's  administrative  status.
           The  value formed on the interface, and the in-
           terface will be advertised as an internal route
           to  some  area.   The  value 'disabled' denotes
           that the interface is external to OSPF."
       DEFVAL { enabled }
       ::= { nsVrOspfIfEntry 5 }

    nsVrOspfIfRtrPriority OBJECT-TYPE
        SYNTAX   DesignatedRouterPriority

        MAX-ACCESS   read-create
        STATUS   current
        DESCRIPTION
           "The  priority  of  this  interface.   Used  in
           multi-access  networks,  this  field is used in
           the designated router election algorithm.   The
           value 0 signifies that the router is not eligi-
           ble to become the  designated  router  on  this
           particular  network.   In the event of a tie in
           this value, routers will use their Router ID as
           a tie breaker."
       DEFVAL { 1 }
       ::= { nsVrOspfIfEntry 6 }

    nsVrOspfIfTransitDelay OBJECT-TYPE
        SYNTAX   UpToMaxAge
        MAX-ACCESS   read-create
        STATUS   current
        DESCRIPTION
           "The estimated number of seconds  it  takes  to
           transmit  a  link state update packet over this
           interface."
       DEFVAL { 1 }
       ::= { nsVrOspfIfEntry 7 }

    nsVrOspfIfRetransInterval OBJECT-TYPE
        SYNTAX   UpToMaxAge
        MAX-ACCESS   read-create
        STATUS   current
        DESCRIPTION
           "The number of seconds between  link-state  ad-
           vertisement  retransmissions,  for  adjacencies
           belonging to this  interface.   This  value  is
           also used when retransmitting database descrip-
           tion and link-state request packets."
       DEFVAL { 5 }
       ::= { nsVrOspfIfEntry 8 }

    nsVrOspfIfHelloInterval OBJECT-TYPE
        SYNTAX   HelloRange
        MAX-ACCESS   read-create
        STATUS   current
        DESCRIPTION
           "The length of time, in  seconds,  between  the
           Hello  packets that the router sends on the in-

           terface.  This value must be the same  for  all
           routers attached to a common network."
       DEFVAL { 10 }
       ::= { nsVrOspfIfEntry 9 }

    nsVrOspfIfRtrDeadInterval OBJECT-TYPE
        SYNTAX   PositiveInteger
        MAX-ACCESS   read-create
        STATUS   current
        DESCRIPTION
           "The number of seconds that  a  router's  Hello
           packets  have  not been seen before it's neigh-
           bors declare the router down.  This  should  be
           some  multiple  of  the  Hello  interval.  This
           value must be the same for all routers attached
           to a common network."
       DEFVAL { 40 }
       ::= { nsVrOspfIfEntry 10 }

    nsVrOspfIfPollInterval OBJECT-TYPE
        SYNTAX   PositiveInteger
        MAX-ACCESS   read-create
        STATUS   current
        DESCRIPTION
           "The larger time interval, in seconds,  between
           the  Hello  packets  sent  to  an inactive non-
           broadcast multi- access neighbor."
       DEFVAL { 120 }
       ::= { nsVrOspfIfEntry 11 }

    nsVrOspfIfState OBJECT-TYPE
        SYNTAX   INTEGER    {
                    down (1),
                    loopback (2),
                    waiting (3),
                    pointToPoint (4),
                    designatedRouter (5),
                    backupDesignatedRouter (6),
                    otherDesignatedRouter (7)
                  }
        MAX-ACCESS   read-only
        STATUS   current
        DESCRIPTION
           "The OSPF Interface State."
       DEFVAL { down }

       ::= { nsVrOspfIfEntry 12 }

    nsVrOspfIfDesignatedRouter OBJECT-TYPE
        SYNTAX   IpAddress
        MAX-ACCESS   read-only
        STATUS   current
        DESCRIPTION
           "The IP Address of the Designated Router."
       DEFVAL   { '00000000'H }    -- 0.0.0.0
       ::= { nsVrOspfIfEntry 13 }

    nsVrOspfIfBackupDesignatedRouter OBJECT-TYPE
        SYNTAX   IpAddress
        MAX-ACCESS   read-only
        STATUS   current
        DESCRIPTION
           "The  IP  Address  of  the  Backup   Designated
           Router."
       DEFVAL   { '00000000'H }    -- 0.0.0.0
       ::= { nsVrOspfIfEntry 14 }

    nsVrOspfIfEvents OBJECT-TYPE
        SYNTAX   Counter32
        MAX-ACCESS   read-only
        STATUS   current
        DESCRIPTION
           "The number of times this  OSPF  interface  has
           changed its state, or an error has occurred."
       ::= { nsVrOspfIfEntry 15 }

    nsVrOspfIfAuthKey OBJECT-TYPE
        SYNTAX   OCTET STRING (SIZE (0..256))
        MAX-ACCESS   read-create
        STATUS   current
        DESCRIPTION
           "The Authentication Key.  If the Area's Author-
           ization  Type  is  simplePassword,  and the key
           length is shorter than 8 octets, the agent will
           left adjust and zero fill to 8 octets.

           Note that unauthenticated  interfaces  need  no
           authentication key, and simple password authen-
           tication cannot use a key of more  than  8  oc-
           tets.  Larger keys are useful only with authen-
           tication mechanisms not specified in this docu-

           ment.

           When read, nsVrOspfIfAuthKey always returns an  Oc-
           tet String of length zero."
       REFERENCE
          "OSPF Version 2, Section 9  The  Interface  Data
          Structure"
      DEFVAL   { '0000000000000000'H }    -- 0.0.0.0.0.0.0.0
      ::= { nsVrOspfIfEntry 16 }

    nsVrOspfIfStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
       ::= { nsVrOspfIfEntry 17 }

    nsVrOspfIfMulticastForwarding OBJECT-TYPE
        SYNTAX   INTEGER    {
                            blocked (1),        -- no multicast forwarding
                            multicast (2),        -- using multicast address
                            unicast (3)        -- to each OSPF neighbor
                  }
        MAX-ACCESS   read-create
        STATUS   current
        DESCRIPTION
           "The way multicasts should  forwarded  on  this
           interface;  not  forwarded,  forwarded  as data
           link multicasts, or forwarded as data link uni-
           casts.   Data link multicasting is not meaning-
           ful on point to point and NBMA interfaces,  and
           setting nsVrOspfMulticastForwarding to 0 effective-
           ly disables all multicast forwarding."
       DEFVAL { blocked }
       ::= { nsVrOspfIfEntry 18 }

    nsVrOspfIfDemand OBJECT-TYPE
        SYNTAX   TruthValue
        MAX-ACCESS   read-create
        STATUS   current
        DESCRIPTION
           "Indicates whether Demand OSPF procedures (hel-

           lo supression to FULL neighbors and setting the
           DoNotAge flag on proogated LSAs) should be per-
           formed on this interface."
       DEFVAL { false }
       ::= { nsVrOspfIfEntry 19 }

    nsVrOspfIfAuthType OBJECT-TYPE
        SYNTAX   INTEGER (0..255)
                    -- none (0),
                    -- simplePassword (1)
                    -- md5 (2)
                    -- reserved for specification by IANA (> 2)
        MAX-ACCESS   read-create
        STATUS   current
        DESCRIPTION
           "The authentication type specified for  an  in-
           terface.   Additional  authentication types may
           be assigned locally."
       REFERENCE
          "OSPF Version 2, Appendix E Authentication"
      DEFVAL { 0 }        -- no authentication, by default
      ::= { nsVrOspfIfEntry 20 }

    nsVrOspfIfVRID OBJECT-TYPE
        SYNTAX   INTEGER (0..65535)
        MAX-ACCESS   read-only
        STATUS   current
        DESCRIPTION
           "Virtual Router ID. VRID range for system created 
           VRs: [1-1024] and for user created VRs: [1025-2048]"
       ::= { nsVrOspfIfEntry 21 }

--  OSPF Interface Metric Table

--      The Metric Table describes the metrics to be advertised
--      for a specified interface at the various types of service.
--      As such, this table is an adjunct of the OSPF Interface
--      Table.

-- Types of service, as defined by RFC 791, have the ability
-- to request low delay, high bandwidth, or reliable linkage.

-- For the purposes of this specification, the measure of
-- bandwidth

--      Metric = 10^8 / ifSpeed

-- is the default value.  For multiple link interfaces, note
-- that ifSpeed is the sum of the individual link speeds.
-- This yields a number having the following typical values:

--      Network Type/bit rate   Metric

--      >= 100 MBPS                 1
--      Ethernet/802.3             10

--      E1                         48
--      T1 (ESF)                   65
--       64 KBPS                 1562
--       56 KBPS                 1785
--       19.2 KBPS               5208
--        9.6 KBPS              10416

-- Routes that are not specified use the default (TOS 0) metric

    nsVrOspfIfMetricTable OBJECT-TYPE
        SYNTAX   SEQUENCE OF  NsVrOspfIfMetricEntry
        MAX-ACCESS   not-accessible
        STATUS   current
        DESCRIPTION
           "The TOS metrics for  a  non-virtual  interface
           identified by the interface index."
       REFERENCE
          "OSPF Version 2, Appendix C.3  Router  interface
          parameters"
      ::= { nsVrOspf 8 }

    nsVrOspfIfMetricEntry OBJECT-TYPE
        SYNTAX    NsVrOspfIfMetricEntry
        MAX-ACCESS   not-accessible
        STATUS   current
        DESCRIPTION
           "A particular TOS metric for a non-virtual  in-
           terface identified by the interface index."
       REFERENCE
          "OSPF Version 2, Appendix C.3  Router  interface
          parameters"
      INDEX { nsVrOspfIfMetricVRID,
              nsVrOspfIfMetricIpAddress,
              nsVrOspfIfMetricAddressLessIf,
              nsVrOspfIfMetricTOS}
      ::= { nsVrOspfIfMetricTable 1 }

 NsVrOspfIfMetricEntry ::=
    SEQUENCE {
        nsVrOspfIfMetricIpAddress
            IpAddress,
        nsVrOspfIfMetricAddressLessIf
            Integer32,
        nsVrOspfIfMetricTOS
            TOSType,
        nsVrOspfIfMetricValue
            Metric,
        nsVrOspfIfMetricStatus
            RowStatus,
        nsVrOspfIfMetricVRID
            INTEGER

              }

    nsVrOspfIfMetricIpAddress OBJECT-TYPE
        SYNTAX   IpAddress
        MAX-ACCESS   read-only
        STATUS   current
        DESCRIPTION
           "The IP address of this OSPF interface.  On row
           creation,  this  can  be  derived  from the in-
           stance."
       ::= { nsVrOspfIfMetricEntry 1 }

    nsVrOspfIfMetricAddressLessIf OBJECT-TYPE
        SYNTAX   Integer32
        MAX-ACCESS   read-only
        STATUS   current
        DESCRIPTION
           "For the purpose of easing  the  instancing  of
           addressed   and  addressless  interfaces;  This
           variable takes the value 0 on  interfaces  with
           IP  Addresses, and the value of ifIndex for in-
           terfaces having no IP Address.   On  row  crea-
           tion, this can be derived from the instance."
       ::= { nsVrOspfIfMetricEntry 2 }

    nsVrOspfIfMetricTOS OBJECT-TYPE
        SYNTAX   TOSType
        MAX-ACCESS   read-only
        STATUS   current
        DESCRIPTION
           "The type of service metric  being  referenced.
           On  row  creation, this can be derived from the
           instance."
       ::= { nsVrOspfIfMetricEntry 3 }

    nsVrOspfIfMetricValue OBJECT-TYPE
        SYNTAX   Metric
        MAX-ACCESS   read-create
        STATUS   current
        DESCRIPTION
           "The metric of using this type  of  service  on
           this interface.  The default value of the TOS 0
           Metric is 10^8 / ifSpeed."
       ::= { nsVrOspfIfMetricEntry 4 }

    nsVrOspfIfMetricStatus OBJECT-TYPE

        SYNTAX   RowStatus
        MAX-ACCESS   read-create
        STATUS   current
        DESCRIPTION
           "This variable displays the status of  the  en-
           try.  Setting it to 'invalid' has the effect of
           rendering it inoperative.  The internal  effect
           (row removal) is implementation dependent."
       ::= { nsVrOspfIfMetricEntry 5 }

    nsVrOspfIfMetricVRID OBJECT-TYPE
        SYNTAX   INTEGER (0..65535)
        MAX-ACCESS   read-only
        STATUS   current
        DESCRIPTION
           "Virtual Router ID. VRID range for system created 
           VRs: [1-1024] and for user created VRs: [1025-2048]"
       ::= { nsVrOspfIfMetricEntry 6 }

--  OSPF Virtual Interface Table

--      The Virtual Interface Table describes the virtual
--      links that the OSPF Process is configured to
--      carry on.

    nsVrOspfVirtIfTable OBJECT-TYPE
        SYNTAX   SEQUENCE OF  NsVrOspfVirtIfEntry
        MAX-ACCESS   not-accessible
        STATUS   current
        DESCRIPTION
           "Information about this router's virtual inter-
           faces."
       REFERENCE
          "OSPF Version  2,  Appendix  C.4   Virtual  link
          parameters"
      ::= { nsVrOspf 9 }

    nsVrOspfVirtIfEntry OBJECT-TYPE
        SYNTAX    NsVrOspfVirtIfEntry
        MAX-ACCESS   not-accessible
        STATUS   current
        DESCRIPTION
           "Information about a single Virtual Interface."
       INDEX { nsVrOspfVirtIfVRID, nsVrOspfVirtIfAreaId, nsVrOspfVirtIfNeighbor}
       ::= { nsVrOspfVirtIfTable 1 }

 NsVrOspfVirtIfEntry ::=
    SEQUENCE {
        nsVrOspfVirtIfAreaId
            AreaID,
        nsVrOspfVirtIfNeighbor
            RouterID,
        nsVrOspfVirtIfTransitDelay
            UpToMaxAge,
        nsVrOspfVirtIfRetransInterval

            UpToMaxAge,
        nsVrOspfVirtIfHelloInterval
            HelloRange,
        nsVrOspfVirtIfRtrDeadInterval
            PositiveInteger,
        nsVrOspfVirtIfState
            INTEGER,
        nsVrOspfVirtIfEvents
            Counter32,
        nsVrOspfVirtIfAuthType
            INTEGER,
        nsVrOspfVirtIfAuthKey
            OCTET STRING,
        nsVrOspfVirtIfStatus
            RowStatus,
        nsVrOspfVirtIfVRID
            INTEGER
              }

    nsVrOspfVirtIfAreaId OBJECT-TYPE
        SYNTAX   AreaID
        MAX-ACCESS   read-only
        STATUS   current
        DESCRIPTION
           "The  Transit  Area  that  the   Virtual   Link
           traverses.  By definition, this is not 0.0.0.0"
       ::= { nsVrOspfVirtIfEntry 1 }

    nsVrOspfVirtIfNeighbor OBJECT-TYPE
        SYNTAX   RouterID
        MAX-ACCESS   read-only
        STATUS   current
        DESCRIPTION
           "The Router ID of the Virtual Neighbor."
       ::= { nsVrOspfVirtIfEntry 2 }

    nsVrOspfVirtIfTransitDelay OBJECT-TYPE
        SYNTAX   UpToMaxAge
        MAX-ACCESS   read-create
        STATUS   current
        DESCRIPTION
           "The estimated number of seconds  it  takes  to
           transmit  a link- state update packet over this
           interface."
       DEFVAL { 1 }
       ::= { nsVrOspfVirtIfEntry 3 }

    nsVrOspfVirtIfRetransInterval OBJECT-TYPE
        SYNTAX   UpToMaxAge
        MAX-ACCESS   read-create
        STATUS   current
        DESCRIPTION
           "The number of seconds between  link-state  ad-
           vertisement  retransmissions,  for  adjacencies
           belonging to this  interface.   This  value  is
           also used when retransmitting database descrip-
           tion  and  link-state  request  packets.   This
           value  should  be well over the expected round-
           trip time."
       DEFVAL { 5 }
       ::= { nsVrOspfVirtIfEntry 4 }

    nsVrOspfVirtIfHelloInterval OBJECT-TYPE
        SYNTAX   HelloRange
        MAX-ACCESS   read-create
        STATUS   current
        DESCRIPTION
           "The length of time, in  seconds,  between  the
           Hello  packets that the router sends on the in-
           terface.  This value must be the same  for  the
           virtual neighbor."
       DEFVAL { 10 }
       ::= { nsVrOspfVirtIfEntry 5 }

    nsVrOspfVirtIfRtrDeadInterval OBJECT-TYPE
        SYNTAX   PositiveInteger
        MAX-ACCESS   read-create
        STATUS   current
        DESCRIPTION
           "The number of seconds that  a  router's  Hello
           packets  have  not been seen before it's neigh-
           bors declare the router down.  This  should  be
           some  multiple  of  the  Hello  interval.  This
           value must be the same for the  virtual  neigh-
           bor."
       DEFVAL { 60 }
       ::= { nsVrOspfVirtIfEntry 6 }

    nsVrOspfVirtIfState OBJECT-TYPE
        SYNTAX   INTEGER    {
                    down (1),            -- these use the same encoding
                    pointToPoint (4)     -- as the nsVrOspfIfTable

                  }
        MAX-ACCESS   read-only
        STATUS   current
        DESCRIPTION
           "OSPF virtual interface states."
       DEFVAL   { down }
       ::= { nsVrOspfVirtIfEntry 7 }

    nsVrOspfVirtIfEvents OBJECT-TYPE
        SYNTAX   Counter32
        MAX-ACCESS   read-only
        STATUS   current
        DESCRIPTION
           "The number of state changes or error events on
           this Virtual Link"
       ::= { nsVrOspfVirtIfEntry 8 }

    nsVrOspfVirtIfAuthKey OBJECT-TYPE
        SYNTAX   OCTET STRING (SIZE(0..256))
        MAX-ACCESS   read-create
        STATUS   current
        DESCRIPTION
           "If Authentication Type is simplePassword,  the
           device  will left adjust and zero fill to 8 oc-
           tets.

           Note that unauthenticated  interfaces  need  no
           authentication key, and simple password authen-
           tication cannot use a key of more  than  8  oc-
           tets.  Larger keys are useful only with authen-
           tication mechanisms not specified in this docu-
           ment.

           When  read,  nsVrOspfVifAuthKey  always  returns  a
           string of length zero."
       REFERENCE
          "OSPF Version 2, Section 9  The  Interface  Data
          Structure"
      DEFVAL   { '0000000000000000'H }    -- 0.0.0.0.0.0.0.0
      ::= { nsVrOspfVirtIfEntry 9 }

    nsVrOspfVirtIfStatus OBJECT-TYPE
        SYNTAX   RowStatus
        MAX-ACCESS   read-create
        STATUS   current

        DESCRIPTION
           "This variable displays the status of  the  en-
           try.  Setting it to 'invalid' has the effect of
           rendering it inoperative.  The internal  effect
           (row removal) is implementation dependent."
       ::= { nsVrOspfVirtIfEntry 10 }

    nsVrOspfVirtIfAuthType OBJECT-TYPE
        SYNTAX   INTEGER (0..255)
                    -- none (0),
                    -- simplePassword (1)
                    -- md5 (2)
                    -- reserved for specification by IANA (> 2)
        MAX-ACCESS   read-create
        STATUS   current
        DESCRIPTION
           "The authentication type specified for a virtu-
           al  interface.  Additional authentication types
           may be assigned locally."
       REFERENCE
          "OSPF Version 2, Appendix E Authentication"
      DEFVAL { 0 }        -- no authentication, by default
      ::= { nsVrOspfVirtIfEntry 11 }

    nsVrOspfVirtIfVRID OBJECT-TYPE
        SYNTAX   INTEGER (0..65535)
        MAX-ACCESS   read-only
        STATUS   current
        DESCRIPTION
           "Virtual Router ID. VRID range for system created 
           VRs: [1-1024] and for user created VRs: [1025-2048]"
       ::= { nsVrOspfVirtIfEntry 12 }

--  OSPF Neighbor Table

--      The OSPF Neighbor Table describes all neighbors in
--      the locality of the subject router.

    nsVrOspfNbrTable OBJECT-TYPE
        SYNTAX   SEQUENCE OF  NsVrOspfNbrEntry
        MAX-ACCESS   not-accessible
        STATUS   current
        DESCRIPTION
           "A table of non-virtual neighbor information."
       REFERENCE
          "OSPF Version 2, Section 10  The  Neighbor  Data
          Structure"
      ::= { nsVrOspf 10 }

    nsVrOspfNbrEntry OBJECT-TYPE
        SYNTAX    NsVrOspfNbrEntry
        MAX-ACCESS   not-accessible
        STATUS   current
        DESCRIPTION

           "The information regarding a single neighbor."
       REFERENCE
          "OSPF Version 2, Section 10  The  Neighbor  Data
          Structure"
      INDEX { nsVrOspfNbrVRID, nsVrOspfNbrIpAddr, nsVrOspfNbrAddressLessIndex}
      ::= { nsVrOspfNbrTable 1 }

 NsVrOspfNbrEntry ::=
    SEQUENCE {
        nsVrOspfNbrIpAddr
            IpAddress,
        nsVrOspfNbrAddressLessIndex
            InterfaceIndex,
        nsVrOspfNbrRtrId
            RouterID,
        nsVrOspfNbrOptions
            Integer32,
        nsVrOspfNbrPriority
            DesignatedRouterPriority,
        nsVrOspfNbrState
            INTEGER,
        nsVrOspfNbrEvents
            Counter32,
        nsVrOspfNbrLsRetransQLen
            Gauge32,
        nsVrOspfNbmaNbrStatus
            RowStatus,
        nsVrOspfNbmaNbrPermanence
            INTEGER,
        nsVrOspfNbrHelloSuppressed
            TruthValue,
        nsVrOspfNbrVRID
            INTEGER
              }

    nsVrOspfNbrIpAddr OBJECT-TYPE
        SYNTAX   IpAddress
        MAX-ACCESS   read-only
        STATUS   current
        DESCRIPTION
           "The IP address this neighbor is using  in  its
           IP  Source  Address.  Note that, on addressless
           links, this will not be 0.0.0.0,  but  the  ad-
           dress of another of the neighbor's interfaces."
       ::= { nsVrOspfNbrEntry 1 }

    nsVrOspfNbrAddressLessIndex OBJECT-TYPE
        SYNTAX   InterfaceIndex
        MAX-ACCESS   read-only

        STATUS   current
        DESCRIPTION
           "On an interface having an  IP  Address,  zero.
           On  addressless  interfaces,  the corresponding
           value of ifIndex in the Internet Standard  MIB.
           On  row  creation, this can be derived from the
           instance."
       ::= { nsVrOspfNbrEntry 2 }

    nsVrOspfNbrRtrId OBJECT-TYPE
        SYNTAX   RouterID
        MAX-ACCESS   read-only
        STATUS   current
        DESCRIPTION
           "A 32-bit integer (represented as a type  IpAd-
           dress)  uniquely  identifying  the  neighboring
           router in the Autonomous System."
       DEFVAL   { '00000000'H }    -- 0.0.0.0
       ::= { nsVrOspfNbrEntry 3 }

    nsVrOspfNbrOptions OBJECT-TYPE
        SYNTAX   Integer32
        MAX-ACCESS   read-only
        STATUS   current
        DESCRIPTION
           "A Bit Mask corresponding to the neighbor's op-
           tions field.

           Bit 0, if set, indicates that the  system  will
           operate  on  Type of Service metrics other than
           TOS 0.  If zero, the neighbor will  ignore  all
           metrics except the TOS 0 metric.

           Bit 1, if set, indicates  that  the  associated
           area  accepts and operates on external informa-
           tion; if zero, it is a stub area.

           Bit 2, if set, indicates that the system is ca-
           pable  of routing IP Multicast datagrams; i.e.,
           that it implements the Multicast Extensions  to
           OSPF.

           Bit 3, if set, indicates  that  the  associated
           area  is  an  NSSA.  These areas are capable of
           carrying type 7 external advertisements,  which
           are  translated into type 5 external advertise-

           ments at NSSA borders."
       REFERENCE
          "OSPF Version 2, Section 12.1.2 Options"
      DEFVAL { 0 }
      ::= { nsVrOspfNbrEntry 4 }

    nsVrOspfNbrPriority OBJECT-TYPE
        SYNTAX   DesignatedRouterPriority
        MAX-ACCESS   read-create
        STATUS   current
        DESCRIPTION
           "The priority of this neighbor in the designat-
           ed router election algorithm.  The value 0 sig-
           nifies that the neighbor is not eligible to be-
           come  the  designated router on this particular
           network."
       DEFVAL { 1 }
       ::= { nsVrOspfNbrEntry 5 }

    nsVrOspfNbrState OBJECT-TYPE
        SYNTAX   INTEGER    {
                    down (1),
                    attempt (2),
                    init (3),
                    twoWay (4),
                    exchangeStart (5),
                    exchange (6),
                    loading (7),
                    full (8)
                  }
        MAX-ACCESS   read-only
        STATUS   current
        DESCRIPTION
           "The State of the relationship with this Neigh-
           bor."
       REFERENCE
          "OSPF Version 2, Section 10.1 Neighbor States"
      DEFVAL   { down }
      ::= { nsVrOspfNbrEntry 6 }

    nsVrOspfNbrEvents OBJECT-TYPE
        SYNTAX   Counter32
        MAX-ACCESS   read-only
        STATUS   current
        DESCRIPTION

           "The number of times this neighbor relationship
           has changed state, or an error has occurred."
       ::= { nsVrOspfNbrEntry 7 }

    nsVrOspfNbrLsRetransQLen OBJECT-TYPE
        SYNTAX   Gauge32
        MAX-ACCESS   read-only
        STATUS   current
        DESCRIPTION
           "The  current  length  of  the   retransmission
           queue."
       ::= { nsVrOspfNbrEntry 8 }

    nsVrOspfNbmaNbrStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
       ::= { nsVrOspfNbrEntry 9 }

    nsVrOspfNbmaNbrPermanence OBJECT-TYPE
        SYNTAX   INTEGER    {
                    dynamic (1),        -- learned through protocol
                    permanent (2)       -- configured address
                  }
        MAX-ACCESS   read-only
        STATUS   current
        DESCRIPTION
           "This variable displays the status of  the  en-
           try.   'dynamic'  and  'permanent' refer to how
           the neighbor became known."
       DEFVAL { permanent }
       ::= { nsVrOspfNbrEntry 10 }

    nsVrOspfNbrHelloSuppressed OBJECT-TYPE
        SYNTAX   TruthValue
        MAX-ACCESS   read-only
        STATUS   current
        DESCRIPTION
           "Indicates whether Hellos are being  suppressed

           to the neighbor"
       ::= { nsVrOspfNbrEntry 11 }

    nsVrOspfNbrVRID OBJECT-TYPE
        SYNTAX   INTEGER (0..65535)
        MAX-ACCESS   read-only
        STATUS   current
        DESCRIPTION
           "Virtual Router ID. VRID range for system created 
           VRs: [1-1024] and for user created VRs: [1025-2048]"
       ::= { nsVrOspfNbrEntry 12 }

--  OSPF Virtual Neighbor Table

--      This table describes all virtual neighbors.
--      Since Virtual Links are configured in the
--      virtual interface table, this table is read-only.

    nsVrOspfVirtNbrTable OBJECT-TYPE
        SYNTAX   SEQUENCE OF  NsVrOspfVirtNbrEntry
        MAX-ACCESS   not-accessible
        STATUS   current
        DESCRIPTION
           "A table of virtual neighbor information."
       REFERENCE
          "OSPF Version 2, Section 15  Virtual Links"
      ::= { nsVrOspf 11 }

    nsVrOspfVirtNbrEntry OBJECT-TYPE
        SYNTAX    NsVrOspfVirtNbrEntry
        MAX-ACCESS   not-accessible
        STATUS   current
        DESCRIPTION
           "Virtual neighbor information."
       INDEX { nsVrOspfVirtNbrVRID, nsVrOspfVirtNbrArea, nsVrOspfVirtNbrRtrId}
       ::= { nsVrOspfVirtNbrTable 1 }

 NsVrOspfVirtNbrEntry ::=
    SEQUENCE {
        nsVrOspfVirtNbrArea
            AreaID,
        nsVrOspfVirtNbrRtrId
            RouterID,
        nsVrOspfVirtNbrIpAddr
            IpAddress,
        nsVrOspfVirtNbrOptions
            Integer32,
        nsVrOspfVirtNbrState
            INTEGER,
        nsVrOspfVirtNbrEvents
            Counter32,
        nsVrOspfVirtNbrLsRetransQLen
            Gauge32,
        nsVrOspfVirtNbrHelloSuppressed
                TruthValue,
        nsVrOspfVirtNbrVRID
            INTEGER

              }

    nsVrOspfVirtNbrArea OBJECT-TYPE
        SYNTAX   AreaID
        MAX-ACCESS   read-only
        STATUS   current
        DESCRIPTION
           "The Transit Area Identifier."
       ::= { nsVrOspfVirtNbrEntry 1 }

    nsVrOspfVirtNbrRtrId OBJECT-TYPE
        SYNTAX   RouterID
        MAX-ACCESS   read-only
        STATUS   current
        DESCRIPTION
           "A  32-bit  integer  uniquely  identifying  the
           neighboring router in the Autonomous System."
       ::= { nsVrOspfVirtNbrEntry 2 }

    nsVrOspfVirtNbrIpAddr OBJECT-TYPE
        SYNTAX   IpAddress
        MAX-ACCESS   read-only
        STATUS   current
        DESCRIPTION
           "The IP address this Virtual  Neighbor  is  us-
           ing."
       ::= { nsVrOspfVirtNbrEntry 3 }

    nsVrOspfVirtNbrOptions OBJECT-TYPE
        SYNTAX   Integer32
        MAX-ACCESS   read-only
        STATUS   current
        DESCRIPTION
           "A Bit Mask corresponding to the neighbor's op-
           tions field.

           Bit 1, if set, indicates that the  system  will
           operate  on  Type of Service metrics other than
           TOS 0.  If zero, the neighbor will  ignore  all
           metrics except the TOS 0 metric.

           Bit 2, if set, indicates  that  the  system  is
           Network  Multicast  capable; ie, that it imple-
           ments OSPF Multicast Routing."
       ::= { nsVrOspfVirtNbrEntry 4 }

    nsVrOspfVirtNbrState OBJECT-TYPE
        SYNTAX   INTEGER    {
                    down (1),
                    attempt (2),
                    init (3),
                    twoWay (4),
                    exchangeStart (5),
                    exchange (6),
                    loading (7),
                    full (8)
                  }
        MAX-ACCESS   read-only
        STATUS   current
        DESCRIPTION
           "The state of the  Virtual  Neighbor  Relation-
           ship."
       ::= { nsVrOspfVirtNbrEntry 5 }

    nsVrOspfVirtNbrEvents OBJECT-TYPE
        SYNTAX   Counter32
        MAX-ACCESS   read-only
        STATUS   current
        DESCRIPTION
           "The number of  times  this  virtual  link  has
           changed its state, or an error has occurred."
       ::= { nsVrOspfVirtNbrEntry 6 }

    nsVrOspfVirtNbrLsRetransQLen OBJECT-TYPE
        SYNTAX   Gauge32
        MAX-ACCESS   read-only
        STATUS   current
        DESCRIPTION
           "The  current  length  of  the   retransmission
           queue."
       ::= { nsVrOspfVirtNbrEntry 7 }

    nsVrOspfVirtNbrHelloSuppressed OBJECT-TYPE
        SYNTAX   TruthValue
        MAX-ACCESS   read-only
        STATUS   current
        DESCRIPTION
           "Indicates whether Hellos are being  suppressed
           to the neighbor"
       ::= { nsVrOspfVirtNbrEntry 8 }

    nsVrOspfVirtNbrVRID OBJECT-TYPE
        SYNTAX   INTEGER (0..65535)
        MAX-ACCESS   read-only
        STATUS   current
        DESCRIPTION
           "Virtual Router ID. VRID range for system created 
           VRs: [1-1024] and for user created VRs: [1025-2048]"
       ::= { nsVrOspfVirtNbrEntry 9 }

--  OSPF Link State Database, External

--      The Link State Database contains the Link State
--      Advertisements from throughout the areas that the
--      device is attached to.

--             This table is identical to the OSPF LSDB Table in
--      format, but contains only External Link State
--             Advertisements.  The purpose is to allow external
--      LSAs to be displayed once for the router rather
--      than once in each non-stub area.

    nsVrOspfExtLsdbTable OBJECT-TYPE
        SYNTAX   SEQUENCE OF  NsVrOspfExtLsdbEntry
        MAX-ACCESS   not-accessible
        STATUS   current
        DESCRIPTION
           "The OSPF Process's Links State Database."
       REFERENCE
          "OSPF Version 2, Section 12  Link  State  Adver-
          tisements"
      ::= { nsVrOspf 12 }

    nsVrOspfExtLsdbEntry OBJECT-TYPE
        SYNTAX    NsVrOspfExtLsdbEntry
        MAX-ACCESS   not-accessible
        STATUS   current
        DESCRIPTION
           "A single Link State Advertisement."
       INDEX { nsVrOspfExtLsdbVRID, nsVrOspfExtLsdbType, nsVrOspfExtLsdbLsid, nsVrOspfExtLsdbRouterId}
       ::= { nsVrOspfExtLsdbTable 1 }

 NsVrOspfExtLsdbEntry ::=
    SEQUENCE {
        nsVrOspfExtLsdbType
            INTEGER,
        nsVrOspfExtLsdbLsid
            IpAddress,
        nsVrOspfExtLsdbRouterId
            RouterID,
        nsVrOspfExtLsdbSequence
            Integer32,
        nsVrOspfExtLsdbAge
            Integer32,
        nsVrOspfExtLsdbChecksum
            Integer32,
        nsVrOspfExtLsdbAdvertisement
            OCTET STRING,
        nsVrOspfExtLsdbVRID
            INTEGER
              }

    nsVrOspfExtLsdbType OBJECT-TYPE
        SYNTAX   INTEGER    {
                    asExternalLink (5)
                  }
        MAX-ACCESS   read-only
        STATUS   current
        DESCRIPTION
           "The type  of  the  link  state  advertisement.
           Each  link state type has a separate advertise-
           ment format."
       REFERENCE
          "OSPF Version 2, Appendix A.4.1 The  Link  State
          Advertisement header"
      ::= { nsVrOspfExtLsdbEntry 1 }

    nsVrOspfExtLsdbLsid OBJECT-TYPE
        SYNTAX   IpAddress
        MAX-ACCESS   read-only
        STATUS   current
        DESCRIPTION
           "The Link State ID is an LS Type Specific field
           containing either a Router ID or an IP Address;
           it identifies the piece of the  routing  domain
           that is being described by the advertisement."
       REFERENCE
          "OSPF Version 2, Section 12.1.4 Link State ID"
      ::= { nsVrOspfExtLsdbEntry 2 }

    nsVrOspfExtLsdbRouterId OBJECT-TYPE
        SYNTAX   RouterID
        MAX-ACCESS   read-only
        STATUS   current
        DESCRIPTION
           "The 32 bit number that uniquely identifies the
           originating router in the Autonomous System."
       REFERENCE
          "OSPF Version 2, Appendix C.1 Global parameters"
      ::= { nsVrOspfExtLsdbEntry 3 }

--  Note that the OSPF Sequence Number is a 32 bit signed
--  integer.  It starts with the value '80000001'h,
--  or -'7FFFFFFF'h, and increments until '7FFFFFFF'h
--  Thus, a typical sequence number will be very negative.

    nsVrOspfExtLsdbSequence OBJECT-TYPE
        SYNTAX   Integer32
        MAX-ACCESS   read-only
        STATUS   current
        DESCRIPTION
           "The sequence number field is a  signed  32-bit
           integer.   It  is used to detect old and dupli-
           cate link state advertisements.  The  space  of
           sequence  numbers  is  linearly  ordered.   The
           larger the sequence number the more recent  the
           advertisement."
       REFERENCE
          "OSPF Version  2,  Section  12.1.6  LS  sequence
          number"
      ::= { nsVrOspfExtLsdbEntry 4 }

    nsVrOspfExtLsdbAge OBJECT-TYPE
        SYNTAX   Integer32    -- Should be 0..MaxAge
        MAX-ACCESS   read-only
        STATUS   current
        DESCRIPTION
           "This field is the age of the link state adver-
           tisement in seconds."
       REFERENCE
          "OSPF Version 2, Section 12.1.1 LS age"
      ::= { nsVrOspfExtLsdbEntry 5 }

    nsVrOspfExtLsdbChecksum OBJECT-TYPE
        SYNTAX   Integer32
        MAX-ACCESS   read-only
        STATUS   current
        DESCRIPTION
           "This field is the  checksum  of  the  complete
           contents  of  the  advertisement, excepting the
           age field.  The age field is excepted  so  that
           an   advertisement's  age  can  be  incremented
           without updating the  checksum.   The  checksum
           used  is  the same that is used for ISO connec-
           tionless datagrams; it is commonly referred  to
           as the Fletcher checksum."
       REFERENCE
          "OSPF Version 2, Section 12.1.7 LS checksum"
      ::= { nsVrOspfExtLsdbEntry 6 }

    nsVrOspfExtLsdbAdvertisement OBJECT-TYPE

        SYNTAX   OCTET STRING (SIZE(36))
        MAX-ACCESS   read-only
        STATUS   current
        DESCRIPTION
           "The entire Link State Advertisement, including
           its header."
       REFERENCE
          "OSPF Version 2, Section 12  Link  State  Adver-
          tisements"
      ::= { nsVrOspfExtLsdbEntry 7 }

    nsVrOspfExtLsdbVRID OBJECT-TYPE
        SYNTAX   INTEGER (0..65535)
        MAX-ACCESS   read-only
        STATUS   current
        DESCRIPTION
           "Virtual Router ID. VRID range for system created 
           VRs: [1-1024] and for user created VRs: [1025-2048]"
       ::= { nsVrOspfExtLsdbEntry 8 }


--
--      The OSPF Area Aggregate Table
--
--      This table replaces the OSPF Area Summary Table, being an
--      extension of that for CIDR routers.

    nsVrOspfAreaAggregateTable OBJECT-TYPE
        SYNTAX   SEQUENCE OF  NsVrOspfAreaAggregateEntry
        MAX-ACCESS   not-accessible
        STATUS   current
        DESCRIPTION
           "A range of IP addresses  specified  by  an  IP
           address/IP  network  mask  pair.   For example,
           class B address range of X.X.X.X with a network
           mask  of  255.255.0.0 includes all IP addresses
           from X.X.0.0  to  X.X.255.255.   Note  that  if
           ranges  are configured such that one range sub-
           sumes  another  range  (e.g.,   10.0.0.0   mask
           255.0.0.0  and  10.1.0.0 mask 255.255.0.0), the
           most specific match is the preferred one."
       REFERENCE
          "OSPF Version 2, Appendix C.2  Area parameters"
      ::= { nsVrOspf 14 }

    nsVrOspfAreaAggregateEntry OBJECT-TYPE
        SYNTAX    NsVrOspfAreaAggregateEntry
        MAX-ACCESS   not-accessible
        STATUS   current
        DESCRIPTION
           "A range of IP addresses  specified  by  an  IP
           address/IP  network  mask  pair.   For example,
           class B address range of X.X.X.X with a network
           mask  of  255.255.0.0 includes all IP addresses
           from X.X.0.0  to  X.X.255.255.   Note  that  if
           ranges are range configured such that one range
           subsumes another  range  (e.g.,  10.0.0.0  mask
           255.0.0.0  and  10.1.0.0 mask 255.255.0.0), the

           most specific match is the preferred one."
       REFERENCE
          "OSPF Version 2, Appendix C.2  Area parameters"
      INDEX { nsVrOspfAreaAggregateVRID, nsVrOspfAreaAggregateAreaID, nsVrOspfAreaAggregateLsdbType,
              nsVrOspfAreaAggregateNet, nsVrOspfAreaAggregateMask}
      ::= { nsVrOspfAreaAggregateTable 1 }

 NsVrOspfAreaAggregateEntry ::=
    SEQUENCE {
        nsVrOspfAreaAggregateAreaID
            AreaID,
        nsVrOspfAreaAggregateLsdbType
            INTEGER,
        nsVrOspfAreaAggregateNet
            IpAddress,
        nsVrOspfAreaAggregateMask
            IpAddress,
        nsVrOspfAreaAggregateStatus
            RowStatus,
        nsVrOspfAreaAggregateEffect
            INTEGER,
        nsVrOspfAreaAggregateVRID
            INTEGER
              }

    nsVrOspfAreaAggregateAreaID OBJECT-TYPE
        SYNTAX   AreaID
        MAX-ACCESS   read-only
        STATUS   current
        DESCRIPTION
           "The Area the Address Aggregate is to be  found
           within."
       REFERENCE
          "OSPF Version 2, Appendix C.2 Area parameters"
      ::= { nsVrOspfAreaAggregateEntry 1 }

    nsVrOspfAreaAggregateLsdbType OBJECT-TYPE
        SYNTAX   INTEGER    {
                    summaryLink (3),
                    nssaExternalLink (7)
                  }
        MAX-ACCESS   read-only
        STATUS   current
        DESCRIPTION
           "The type of the Address Aggregate.  This field
           specifies  the  Lsdb type that this Address Ag-
           gregate applies to."
       REFERENCE

          "OSPF Version 2, Appendix A.4.1 The  Link  State
          Advertisement header"
      ::= { nsVrOspfAreaAggregateEntry 2 }

    nsVrOspfAreaAggregateNet OBJECT-TYPE
        SYNTAX   IpAddress
        MAX-ACCESS   read-only
        STATUS   current
        DESCRIPTION
           "The IP Address of the Net or Subnet  indicated
           by the range."
       REFERENCE
          "OSPF Version 2, Appendix C.2 Area parameters"
      ::= { nsVrOspfAreaAggregateEntry 3 }

    nsVrOspfAreaAggregateMask OBJECT-TYPE
        SYNTAX   IpAddress
        MAX-ACCESS   read-only
        STATUS   current
        DESCRIPTION
           "The Subnet Mask that pertains to  the  Net  or
           Subnet."
       REFERENCE
          "OSPF Version 2, Appendix C.2 Area parameters"
      ::= { nsVrOspfAreaAggregateEntry 4 }

    nsVrOspfAreaAggregateStatus OBJECT-TYPE
        SYNTAX   RowStatus
        MAX-ACCESS   read-create
        STATUS   current
        DESCRIPTION
           "This variable displays the status of  the  en-
           try.  Setting it to 'invalid' has the effect of
           rendering it inoperative.  The internal  effect
           (row removal) is implementation dependent."
       ::= { nsVrOspfAreaAggregateEntry 5 }

    nsVrOspfAreaAggregateEffect OBJECT-TYPE
        SYNTAX   INTEGER    {
                    advertiseMatching (1),
                    doNotAdvertiseMatching (2)
                  }
        MAX-ACCESS   read-create
        STATUS   current

        DESCRIPTION
           "Subnets subsumed by ranges either trigger  the
           advertisement  of  the indicated aggregate (ad-
           vertiseMatching), or result in the subnet's not
           being advertised at all outside the area."
       DEFVAL   { advertiseMatching }
       ::= { nsVrOspfAreaAggregateEntry 6 }

    nsVrOspfAreaAggregateVRID OBJECT-TYPE
        SYNTAX   INTEGER (0..65535)
        MAX-ACCESS   read-only
        STATUS   current
        DESCRIPTION
           "Virtual Router ID. VRID range for system created 
           VRs: [1-1024] and for user created VRs: [1025-2048]"
       ::= { nsVrOspfAreaAggregateEntry 7 }

END
