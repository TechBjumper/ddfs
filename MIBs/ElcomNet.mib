--  Elcom International MIB
--  Copyright 2016 Elcom International Pvt. Ltd.
--  Revision: 1.0.1
--  Release Date : 29.07.2017

 RFC1213-MIB DEFINITIONS ::= BEGIN

          IMPORTS
                  mgmt, Counter,
                          TimeTicks
                      FROM RFC1155-SMI
					  
                  OBJECT-TYPE
                          FROM RFC-1212;

          --  This MIB module uses the extended OBJECT-TYPE macro as
          --  defined in [14];


          --  MIB-II (same prefix as MIB-I)

          mib-2      OBJECT IDENTIFIER ::= { mgmt 1 }

          -- textual conventions

          DisplayString ::=
              OCTET STRING
          -- This data type is used to model textual information taken
          -- from the NVT ASCII character set.  By convention, objects
          -- with this syntax are declared as having






          --
          --      SIZE (0..255)

          PhysAddress ::=
              OCTET STRING
          -- This data type is used to model media addresses.  For many
          -- types of media, this will be in a binary representation.
          -- For example, an ethernet address would be represented as
          -- a string of 6 octets.


          -- groups in MIB-II

          system       OBJECT IDENTIFIER ::= { mib-2 1 }

          


          -- the System group

          -- Implementation of the System group is mandatory for all
          -- systems.  If an agent is not configured to have a value
          -- for any of these variables, a string of length 0 is
          -- returned.

          sysDescr OBJECT-TYPE
              SYNTAX  DisplayString (SIZE (0..255))
               ACCESS  read-only
              STATUS  mandatory





              DESCRIPTION
                      "A textual description of the entity.  This value
                      should include the full name and version
                      identification of the system's hardware type,
                      software operating-system, and networking
                      software.  It is mandatory that this only contain
                      printable ASCII characters."
              ::= { system 1 }

          sysObjectID OBJECT-TYPE
              SYNTAX  OBJECT IDENTIFIER
               ACCESS  read-only
              STATUS  mandatory
              DESCRIPTION
                      "The vendor's authoritative identification of the
                      network management subsystem contained in the
                      entity.  This value is allocated within the SMI
                      enterprises subtree (1.3.6.1.4.1) and provides an
                      easy and unambiguous means for determining `what
                      kind of box' is being managed.  For example, if
                      vendor `Flintstones, Inc.' was assigned the
                      subtree 1.3.6.1.4.1.4242, it could assign the
                      identifier 1.3.6.1.4.1.4242.1.1 to its `Fred
                      Router'."
              ::= { system 2 }

          sysUpTime OBJECT-TYPE
              SYNTAX  TimeTicks
               ACCESS  read-only
              STATUS  mandatory
              DESCRIPTION
                      "The time (in hundredths of a second) since the
                      network management portion of the system was last
                      re-initialized."
              ::= { system 3 }

          sysContact OBJECT-TYPE
              SYNTAX  DisplayString (SIZE (0..255))
               ACCESS  read-write
              STATUS  mandatory
              DESCRIPTION
                      "The textual identification of the contact person
                      for this managed node, together with information
                      on how to contact this person."
              ::= { system 4 }

          sysName OBJECT-TYPE
              SYNTAX  DisplayString (SIZE (0..255))





               ACCESS  read-write
              STATUS  mandatory
              DESCRIPTION
                      "An administratively-assigned name for this
                      managed node.  By convention, this is the node's
                      fully-qualified domain name."
              ::= { system 5 }

          sysLocation OBJECT-TYPE
              SYNTAX  DisplayString (SIZE (0..255))
               ACCESS  read-write
              STATUS  mandatory
              DESCRIPTION
                      "The physical location of this node (e.g.,
                      `telephone closet, 3rd floor')."
              ::= { system 6 }

          sysServices OBJECT-TYPE
              SYNTAX  Integer32 (0..127)
               ACCESS  read-only
              STATUS  mandatory
              DESCRIPTION
                      "A value which indicates the set of services that
                      this entity primarily offers.

                      The value is a sum.  This sum initially takes the
                      value zero, Then, for each layer, L, in the range
                      1 through 7, that this node performs transactions
                      for, 2 raised to (L - 1) is added to the sum.  For
                      example, a node which performs primarily routing
                      functions would have a value of 4 (2^(3-1)).  In
                      contrast, a node which is a host offering
                      application services would have a value of 72
                      (2^(4-1) + 2^(7-1)).  Note that in the context of
                      the Internet suite of protocols, values should be
                      calculated accordingly:

                           layer  functionality
                               1  physical (e.g., repeaters)
                               2  datalink/subnetwork (e.g., bridges)
                               3  internet (e.g., IP gateways)
                               4  end-to-end  (e.g., IP hosts)
                               7  applications (e.g., mail relays)

                      For systems including OSI protocols, layers 5 and
                      6 may also be counted."
              ::= { system 7 }


END


-- ElcomNet-MIB { iso org(3) dod(6) internet(1) private(4)
--    enterprises(1) elcom(40367) }

ElcomNet-MIB DEFINITIONS ::= BEGIN

IMPORTS 

   enterprises, IpAddress, Gauge, TimeTicks             FROM RFC1155-SMI
   DisplayString                                        FROM RFC1213-MIB
   OBJECT-TYPE                                          FROM RFC-1212
   TRAP-TYPE                                            FROM RFC-1215;

elcom                            OBJECT IDENTIFIER ::=  { enterprises 40367 }
 

ed 					OBJECT IDENTIFIER ::= { elcom 12 }

edProducts     		OBJECT IDENTIFIER ::= { ed 1 }
edManagement   		OBJECT IDENTIFIER ::= { ed 2 }
edConnectedPduMgmt  OBJECT IDENTIFIER ::= { ed 3 }
--
 

--
eAMIMS     		OBJECT IDENTIFIER ::= { edProducts 1 } 


edAppliance   	 	OBJECT IDENTIFIER ::= { edManagement 1  }
edPowerMgmt     	OBJECT IDENTIFIER ::= { edManagement 2  }
edTrapObject   		OBJECT IDENTIFIER ::= { edManagement 3 	} 




edHostName OBJECT-TYPE
        SYNTAX             	DisplayString ( SIZE (0..32) )
        ACCESS         		read-only
        STATUS             	mandatory
        DESCRIPTION
        "The appliance name"
::= { edAppliance 1 }

edProductModel OBJECT-TYPE
        SYNTAX             DisplayString ( SIZE (0..50) )
         ACCESS         		read-only
        STATUS             mandatory
        DESCRIPTION
        "The appliance product model"
::= { edAppliance 2 }

edPartNumber OBJECT-TYPE
        SYNTAX             DisplayString ( SIZE (0..32) )
         ACCESS         read-only
        STATUS             mandatory
        DESCRIPTION
        "The part number of this appliance as shown on the label
         attached or imprinted on the appliance."
::= { edAppliance 3 }

edSerialNumber OBJECT-TYPE
        SYNTAX             DisplayString ( SIZE (0..32) )
         ACCESS         read-only
        STATUS             mandatory
        DESCRIPTION
        "The serial number of this appliance as shown on the label
         attached or imprinted on the appliance."
::= { edAppliance 4 }

edBootcodeVersion OBJECT-TYPE
        SYNTAX             DisplayString ( SIZE (0..32) )
         ACCESS         read-only
        STATUS             mandatory
        DESCRIPTION 
        "The version of the bootcode of this appliance."
::= { edAppliance 5 }

edFirmwareVersion OBJECT-TYPE
        SYNTAX             DisplayString ( SIZE (0..32) )
         ACCESS         read-only
        STATUS             mandatory
        DESCRIPTION 
        "The version of the firmware of this appliance."
::= { edAppliance 6 }





edPowerMgmtPDUTable OBJECT IDENTIFIER::= { edPowerMgmt 1 }
 
edPowerMgmtPDUTableData OBJECT IDENTIFIER::= { edPowerMgmtPDUTable 1 }

edPowerMgmtPDUTableNumber       OBJECT-TYPE
        SYNTAX             Integer32
         ACCESS         read-only
        STATUS             mandatory
        DESCRIPTION
        "Index Number"
::= { edPowerMgmtPDUTableData 1 }


edPowerMgmtPDUTableFirmwareVersion       OBJECT-TYPE
        SYNTAX             DisplayString
         ACCESS         read-only
        STATUS             mandatory
        DESCRIPTION
        "Version of the PDU firmware.
         Returns N/A if not applicable."
::= { edPowerMgmtPDUTableData 2 }



edPowerMgmtPDUTableNumberOfOutlets OBJECT-TYPE
        SYNTAX             Integer32
         ACCESS         read-only
        STATUS             mandatory
        DESCRIPTION
        "Number of outlets of the PDU."
::= { edPowerMgmtPDUTableData 3 }

edPowerMgmtPDUTableNumberOfPhases OBJECT-TYPE
        SYNTAX             Integer32
         ACCESS         read-only
        STATUS             mandatory
        DESCRIPTION
        "Number of phases of the PDU."
::= { edPowerMgmtPDUTableData 4 }


edPowerMgmtPDUTableNumberOfSensors OBJECT-TYPE
        SYNTAX             Integer32
         ACCESS         read-only
        STATUS             mandatory
        DESCRIPTION
        "Number of sensors in the PDU."
::= { edPowerMgmtPDUTableData 5 }



edPowerMgmtPDUTableVendor   OBJECT-TYPE
        SYNTAX             DisplayString
         ACCESS         	  read-only
        STATUS             mandatory
        DESCRIPTION
        "Vendor of the PDU.
         Returns N/A if not applicable."
::= { edPowerMgmtPDUTableData 6 }


edPowerMgmtAggrInfoTable OBJECT IDENTIFIER::= { edPowerMgmt 2 }

edPowerMgmtAggrsData OBJECT IDENTIFIER::= { edPowerMgmtAggrInfoTable 1 }


edPowerMgmtAggrInfoNumber       OBJECT-TYPE
        SYNTAX             		Integer32
         ACCESS         			read-only
        STATUS             		mandatory
        DESCRIPTION
        "Index Number"
::= { edPowerMgmtAggrsData 1 }
 


edPowerMgmtAggrInfoTableVoltageValue OBJECT-TYPE
        SYNTAX             Integer32
         ACCESS         read-only
        STATUS             mandatory
        DESCRIPTION
		"Aggrgate voltage of phase is (if vRphase R > vYphase && vRphase R > vBphase) 
		aggregate voltage of R Phase .The recieved value 
		if 23024 then actual value in decimal willbe 230.24 Volts ,
		if recieved 12 then 0.12 Volt. Returns 0 if not supported."
::= { edPowerMgmtAggrsData 2 }


edPowerMgmtAggrInfoTableCurrentValue OBJECT-TYPE
        SYNTAX             Integer32
         ACCESS         read-only
        STATUS             mandatory
        DESCRIPTION
        "Addition of mandatory of all Outlet.The recieved value 
		if 1234 then actual value in decimal willbe 12.34 Amp, if recieved 
		value is 12 then 0.12 Amp .Returns 0 if not supported."
::= { edPowerMgmtAggrsData 3 }


edPowerMgmtAggrInfoTableApearentEnergyValue OBJECT-TYPE
        SYNTAX             Integer32
         ACCESS         read-only
        STATUS             mandatory
        DESCRIPTION
       "addition of ApearentEnergy(KVaHr) of all outlet.The recieved value
	   if 23024 then actual value in decimal willbe 2.3024 KVaHr , if recieved 12
	   then 0.0012 KVaHr. Returns 0 if not supported."
::= { edPowerMgmtAggrsData 4 }


edPowerMgmtAggrInfoTableReactiveEnergyValue OBJECT-TYPE
        SYNTAX             Integer32
         ACCESS         read-only
        STATUS             mandatory
        DESCRIPTION
         "addition of ReactiveEnergy(KVarHr) of all outlet.The recieved value 
		 if 23024 then actual value in decimal willbe 2.3024 KVarHr , if recieved 12 
		 then 0.0012 KVarHr. Returns 0 if not supported."
::= { edPowerMgmtAggrsData 5 }

edPowerMgmtAggrInfoTableActiveEnergyValue OBJECT-TYPE
        SYNTAX             Integer32
         ACCESS         read-only
        STATUS             mandatory
        DESCRIPTION
      "addition of ActiveEnergy(KWattHr) of all outlets.The recieved value 
	  if 23024 then actual value in decimal willbe 2.3024 KWattHr , if recieved 12
	  then 0.0012 KWattHr. Returns 0 if not supported."
::= { edPowerMgmtAggrsData 6 }


edPowerMgmtAggrInfoTableInstantaneousPowerValue OBJECT-TYPE
        SYNTAX             Integer32
         ACCESS         read-only
        STATUS             mandatory
        DESCRIPTION
      "addition of  Instantaneous Power(KWatt) of all outlet.The recieved value 
	  if 230 then actual value in decimal willbe 2.30 KWatt , if recieved 12 
	  then 0.12 KWatt. Returns 0 if not supported."
::= { edPowerMgmtAggrsData 7 }

edPowerMgmtAggrInfoTablePowerFactorValue OBJECT-TYPE
        SYNTAX             Integer32
         ACCESS         read-only
        STATUS             mandatory
        DESCRIPTION
      	"average of powerfactor(pF) of all outlet.The recieved value 
		if 9999 then actual value in decimal willbe 99.99 pf , if recieved 12
		then 0.12 pf. Returns 0 if not supported."

::= { edPowerMgmtAggrsData 8 }


edPowerMgmtTotalNumberOfOutlets OBJECT-TYPE
        SYNTAX             Integer32
         ACCESS         read-only
        STATUS             mandatory
        DESCRIPTION
        "Number of outlets managed by the appliance."
::= { edPowerMgmt 3 }
 


edPowerMgmtOutletsTable OBJECT IDENTIFIER::= { edPowerMgmt 4 }

edPowerMgmtOutletData OBJECT IDENTIFIER::= { edPowerMgmtOutletsTable 1 }

edPowerMgmtOutletsTableIndex        			OBJECT IDENTIFIER::= { edPowerMgmtOutletData 1 }
edPowerMgmtOutletsTableIndexNumber        		OBJECT IDENTIFIER::= { edPowerMgmtOutletsTableIndex 1 }

edPowerMgmtOutletsTableVoltage        			OBJECT IDENTIFIER::= { edPowerMgmtOutletData 2 }
edPowerMgmtOutletsTableVoltageValue        		OBJECT IDENTIFIER::= { edPowerMgmtOutletsTableVoltage 1 }
edPowerMgmtOutletsTableCurrent       	 		OBJECT IDENTIFIER::= { edPowerMgmtOutletData 3 }
edPowerMgmtOutletsTableCurrentValue        		OBJECT IDENTIFIER::= { edPowerMgmtOutletsTableCurrent 1 }
edPowerMgmtOutletsTableApearentEnergy   		OBJECT IDENTIFIER::= { edPowerMgmtOutletData 4 }
edPowerMgmtOutletsTableApearentEnergyValue      OBJECT IDENTIFIER::= { edPowerMgmtOutletsTableApearentEnergy 1 }
edPowerMgmtOutletsTableReactiveEnergy      		OBJECT IDENTIFIER::= { edPowerMgmtOutletData 5 }
edPowerMgmtOutletsTableReactiveEnergyValue      OBJECT IDENTIFIER::= { edPowerMgmtOutletsTableReactiveEnergy 1 }
edPowerMgmtOutletsTableActiveEnergy  			OBJECT IDENTIFIER::= { edPowerMgmtOutletData 6 }
edPowerMgmtOutletsTableActiveEnergyValue        OBJECT IDENTIFIER::= { edPowerMgmtOutletsTableActiveEnergy 1 }
edPowerMgmtOutletsTableInstantaneousPower  		OBJECT IDENTIFIER::= { edPowerMgmtOutletData 7 }
edPowerMgmtOutletsTableInstantaneousPowerValue  OBJECT IDENTIFIER::= { edPowerMgmtOutletsTableInstantaneousPower 1 }
edPowerMgmtOutletsTablePowerFactor    			OBJECT IDENTIFIER::= { edPowerMgmtOutletData 8 }
edPowerMgmtOutletsTablePowerFactorValue        	OBJECT IDENTIFIER::= { edPowerMgmtOutletsTablePowerFactor 1 }
edPowerMgmtOutletsTableFreq    					OBJECT IDENTIFIER::= { edPowerMgmtOutletData 9 }
edPowerMgmtOutletsTableFreqValue        		OBJECT IDENTIFIER::= { edPowerMgmtOutletsTableFreq 1 }
edPowerMgmtOutletsTableOutletswitching        	OBJECT IDENTIFIER::= { edPowerMgmtOutletData 10 }
edPowerMgmtOutletsTableOutletControl        	OBJECT IDENTIFIER::= { edPowerMgmtOutletsTableOutletswitching 1 }





edPowerMgmtOutletsTableIndexNumber1 OBJECT-TYPE
        SYNTAX             Integer32
         ACCESS         read-only
        STATUS             mandatory
        DESCRIPTION
         "Index Number of the outlet in the PDU."
::= { edPowerMgmtOutletsTableIndexNumber 1 }


edPowerMgmtOutletsTableIndexNumber2 OBJECT-TYPE
        SYNTAX             Integer32
         ACCESS         read-only
        STATUS             mandatory
        DESCRIPTION
         "Index Number of the outlet in the PDU."
::= { edPowerMgmtOutletsTableIndexNumber 2 }

edPowerMgmtOutletsTableIndexNumber3 OBJECT-TYPE
        SYNTAX             Integer32
         ACCESS         read-only
        STATUS             mandatory
        DESCRIPTION
        "Index Number of the outlet in the PDU."
::= { edPowerMgmtOutletsTableIndexNumber 3 }


edPowerMgmtOutletsTableIndexNumber4 OBJECT-TYPE
        SYNTAX             Integer32
         ACCESS         read-only
        STATUS             mandatory
        DESCRIPTION
        "Index Number of the outlet in the PDU."
::= { edPowerMgmtOutletsTableIndexNumber 4 }


edPowerMgmtOutletsTableIndexNumber5 OBJECT-TYPE
        SYNTAX             Integer32
         ACCESS         read-only
        STATUS             mandatory
        DESCRIPTION
        "Index Number of the outlet in the PDU."
::= { edPowerMgmtOutletsTableIndexNumber 5 }


edPowerMgmtOutletsTableIndexNumber6 OBJECT-TYPE
        SYNTAX             Integer32
         ACCESS         read-only
        STATUS             mandatory
        DESCRIPTION
         "Index Number of the outlet in the PDU."
::= { edPowerMgmtOutletsTableIndexNumber 6 }


edPowerMgmtOutletsTableIndexNumber7 OBJECT-TYPE
        SYNTAX             Integer32
         ACCESS         read-only
        STATUS             mandatory
        DESCRIPTION
        "Index Number of the outlet in the PDU."
::= { edPowerMgmtOutletsTableIndexNumber 7 }


edPowerMgmtOutletsTableIndexNumber8 OBJECT-TYPE
        SYNTAX             Integer32
         ACCESS         read-only
        STATUS             mandatory
        DESCRIPTION
       "Index Number of the outlet in the PDU."
::= { edPowerMgmtOutletsTableIndexNumber 8 }


edPowerMgmtOutletsTableIndexNumber9 OBJECT-TYPE
        SYNTAX             Integer32
         ACCESS         read-only
        STATUS             mandatory
        DESCRIPTION
         "Index Number of the outlet in the PDU."
::= { edPowerMgmtOutletsTableIndexNumber 9 }


edPowerMgmtOutletsTableIndexNumber10 OBJECT-TYPE
        SYNTAX             Integer32
         ACCESS         read-only
        STATUS             mandatory
        DESCRIPTION
        "Index Number of the outlet in the PDU."
::= { edPowerMgmtOutletsTableIndexNumber 10 }


edPowerMgmtOutletsTableIndexNumber11 OBJECT-TYPE
        SYNTAX             Integer32
         ACCESS         read-only
        STATUS             mandatory
        DESCRIPTION
      "Index Number of the outlet in the PDU."
::= { edPowerMgmtOutletsTableIndexNumber 11 }


edPowerMgmtOutletsTableIndexNumber12 OBJECT-TYPE
        SYNTAX             Integer32
         ACCESS         read-only
        STATUS             mandatory
        DESCRIPTION
       "Index Number of the outlet in the PDU."
::= { edPowerMgmtOutletsTableIndexNumber 12 }


edPowerMgmtOutletsTableIndexNumber13 OBJECT-TYPE
        SYNTAX             Integer32
         ACCESS         read-only
        STATUS             mandatory
        DESCRIPTION
        "Index Number of the outlet in the PDU."
::= { edPowerMgmtOutletsTableIndexNumber 13 }


edPowerMgmtOutletsTableIndexNumber14 OBJECT-TYPE
        SYNTAX             Integer32
         ACCESS         read-only
        STATUS             mandatory
        DESCRIPTION
       "Index Number of the outlet in the PDU."
::= { edPowerMgmtOutletsTableIndexNumber 14 }


edPowerMgmtOutletsTableIndexNumber15 OBJECT-TYPE
        SYNTAX             Integer32
         ACCESS         read-only
        STATUS             mandatory
        DESCRIPTION
       "Index Number of the outlet in the PDU."
::= { edPowerMgmtOutletsTableIndexNumber 15 }


edPowerMgmtOutletsTableIndexNumber16 OBJECT-TYPE
        SYNTAX             Integer32
         ACCESS         read-only
        STATUS             mandatory
        DESCRIPTION
      "Index Number of the outlet in the PDU."
::= { edPowerMgmtOutletsTableIndexNumber 16 }


edPowerMgmtOutletsTableIndexNumber17 OBJECT-TYPE
        SYNTAX             Integer32
         ACCESS         read-only
        STATUS             mandatory
        DESCRIPTION
       "Index Number of the outlet in the PDU."
::= { edPowerMgmtOutletsTableIndexNumber 17 }


edPowerMgmtOutletsTableIndexNumber18 OBJECT-TYPE
        SYNTAX             Integer32
         ACCESS         read-only
        STATUS             mandatory
        DESCRIPTION
          "Index Number of the outlet in the PDU."
::= { edPowerMgmtOutletsTableIndexNumber 18 }


edPowerMgmtOutletsTableIndexNumber19 OBJECT-TYPE
        SYNTAX             Integer32
         ACCESS         read-only
        STATUS             mandatory
        DESCRIPTION
          "Index Number of the outlet in the PDU."
::= { edPowerMgmtOutletsTableIndexNumber 19 }


edPowerMgmtOutletsTableIndexNumber20 OBJECT-TYPE
        SYNTAX             Integer32
         ACCESS         read-only
        STATUS             mandatory
        DESCRIPTION
          "Index Number of the outlet in the PDU."
::= { edPowerMgmtOutletsTableIndexNumber 20 }


edPowerMgmtOutletsTableIndexNumber21 OBJECT-TYPE
        SYNTAX             Integer32
         ACCESS         read-only
        STATUS             mandatory
        DESCRIPTION
          "Index Number of the outlet in the PDU."
::= { edPowerMgmtOutletsTableIndexNumber 21 }


edPowerMgmtOutletsTableIndexNumber22 OBJECT-TYPE
        SYNTAX             Integer32
         ACCESS         read-only
        STATUS             mandatory
        DESCRIPTION
          "Index Number of the outlet in the PDU."
::= { edPowerMgmtOutletsTableIndexNumber 22 }


edPowerMgmtOutletsTableIndexNumber23 OBJECT-TYPE
        SYNTAX             Integer32
         ACCESS         read-only
        STATUS             mandatory
        DESCRIPTION
          "Index Number of the outlet in the PDU."
::= { edPowerMgmtOutletsTableIndexNumber 23 }


edPowerMgmtOutletsTableIndexNumber24 OBJECT-TYPE
        SYNTAX             Integer32
         ACCESS         read-only
        STATUS             mandatory
        DESCRIPTION
          "Index Number of the outlet in the PDU."
::= { edPowerMgmtOutletsTableIndexNumber 24 }

edPowerMgmtOutletsTableIndexNumber25 OBJECT-TYPE
        SYNTAX             Integer32
         ACCESS         read-only
        STATUS             mandatory
        DESCRIPTION
          "Index Number of the outlet in the PDU."
::= { edPowerMgmtOutletsTableIndexNumber 25 }


edPowerMgmtOutletsTableIndexNumber26 OBJECT-TYPE
        SYNTAX             Integer32
         ACCESS         read-only
        STATUS             mandatory
        DESCRIPTION
          "Index Number of the outlet in the PDU."
::= { edPowerMgmtOutletsTableIndexNumber 26 }


edPowerMgmtOutletsTableIndexNumber27 OBJECT-TYPE
        SYNTAX             Integer32
         ACCESS         read-only
        STATUS             mandatory
        DESCRIPTION
          "Index Number of the outlet in the PDU."
::= { edPowerMgmtOutletsTableIndexNumber 27 }

edPowerMgmtOutletsTableIndexNumber28 OBJECT-TYPE
        SYNTAX             Integer32
         ACCESS         read-only
        STATUS             mandatory
        DESCRIPTION
          "Index Number of the outlet in the PDU."
::= { edPowerMgmtOutletsTableIndexNumber 28 }

edPowerMgmtOutletsTableIndexNumber29 OBJECT-TYPE
        SYNTAX             Integer32
         ACCESS         read-only
        STATUS             mandatory
        DESCRIPTION
          "Index Number of the outlet in the PDU."
::= { edPowerMgmtOutletsTableIndexNumber 29 }

edPowerMgmtOutletsTableIndexNumber30 OBJECT-TYPE
        SYNTAX             Integer32
         ACCESS         read-only
        STATUS             mandatory
        DESCRIPTION
          "Index Number of the outlet in the PDU."
::= { edPowerMgmtOutletsTableIndexNumber 30 }

edPowerMgmtOutletsTableIndexNumber31 OBJECT-TYPE
        SYNTAX             Integer32
         ACCESS         read-only
        STATUS             mandatory
        DESCRIPTION
          "Index Number of the outlet in the PDU."
::= { edPowerMgmtOutletsTableIndexNumber 31 }

edPowerMgmtOutletsTableIndexNumber32 OBJECT-TYPE
        SYNTAX             Integer32
         ACCESS         read-only
        STATUS             mandatory
        DESCRIPTION
          "Index Number of the outlet in the PDU."
::= { edPowerMgmtOutletsTableIndexNumber 32 }

edPowerMgmtOutletsTableIndexNumber33 OBJECT-TYPE
        SYNTAX             Integer32
         ACCESS         read-only
        STATUS             mandatory
        DESCRIPTION
          "Index Number of the outlet in the PDU."
::= { edPowerMgmtOutletsTableIndexNumber 33 }

edPowerMgmtOutletsTableIndexNumber34 OBJECT-TYPE
        SYNTAX             Integer32
         ACCESS         read-only
        STATUS             mandatory
        DESCRIPTION
          "Index Number of the outlet in the PDU."
::= { edPowerMgmtOutletsTableIndexNumber 34 }


edPowerMgmtOutletsTableIndexNumber35 OBJECT-TYPE
        SYNTAX             Integer32
         ACCESS         read-only
        STATUS             mandatory
        DESCRIPTION
          "Index Number of the outlet in the PDU."
::= { edPowerMgmtOutletsTableIndexNumber 35 }


edPowerMgmtOutletsTableIndexNumber36 OBJECT-TYPE
        SYNTAX             Integer32
         ACCESS         read-only
        STATUS             mandatory
        DESCRIPTION
          "Index Number of the outlet in the PDU."
::= { edPowerMgmtOutletsTableIndexNumber 36 }


edPowerMgmtOutletsTableIndexNumber37 OBJECT-TYPE
        SYNTAX             Integer32
         ACCESS         read-only
        STATUS             mandatory
        DESCRIPTION
          "Index Number of the outlet in the PDU."
::= { edPowerMgmtOutletsTableIndexNumber 37 }


edPowerMgmtOutletsTableIndexNumber38 OBJECT-TYPE
        SYNTAX             Integer32
         ACCESS         read-only
        STATUS             mandatory
        DESCRIPTION
          "Index Number of the outlet in the PDU."
::= { edPowerMgmtOutletsTableIndexNumber 38 }


edPowerMgmtOutletsTableIndexNumber39 OBJECT-TYPE
        SYNTAX             Integer32
         ACCESS         read-only
        STATUS             mandatory
        DESCRIPTION
          "Index Number of the outlet in the PDU."
::= { edPowerMgmtOutletsTableIndexNumber 39 }


edPowerMgmtOutletsTableIndexNumber40 OBJECT-TYPE
        SYNTAX             Integer32
         ACCESS         read-only
        STATUS             mandatory
        DESCRIPTION
          "Index Number of the outlet in the PDU."
::= { edPowerMgmtOutletsTableIndexNumber 40 }


edPowerMgmtOutletsTableIndexNumber41 OBJECT-TYPE
        SYNTAX             Integer32
         ACCESS         		read-only
        STATUS             mandatory
        DESCRIPTION
          "Index Number of the outlet in the PDU."
::= { edPowerMgmtOutletsTableIndexNumber 41 }


edPowerMgmtOutletsTableIndexNumber42 OBJECT-TYPE
        SYNTAX             Integer32
         ACCESS         read-only
        STATUS             mandatory
        DESCRIPTION
          "Index Number of the outlet in the PDU."
::= { edPowerMgmtOutletsTableIndexNumber 42 }







edPowerMgmtOutletsTableVoltageOutlet1 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 1 }


edPowerMgmtOutletsTableVoltageOutlet2 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 2 }

edPowerMgmtOutletsTableVoltageOutlet3 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 3 }


edPowerMgmtOutletsTableVoltageOutlet4 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 4 }


edPowerMgmtOutletsTableVoltageOutlet5 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 5 }


edPowerMgmtOutletsTableVoltageOutlet6 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 6 }


edPowerMgmtOutletsTableVoltageOutlet7 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 7 }


edPowerMgmtOutletsTableVoltageOutlet8 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 8 }


edPowerMgmtOutletsTableVoltageOutlet9 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 9 }


edPowerMgmtOutletsTableVoltageOutlet10 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 10 }


edPowerMgmtOutletsTableVoltageOutlet11 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 11 }


edPowerMgmtOutletsTableVoltageOutlet12 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 12 }


edPowerMgmtOutletsTableVoltageOutlet13 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 13 }


edPowerMgmtOutletsTableVoltageOutlet14 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 14 }


edPowerMgmtOutletsTableVoltageOutlet15 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 15 }


edPowerMgmtOutletsTableVoltageOutlet16 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 16 }


edPowerMgmtOutletsTableVoltageOutlet17 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 17 }


edPowerMgmtOutletsTableVoltageOutlet18 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 18 }


edPowerMgmtOutletsTableVoltageOutlet19 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 19 }


edPowerMgmtOutletsTableVoltageOutlet20 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 20 }


edPowerMgmtOutletsTableVoltageOutlet21 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 21 }


edPowerMgmtOutletsTableVoltageOutlet22 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 22 }


edPowerMgmtOutletsTableVoltageOutlet23 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 23 }


edPowerMgmtOutletsTableVoltageOutlet24 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 24 }

edPowerMgmtOutletsTableVoltageOutlet25 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 25 }


edPowerMgmtOutletsTableVoltageOutlet26 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 26 }


edPowerMgmtOutletsTableVoltageOutlet27 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 27 }

edPowerMgmtOutletsTableVoltageOutlet28 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 28 }

edPowerMgmtOutletsTableVoltageOutlet29 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 29 }

edPowerMgmtOutletsTableVoltageOutlet30 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 30 }

edPowerMgmtOutletsTableVoltageOutlet31 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 31 }

edPowerMgmtOutletsTableVoltageOutlet32 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 32 }

edPowerMgmtOutletsTableVoltageOutlet33 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 33 }

edPowerMgmtOutletsTableVoltageOutlet34 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 34 }


edPowerMgmtOutletsTableVoltageOutlet35 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 35 }


edPowerMgmtOutletsTableVoltageOutlet36 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 36 }


edPowerMgmtOutletsTableVoltageOutlet37 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 37 }


edPowerMgmtOutletsTableVoltageOutlet38 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 38 }


edPowerMgmtOutletsTableVoltageOutlet39 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 39 }


edPowerMgmtOutletsTableVoltageOutlet40 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 40 }


edPowerMgmtOutletsTableVoltageOutlet41 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 41 }


edPowerMgmtOutletsTableVoltageOutlet42 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtOutletsTableVoltageValue 42 }








edPowerMgmtOutletsTableCurrentOutlet1 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtOutletsTableCurrentValue 1 }


edPowerMgmtOutletsTableCurrentOutlet2 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtOutletsTableCurrentValue 2 }

edPowerMgmtOutletsTableCurrentOutlet3 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtOutletsTableCurrentValue 3 }


edPowerMgmtOutletsTableCurrentOutlet4 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtOutletsTableCurrentValue 4 }


edPowerMgmtOutletsTableCurrentOutlet5 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtOutletsTableCurrentValue 5 }


edPowerMgmtOutletsTableCurrentOutlet6 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtOutletsTableCurrentValue 6 }


edPowerMgmtOutletsTableCurrentOutlet7 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtOutletsTableCurrentValue 7 }


edPowerMgmtOutletsTableCurrentOutlet8 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtOutletsTableCurrentValue 8 }


edPowerMgmtOutletsTableCurrentOutlet9 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtOutletsTableCurrentValue 9 }


edPowerMgmtOutletsTableCurrentOutlet10 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtOutletsTableCurrentValue 10 }


edPowerMgmtOutletsTableCurrentOutlet11 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtOutletsTableCurrentValue 11 }


edPowerMgmtOutletsTableCurrentOutlet12 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtOutletsTableCurrentValue 12 }


edPowerMgmtOutletsTableCurrentOutlet13 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtOutletsTableCurrentValue 13 }


edPowerMgmtOutletsTableCurrentOutlet14 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtOutletsTableCurrentValue 14 }


edPowerMgmtOutletsTableCurrentOutlet15 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtOutletsTableCurrentValue 15 }


edPowerMgmtOutletsTableCurrentOutlet16 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtOutletsTableCurrentValue 16 }


edPowerMgmtOutletsTableCurrentOutlet17 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtOutletsTableCurrentValue 17 }


edPowerMgmtOutletsTableCurrentOutlet18 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtOutletsTableCurrentValue 18 }


edPowerMgmtOutletsTableCurrentOutlet19 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtOutletsTableCurrentValue 19 }


edPowerMgmtOutletsTableCurrentOutlet20 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtOutletsTableCurrentValue 20 }


edPowerMgmtOutletsTableCurrentOutlet21 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtOutletsTableCurrentValue 21 }


edPowerMgmtOutletsTableCurrentOutlet22 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtOutletsTableCurrentValue 22 }


edPowerMgmtOutletsTableCurrentOutlet23 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtOutletsTableCurrentValue 23 }


edPowerMgmtOutletsTableCurrentOutlet24 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtOutletsTableCurrentValue 24 }

edPowerMgmtOutletsTableCurrentOutlet25 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtOutletsTableCurrentValue 25 }


edPowerMgmtOutletsTableCurrentOutlet26 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtOutletsTableCurrentValue 26 }


edPowerMgmtOutletsTableCurrentOutlet27 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtOutletsTableCurrentValue 27 }

edPowerMgmtOutletsTableCurrentOutlet28 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtOutletsTableCurrentValue 28 }

edPowerMgmtOutletsTableCurrentOutlet29 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtOutletsTableCurrentValue 29 }

edPowerMgmtOutletsTableCurrentOutlet30 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtOutletsTableCurrentValue 30 }

edPowerMgmtOutletsTableCurrentOutlet31 OBJECT-TYPE
        SYNTAX             Integer32
         ACCESS         read-only
        STATUS             mandatory
        DESCRIPTION
      "Actual value of Current for the outlet(Amp).The recieved value 
		if 1234 then actual value in decimal willbe 12.34 Amp, if recieved 
		value is 12 then 0.12 Amp .Returns 0 if not supported."
::= { edPowerMgmtOutletsTableCurrentValue 31 }

edPowerMgmtOutletsTableCurrentOutlet32 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtOutletsTableCurrentValue 32 }

edPowerMgmtOutletsTableCurrentOutlet33 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtOutletsTableCurrentValue 33 }

edPowerMgmtOutletsTableCurrentOutlet34 OBJECT-TYPE
        SYNTAX             Integer32
         ACCESS         read-only
        STATUS             mandatory
        DESCRIPTION
       "Actual value of Current for the outlet(Amp).The recieved value 
		if 1234 then actual value in decimal willbe 12.34 Amp, if recieved 
		value is 12 then 0.12 Amp .Returns 0 if not supported."
::= { edPowerMgmtOutletsTableCurrentValue 34 }


edPowerMgmtOutletsTableCurrentOutlet35 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtOutletsTableCurrentValue 35 }


edPowerMgmtOutletsTableCurrentOutlet36 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtOutletsTableCurrentValue 36 }


edPowerMgmtOutletsTableCurrentOutlet37 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtOutletsTableCurrentValue 37 }


edPowerMgmtOutletsTableCurrentOutlet38 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtOutletsTableCurrentValue 38 }


edPowerMgmtOutletsTableCurrentOutlet39 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtOutletsTableCurrentValue 39 }


edPowerMgmtOutletsTableCurrentOutlet40 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtOutletsTableCurrentValue 40 }


edPowerMgmtOutletsTableCurrentOutlet41 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtOutletsTableCurrentValue 41 }


edPowerMgmtOutletsTableCurrentOutlet42 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtOutletsTableCurrentValue 42 }









edPowerMgmtOutletsTableApearentEnergyOutlet1 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtOutletsTableApearentEnergyValue 1 }


edPowerMgmtOutletsTableApearentEnergyOutlet2 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtOutletsTableApearentEnergyValue 2 }

edPowerMgmtOutletsTableApearentEnergyOutlet3 OBJECT-TYPE
        SYNTAX             Integer32
         ACCESS         read-only
        STATUS             mandatory
        DESCRIPTION
      "Actual value of ApearentEnergy(KVaHr) for the outlet.The recieved value
		if 23024 then actual value in decimal willbe 2.3024 KVaHr , if recieved 12
		then 0.0012 KVaHr. Returns 0 if not supported."
::= { edPowerMgmtOutletsTableApearentEnergyValue 3 }


edPowerMgmtOutletsTableApearentEnergyOutlet4 OBJECT-TYPE
        SYNTAX             Integer32
         ACCESS         read-only
        STATUS             mandatory
        DESCRIPTION
      "Actual value of ApearentEnergy(KVaHr) for the outlet.The recieved value
		if 23024 then actual value in decimal willbe 2.3024 KVaHr , if recieved 12
		then 0.0012 KVaHr. Returns 0 if not supported."
::= { edPowerMgmtOutletsTableApearentEnergyValue 4 }


edPowerMgmtOutletsTableApearentEnergyOutlet5 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtOutletsTableApearentEnergyValue 5 }


edPowerMgmtOutletsTableApearentEnergyOutlet6 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtOutletsTableApearentEnergyValue 6 }


edPowerMgmtOutletsTableApearentEnergyOutlet7 OBJECT-TYPE
        SYNTAX             Integer32
         ACCESS         read-only
        STATUS             mandatory
        DESCRIPTION
        "Actual value of ApearentEnergy(KVaHr) for the outlet.The recieved value
		if 23024 then actual value in decimal willbe 2.3024 KVaHr , if recieved 12
		then 0.0012 KVaHr. Returns 0 if not supported."
::= { edPowerMgmtOutletsTableApearentEnergyValue 7 }


edPowerMgmtOutletsTableApearentEnergyOutlet8 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtOutletsTableApearentEnergyValue 8 }


edPowerMgmtOutletsTableApearentEnergyOutlet9 OBJECT-TYPE
        SYNTAX             Integer32
         ACCESS         read-only
        STATUS             mandatory
        DESCRIPTION
     "Actual value of ApearentEnergy(KVaHr) for the outlet.The recieved value
		if 23024 then actual value in decimal willbe 2.3024 KVaHr , if recieved 12
		then 0.0012 KVaHr. Returns 0 if not supported."
::= { edPowerMgmtOutletsTableApearentEnergyValue 9 }


edPowerMgmtOutletsTableApearentEnergyOutlet10 OBJECT-TYPE
        SYNTAX             Integer32
         ACCESS         read-only
        STATUS             mandatory
        DESCRIPTION
     "Actual value of ApearentEnergy(KVaHr) for the outlet.The recieved value
		if 23024 then actual value in decimal willbe 2.3024 KVaHr , if recieved 12
		then 0.0012 KVaHr. Returns 0 if not supported."
::= { edPowerMgmtOutletsTableApearentEnergyValue 10 }


edPowerMgmtOutletsTableApearentEnergyOutlet11 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtOutletsTableApearentEnergyValue 11 }


edPowerMgmtOutletsTableApearentEnergyOutlet12 OBJECT-TYPE
        SYNTAX             Integer32
         ACCESS         read-only
        STATUS             mandatory
        DESCRIPTION
   "Actual value of ApearentEnergy(KVaHr) for the outlet.The recieved value
		if 23024 then actual value in decimal willbe 2.3024 KVaHr , if recieved 12
		then 0.0012 KVaHr. Returns 0 if not supported."
::= { edPowerMgmtOutletsTableApearentEnergyValue 12 }


edPowerMgmtOutletsTableApearentEnergyOutlet13 OBJECT-TYPE
        SYNTAX             Integer32
         ACCESS         read-only
        STATUS             mandatory
        DESCRIPTION
      "Actual value of ApearentEnergy(KVaHr) for the outlet.The recieved value
		if 23024 then actual value in decimal willbe 2.3024 KVaHr , if recieved 12
		then 0.0012 KVaHr. Returns 0 if not supported."
::= { edPowerMgmtOutletsTableApearentEnergyValue 13 }


edPowerMgmtOutletsTableApearentEnergyOutlet14 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtOutletsTableApearentEnergyValue 14 }


edPowerMgmtOutletsTableApearentEnergyOutlet15 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtOutletsTableApearentEnergyValue 15 }


edPowerMgmtOutletsTableApearentEnergyOutlet16 OBJECT-TYPE
        SYNTAX             Integer32
         ACCESS         read-only
        STATUS             mandatory
        DESCRIPTION
          "Actual value of ApearentEnergy(KVaHr) for the outlet.The recieved value
		if 23024 then actual value in decimal willbe 2.3024 KVaHr , if recieved 12
		then 0.0012 KVaHr. Returns 0 if not supported."
::= { edPowerMgmtOutletsTableApearentEnergyValue 16 }


edPowerMgmtOutletsTableApearentEnergyOutlet17 OBJECT-TYPE
        SYNTAX             Integer32
         ACCESS         read-only
        STATUS             mandatory
        DESCRIPTION
          "Actual value of ApearentEnergy(KVaHr) for the outlet.The recieved value
		if 23024 then actual value in decimal willbe 2.3024 KVaHr , if recieved 12
		then 0.0012 KVaHr. Returns 0 if not supported."
::= { edPowerMgmtOutletsTableApearentEnergyValue 17 }


edPowerMgmtOutletsTableApearentEnergyOutlet18 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 18 }


edPowerMgmtOutletsTableApearentEnergyOutlet19 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 19 }


edPowerMgmtOutletsTableApearentEnergyOutlet20 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 20 }


edPowerMgmtOutletsTableApearentEnergyOutlet21 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 21 }


edPowerMgmtOutletsTableApearentEnergyOutlet22 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 22 }


edPowerMgmtOutletsTableApearentEnergyOutlet23 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 23 }


edPowerMgmtOutletsTableApearentEnergyOutlet24 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 24 }

edPowerMgmtOutletsTableApearentEnergyOutlet25 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 25 }


edPowerMgmtOutletsTableApearentEnergyOutlet26 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 26 }


edPowerMgmtOutletsTableApearentEnergyOutlet27 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 27 }

edPowerMgmtOutletsTableApearentEnergyOutlet28 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 28 }

edPowerMgmtOutletsTableApearentEnergyOutlet29 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 29 }

edPowerMgmtOutletsTableApearentEnergyOutlet30 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 30 }

edPowerMgmtOutletsTableApearentEnergyOutlet31 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 31 }

edPowerMgmtOutletsTableApearentEnergyOutlet32 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 32 }

edPowerMgmtOutletsTableApearentEnergyOutlet33 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 33 }

edPowerMgmtOutletsTableApearentEnergyOutlet34 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 34 }


edPowerMgmtOutletsTableApearentEnergyOutlet35 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 35 }


edPowerMgmtOutletsTableApearentEnergyOutlet36 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 36 }


edPowerMgmtOutletsTableApearentEnergyOutlet37 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 37 }


edPowerMgmtOutletsTableApearentEnergyOutlet38 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 38 }


edPowerMgmtOutletsTableApearentEnergyOutlet39 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 39 }


edPowerMgmtOutletsTableApearentEnergyOutlet40 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 40 }


edPowerMgmtOutletsTableApearentEnergyOutlet41 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 41 }


edPowerMgmtOutletsTableApearentEnergyOutlet42 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtOutletsTableApearentEnergyValue 42 }





edPowerMgmtOutletsTableReactiveEnergyOutlet1 OBJECT-TYPE
        SYNTAX             Integer32
         ACCESS         read-only
        STATUS             mandatory
        DESCRIPTION
		"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 1 }


edPowerMgmtOutletsTableReactiveEnergyOutlet2 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 2 }

edPowerMgmtOutletsTableReactiveEnergyOutlet3 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 3 }


edPowerMgmtOutletsTableReactiveEnergyOutlet4 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 4 }


edPowerMgmtOutletsTableReactiveEnergyOutlet5 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 5 }


edPowerMgmtOutletsTableReactiveEnergyOutlet6 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 6 }


edPowerMgmtOutletsTableReactiveEnergyOutlet7 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 7 }


edPowerMgmtOutletsTableReactiveEnergyOutlet8 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 8 }


edPowerMgmtOutletsTableReactiveEnergyOutlet9 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 9 }


edPowerMgmtOutletsTableReactiveEnergyOutlet10 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 10 }


edPowerMgmtOutletsTableReactiveEnergyOutlet11 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 11 }


edPowerMgmtOutletsTableReactiveEnergyOutlet12 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 12 }


edPowerMgmtOutletsTableReactiveEnergyOutlet13 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 13 }


edPowerMgmtOutletsTableReactiveEnergyOutlet14 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 14 }


edPowerMgmtOutletsTableReactiveEnergyOutlet15 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 15 }


edPowerMgmtOutletsTableReactiveEnergyOutlet16 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 16 }


edPowerMgmtOutletsTableReactiveEnergyOutlet17 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 17 }


edPowerMgmtOutletsTableReactiveEnergyOutlet18 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 18 }


edPowerMgmtOutletsTableReactiveEnergyOutlet19 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 19 }


edPowerMgmtOutletsTableReactiveEnergyOutlet20 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 20 }


edPowerMgmtOutletsTableReactiveEnergyOutlet21 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 21 }


edPowerMgmtOutletsTableReactiveEnergyOutlet22 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 22 }


edPowerMgmtOutletsTableReactiveEnergyOutlet23 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 23 }


edPowerMgmtOutletsTableReactiveEnergyOutlet24 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 24 }

edPowerMgmtOutletsTableReactiveEnergyOutlet25 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 25 }


edPowerMgmtOutletsTableReactiveEnergyOutlet26 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 26 }


edPowerMgmtOutletsTableReactiveEnergyOutlet27 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 27 }

edPowerMgmtOutletsTableReactiveEnergyOutlet28 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 28 }

edPowerMgmtOutletsTableReactiveEnergyOutlet29 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 29 }

edPowerMgmtOutletsTableReactiveEnergyOutlet30 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 30 }

edPowerMgmtOutletsTableReactiveEnergyOutlet31 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 31 }

edPowerMgmtOutletsTableReactiveEnergyOutlet32 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 32 }

edPowerMgmtOutletsTableReactiveEnergyOutlet33 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 33 }

edPowerMgmtOutletsTableReactiveEnergyOutlet34 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 34 }


edPowerMgmtOutletsTableReactiveEnergyOutlet35 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 35 }


edPowerMgmtOutletsTableReactiveEnergyOutlet36 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 36 }


edPowerMgmtOutletsTableReactiveEnergyOutlet37 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 37 }


edPowerMgmtOutletsTableReactiveEnergyOutlet38 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 38 }


edPowerMgmtOutletsTableReactiveEnergyOutlet39 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 39 }


edPowerMgmtOutletsTableReactiveEnergyOutlet40 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 40 }


edPowerMgmtOutletsTableReactiveEnergyOutlet41 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 41 }


edPowerMgmtOutletsTableReactiveEnergyOutlet42 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtOutletsTableReactiveEnergyValue 42 }




edPowerMgmtOutletsTableActiveEnergyOutlet1 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 1 }


edPowerMgmtOutletsTableActiveEnergyOutlet2 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 2 }

edPowerMgmtOutletsTableActiveEnergyOutlet3 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 3 }


edPowerMgmtOutletsTableActiveEnergyOutlet4 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 4 }


edPowerMgmtOutletsTableActiveEnergyOutlet5 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 5 }


edPowerMgmtOutletsTableActiveEnergyOutlet6 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 6 }


edPowerMgmtOutletsTableActiveEnergyOutlet7 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 7 }


edPowerMgmtOutletsTableActiveEnergyOutlet8 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 8 }


edPowerMgmtOutletsTableActiveEnergyOutlet9 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 9 }


edPowerMgmtOutletsTableActiveEnergyOutlet10 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 10 }


edPowerMgmtOutletsTableActiveEnergyOutlet11 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 11 }


edPowerMgmtOutletsTableActiveEnergyOutlet12 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 12 }


edPowerMgmtOutletsTableActiveEnergyOutlet13 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 13 }


edPowerMgmtOutletsTableActiveEnergyOutlet14 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 14 }


edPowerMgmtOutletsTableActiveEnergyOutlet15 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 15 }


edPowerMgmtOutletsTableActiveEnergyOutlet16 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 16 }


edPowerMgmtOutletsTableActiveEnergyOutlet17 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 17 }


edPowerMgmtOutletsTableActiveEnergyOutlet18 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 18 }


edPowerMgmtOutletsTableActiveEnergyOutlet19 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 19 }


edPowerMgmtOutletsTableActiveEnergyOutlet20 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 20 }


edPowerMgmtOutletsTableActiveEnergyOutlet21 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 21 }


edPowerMgmtOutletsTableActiveEnergyOutlet22 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 22 }


edPowerMgmtOutletsTableActiveEnergyOutlet23 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 23 }


edPowerMgmtOutletsTableActiveEnergyOutlet24 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 24 }

edPowerMgmtOutletsTableActiveEnergyOutlet25 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 25 }


edPowerMgmtOutletsTableActiveEnergyOutlet26 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 26 }


edPowerMgmtOutletsTableActiveEnergyOutlet27 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 27 }

edPowerMgmtOutletsTableActiveEnergyOutlet28 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 28 }

edPowerMgmtOutletsTableActiveEnergyOutlet29 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 29 }

edPowerMgmtOutletsTableActiveEnergyOutlet30 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 30 }

edPowerMgmtOutletsTableActiveEnergyOutlet31 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 31 }

edPowerMgmtOutletsTableActiveEnergyOutlet32 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 32 }

edPowerMgmtOutletsTableActiveEnergyOutlet33 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 33 }

edPowerMgmtOutletsTableActiveEnergyOutlet34 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 34 }


edPowerMgmtOutletsTableActiveEnergyOutlet35 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 35 }


edPowerMgmtOutletsTableActiveEnergyOutlet36 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 36 }


edPowerMgmtOutletsTableActiveEnergyOutlet37 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 37 }


edPowerMgmtOutletsTableActiveEnergyOutlet38 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 38 }


edPowerMgmtOutletsTableActiveEnergyOutlet39 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 39 }


edPowerMgmtOutletsTableActiveEnergyOutlet40 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 40 }


edPowerMgmtOutletsTableActiveEnergyOutlet41 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 41 }


edPowerMgmtOutletsTableActiveEnergyOutlet42 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtOutletsTableActiveEnergyValue 42 }









edPowerMgmtOutletsTableInstantaneousPowerOutlet1 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 1 }


edPowerMgmtOutletsTableInstantaneousPowerOutlet2 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 2 }

edPowerMgmtOutletsTableInstantaneousPowerOutlet3 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 3 }


edPowerMgmtOutletsTableInstantaneousPowerOutlet4 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 4 }


edPowerMgmtOutletsTableInstantaneousPowerOutlet5 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 5 }


edPowerMgmtOutletsTableInstantaneousPowerOutlet6 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 6 }


edPowerMgmtOutletsTableInstantaneousPowerOutlet7 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 7 }


edPowerMgmtOutletsTableInstantaneousPowerOutlet8 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 8 }


edPowerMgmtOutletsTableInstantaneousPowerOutlet9 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 9 }


edPowerMgmtOutletsTableInstantaneousPowerOutlet10 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 10 }


edPowerMgmtOutletsTableInstantaneousPowerOutlet11 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 11 }


edPowerMgmtOutletsTableInstantaneousPowerOutlet12 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 12 }


edPowerMgmtOutletsTableInstantaneousPowerOutlet13 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 13 }


edPowerMgmtOutletsTableInstantaneousPowerOutlet14 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 14 }


edPowerMgmtOutletsTableInstantaneousPowerOutlet15 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 15 }


edPowerMgmtOutletsTableInstantaneousPowerOutlet16 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 16 }


edPowerMgmtOutletsTableInstantaneousPowerOutlet17 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 17 }


edPowerMgmtOutletsTableInstantaneousPowerOutlet18 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 18 }


edPowerMgmtOutletsTableInstantaneousPowerOutlet19 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 19 }


edPowerMgmtOutletsTableInstantaneousPowerOutlet20 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 20 }


edPowerMgmtOutletsTableInstantaneousPowerOutlet21 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 21 }


edPowerMgmtOutletsTableInstantaneousPowerOutlet22 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 22 }


edPowerMgmtOutletsTableInstantaneousPowerOutlet23 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 23 }


edPowerMgmtOutletsTableInstantaneousPowerOutlet24 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 24 }

edPowerMgmtOutletsTableInstantaneousPowerOutlet25 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 25 }


edPowerMgmtOutletsTableInstantaneousPowerOutlet26 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 26 }


edPowerMgmtOutletsTableInstantaneousPowerOutlet27 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 27 }

edPowerMgmtOutletsTableInstantaneousPowerOutlet28 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 28 }

edPowerMgmtOutletsTableInstantaneousPowerOutlet29 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 29 }

edPowerMgmtOutletsTableInstantaneousPowerOutlet30 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 30 }

edPowerMgmtOutletsTableInstantaneousPowerOutlet31 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 31 }

edPowerMgmtOutletsTableInstantaneousPowerOutlet32 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 32 }

edPowerMgmtOutletsTableInstantaneousPowerOutlet33 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 33 }

edPowerMgmtOutletsTableInstantaneousPowerOutlet34 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 34 }


edPowerMgmtOutletsTableInstantaneousPowerOutlet35 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 35 }


edPowerMgmtOutletsTableInstantaneousPowerOutlet36 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 36 }


edPowerMgmtOutletsTableInstantaneousPowerOutlet37 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 37 }


edPowerMgmtOutletsTableInstantaneousPowerOutlet38 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 38 }


edPowerMgmtOutletsTableInstantaneousPowerOutlet39 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 39 }


edPowerMgmtOutletsTableInstantaneousPowerOutlet40 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 40 }


edPowerMgmtOutletsTableInstantaneousPowerOutlet41 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 41 }


edPowerMgmtOutletsTableInstantaneousPowerOutlet42 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtOutletsTableInstantaneousPowerValue 42 }







edPowerMgmtOutletsTablePowerFactorOutlet1 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 1 }


edPowerMgmtOutletsTablePowerFactorOutlet2 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 2 }

edPowerMgmtOutletsTablePowerFactorOutlet3 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 3 }


edPowerMgmtOutletsTablePowerFactorOutlet4 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 4 }


edPowerMgmtOutletsTablePowerFactorOutlet5 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 5 }


edPowerMgmtOutletsTablePowerFactorOutlet6 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 6 }


edPowerMgmtOutletsTablePowerFactorOutlet7 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 7 }


edPowerMgmtOutletsTablePowerFactorOutlet8 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 8 }


edPowerMgmtOutletsTablePowerFactorOutlet9 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 9 }


edPowerMgmtOutletsTablePowerFactorOutlet10 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 10 }


edPowerMgmtOutletsTablePowerFactorOutlet11 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 11 }


edPowerMgmtOutletsTablePowerFactorOutlet12 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 12 }


edPowerMgmtOutletsTablePowerFactorOutlet13 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 13 }


edPowerMgmtOutletsTablePowerFactorOutlet14 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 14 }


edPowerMgmtOutletsTablePowerFactorOutlet15 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 15 }


edPowerMgmtOutletsTablePowerFactorOutlet16 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 16 }


edPowerMgmtOutletsTablePowerFactorOutlet17 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 17 }


edPowerMgmtOutletsTablePowerFactorOutlet18 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 18 }


edPowerMgmtOutletsTablePowerFactorOutlet19 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 19 }


edPowerMgmtOutletsTablePowerFactorOutlet20 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 20 }


edPowerMgmtOutletsTablePowerFactorOutlet21 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 21 }


edPowerMgmtOutletsTablePowerFactorOutlet22 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 22 }


edPowerMgmtOutletsTablePowerFactorOutlet23 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 23 }


edPowerMgmtOutletsTablePowerFactorOutlet24 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 24 }

edPowerMgmtOutletsTablePowerFactorOutlet25 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 25 }


edPowerMgmtOutletsTablePowerFactorOutlet26 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 26 }


edPowerMgmtOutletsTablePowerFactorOutlet27 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 27 }

edPowerMgmtOutletsTablePowerFactorOutlet28 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 28 }

edPowerMgmtOutletsTablePowerFactorOutlet29 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 29 }

edPowerMgmtOutletsTablePowerFactorOutlet30 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 30 }

edPowerMgmtOutletsTablePowerFactorOutlet31 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 31 }

edPowerMgmtOutletsTablePowerFactorOutlet32 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 32 }

edPowerMgmtOutletsTablePowerFactorOutlet33 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 33 }

edPowerMgmtOutletsTablePowerFactorOutlet34 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 34 }


edPowerMgmtOutletsTablePowerFactorOutlet35 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 35 }


edPowerMgmtOutletsTablePowerFactorOutlet36 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 36 }


edPowerMgmtOutletsTablePowerFactorOutlet37 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 37 }


edPowerMgmtOutletsTablePowerFactorOutlet38 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 38 }


edPowerMgmtOutletsTablePowerFactorOutlet39 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 39 }


edPowerMgmtOutletsTablePowerFactorOutlet40 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 40 }


edPowerMgmtOutletsTablePowerFactorOutlet41 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 41 }


edPowerMgmtOutletsTablePowerFactorOutlet42 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtOutletsTablePowerFactorValue 42 }







edPowerMgmtOutletsTableFreqOutlet1 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 1 }


edPowerMgmtOutletsTableFreqOutlet2 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 2 }

edPowerMgmtOutletsTableFreqOutlet3 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 3 }


edPowerMgmtOutletsTableFreqOutlet4 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 4 }


edPowerMgmtOutletsTableFreqOutlet5 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 5 }


edPowerMgmtOutletsTableFreqOutlet6 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 6 }


edPowerMgmtOutletsTableFreqOutlet7 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 7 }


edPowerMgmtOutletsTableFreqOutlet8 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 8 }


edPowerMgmtOutletsTableFreqOutlet9 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 9 }


edPowerMgmtOutletsTableFreqOutlet10 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 10 }


edPowerMgmtOutletsTableFreqOutlet11 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 11 }


edPowerMgmtOutletsTableFreqOutlet12 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 12 }


edPowerMgmtOutletsTableFreqOutlet13 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 13 }


edPowerMgmtOutletsTableFreqOutlet14 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 14 }


edPowerMgmtOutletsTableFreqOutlet15 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 15 }


edPowerMgmtOutletsTableFreqOutlet16 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 16 }


edPowerMgmtOutletsTableFreqOutlet17 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 17 }


edPowerMgmtOutletsTableFreqOutlet18 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 18 }


edPowerMgmtOutletsTableFreqOutlet19 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 19 }


edPowerMgmtOutletsTableFreqOutlet20 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 20 }


edPowerMgmtOutletsTableFreqOutlet21 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 21 }


edPowerMgmtOutletsTableFreqOutlet22 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 22 }


edPowerMgmtOutletsTableFreqOutlet23 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 23 }


edPowerMgmtOutletsTableFreqOutlet24 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 24 }

edPowerMgmtOutletsTableFreqOutlet25 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 25 }


edPowerMgmtOutletsTableFreqOutlet26 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 26 }


edPowerMgmtOutletsTableFreqOutlet27 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 27 }

edPowerMgmtOutletsTableFreqOutlet28 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 28 }

edPowerMgmtOutletsTableFreqOutlet29 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 29 }

edPowerMgmtOutletsTableFreqOutlet30 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 30 }

edPowerMgmtOutletsTableFreqOutlet31 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 31 }

edPowerMgmtOutletsTableFreqOutlet32 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 32 }

edPowerMgmtOutletsTableFreqOutlet33 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 33 }

edPowerMgmtOutletsTableFreqOutlet34 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 34 }


edPowerMgmtOutletsTableFreqOutlet35 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 35 }


edPowerMgmtOutletsTableFreqOutlet36 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 36 }


edPowerMgmtOutletsTableFreqOutlet37 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 37 }


edPowerMgmtOutletsTableFreqOutlet38 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 38 }


edPowerMgmtOutletsTableFreqOutlet39 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 39 }


edPowerMgmtOutletsTableFreqOutlet40 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 40 }


edPowerMgmtOutletsTableFreqOutlet41 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 41 }


edPowerMgmtOutletsTableFreqOutlet42 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtOutletsTableFreqValue 42 }






edPowerMgmtOutletsTableControlOutlet1 OBJECT-TYPE
        SYNTAX INTEGER {
			switchingDisabled     (2),    			
			outletOn              (1),
			outletOff             (0)  
			
		}    
        ACCESS         read-write
        STATUS             mandatory
        DESCRIPTION
         "Getting this variable will return the outlet state. If 
       the outlet is on, the outletOn (1) value will be returned.
       If the outlet is off, the outletOff (0) value will be
       returned. and if returned 2 then switching is prohibited"
::= { edPowerMgmtOutletsTableOutletControl 1 }


edPowerMgmtOutletsTableControlOutlet2 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 2 }

edPowerMgmtOutletsTableControlOutlet3 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 3 }


edPowerMgmtOutletsTableControlOutlet4 OBJECT-TYPE
            SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 4 }


edPowerMgmtOutletsTableControlOutlet5 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 5 }


edPowerMgmtOutletsTableControlOutlet6 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 6 }


edPowerMgmtOutletsTableControlOutlet7 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 7 }


edPowerMgmtOutletsTableControlOutlet8 OBJECT-TYPE
            SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 8 }


edPowerMgmtOutletsTableControlOutlet9 OBJECT-TYPE
              SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 9 }


edPowerMgmtOutletsTableControlOutlet10 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 10 }


edPowerMgmtOutletsTableControlOutlet11 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 11 }


edPowerMgmtOutletsTableControlOutlet12 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 12 }


edPowerMgmtOutletsTableControlOutlet13 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 13 }


edPowerMgmtOutletsTableControlOutlet14 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 14 }


edPowerMgmtOutletsTableControlOutlet15 OBJECT-TYPE
           SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 15 }


edPowerMgmtOutletsTableControlOutlet16 OBJECT-TYPE
                SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 16 }


edPowerMgmtOutletsTableControlOutlet17 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 17 }


edPowerMgmtOutletsTableControlOutlet18 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 18 }


edPowerMgmtOutletsTableControlOutlet19 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 19 }


edPowerMgmtOutletsTableControlOutlet20 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 20 }


edPowerMgmtOutletsTableControlOutlet21 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 21 }


edPowerMgmtOutletsTableControlOutlet22 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 22 }


edPowerMgmtOutletsTableControlOutlet23 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 23 }


edPowerMgmtOutletsTableControlOutlet24 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 24 }

edPowerMgmtOutletsTableControlOutlet25 OBJECT-TYPE
           SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 25 }


edPowerMgmtOutletsTableControlOutlet26 OBJECT-TYPE
            SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 26 }


edPowerMgmtOutletsTableControlOutlet27 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 27 }

edPowerMgmtOutletsTableControlOutlet28 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 28 }

edPowerMgmtOutletsTableControlOutlet29 OBJECT-TYPE
                SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 29 }

edPowerMgmtOutletsTableControlOutlet30 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 30 }

edPowerMgmtOutletsTableControlOutlet31 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 31 }

edPowerMgmtOutletsTableControlOutlet32 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 32 }

edPowerMgmtOutletsTableControlOutlet33 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 33 }

edPowerMgmtOutletsTableControlOutlet34 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 34 }


edPowerMgmtOutletsTableControlOutlet35 OBJECT-TYPE
                SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 35 }


edPowerMgmtOutletsTableControlOutlet36 OBJECT-TYPE
                 SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 36 }


edPowerMgmtOutletsTableControlOutlet37 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 37 }


edPowerMgmtOutletsTableControlOutlet38 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 38 }


edPowerMgmtOutletsTableControlOutlet39 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 39 }


edPowerMgmtOutletsTableControlOutlet40 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 40 }


edPowerMgmtOutletsTableControlOutlet41 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 41 }


edPowerMgmtOutletsTableControlOutlet42 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtOutletsTableOutletControl 42 }




edPowerMgmtTotalNumberOfPhases OBJECT-TYPE
        SYNTAX             Integer32
         ACCESS         		read-only
        STATUS             mandatory
        DESCRIPTION
        "Number of Phases managed by the appliance."
::= { edPowerMgmt 5 }

edPowerMgmtPhasesTable OBJECT IDENTIFIER::= { edPowerMgmt 6 }

edPowerMgmtPhasesData OBJECT IDENTIFIER::= { edPowerMgmtPhasesTable 1 }
edPowerMgmtPhasesTableIndexNumber OBJECT IDENTIFIER::= { edPowerMgmtPhasesData 1 }
edPowerMgmtPhasesTableVoltageValue OBJECT IDENTIFIER::= { edPowerMgmtPhasesData 2 }
edPowerMgmtPhasesTablecurrentValue OBJECT IDENTIFIER::= { edPowerMgmtPhasesData 3 }
edPowerMgmtPhasesTableApearentEnergyValue OBJECT IDENTIFIER::= { edPowerMgmtPhasesData 4 }
edPowerMgmtPhasesTableReactiveEnergyValue OBJECT IDENTIFIER::= { edPowerMgmtPhasesData 5 }
edPowerMgmtPhasesTableActiveEnergyValue OBJECT IDENTIFIER::= { edPowerMgmtPhasesData 6 }
edPowerMgmtPhasesTableInstantaneousPowerValue OBJECT IDENTIFIER::= { edPowerMgmtPhasesData 7 }
edPowerMgmtPhasesTablePowerFactorValue OBJECT IDENTIFIER::= { edPowerMgmtPhasesData 8 }

edPowerMgmtPhasesTableIndexNumber1 OBJECT-TYPE
        SYNTAX             Integer32
         ACCESS         read-only
        STATUS             mandatory
        DESCRIPTION
         "Index Number of the outlet in the PDU."
::= { edPowerMgmtPhasesTableIndexNumber 1 }

edPowerMgmtPhasesTableIndexNumber2 OBJECT-TYPE
        SYNTAX             Integer32
         ACCESS         read-only
        STATUS             mandatory
        DESCRIPTION
         "Index Number of the outlet in the PDU."
::= { edPowerMgmtPhasesTableIndexNumber 2 }


edPowerMgmtPhasesTableIndexNumber3 OBJECT-TYPE
        SYNTAX             Integer32
         ACCESS         read-only
        STATUS             mandatory
        DESCRIPTION
         "Index Number of the outlet in the PDU."
::= { edPowerMgmtPhasesTableIndexNumber 3 }


edPowerMgmtPhasesTableVoltageValuePhase1 OBJECT-TYPE
        SYNTAX             Integer32
         ACCESS         read-only
        STATUS             mandatory
        DESCRIPTION
        "Value of R Phase recieved from device.
		if recieved 23024 then actual value in decimal willbe 230.24 Volts ,
		if recieved 12 then 0.12 Volt. Returns 0 if not supported."
::= { edPowerMgmtPhasesTableVoltageValue 1 }

edPowerMgmtPhasesTableVoltageValuePhase2 OBJECT-TYPE
        SYNTAX             Integer32
         ACCESS         read-only
        STATUS             mandatory
        DESCRIPTION
        "Value of Y Phase recieved from device.
		if recieved 23024 then actual value in decimal willbe 230.24 Volts ,
		if recieved 12 then 0.12 Volt. Returns 0 if not supported."
::= { edPowerMgmtPhasesTableVoltageValue 2 }

edPowerMgmtPhasesTableVoltageValuePhase3 OBJECT-TYPE
        SYNTAX             Integer32
         ACCESS         read-only
        STATUS             mandatory
        DESCRIPTION
        "Value of B Phase recieved from device.
		if recieved 23024 then actual value in decimal willbe 230.24 Volts ,
		if recieved 12 then 0.12 Volt. Returns 0 if not supported."
::= { edPowerMgmtPhasesTableVoltageValue 3 }


edPowerMgmtPhasesTablecurrentPhase1 OBJECT-TYPE
        SYNTAX             Integer32
         ACCESS         read-only
        STATUS             mandatory
        DESCRIPTION
        "Current of R Phase in Ampere ,if recieved 1234 then actual value in decimal willbe 12.34 Amp, if recieved 
		value is 12 then 0.12 Amp .Returns 0 if not supported."
::= { edPowerMgmtPhasesTablecurrentValue 1 }


edPowerMgmtPhasesTablecurrentPhase2 OBJECT-TYPE
        SYNTAX             Integer32
         ACCESS         read-only
        STATUS             mandatory
        DESCRIPTION
        "Current of Y Phase in Ampere ,if recieved 1234 then actual value in decimal willbe 12.34 Amp, if recieved 
		value is 12 then 0.12 Amp .Returns 0 if not supported."
::= { edPowerMgmtPhasesTablecurrentValue 2 }



edPowerMgmtPhasesTablecurrentPhase3 OBJECT-TYPE
        SYNTAX             Integer32
         ACCESS         read-only
        STATUS             mandatory
        DESCRIPTION
        "Current of B Phase in Ampere ,if recieved 1234 then actual value in decimal willbe 12.34 Amp, if recieved 
		value is 12 then 0.12 Amp .Returns 0 if not supported."
::= { edPowerMgmtPhasesTablecurrentValue 3 }



edPowerMgmtPhasesTableApearentEnergyPhase1 OBJECT-TYPE
        SYNTAX             Integer32
         ACCESS         read-only
        STATUS             mandatory
        DESCRIPTION
        "ApearentEnergy(KVaHr) of R Phase if recieved 23024 then actual value in decimal willbe 2.3024 KVaHr , if recieved 12
	   then 0.0012 KVaHr. Returns 0 if not supported."
::= { edPowerMgmtPhasesTableApearentEnergyValue 1 }


edPowerMgmtPhasesTableApearentEnergyPhase2 OBJECT-TYPE
        SYNTAX             Integer32
         ACCESS         read-only
        STATUS             mandatory
        DESCRIPTION
        "ApearentEnergy(KVaHr) of Y Phase if recieved 23024 then actual value in decimal willbe 2.3024 KVaHr , if recieved 12
	   then 0.0012 KVaHr. Returns 0 if not supported."
::= { edPowerMgmtPhasesTableApearentEnergyValue 2 }

edPowerMgmtPhasesTableApearentEnergyPhase3 OBJECT-TYPE
        SYNTAX             Integer32
         ACCESS         read-only
        STATUS             mandatory
        DESCRIPTION
        "ApearentEnergy(KVaHr) of B Phase if recieved 23024 then actual value in decimal willbe 2.3024 KVaHr , if recieved 12
	   then 0.0012 KVaHr. Returns 0 if not supported."
::= { edPowerMgmtPhasesTableApearentEnergyValue 3 }


edPowerMgmtPhasesTableReactiveEnergyPhase1 OBJECT-TYPE
        SYNTAX             Integer32
         ACCESS         read-only
        STATUS             mandatory
        DESCRIPTION
        "ReactiveEnergy(KVarHr) of R Phase if recieved 23024 then actual value in decimal willbe 2.3024 KVaHr , if recieved 12
	   then 0.0012 KVaHr. Returns 0 if not supported."
::= { edPowerMgmtPhasesTableReactiveEnergyValue 1 }



edPowerMgmtPhasesTableReactiveEnergyPhase2 OBJECT-TYPE
        SYNTAX             Integer32
         ACCESS         read-only
        STATUS             mandatory
        DESCRIPTION
        "ReactiveEnergy(KVarHr) of Y Phase if recieved 23024 then actual value in decimal willbe 2.3024 KVaHr , if recieved 12
	   then 0.0012 KVaHr. Returns 0 if not supported."
::= { edPowerMgmtPhasesTableReactiveEnergyValue 2 }



edPowerMgmtPhasesTableReactiveEnergyPhase3 OBJECT-TYPE
        SYNTAX             Integer32
         ACCESS         read-only
        STATUS             mandatory
        DESCRIPTION
        "ReactiveEnergy(KVarHr) of B Phase if recieved 23024 then actual value in decimal willbe 2.3024 KVaHr , if recieved 12
	   then 0.0012 KVaHr. Returns 0 if not supported."
::= { edPowerMgmtPhasesTableReactiveEnergyValue 3 }

edPowerMgmtPhasesTableActiveEnergyPhase1 OBJECT-TYPE
        SYNTAX             Integer32
         ACCESS         read-only
        STATUS             mandatory
        DESCRIPTION
        "ActiveEnergy(KWattHr) of R Phase if recieved 23024 then actual value in decimal willbe 2.3024 KVaHr , if recieved 12
	   then 0.0012 KVaHr. Returns 0 if not supported."
::= { edPowerMgmtPhasesTableActiveEnergyValue 1 }

edPowerMgmtPhasesTableActiveEnergyPhase2 OBJECT-TYPE
        SYNTAX             Integer32
         ACCESS         read-only
        STATUS             mandatory
        DESCRIPTION
        "ActiveEnergy(KWattHr) of Y Phase if recieved 23024 then actual value in decimal willbe 2.3024 KVaHr , if recieved 12
	   then 0.0012 KVaHr. Returns 0 if not supported."
::= { edPowerMgmtPhasesTableActiveEnergyValue 2 }

edPowerMgmtPhasesTableActiveEnergyPhase3 OBJECT-TYPE
        SYNTAX             Integer32
         ACCESS         read-only
        STATUS             mandatory
        DESCRIPTION
        "ActiveEnergy(KWattHr) of B Phase if recieved 23024 then actual value in decimal willbe 2.3024 KVaHr , if recieved 12
	   then 0.0012 KVaHr. Returns 0 if not supported."
::= { edPowerMgmtPhasesTableActiveEnergyValue 3 }


edPowerMgmtPhasesTableInstantaneousPowerPhase1 OBJECT-TYPE
        SYNTAX             Integer32
         ACCESS         read-only
        STATUS             mandatory
        DESCRIPTION
        "Instantaneous Power(KWatt) of R Phase if recieved 23024 then actual value in decimal willbe 2.3024 KVaHr , if recieved 12
	   then 0.0012 KVaHr. Returns 0 if not supported."
::= { edPowerMgmtPhasesTableInstantaneousPowerValue 1 }


edPowerMgmtPhasesTableInstantaneousPowerPhase2 OBJECT-TYPE
        SYNTAX             Integer32
         ACCESS         read-only
        STATUS             mandatory
        DESCRIPTION
        "Instantaneous Power(KWatt) of Y Phase if recieved 23024 then actual value in decimal willbe 2.3024 KVaHr , if recieved 12
	   then 0.0012 KVaHr. Returns 0 if not supported."
::= { edPowerMgmtPhasesTableInstantaneousPowerValue 2 }


edPowerMgmtPhasesTableInstantaneousPowerPhase3 OBJECT-TYPE
        SYNTAX             Integer32
         ACCESS         read-only
        STATUS             mandatory
        DESCRIPTION
        "Instantaneous Power(KWatt) of B Phase if recieved 23024 then actual value in decimal willbe 2.3024 KVaHr , if recieved 12
	   then 0.0012 KVaHr. Returns 0 if not supported."
::= { edPowerMgmtPhasesTableInstantaneousPowerValue 3 }


edPowerMgmtPhasesTablePowerFactorPhase1 OBJECT-TYPE
        SYNTAX             Integer32
         ACCESS         read-only
        STATUS             mandatory
        DESCRIPTION
        "average of powerfactor(pF) R Phase.The recieved value 
		if 9999 then actual value in decimal willbe 99.99 pf , if recieved 12
		then 0.12 pf. Returns 0 if not supported."
::= { edPowerMgmtPhasesTablePowerFactorValue 1 }

edPowerMgmtPhasesTablePowerFactorPhase2 OBJECT-TYPE
        SYNTAX             Integer32
         ACCESS         read-only
        STATUS             mandatory
        DESCRIPTION
        "average of powerfactor(pF) Y Phase.The recieved value 
		if 9999 then actual value in decimal willbe 99.99 pf , if recieved 12
		then 0.12 pf. Returns 0 if not supported."
::= { edPowerMgmtPhasesTablePowerFactorValue 2 }

edPowerMgmtPhasesTablePowerFactorPhase3 OBJECT-TYPE
        SYNTAX             Integer32
         ACCESS         read-only
        STATUS             mandatory
        DESCRIPTION
        "average of powerfactor(pF) B Phase.The recieved value 
		if 9999 then actual value in decimal willbe 99.99 pf , if recieved 12
		then 0.12 pf. Returns 0 if not supported."
::= { edPowerMgmtPhasesTablePowerFactorValue 3 }


edPowerMgmtTotalNumberOfSensor OBJECT-TYPE
        SYNTAX             Integer32
         ACCESS         read-only
        STATUS             mandatory
        DESCRIPTION
        "Number of Sensors managed by the appliance."
::= { edPowerMgmt 7 }


edPowerMgmtSensorsTable OBJECT IDENTIFIER ::= { edPowerMgmt 8 }

edPowerMgmtSensorsData OBJECT IDENTIFIER ::= { edPowerMgmtSensorsTable 1 }

edPowerMgmtSensorsTableNumber OBJECT IDENTIFIER ::= { edPowerMgmtSensorsData 1 }
edPowerMgmtSensorsTableSensorType OBJECT IDENTIFIER ::= { edPowerMgmtSensorsData 2 }
edPowerMgmtSensorsTableSensorValue OBJECT IDENTIFIER::= { edPowerMgmtSensorsData 3 }

edPowerMgmtSensorsTableSensor1 OBJECT-TYPE
        SYNTAX             Integer32
         ACCESS         read-only
        STATUS             mandatory
        DESCRIPTION
        "Number of the sensor in the PDU."
::= { edPowerMgmtSensorsTableNumber 1 }


edPowerMgmtSensorsTableSensor2 OBJECT-TYPE
        SYNTAX             Integer32
         ACCESS         read-only
        STATUS             mandatory
        DESCRIPTION
        "Number of the sensor in the PDU."
::= { edPowerMgmtSensorsTableNumber 2 }


edPowerMgmtSensorsTableSensor3 OBJECT-TYPE
        SYNTAX             Integer32
         ACCESS         read-only
        STATUS             mandatory
        DESCRIPTION
        "Number of the sensor in the PDU."
::= { edPowerMgmtSensorsTableNumber 3 }

edPowerMgmtSensorsTableSensor4 OBJECT-TYPE
        SYNTAX             Integer32
         ACCESS         read-only
        STATUS             mandatory
        DESCRIPTION
        "Number of the sensor in the PDU."
::= { edPowerMgmtSensorsTableNumber 4 }

edPowerMgmtSensorsTableSensorType1 OBJECT-TYPE
         SYNTAX INTEGER {
		humidity     (2),    			
		temprature   (1),
		nosens      (0)  
		
		}
         ACCESS         read-only
        STATUS             mandatory
        DESCRIPTION
        "returns value displaying type of Sensor."
::= { edPowerMgmtSensorsTableSensorType 1 }

edPowerMgmtSensorsTableSensorType2 OBJECT-TYPE
         SYNTAX INTEGER {
		humidity     (2),    			
		temprature   (1),
		nosens      (0)  
		
		}
         ACCESS         read-only
        STATUS             mandatory
        DESCRIPTION
        "returns value displaying type of Sensor."
::= { edPowerMgmtSensorsTableSensorType 2 }

edPowerMgmtSensorsTableSensorType3 OBJECT-TYPE
         SYNTAX INTEGER {
		humidity     (2),    			
		temprature   (1),
		nosens      (0)  
		
		}
         ACCESS         read-only
        STATUS             mandatory
        DESCRIPTION
        "returns value displaying type of Sensor."
::= { edPowerMgmtSensorsTableSensorType 3 }


edPowerMgmtSensorsTableSensorType4 OBJECT-TYPE
         SYNTAX INTEGER {
		humidity     (2),    			
		temprature   (1),
		nosens      (0)  
		
		}
         ACCESS         read-only
        STATUS             mandatory
        DESCRIPTION
        "returns value displaying type of Sensor."
::= { edPowerMgmtSensorsTableSensorType 4 }



edPowerMgmtSensorsTableSensorValueSensor1 OBJECT-TYPE
        SYNTAX             Integer32
         ACCESS         read-only
        STATUS             mandatory
        DESCRIPTION
        "returns value of Sensor
         Returns 0 if not supported."
::= { edPowerMgmtSensorsTableSensorValue 1 }

edPowerMgmtSensorsTableSensorValueSensor2 OBJECT-TYPE
        SYNTAX             Integer32
         ACCESS         read-only
        STATUS             mandatory
        DESCRIPTION
        "returns value of Sensor
         Returns 0 if not supported."
::= { edPowerMgmtSensorsTableSensorValue 2 }

edPowerMgmtSensorsTableSensorValueSensor3 OBJECT-TYPE
        SYNTAX             Integer32
         ACCESS         read-only
        STATUS             mandatory
        DESCRIPTION
        "returns value of Sensor
         Returns 0 if not supported."
::= { edPowerMgmtSensorsTableSensorValue 3 }

edPowerMgmtSensorsTableSensorValueSensor4 OBJECT-TYPE
        SYNTAX             Integer32
         ACCESS         read-only
        STATUS             mandatory
        DESCRIPTION
        "returns value of Sensor
         Returns 0 if not supported."
::= { edPowerMgmtSensorsTableSensorValue 4 }


----------- Daisy Chaining pduData 1 ----------------------


edConectedPdu1Data OBJECT IDENTIFIER::= { edConnectedPduMgmt 1 }

edPowerMgmtPDU1TableData OBJECT IDENTIFIER::= { edConectedPdu1Data 1 }

edPowerMgmtPDU1TableNumber       OBJECT-TYPE
        SYNTAX             Integer32
         ACCESS         read-only
        STATUS             mandatory
        DESCRIPTION
        "Index Number"
::= { edPowerMgmtPDU1TableData 1 }


edPowerMgmtPDU1TableProductCode      OBJECT-TYPE
        SYNTAX             DisplayString
         ACCESS         read-only
        STATUS             mandatory
        DESCRIPTION
        "Version of the PDU firmware.
         Returns N/A if not applicable."
::= { edPowerMgmtPDU1TableData 2 }



edPowerMgmtPDU1TableSerialNumber OBJECT-TYPE
        SYNTAX             Integer32
         ACCESS         read-only
        STATUS             mandatory
        DESCRIPTION
        "Number of outlets of the PDU."
::= { edPowerMgmtPDU1TableData 3 }




edPowerMgmtPDU1TableFirmwareVersion       OBJECT-TYPE
        SYNTAX             DisplayString
         ACCESS         read-only
        STATUS             mandatory
        DESCRIPTION
        "Version of the PDU firmware.
         Returns N/A if not applicable."
::= { edPowerMgmtPDU1TableData 4 }



edPowerMgmtPDU1TableNumberOfOutlets OBJECT-TYPE
        SYNTAX             Integer32
         ACCESS         read-only
        STATUS             mandatory
        DESCRIPTION
        "Number of outlets of the PDU."
::= { edPowerMgmtPDU1TableData 5 }

edPowerMgmtPDU1TableNumberOfPhases OBJECT-TYPE
        SYNTAX             Integer32
         ACCESS         read-only
        STATUS             mandatory
        DESCRIPTION
        "Number of phases of the PDU."
::= { edPowerMgmtPDU1TableData 6 }


edPowerMgmtPDU1TableNumberOfSensors OBJECT-TYPE
        SYNTAX             Integer32
         ACCESS         read-only
        STATUS             mandatory
        DESCRIPTION
        "Number of sensors in the PDU."
::= { edPowerMgmtPDU1TableData 7 }



edPowerMgmtPDU1TableVendor   OBJECT-TYPE
        SYNTAX             DisplayString
         ACCESS         	  read-only
        STATUS             mandatory
        DESCRIPTION
        "Vendor of the PDU.
         Returns N/A if not applicable."
::= { edPowerMgmtPDU1TableData 8 }


edPowerMgmtPDU1AggrInfoTable OBJECT IDENTIFIER::= { edConectedPdu1Data 2 }

edPowerMgmtPDU1AggrsData OBJECT IDENTIFIER::= { edPowerMgmtPDU1AggrInfoTable 1 }


edPowerMgmtPDU1AggrInfoNumber       OBJECT-TYPE
        SYNTAX             		Integer32
         ACCESS         			read-only
        STATUS             		mandatory
        DESCRIPTION
        "Index Number"
::= { edPowerMgmtPDU1AggrsData 1 }
 


edPowerMgmtPDU1AggrInfoTableVoltageValue OBJECT-TYPE
        SYNTAX             Integer32
         ACCESS         read-only
        STATUS             mandatory
        DESCRIPTION
		"Aggrgate voltage of phase is (if vRphase R > vYphase && vRphase R > vBphase) 
		aggregate voltage of R Phase .The recieved value 
		if 23024 then actual value in decimal willbe 230.24 Volts ,
		if recieved 12 then 0.12 Volt. Returns 0 if not supported."
::= { edPowerMgmtPDU1AggrsData 2 }


edPowerMgmtPDU1AggrInfoTableCurrentValue OBJECT-TYPE
        SYNTAX             Integer32
         ACCESS         read-only
        STATUS             mandatory
        DESCRIPTION
        "Addition of mandatory of all Outlet.The recieved value 
		if 1234 then actual value in decimal willbe 12.34 Amp, if recieved 
		value is 12 then 0.12 Amp .Returns 0 if not supported."
::= { edPowerMgmtPDU1AggrsData 3 }


edPowerMgmtPDU1AggrInfoTableApearentEnergyValue OBJECT-TYPE
        SYNTAX             Integer32
         ACCESS         read-only
        STATUS             mandatory
        DESCRIPTION
       "addition of ApearentEnergy(KVaHr) of all outlet.The recieved value
	   if 23024 then actual value in decimal willbe 2.3024 KVaHr , if recieved 12
	   then 0.0012 KVaHr. Returns 0 if not supported."
::= { edPowerMgmtPDU1AggrsData 4 }


edPowerMgmtPDU1AggrInfoTableReactiveEnergyValue OBJECT-TYPE
        SYNTAX             Integer32
         ACCESS         read-only
        STATUS             mandatory
        DESCRIPTION
         "addition of ReactiveEnergy(KVarHr) of all outlet.The recieved value 
		 if 23024 then actual value in decimal willbe 2.3024 KVarHr , if recieved 12 
		 then 0.0012 KVarHr. Returns 0 if not supported."
::= { edPowerMgmtPDU1AggrsData 5 }

edPowerMgmtPDU1AggrInfoTableActiveEnergyValue OBJECT-TYPE
        SYNTAX             Integer32
         ACCESS         read-only
        STATUS             mandatory
        DESCRIPTION
      "addition of ActiveEnergy(KWattHr) of all outlets.The recieved value 
	  if 23024 then actual value in decimal willbe 2.3024 KWattHr , if recieved 12
	  then 0.0012 KWattHr. Returns 0 if not supported."
::= { edPowerMgmtPDU1AggrsData 6 }


edPowerMgmtPDU1AggrInfoTableInstantaneousPowerValue OBJECT-TYPE
        SYNTAX             Integer32
         ACCESS         read-only
        STATUS             mandatory
        DESCRIPTION
      "addition of  Instantaneous Power(KWatt) of all outlet.The recieved value 
	  if 230 then actual value in decimal willbe 2.30 KWatt , if recieved 12 
	  then 0.12 KWatt. Returns 0 if not supported."
::= { edPowerMgmtPDU1AggrsData 7 }

edPowerMgmtPDU1AggrInfoTablePowerFactorValue OBJECT-TYPE
        SYNTAX             Integer32
         ACCESS         read-only
        STATUS             mandatory
        DESCRIPTION
      	"average of powerfactor(pF) of all outlet.The recieved value 
		if 9999 then actual value in decimal willbe 99.99 pf , if recieved 12
		then 0.12 pf. Returns 0 if not supported."

::= { edPowerMgmtPDU1AggrsData 8 }


edPowerMgmtPDU1TotalNumberOfOutlets OBJECT-TYPE
        SYNTAX             Integer32
         ACCESS         read-only
        STATUS             mandatory
        DESCRIPTION
        "Number of outlets managed by the appliance."
::= { edConectedPdu1Data 3 }
 


edPowerMgmtPDU1OutletsTable OBJECT IDENTIFIER::= { edConectedPdu1Data 4 }

edPowerMgmtPDU1OutletData OBJECT IDENTIFIER::= { edPowerMgmtPDU1OutletsTable 1 }

edPowerMgmtPDU1OutletsTableIndex        			OBJECT IDENTIFIER::= { edPowerMgmtPDU1OutletData 1 }
edPowerMgmtPDU1OutletsTableIndexNumber        		OBJECT IDENTIFIER::= { edPowerMgmtPDU1OutletsTableIndex 1 }

edPowerMgmtPDU1OutletsTableVoltage        			OBJECT IDENTIFIER::= { edPowerMgmtPDU1OutletData 2 }
edPowerMgmtPDU1OutletsTableVoltageValue        		OBJECT IDENTIFIER::= { edPowerMgmtPDU1OutletsTableVoltage 1 }
edPowerMgmtPDU1OutletsTableCurrent       	 		OBJECT IDENTIFIER::= { edPowerMgmtPDU1OutletData 3 }
edPowerMgmtPDU1OutletsTableCurrentValue        		OBJECT IDENTIFIER::= { edPowerMgmtPDU1OutletsTableCurrent 1 }
edPowerMgmtPDU1OutletsTableApearentEnergy   		OBJECT IDENTIFIER::= { edPowerMgmtPDU1OutletData 4 }
edPowerMgmtPDU1OutletsTableApearentEnergyValue      OBJECT IDENTIFIER::= { edPowerMgmtPDU1OutletsTableApearentEnergy 1 }
edPowerMgmtPDU1OutletsTableReactiveEnergy      		OBJECT IDENTIFIER::= { edPowerMgmtPDU1OutletData 5 }
edPowerMgmtPDU1OutletsTableReactiveEnergyValue      OBJECT IDENTIFIER::= { edPowerMgmtPDU1OutletsTableReactiveEnergy 1 }
edPowerMgmtPDU1OutletsTableActiveEnergy  			OBJECT IDENTIFIER::= { edPowerMgmtPDU1OutletData 6 }
edPowerMgmtPDU1OutletsTableActiveEnergyValue        OBJECT IDENTIFIER::= { edPowerMgmtPDU1OutletsTableActiveEnergy 1 }
edPowerMgmtPDU1OutletsTableInstantaneousPower  		OBJECT IDENTIFIER::= { edPowerMgmtPDU1OutletData 7 }
edPowerMgmtPDU1OutletsTableInstantaneousPowerValue  OBJECT IDENTIFIER::= { edPowerMgmtPDU1OutletsTableInstantaneousPower 1 }
edPowerMgmtPDU1OutletsTablePowerFactor    			OBJECT IDENTIFIER::= { edPowerMgmtPDU1OutletData 8 }
edPowerMgmtPDU1OutletsTablePowerFactorValue        	OBJECT IDENTIFIER::= { edPowerMgmtPDU1OutletsTablePowerFactor 1 }
edPowerMgmtPDU1OutletsTableFreq    					OBJECT IDENTIFIER::= { edPowerMgmtPDU1OutletData 9 }
edPowerMgmtPDU1OutletsTableFreqValue        		OBJECT IDENTIFIER::= { edPowerMgmtPDU1OutletsTableFreq 1 }
edPowerMgmtPDU1OutletsTableOutletswitching        	OBJECT IDENTIFIER::= { edPowerMgmtPDU1OutletData 10 }
edPowerMgmtPDU1OutletsTableOutletControl        	OBJECT IDENTIFIER::= { edPowerMgmtPDU1OutletsTableOutletswitching 1 }





edPowerMgmtPDU1OutletsTableIndexNumber1 OBJECT-TYPE
        SYNTAX             Integer32
         ACCESS         read-only
        STATUS             mandatory
        DESCRIPTION
         "Index Number of the outlet in the PDU."
::= { edPowerMgmtPDU1OutletsTableIndexNumber 1 }


edPowerMgmtPDU1OutletsTableIndexNumber2 OBJECT-TYPE
        SYNTAX             Integer32
         ACCESS         read-only
        STATUS             mandatory
        DESCRIPTION
         "Index Number of the outlet in the PDU."
::= { edPowerMgmtPDU1OutletsTableIndexNumber 2 }

edPowerMgmtPDU1OutletsTableIndexNumber3 OBJECT-TYPE
        SYNTAX             Integer32
         ACCESS         read-only
        STATUS             mandatory
        DESCRIPTION
        "Index Number of the outlet in the PDU."
::= { edPowerMgmtPDU1OutletsTableIndexNumber 3 }


edPowerMgmtPDU1OutletsTableIndexNumber4 OBJECT-TYPE
        SYNTAX             Integer32
         ACCESS         read-only
        STATUS             mandatory
        DESCRIPTION
        "Index Number of the outlet in the PDU."
::= { edPowerMgmtPDU1OutletsTableIndexNumber 4 }


edPowerMgmtPDU1OutletsTableIndexNumber5 OBJECT-TYPE
        SYNTAX             Integer32
         ACCESS         read-only
        STATUS             mandatory
        DESCRIPTION
        "Index Number of the outlet in the PDU."
::= { edPowerMgmtPDU1OutletsTableIndexNumber 5 }


edPowerMgmtPDU1OutletsTableIndexNumber6 OBJECT-TYPE
        SYNTAX             Integer32
         ACCESS         read-only
        STATUS             mandatory
        DESCRIPTION
         "Index Number of the outlet in the PDU."
::= { edPowerMgmtPDU1OutletsTableIndexNumber 6 }


edPowerMgmtPDU1OutletsTableIndexNumber7 OBJECT-TYPE
        SYNTAX             Integer32
         ACCESS         read-only
        STATUS             mandatory
        DESCRIPTION
        "Index Number of the outlet in the PDU."
::= { edPowerMgmtPDU1OutletsTableIndexNumber 7 }


edPowerMgmtPDU1OutletsTableIndexNumber8 OBJECT-TYPE
        SYNTAX             Integer32
         ACCESS         read-only
        STATUS             mandatory
        DESCRIPTION
       "Index Number of the outlet in the PDU."
::= { edPowerMgmtPDU1OutletsTableIndexNumber 8 }


edPowerMgmtPDU1OutletsTableIndexNumber9 OBJECT-TYPE
        SYNTAX             Integer32
         ACCESS         read-only
        STATUS             mandatory
        DESCRIPTION
         "Index Number of the outlet in the PDU."
::= { edPowerMgmtPDU1OutletsTableIndexNumber 9 }


edPowerMgmtPDU1OutletsTableIndexNumber10 OBJECT-TYPE
        SYNTAX             Integer32
         ACCESS         read-only
        STATUS             mandatory
        DESCRIPTION
        "Index Number of the outlet in the PDU."
::= { edPowerMgmtPDU1OutletsTableIndexNumber 10 }


edPowerMgmtPDU1OutletsTableIndexNumber11 OBJECT-TYPE
        SYNTAX             Integer32
         ACCESS         read-only
        STATUS             mandatory
        DESCRIPTION
      "Index Number of the outlet in the PDU."
::= { edPowerMgmtPDU1OutletsTableIndexNumber 11 }


edPowerMgmtPDU1OutletsTableIndexNumber12 OBJECT-TYPE
        SYNTAX             Integer32
         ACCESS         read-only
        STATUS             mandatory
        DESCRIPTION
       "Index Number of the outlet in the PDU."
::= { edPowerMgmtPDU1OutletsTableIndexNumber 12 }


edPowerMgmtPDU1OutletsTableIndexNumber13 OBJECT-TYPE
        SYNTAX             Integer32
         ACCESS         read-only
        STATUS             mandatory
        DESCRIPTION
        "Index Number of the outlet in the PDU."
::= { edPowerMgmtPDU1OutletsTableIndexNumber 13 }


edPowerMgmtPDU1OutletsTableIndexNumber14 OBJECT-TYPE
        SYNTAX             Integer32
         ACCESS         read-only
        STATUS             mandatory
        DESCRIPTION
       "Index Number of the outlet in the PDU."
::= { edPowerMgmtPDU1OutletsTableIndexNumber 14 }


edPowerMgmtPDU1OutletsTableIndexNumber15 OBJECT-TYPE
        SYNTAX             Integer32
         ACCESS         read-only
        STATUS             mandatory
        DESCRIPTION
       "Index Number of the outlet in the PDU."
::= { edPowerMgmtPDU1OutletsTableIndexNumber 15 }


edPowerMgmtPDU1OutletsTableIndexNumber16 OBJECT-TYPE
        SYNTAX             Integer32
         ACCESS         read-only
        STATUS             mandatory
        DESCRIPTION
      "Index Number of the outlet in the PDU."
::= { edPowerMgmtPDU1OutletsTableIndexNumber 16 }


edPowerMgmtPDU1OutletsTableIndexNumber17 OBJECT-TYPE
        SYNTAX             Integer32
         ACCESS         read-only
        STATUS             mandatory
        DESCRIPTION
       "Index Number of the outlet in the PDU."
::= { edPowerMgmtPDU1OutletsTableIndexNumber 17 }


edPowerMgmtPDU1OutletsTableIndexNumber18 OBJECT-TYPE
        SYNTAX             Integer32
         ACCESS         read-only
        STATUS             mandatory
        DESCRIPTION
          "Index Number of the outlet in the PDU."
::= { edPowerMgmtPDU1OutletsTableIndexNumber 18 }


edPowerMgmtPDU1OutletsTableIndexNumber19 OBJECT-TYPE
        SYNTAX             Integer32
         ACCESS         read-only
        STATUS             mandatory
        DESCRIPTION
          "Index Number of the outlet in the PDU."
::= { edPowerMgmtPDU1OutletsTableIndexNumber 19 }


edPowerMgmtPDU1OutletsTableIndexNumber20 OBJECT-TYPE
        SYNTAX             Integer32
         ACCESS         read-only
        STATUS             mandatory
        DESCRIPTION
          "Index Number of the outlet in the PDU."
::= { edPowerMgmtPDU1OutletsTableIndexNumber 20 }


edPowerMgmtPDU1OutletsTableIndexNumber21 OBJECT-TYPE
        SYNTAX             Integer32
         ACCESS         read-only
        STATUS             mandatory
        DESCRIPTION
          "Index Number of the outlet in the PDU."
::= { edPowerMgmtPDU1OutletsTableIndexNumber 21 }


edPowerMgmtPDU1OutletsTableIndexNumber22 OBJECT-TYPE
        SYNTAX             Integer32
         ACCESS         read-only
        STATUS             mandatory
        DESCRIPTION
          "Index Number of the outlet in the PDU."
::= { edPowerMgmtPDU1OutletsTableIndexNumber 22 }


edPowerMgmtPDU1OutletsTableIndexNumber23 OBJECT-TYPE
        SYNTAX             Integer32
         ACCESS         read-only
        STATUS             mandatory
        DESCRIPTION
          "Index Number of the outlet in the PDU."
::= { edPowerMgmtPDU1OutletsTableIndexNumber 23 }


edPowerMgmtPDU1OutletsTableIndexNumber24 OBJECT-TYPE
        SYNTAX             Integer32
         ACCESS         read-only
        STATUS             mandatory
        DESCRIPTION
          "Index Number of the outlet in the PDU."
::= { edPowerMgmtPDU1OutletsTableIndexNumber 24 }

edPowerMgmtPDU1OutletsTableIndexNumber25 OBJECT-TYPE
        SYNTAX             Integer32
         ACCESS         read-only
        STATUS             mandatory
        DESCRIPTION
          "Index Number of the outlet in the PDU."
::= { edPowerMgmtPDU1OutletsTableIndexNumber 25 }


edPowerMgmtPDU1OutletsTableIndexNumber26 OBJECT-TYPE
        SYNTAX             Integer32
         ACCESS         read-only
        STATUS             mandatory
        DESCRIPTION
          "Index Number of the outlet in the PDU."
::= { edPowerMgmtPDU1OutletsTableIndexNumber 26 }


edPowerMgmtPDU1OutletsTableIndexNumber27 OBJECT-TYPE
        SYNTAX             Integer32
         ACCESS         read-only
        STATUS             mandatory
        DESCRIPTION
          "Index Number of the outlet in the PDU."
::= { edPowerMgmtPDU1OutletsTableIndexNumber 27 }

edPowerMgmtPDU1OutletsTableIndexNumber28 OBJECT-TYPE
        SYNTAX             Integer32
         ACCESS         read-only
        STATUS             mandatory
        DESCRIPTION
          "Index Number of the outlet in the PDU."
::= { edPowerMgmtPDU1OutletsTableIndexNumber 28 }

edPowerMgmtPDU1OutletsTableIndexNumber29 OBJECT-TYPE
        SYNTAX             Integer32
         ACCESS         read-only
        STATUS             mandatory
        DESCRIPTION
          "Index Number of the outlet in the PDU."
::= { edPowerMgmtPDU1OutletsTableIndexNumber 29 }

edPowerMgmtPDU1OutletsTableIndexNumber30 OBJECT-TYPE
        SYNTAX             Integer32
         ACCESS         read-only
        STATUS             mandatory
        DESCRIPTION
          "Index Number of the outlet in the PDU."
::= { edPowerMgmtPDU1OutletsTableIndexNumber 30 }

edPowerMgmtPDU1OutletsTableIndexNumber31 OBJECT-TYPE
        SYNTAX             Integer32
         ACCESS         read-only
        STATUS             mandatory
        DESCRIPTION
          "Index Number of the outlet in the PDU."
::= { edPowerMgmtPDU1OutletsTableIndexNumber 31 }

edPowerMgmtPDU1OutletsTableIndexNumber32 OBJECT-TYPE
        SYNTAX             Integer32
         ACCESS         read-only
        STATUS             mandatory
        DESCRIPTION
          "Index Number of the outlet in the PDU."
::= { edPowerMgmtPDU1OutletsTableIndexNumber 32 }

edPowerMgmtPDU1OutletsTableIndexNumber33 OBJECT-TYPE
        SYNTAX             Integer32
         ACCESS         read-only
        STATUS             mandatory
        DESCRIPTION
          "Index Number of the outlet in the PDU."
::= { edPowerMgmtPDU1OutletsTableIndexNumber 33 }

edPowerMgmtPDU1OutletsTableIndexNumber34 OBJECT-TYPE
        SYNTAX             Integer32
         ACCESS         read-only
        STATUS             mandatory
        DESCRIPTION
          "Index Number of the outlet in the PDU."
::= { edPowerMgmtPDU1OutletsTableIndexNumber 34 }


edPowerMgmtPDU1OutletsTableIndexNumber35 OBJECT-TYPE
        SYNTAX             Integer32
         ACCESS         read-only
        STATUS             mandatory
        DESCRIPTION
          "Index Number of the outlet in the PDU."
::= { edPowerMgmtPDU1OutletsTableIndexNumber 35 }


edPowerMgmtPDU1OutletsTableIndexNumber36 OBJECT-TYPE
        SYNTAX             Integer32
         ACCESS         read-only
        STATUS             mandatory
        DESCRIPTION
          "Index Number of the outlet in the PDU."
::= { edPowerMgmtPDU1OutletsTableIndexNumber 36 }


edPowerMgmtPDU1OutletsTableIndexNumber37 OBJECT-TYPE
        SYNTAX             Integer32
         ACCESS         read-only
        STATUS             mandatory
        DESCRIPTION
          "Index Number of the outlet in the PDU."
::= { edPowerMgmtPDU1OutletsTableIndexNumber 37 }


edPowerMgmtPDU1OutletsTableIndexNumber38 OBJECT-TYPE
        SYNTAX             Integer32
         ACCESS         read-only
        STATUS             mandatory
        DESCRIPTION
          "Index Number of the outlet in the PDU."
::= { edPowerMgmtPDU1OutletsTableIndexNumber 38 }


edPowerMgmtPDU1OutletsTableIndexNumber39 OBJECT-TYPE
        SYNTAX             Integer32
         ACCESS         read-only
        STATUS             mandatory
        DESCRIPTION
          "Index Number of the outlet in the PDU."
::= { edPowerMgmtPDU1OutletsTableIndexNumber 39 }


edPowerMgmtPDU1OutletsTableIndexNumber40 OBJECT-TYPE
        SYNTAX             Integer32
         ACCESS         read-only
        STATUS             mandatory
        DESCRIPTION
          "Index Number of the outlet in the PDU."
::= { edPowerMgmtPDU1OutletsTableIndexNumber 40 }


edPowerMgmtPDU1OutletsTableIndexNumber41 OBJECT-TYPE
        SYNTAX             Integer32
         ACCESS         		read-only
        STATUS             mandatory
        DESCRIPTION
          "Index Number of the outlet in the PDU."
::= { edPowerMgmtPDU1OutletsTableIndexNumber 41 }


edPowerMgmtPDU1OutletsTableIndexNumber42 OBJECT-TYPE
        SYNTAX             Integer32
         ACCESS         read-only
        STATUS             mandatory
        DESCRIPTION
          "Index Number of the outlet in the PDU."
::= { edPowerMgmtPDU1OutletsTableIndexNumber 42 }







edPowerMgmtPDU1OutletsTableVoltageOutlet1 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 1 }


edPowerMgmtPDU1OutletsTableVoltageOutlet2 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 2 }

edPowerMgmtPDU1OutletsTableVoltageOutlet3 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 3 }


edPowerMgmtPDU1OutletsTableVoltageOutlet4 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 4 }


edPowerMgmtPDU1OutletsTableVoltageOutlet5 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 5 }


edPowerMgmtPDU1OutletsTableVoltageOutlet6 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 6 }


edPowerMgmtPDU1OutletsTableVoltageOutlet7 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 7 }


edPowerMgmtPDU1OutletsTableVoltageOutlet8 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 8 }


edPowerMgmtPDU1OutletsTableVoltageOutlet9 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 9 }


edPowerMgmtPDU1OutletsTableVoltageOutlet10 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 10 }


edPowerMgmtPDU1OutletsTableVoltageOutlet11 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 11 }


edPowerMgmtPDU1OutletsTableVoltageOutlet12 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 12 }


edPowerMgmtPDU1OutletsTableVoltageOutlet13 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 13 }


edPowerMgmtPDU1OutletsTableVoltageOutlet14 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 14 }


edPowerMgmtPDU1OutletsTableVoltageOutlet15 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 15 }


edPowerMgmtPDU1OutletsTableVoltageOutlet16 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 16 }


edPowerMgmtPDU1OutletsTableVoltageOutlet17 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 17 }


edPowerMgmtPDU1OutletsTableVoltageOutlet18 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 18 }


edPowerMgmtPDU1OutletsTableVoltageOutlet19 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 19 }


edPowerMgmtPDU1OutletsTableVoltageOutlet20 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 20 }


edPowerMgmtPDU1OutletsTableVoltageOutlet21 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 21 }


edPowerMgmtPDU1OutletsTableVoltageOutlet22 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 22 }


edPowerMgmtPDU1OutletsTableVoltageOutlet23 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 23 }


edPowerMgmtPDU1OutletsTableVoltageOutlet24 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 24 }

edPowerMgmtPDU1OutletsTableVoltageOutlet25 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 25 }


edPowerMgmtPDU1OutletsTableVoltageOutlet26 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 26 }


edPowerMgmtPDU1OutletsTableVoltageOutlet27 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 27 }

edPowerMgmtPDU1OutletsTableVoltageOutlet28 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 28 }

edPowerMgmtPDU1OutletsTableVoltageOutlet29 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 29 }

edPowerMgmtPDU1OutletsTableVoltageOutlet30 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 30 }

edPowerMgmtPDU1OutletsTableVoltageOutlet31 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 31 }

edPowerMgmtPDU1OutletsTableVoltageOutlet32 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 32 }

edPowerMgmtPDU1OutletsTableVoltageOutlet33 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 33 }

edPowerMgmtPDU1OutletsTableVoltageOutlet34 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 34 }


edPowerMgmtPDU1OutletsTableVoltageOutlet35 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 35 }


edPowerMgmtPDU1OutletsTableVoltageOutlet36 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 36 }


edPowerMgmtPDU1OutletsTableVoltageOutlet37 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 37 }


edPowerMgmtPDU1OutletsTableVoltageOutlet38 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 38 }


edPowerMgmtPDU1OutletsTableVoltageOutlet39 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 39 }


edPowerMgmtPDU1OutletsTableVoltageOutlet40 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 40 }


edPowerMgmtPDU1OutletsTableVoltageOutlet41 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 41 }


edPowerMgmtPDU1OutletsTableVoltageOutlet42 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU1OutletsTableVoltageValue 42 }








edPowerMgmtPDU1OutletsTableCurrentOutlet1 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU1OutletsTableCurrentValue 1 }


edPowerMgmtPDU1OutletsTableCurrentOutlet2 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU1OutletsTableCurrentValue 2 }

edPowerMgmtPDU1OutletsTableCurrentOutlet3 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU1OutletsTableCurrentValue 3 }


edPowerMgmtPDU1OutletsTableCurrentOutlet4 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU1OutletsTableCurrentValue 4 }


edPowerMgmtPDU1OutletsTableCurrentOutlet5 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU1OutletsTableCurrentValue 5 }


edPowerMgmtPDU1OutletsTableCurrentOutlet6 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU1OutletsTableCurrentValue 6 }


edPowerMgmtPDU1OutletsTableCurrentOutlet7 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU1OutletsTableCurrentValue 7 }


edPowerMgmtPDU1OutletsTableCurrentOutlet8 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU1OutletsTableCurrentValue 8 }


edPowerMgmtPDU1OutletsTableCurrentOutlet9 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU1OutletsTableCurrentValue 9 }


edPowerMgmtPDU1OutletsTableCurrentOutlet10 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU1OutletsTableCurrentValue 10 }


edPowerMgmtPDU1OutletsTableCurrentOutlet11 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU1OutletsTableCurrentValue 11 }


edPowerMgmtPDU1OutletsTableCurrentOutlet12 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU1OutletsTableCurrentValue 12 }


edPowerMgmtPDU1OutletsTableCurrentOutlet13 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU1OutletsTableCurrentValue 13 }


edPowerMgmtPDU1OutletsTableCurrentOutlet14 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU1OutletsTableCurrentValue 14 }


edPowerMgmtPDU1OutletsTableCurrentOutlet15 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU1OutletsTableCurrentValue 15 }


edPowerMgmtPDU1OutletsTableCurrentOutlet16 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU1OutletsTableCurrentValue 16 }


edPowerMgmtPDU1OutletsTableCurrentOutlet17 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU1OutletsTableCurrentValue 17 }


edPowerMgmtPDU1OutletsTableCurrentOutlet18 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU1OutletsTableCurrentValue 18 }


edPowerMgmtPDU1OutletsTableCurrentOutlet19 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU1OutletsTableCurrentValue 19 }


edPowerMgmtPDU1OutletsTableCurrentOutlet20 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU1OutletsTableCurrentValue 20 }


edPowerMgmtPDU1OutletsTableCurrentOutlet21 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU1OutletsTableCurrentValue 21 }


edPowerMgmtPDU1OutletsTableCurrentOutlet22 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU1OutletsTableCurrentValue 22 }


edPowerMgmtPDU1OutletsTableCurrentOutlet23 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU1OutletsTableCurrentValue 23 }


edPowerMgmtPDU1OutletsTableCurrentOutlet24 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU1OutletsTableCurrentValue 24 }

edPowerMgmtPDU1OutletsTableCurrentOutlet25 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU1OutletsTableCurrentValue 25 }


edPowerMgmtPDU1OutletsTableCurrentOutlet26 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU1OutletsTableCurrentValue 26 }


edPowerMgmtPDU1OutletsTableCurrentOutlet27 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU1OutletsTableCurrentValue 27 }

edPowerMgmtPDU1OutletsTableCurrentOutlet28 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU1OutletsTableCurrentValue 28 }

edPowerMgmtPDU1OutletsTableCurrentOutlet29 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU1OutletsTableCurrentValue 29 }

edPowerMgmtPDU1OutletsTableCurrentOutlet30 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU1OutletsTableCurrentValue 30 }

edPowerMgmtPDU1OutletsTableCurrentOutlet31 OBJECT-TYPE
        SYNTAX             Integer32
         ACCESS         read-only
        STATUS             mandatory
        DESCRIPTION
      "Actual value of Current for the outlet(Amp).The recieved value 
		if 1234 then actual value in decimal willbe 12.34 Amp, if recieved 
		value is 12 then 0.12 Amp .Returns 0 if not supported."
::= { edPowerMgmtPDU1OutletsTableCurrentValue 31 }

edPowerMgmtPDU1OutletsTableCurrentOutlet32 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU1OutletsTableCurrentValue 32 }

edPowerMgmtPDU1OutletsTableCurrentOutlet33 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU1OutletsTableCurrentValue 33 }

edPowerMgmtPDU1OutletsTableCurrentOutlet34 OBJECT-TYPE
        SYNTAX             Integer32
         ACCESS         read-only
        STATUS             mandatory
        DESCRIPTION
       "Actual value of Current for the outlet(Amp).The recieved value 
		if 1234 then actual value in decimal willbe 12.34 Amp, if recieved 
		value is 12 then 0.12 Amp .Returns 0 if not supported."
::= { edPowerMgmtPDU1OutletsTableCurrentValue 34 }


edPowerMgmtPDU1OutletsTableCurrentOutlet35 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU1OutletsTableCurrentValue 35 }


edPowerMgmtPDU1OutletsTableCurrentOutlet36 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU1OutletsTableCurrentValue 36 }


edPowerMgmtPDU1OutletsTableCurrentOutlet37 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU1OutletsTableCurrentValue 37 }


edPowerMgmtPDU1OutletsTableCurrentOutlet38 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU1OutletsTableCurrentValue 38 }


edPowerMgmtPDU1OutletsTableCurrentOutlet39 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU1OutletsTableCurrentValue 39 }


edPowerMgmtPDU1OutletsTableCurrentOutlet40 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU1OutletsTableCurrentValue 40 }


edPowerMgmtPDU1OutletsTableCurrentOutlet41 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU1OutletsTableCurrentValue 41 }


edPowerMgmtPDU1OutletsTableCurrentOutlet42 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU1OutletsTableCurrentValue 42 }









edPowerMgmtPDU1OutletsTableApearentEnergyOutlet1 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 1 }


edPowerMgmtPDU1OutletsTableApearentEnergyOutlet2 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 2 }

edPowerMgmtPDU1OutletsTableApearentEnergyOutlet3 OBJECT-TYPE
        SYNTAX             Integer32
         ACCESS         read-only
        STATUS             mandatory
        DESCRIPTION
      "Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 3 }


edPowerMgmtPDU1OutletsTableApearentEnergyOutlet4 OBJECT-TYPE
        SYNTAX             Integer32
         ACCESS         read-only
        STATUS             mandatory
        DESCRIPTION
      "Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 4 }


edPowerMgmtPDU1OutletsTableApearentEnergyOutlet5 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 5 }


edPowerMgmtPDU1OutletsTableApearentEnergyOutlet6 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 6 }


edPowerMgmtPDU1OutletsTableApearentEnergyOutlet7 OBJECT-TYPE
        SYNTAX             Integer32
         ACCESS         read-only
        STATUS             mandatory
        DESCRIPTION
        "Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 7 }


edPowerMgmtPDU1OutletsTableApearentEnergyOutlet8 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 8 }


edPowerMgmtPDU1OutletsTableApearentEnergyOutlet9 OBJECT-TYPE
        SYNTAX             Integer32
         ACCESS         read-only
        STATUS             mandatory
        DESCRIPTION
     "Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 9 }


edPowerMgmtPDU1OutletsTableApearentEnergyOutlet10 OBJECT-TYPE
        SYNTAX             Integer32
         ACCESS         read-only
        STATUS             mandatory
        DESCRIPTION
     "Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 10 }


edPowerMgmtPDU1OutletsTableApearentEnergyOutlet11 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 11 }


edPowerMgmtPDU1OutletsTableApearentEnergyOutlet12 OBJECT-TYPE
        SYNTAX             Integer32
         ACCESS         read-only
        STATUS             mandatory
        DESCRIPTION
   "Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 12 }


edPowerMgmtPDU1OutletsTableApearentEnergyOutlet13 OBJECT-TYPE
        SYNTAX             Integer32
         ACCESS         read-only
        STATUS             mandatory
        DESCRIPTION
      "Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 13 }


edPowerMgmtPDU1OutletsTableApearentEnergyOutlet14 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 14 }


edPowerMgmtPDU1OutletsTableApearentEnergyOutlet15 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 15 }


edPowerMgmtPDU1OutletsTableApearentEnergyOutlet16 OBJECT-TYPE
        SYNTAX             Integer32
         ACCESS         read-only
        STATUS             mandatory
        DESCRIPTION
          "Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 16 }


edPowerMgmtPDU1OutletsTableApearentEnergyOutlet17 OBJECT-TYPE
        SYNTAX             Integer32
         ACCESS         read-only
        STATUS             mandatory
        DESCRIPTION
          "Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 17 }


edPowerMgmtPDU1OutletsTableApearentEnergyOutlet18 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 18 }


edPowerMgmtPDU1OutletsTableApearentEnergyOutlet19 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 19 }


edPowerMgmtPDU1OutletsTableApearentEnergyOutlet20 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 20 }


edPowerMgmtPDU1OutletsTableApearentEnergyOutlet21 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 21 }


edPowerMgmtPDU1OutletsTableApearentEnergyOutlet22 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 22 }


edPowerMgmtPDU1OutletsTableApearentEnergyOutlet23 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 23 }


edPowerMgmtPDU1OutletsTableApearentEnergyOutlet24 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 24 }

edPowerMgmtPDU1OutletsTableApearentEnergyOutlet25 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 25 }


edPowerMgmtPDU1OutletsTableApearentEnergyOutlet26 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 26 }


edPowerMgmtPDU1OutletsTableApearentEnergyOutlet27 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 27 }

edPowerMgmtPDU1OutletsTableApearentEnergyOutlet28 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 28 }

edPowerMgmtPDU1OutletsTableApearentEnergyOutlet29 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 29 }

edPowerMgmtPDU1OutletsTableApearentEnergyOutlet30 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 30 }

edPowerMgmtPDU1OutletsTableApearentEnergyOutlet31 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 31 }

edPowerMgmtPDU1OutletsTableApearentEnergyOutlet32 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 32 }

edPowerMgmtPDU1OutletsTableApearentEnergyOutlet33 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 33 }

edPowerMgmtPDU1OutletsTableApearentEnergyOutlet34 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 34 }


edPowerMgmtPDU1OutletsTableApearentEnergyOutlet35 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 35 }


edPowerMgmtPDU1OutletsTableApearentEnergyOutlet36 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 36 }


edPowerMgmtPDU1OutletsTableApearentEnergyOutlet37 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 37 }


edPowerMgmtPDU1OutletsTableApearentEnergyOutlet38 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 38 }


edPowerMgmtPDU1OutletsTableApearentEnergyOutlet39 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 39 }


edPowerMgmtPDU1OutletsTableApearentEnergyOutlet40 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 40 }


edPowerMgmtPDU1OutletsTableApearentEnergyOutlet41 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 41 }


edPowerMgmtPDU1OutletsTableApearentEnergyOutlet42 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU1OutletsTableApearentEnergyValue 42 }





edPowerMgmtPDU1OutletsTableReactiveEnergyOutlet1 OBJECT-TYPE
        SYNTAX             Integer32
         ACCESS         read-only
        STATUS             mandatory
        DESCRIPTION
		"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 1 }


edPowerMgmtPDU1OutletsTableReactiveEnergyOutlet2 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 2 }

edPowerMgmtPDU1OutletsTableReactiveEnergyOutlet3 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 3 }


edPowerMgmtPDU1OutletsTableReactiveEnergyOutlet4 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 4 }


edPowerMgmtPDU1OutletsTableReactiveEnergyOutlet5 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 5 }


edPowerMgmtPDU1OutletsTableReactiveEnergyOutlet6 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 6 }


edPowerMgmtPDU1OutletsTableReactiveEnergyOutlet7 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 7 }


edPowerMgmtPDU1OutletsTableReactiveEnergyOutlet8 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 8 }


edPowerMgmtPDU1OutletsTableReactiveEnergyOutlet9 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 9 }


edPowerMgmtPDU1OutletsTableReactiveEnergyOutlet10 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 10 }


edPowerMgmtPDU1OutletsTableReactiveEnergyOutlet11 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 11 }


edPowerMgmtPDU1OutletsTableReactiveEnergyOutlet12 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 12 }


edPowerMgmtPDU1OutletsTableReactiveEnergyOutlet13 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 13 }


edPowerMgmtPDU1OutletsTableReactiveEnergyOutlet14 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 14 }


edPowerMgmtPDU1OutletsTableReactiveEnergyOutlet15 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 15 }


edPowerMgmtPDU1OutletsTableReactiveEnergyOutlet16 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 16 }


edPowerMgmtPDU1OutletsTableReactiveEnergyOutlet17 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 17 }


edPowerMgmtPDU1OutletsTableReactiveEnergyOutlet18 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 18 }


edPowerMgmtPDU1OutletsTableReactiveEnergyOutlet19 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 19 }


edPowerMgmtPDU1OutletsTableReactiveEnergyOutlet20 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 20 }


edPowerMgmtPDU1OutletsTableReactiveEnergyOutlet21 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 21 }


edPowerMgmtPDU1OutletsTableReactiveEnergyOutlet22 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 22 }


edPowerMgmtPDU1OutletsTableReactiveEnergyOutlet23 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 23 }


edPowerMgmtPDU1OutletsTableReactiveEnergyOutlet24 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 24 }

edPowerMgmtPDU1OutletsTableReactiveEnergyOutlet25 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 25 }


edPowerMgmtPDU1OutletsTableReactiveEnergyOutlet26 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 26 }


edPowerMgmtPDU1OutletsTableReactiveEnergyOutlet27 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 27 }

edPowerMgmtPDU1OutletsTableReactiveEnergyOutlet28 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 28 }

edPowerMgmtPDU1OutletsTableReactiveEnergyOutlet29 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 29 }

edPowerMgmtPDU1OutletsTableReactiveEnergyOutlet30 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 30 }

edPowerMgmtPDU1OutletsTableReactiveEnergyOutlet31 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 31 }

edPowerMgmtPDU1OutletsTableReactiveEnergyOutlet32 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 32 }

edPowerMgmtPDU1OutletsTableReactiveEnergyOutlet33 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 33 }

edPowerMgmtPDU1OutletsTableReactiveEnergyOutlet34 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 34 }


edPowerMgmtPDU1OutletsTableReactiveEnergyOutlet35 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 35 }


edPowerMgmtPDU1OutletsTableReactiveEnergyOutlet36 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 36 }


edPowerMgmtPDU1OutletsTableReactiveEnergyOutlet37 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 37 }


edPowerMgmtPDU1OutletsTableReactiveEnergyOutlet38 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 38 }


edPowerMgmtPDU1OutletsTableReactiveEnergyOutlet39 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 39 }


edPowerMgmtPDU1OutletsTableReactiveEnergyOutlet40 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 40 }


edPowerMgmtPDU1OutletsTableReactiveEnergyOutlet41 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 41 }


edPowerMgmtPDU1OutletsTableReactiveEnergyOutlet42 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU1OutletsTableReactiveEnergyValue 42 }




edPowerMgmtPDU1OutletsTableActiveEnergyOutlet1 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 1 }


edPowerMgmtPDU1OutletsTableActiveEnergyOutlet2 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 2 }

edPowerMgmtPDU1OutletsTableActiveEnergyOutlet3 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 3 }


edPowerMgmtPDU1OutletsTableActiveEnergyOutlet4 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 4 }


edPowerMgmtPDU1OutletsTableActiveEnergyOutlet5 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 5 }


edPowerMgmtPDU1OutletsTableActiveEnergyOutlet6 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 6 }


edPowerMgmtPDU1OutletsTableActiveEnergyOutlet7 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 7 }


edPowerMgmtPDU1OutletsTableActiveEnergyOutlet8 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 8 }


edPowerMgmtPDU1OutletsTableActiveEnergyOutlet9 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 9 }


edPowerMgmtPDU1OutletsTableActiveEnergyOutlet10 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 10 }


edPowerMgmtPDU1OutletsTableActiveEnergyOutlet11 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 11 }


edPowerMgmtPDU1OutletsTableActiveEnergyOutlet12 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 12 }


edPowerMgmtPDU1OutletsTableActiveEnergyOutlet13 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 13 }


edPowerMgmtPDU1OutletsTableActiveEnergyOutlet14 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 14 }


edPowerMgmtPDU1OutletsTableActiveEnergyOutlet15 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 15 }


edPowerMgmtPDU1OutletsTableActiveEnergyOutlet16 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 16 }


edPowerMgmtPDU1OutletsTableActiveEnergyOutlet17 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 17 }


edPowerMgmtPDU1OutletsTableActiveEnergyOutlet18 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 18 }


edPowerMgmtPDU1OutletsTableActiveEnergyOutlet19 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 19 }


edPowerMgmtPDU1OutletsTableActiveEnergyOutlet20 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 20 }


edPowerMgmtPDU1OutletsTableActiveEnergyOutlet21 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 21 }


edPowerMgmtPDU1OutletsTableActiveEnergyOutlet22 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 22 }


edPowerMgmtPDU1OutletsTableActiveEnergyOutlet23 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 23 }


edPowerMgmtPDU1OutletsTableActiveEnergyOutlet24 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 24 }

edPowerMgmtPDU1OutletsTableActiveEnergyOutlet25 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 25 }


edPowerMgmtPDU1OutletsTableActiveEnergyOutlet26 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 26 }


edPowerMgmtPDU1OutletsTableActiveEnergyOutlet27 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 27 }

edPowerMgmtPDU1OutletsTableActiveEnergyOutlet28 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 28 }

edPowerMgmtPDU1OutletsTableActiveEnergyOutlet29 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 29 }

edPowerMgmtPDU1OutletsTableActiveEnergyOutlet30 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 30 }

edPowerMgmtPDU1OutletsTableActiveEnergyOutlet31 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 31 }

edPowerMgmtPDU1OutletsTableActiveEnergyOutlet32 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 32 }

edPowerMgmtPDU1OutletsTableActiveEnergyOutlet33 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 33 }

edPowerMgmtPDU1OutletsTableActiveEnergyOutlet34 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 34 }


edPowerMgmtPDU1OutletsTableActiveEnergyOutlet35 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 35 }


edPowerMgmtPDU1OutletsTableActiveEnergyOutlet36 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 36 }


edPowerMgmtPDU1OutletsTableActiveEnergyOutlet37 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 37 }


edPowerMgmtPDU1OutletsTableActiveEnergyOutlet38 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 38 }


edPowerMgmtPDU1OutletsTableActiveEnergyOutlet39 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 39 }


edPowerMgmtPDU1OutletsTableActiveEnergyOutlet40 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 40 }


edPowerMgmtPDU1OutletsTableActiveEnergyOutlet41 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 41 }


edPowerMgmtPDU1OutletsTableActiveEnergyOutlet42 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU1OutletsTableActiveEnergyValue 42 }









edPowerMgmtPDU1OutletsTableInstantaneousPowerOutlet1 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 1 }


edPowerMgmtPDU1OutletsTableInstantaneousPowerOutlet2 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 2 }

edPowerMgmtPDU1OutletsTableInstantaneousPowerOutlet3 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 3 }


edPowerMgmtPDU1OutletsTableInstantaneousPowerOutlet4 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 4 }


edPowerMgmtPDU1OutletsTableInstantaneousPowerOutlet5 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 5 }


edPowerMgmtPDU1OutletsTableInstantaneousPowerOutlet6 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 6 }


edPowerMgmtPDU1OutletsTableInstantaneousPowerOutlet7 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 7 }


edPowerMgmtPDU1OutletsTableInstantaneousPowerOutlet8 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 8 }


edPowerMgmtPDU1OutletsTableInstantaneousPowerOutlet9 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 9 }


edPowerMgmtPDU1OutletsTableInstantaneousPowerOutlet10 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 10 }


edPowerMgmtPDU1OutletsTableInstantaneousPowerOutlet11 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 11 }


edPowerMgmtPDU1OutletsTableInstantaneousPowerOutlet12 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 12 }


edPowerMgmtPDU1OutletsTableInstantaneousPowerOutlet13 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 13 }


edPowerMgmtPDU1OutletsTableInstantaneousPowerOutlet14 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 14 }


edPowerMgmtPDU1OutletsTableInstantaneousPowerOutlet15 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 15 }


edPowerMgmtPDU1OutletsTableInstantaneousPowerOutlet16 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 16 }


edPowerMgmtPDU1OutletsTableInstantaneousPowerOutlet17 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 17 }


edPowerMgmtPDU1OutletsTableInstantaneousPowerOutlet18 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 18 }


edPowerMgmtPDU1OutletsTableInstantaneousPowerOutlet19 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 19 }


edPowerMgmtPDU1OutletsTableInstantaneousPowerOutlet20 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 20 }


edPowerMgmtPDU1OutletsTableInstantaneousPowerOutlet21 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 21 }


edPowerMgmtPDU1OutletsTableInstantaneousPowerOutlet22 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 22 }


edPowerMgmtPDU1OutletsTableInstantaneousPowerOutlet23 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 23 }


edPowerMgmtPDU1OutletsTableInstantaneousPowerOutlet24 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 24 }

edPowerMgmtPDU1OutletsTableInstantaneousPowerOutlet25 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 25 }


edPowerMgmtPDU1OutletsTableInstantaneousPowerOutlet26 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 26 }


edPowerMgmtPDU1OutletsTableInstantaneousPowerOutlet27 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 27 }

edPowerMgmtPDU1OutletsTableInstantaneousPowerOutlet28 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 28 }

edPowerMgmtPDU1OutletsTableInstantaneousPowerOutlet29 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 29 }

edPowerMgmtPDU1OutletsTableInstantaneousPowerOutlet30 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 30 }

edPowerMgmtPDU1OutletsTableInstantaneousPowerOutlet31 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 31 }

edPowerMgmtPDU1OutletsTableInstantaneousPowerOutlet32 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 32 }

edPowerMgmtPDU1OutletsTableInstantaneousPowerOutlet33 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 33 }

edPowerMgmtPDU1OutletsTableInstantaneousPowerOutlet34 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 34 }


edPowerMgmtPDU1OutletsTableInstantaneousPowerOutlet35 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 35 }


edPowerMgmtPDU1OutletsTableInstantaneousPowerOutlet36 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 36 }


edPowerMgmtPDU1OutletsTableInstantaneousPowerOutlet37 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 37 }


edPowerMgmtPDU1OutletsTableInstantaneousPowerOutlet38 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 38 }


edPowerMgmtPDU1OutletsTableInstantaneousPowerOutlet39 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 39 }


edPowerMgmtPDU1OutletsTableInstantaneousPowerOutlet40 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 40 }


edPowerMgmtPDU1OutletsTableInstantaneousPowerOutlet41 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 41 }


edPowerMgmtPDU1OutletsTableInstantaneousPowerOutlet42 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU1OutletsTableInstantaneousPowerValue 42 }







edPowerMgmtPDU1OutletsTablePowerFactorOutlet1 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 1 }


edPowerMgmtPDU1OutletsTablePowerFactorOutlet2 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 2 }

edPowerMgmtPDU1OutletsTablePowerFactorOutlet3 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 3 }


edPowerMgmtPDU1OutletsTablePowerFactorOutlet4 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 4 }


edPowerMgmtPDU1OutletsTablePowerFactorOutlet5 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 5 }


edPowerMgmtPDU1OutletsTablePowerFactorOutlet6 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 6 }


edPowerMgmtPDU1OutletsTablePowerFactorOutlet7 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 7 }


edPowerMgmtPDU1OutletsTablePowerFactorOutlet8 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 8 }


edPowerMgmtPDU1OutletsTablePowerFactorOutlet9 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 9 }


edPowerMgmtPDU1OutletsTablePowerFactorOutlet10 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 10 }


edPowerMgmtPDU1OutletsTablePowerFactorOutlet11 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 11 }


edPowerMgmtPDU1OutletsTablePowerFactorOutlet12 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 12 }


edPowerMgmtPDU1OutletsTablePowerFactorOutlet13 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 13 }


edPowerMgmtPDU1OutletsTablePowerFactorOutlet14 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 14 }


edPowerMgmtPDU1OutletsTablePowerFactorOutlet15 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 15 }


edPowerMgmtPDU1OutletsTablePowerFactorOutlet16 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 16 }


edPowerMgmtPDU1OutletsTablePowerFactorOutlet17 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 17 }


edPowerMgmtPDU1OutletsTablePowerFactorOutlet18 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 18 }


edPowerMgmtPDU1OutletsTablePowerFactorOutlet19 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 19 }


edPowerMgmtPDU1OutletsTablePowerFactorOutlet20 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 20 }


edPowerMgmtPDU1OutletsTablePowerFactorOutlet21 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 21 }


edPowerMgmtPDU1OutletsTablePowerFactorOutlet22 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 22 }


edPowerMgmtPDU1OutletsTablePowerFactorOutlet23 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 23 }


edPowerMgmtPDU1OutletsTablePowerFactorOutlet24 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 24 }

edPowerMgmtPDU1OutletsTablePowerFactorOutlet25 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 25 }


edPowerMgmtPDU1OutletsTablePowerFactorOutlet26 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 26 }


edPowerMgmtPDU1OutletsTablePowerFactorOutlet27 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 27 }

edPowerMgmtPDU1OutletsTablePowerFactorOutlet28 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 28 }

edPowerMgmtPDU1OutletsTablePowerFactorOutlet29 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 29 }

edPowerMgmtPDU1OutletsTablePowerFactorOutlet30 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 30 }

edPowerMgmtPDU1OutletsTablePowerFactorOutlet31 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 31 }

edPowerMgmtPDU1OutletsTablePowerFactorOutlet32 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 32 }

edPowerMgmtPDU1OutletsTablePowerFactorOutlet33 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 33 }

edPowerMgmtPDU1OutletsTablePowerFactorOutlet34 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 34 }


edPowerMgmtPDU1OutletsTablePowerFactorOutlet35 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 35 }


edPowerMgmtPDU1OutletsTablePowerFactorOutlet36 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 36 }


edPowerMgmtPDU1OutletsTablePowerFactorOutlet37 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 37 }


edPowerMgmtPDU1OutletsTablePowerFactorOutlet38 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 38 }


edPowerMgmtPDU1OutletsTablePowerFactorOutlet39 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 39 }


edPowerMgmtPDU1OutletsTablePowerFactorOutlet40 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 40 }


edPowerMgmtPDU1OutletsTablePowerFactorOutlet41 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 41 }


edPowerMgmtPDU1OutletsTablePowerFactorOutlet42 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU1OutletsTablePowerFactorValue 42 }







edPowerMgmtPDU1OutletsTableFreqOutlet1 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 1 }


edPowerMgmtPDU1OutletsTableFreqOutlet2 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 2 }

edPowerMgmtPDU1OutletsTableFreqOutlet3 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 3 }


edPowerMgmtPDU1OutletsTableFreqOutlet4 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 4 }


edPowerMgmtPDU1OutletsTableFreqOutlet5 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 5 }


edPowerMgmtPDU1OutletsTableFreqOutlet6 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 6 }


edPowerMgmtPDU1OutletsTableFreqOutlet7 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 7 }


edPowerMgmtPDU1OutletsTableFreqOutlet8 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 8 }


edPowerMgmtPDU1OutletsTableFreqOutlet9 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 9 }


edPowerMgmtPDU1OutletsTableFreqOutlet10 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 10 }


edPowerMgmtPDU1OutletsTableFreqOutlet11 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 11 }


edPowerMgmtPDU1OutletsTableFreqOutlet12 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 12 }


edPowerMgmtPDU1OutletsTableFreqOutlet13 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 13 }


edPowerMgmtPDU1OutletsTableFreqOutlet14 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 14 }


edPowerMgmtPDU1OutletsTableFreqOutlet15 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 15 }


edPowerMgmtPDU1OutletsTableFreqOutlet16 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 16 }


edPowerMgmtPDU1OutletsTableFreqOutlet17 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 17 }


edPowerMgmtPDU1OutletsTableFreqOutlet18 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 18 }


edPowerMgmtPDU1OutletsTableFreqOutlet19 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 19 }


edPowerMgmtPDU1OutletsTableFreqOutlet20 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 20 }


edPowerMgmtPDU1OutletsTableFreqOutlet21 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 21 }


edPowerMgmtPDU1OutletsTableFreqOutlet22 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 22 }


edPowerMgmtPDU1OutletsTableFreqOutlet23 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 23 }


edPowerMgmtPDU1OutletsTableFreqOutlet24 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 24 }

edPowerMgmtPDU1OutletsTableFreqOutlet25 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 25 }


edPowerMgmtPDU1OutletsTableFreqOutlet26 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 26 }


edPowerMgmtPDU1OutletsTableFreqOutlet27 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 27 }

edPowerMgmtPDU1OutletsTableFreqOutlet28 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 28 }

edPowerMgmtPDU1OutletsTableFreqOutlet29 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 29 }

edPowerMgmtPDU1OutletsTableFreqOutlet30 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 30 }

edPowerMgmtPDU1OutletsTableFreqOutlet31 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 31 }

edPowerMgmtPDU1OutletsTableFreqOutlet32 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 32 }

edPowerMgmtPDU1OutletsTableFreqOutlet33 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 33 }

edPowerMgmtPDU1OutletsTableFreqOutlet34 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 34 }


edPowerMgmtPDU1OutletsTableFreqOutlet35 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 35 }


edPowerMgmtPDU1OutletsTableFreqOutlet36 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 36 }


edPowerMgmtPDU1OutletsTableFreqOutlet37 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 37 }


edPowerMgmtPDU1OutletsTableFreqOutlet38 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 38 }


edPowerMgmtPDU1OutletsTableFreqOutlet39 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 39 }


edPowerMgmtPDU1OutletsTableFreqOutlet40 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 40 }


edPowerMgmtPDU1OutletsTableFreqOutlet41 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 41 }


edPowerMgmtPDU1OutletsTableFreqOutlet42 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU1OutletsTableFreqValue 42 }






edPowerMgmtPDU1OutletsTableControlOutlet1 OBJECT-TYPE
        SYNTAX INTEGER {
			switchingDisabled     (2),    			
			outletOn              (1),
			outletOff             (0)  
			
		}    
        ACCESS         read-write
        STATUS             mandatory
        DESCRIPTION
         "Getting this variable will return the outlet state. If 
       the outlet is on, the outletOn (1) value will be returned.
       If the outlet is off, the outletOff (0) value will be
       returned. and if returned 2 then switching is prohibited"
::= { edPowerMgmtPDU1OutletsTableOutletControl 1 }


edPowerMgmtPDU1OutletsTableControlOutlet2 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 2 }

edPowerMgmtPDU1OutletsTableControlOutlet3 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 3 }


edPowerMgmtPDU1OutletsTableControlOutlet4 OBJECT-TYPE
            SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 4 }


edPowerMgmtPDU1OutletsTableControlOutlet5 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 5 }


edPowerMgmtPDU1OutletsTableControlOutlet6 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 6 }


edPowerMgmtPDU1OutletsTableControlOutlet7 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 7 }


edPowerMgmtPDU1OutletsTableControlOutlet8 OBJECT-TYPE
            SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 8 }


edPowerMgmtPDU1OutletsTableControlOutlet9 OBJECT-TYPE
              SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 9 }


edPowerMgmtPDU1OutletsTableControlOutlet10 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 10 }


edPowerMgmtPDU1OutletsTableControlOutlet11 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 11 }


edPowerMgmtPDU1OutletsTableControlOutlet12 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 12 }


edPowerMgmtPDU1OutletsTableControlOutlet13 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 13 }


edPowerMgmtPDU1OutletsTableControlOutlet14 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 14 }


edPowerMgmtPDU1OutletsTableControlOutlet15 OBJECT-TYPE
           SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 15 }


edPowerMgmtPDU1OutletsTableControlOutlet16 OBJECT-TYPE
                SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 16 }


edPowerMgmtPDU1OutletsTableControlOutlet17 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 17 }


edPowerMgmtPDU1OutletsTableControlOutlet18 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 18 }


edPowerMgmtPDU1OutletsTableControlOutlet19 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 19 }


edPowerMgmtPDU1OutletsTableControlOutlet20 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 20 }


edPowerMgmtPDU1OutletsTableControlOutlet21 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 21 }


edPowerMgmtPDU1OutletsTableControlOutlet22 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 22 }


edPowerMgmtPDU1OutletsTableControlOutlet23 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 23 }


edPowerMgmtPDU1OutletsTableControlOutlet24 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 24 }

edPowerMgmtPDU1OutletsTableControlOutlet25 OBJECT-TYPE
           SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 25 }


edPowerMgmtPDU1OutletsTableControlOutlet26 OBJECT-TYPE
            SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 26 }


edPowerMgmtPDU1OutletsTableControlOutlet27 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 27 }

edPowerMgmtPDU1OutletsTableControlOutlet28 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 28 }

edPowerMgmtPDU1OutletsTableControlOutlet29 OBJECT-TYPE
                SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 29 }

edPowerMgmtPDU1OutletsTableControlOutlet30 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 30 }

edPowerMgmtPDU1OutletsTableControlOutlet31 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 31 }

edPowerMgmtPDU1OutletsTableControlOutlet32 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 32 }

edPowerMgmtPDU1OutletsTableControlOutlet33 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 33 }

edPowerMgmtPDU1OutletsTableControlOutlet34 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 34 }


edPowerMgmtPDU1OutletsTableControlOutlet35 OBJECT-TYPE
                SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 35 }


edPowerMgmtPDU1OutletsTableControlOutlet36 OBJECT-TYPE
                 SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 36 }


edPowerMgmtPDU1OutletsTableControlOutlet37 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 37 }


edPowerMgmtPDU1OutletsTableControlOutlet38 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 38 }


edPowerMgmtPDU1OutletsTableControlOutlet39 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 39 }


edPowerMgmtPDU1OutletsTableControlOutlet40 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 40 }


edPowerMgmtPDU1OutletsTableControlOutlet41 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 41 }


edPowerMgmtPDU1OutletsTableControlOutlet42 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU1OutletsTableOutletControl 42 }




edPowerMgmtPDU1TotalNumberOfPhases OBJECT-TYPE
        SYNTAX             Integer32
         ACCESS         		read-only
        STATUS             mandatory
        DESCRIPTION
        "Number of Phases managed by the appliance."
::= { edConectedPdu1Data 5 }

edPowerMgmtPDU1PhasesTable OBJECT IDENTIFIER::= { edConectedPdu1Data 6 }

edPowerMgmtPDU1PhasesData OBJECT IDENTIFIER::= { edPowerMgmtPDU1PhasesTable 1 }
edPowerMgmtPDU1PhasesTableIndexNumber OBJECT IDENTIFIER::= { edPowerMgmtPDU1PhasesData 1 }
edPowerMgmtPDU1PhasesTableVoltageValue OBJECT IDENTIFIER::= { edPowerMgmtPDU1PhasesData 2 }
edPowerMgmtPDU1PhasesTablecurrentValue OBJECT IDENTIFIER::= { edPowerMgmtPDU1PhasesData 3 }
edPowerMgmtPDU1PhasesTableApearentEnergyValue OBJECT IDENTIFIER::= { edPowerMgmtPDU1PhasesData 4 }
edPowerMgmtPDU1PhasesTableReactiveEnergyValue OBJECT IDENTIFIER::= { edPowerMgmtPDU1PhasesData 5 }
edPowerMgmtPDU1PhasesTableActiveEnergyValue OBJECT IDENTIFIER::= { edPowerMgmtPDU1PhasesData 6 }
edPowerMgmtPDU1PhasesTableInstantaneousPowerValue OBJECT IDENTIFIER::= { edPowerMgmtPDU1PhasesData 7 }
edPowerMgmtPDU1PhasesTablePowerFactorValue OBJECT IDENTIFIER::= { edPowerMgmtPDU1PhasesData 8 }

edPowerMgmtPDU1PhasesTableIndexNumber1 OBJECT-TYPE
        SYNTAX             Integer32
         ACCESS         read-only
        STATUS             mandatory
        DESCRIPTION
         "Index Number of the outlet in the PDU."
::= { edPowerMgmtPDU1PhasesTableIndexNumber 1 }

edPowerMgmtPDU1PhasesTableIndexNumber2 OBJECT-TYPE
        SYNTAX             Integer32
         ACCESS         read-only
        STATUS             mandatory
        DESCRIPTION
         "Index Number of the outlet in the PDU."
::= { edPowerMgmtPDU1PhasesTableIndexNumber 2 }


edPowerMgmtPDU1PhasesTableIndexNumber3 OBJECT-TYPE
        SYNTAX             Integer32
         ACCESS         read-only
        STATUS             mandatory
        DESCRIPTION
         "Index Number of the outlet in the PDU."
::= { edPowerMgmtPDU1PhasesTableIndexNumber 3 }


edPowerMgmtPDU1PhasesTableVoltageValuePhase1 OBJECT-TYPE
        SYNTAX             Integer32
         ACCESS         read-only
        STATUS             mandatory
        DESCRIPTION
        "Value of R Phase recieved from device.
		if recieved 23024 then actual value in decimal willbe 230.24 Volts ,
		if recieved 12 then 0.12 Volt. Returns 0 if not supported."
::= { edPowerMgmtPDU1PhasesTableVoltageValue 1 }

edPowerMgmtPDU1PhasesTableVoltageValuePhase2 OBJECT-TYPE
        SYNTAX             Integer32
         ACCESS         read-only
        STATUS             mandatory
        DESCRIPTION
     "Value of Y Phase recieved from device.
		if recieved 23024 then actual value in decimal willbe 230.24 Volts ,
		if recieved 12 then 0.12 Volt. Returns 0 if not supported."
::= { edPowerMgmtPDU1PhasesTableVoltageValue 2 }

edPowerMgmtPDU1PhasesTableVoltageValuePhase3 OBJECT-TYPE
        SYNTAX             Integer32
         ACCESS         read-only
        STATUS             mandatory
        DESCRIPTION
              "Value of B Phase recieved from device.
		if recieved 23024 then actual value in decimal willbe 230.24 Volts ,
		if recieved 12 then 0.12 Volt. Returns 0 if not supported."
::= { edPowerMgmtPDU1PhasesTableVoltageValue 3 }


edPowerMgmtPDU1PhasesTablecurrentPhase1 OBJECT-TYPE
        SYNTAX             Integer32
         ACCESS         read-only
        STATUS             mandatory
        DESCRIPTION
         "Current of R Phase in Ampere ,if recieved 1234 then actual value in decimal willbe 12.34 Amp, if recieved 
		value is 12 then 0.12 Amp .Returns 0 if not supported."
::= { edPowerMgmtPDU1PhasesTablecurrentValue 1 }


edPowerMgmtPDU1PhasesTablecurrentPhase2 OBJECT-TYPE
        SYNTAX             Integer32
         ACCESS         read-only
        STATUS             mandatory
        DESCRIPTION
          "Current of Y Phase in Ampere ,if recieved 1234 then actual value in decimal willbe 12.34 Amp, if recieved 
		value is 12 then 0.12 Amp .Returns 0 if not supported."
::= { edPowerMgmtPDU1PhasesTablecurrentValue 2 }



edPowerMgmtPDU1PhasesTablecurrentPhase3 OBJECT-TYPE
        SYNTAX             Integer32
         ACCESS         read-only
        STATUS             mandatory
        DESCRIPTION
       "Current of B Phase in Ampere ,if recieved 1234 then actual value in decimal willbe 12.34 Amp, if recieved 
		value is 12 then 0.12 Amp .Returns 0 if not supported."
::= { edPowerMgmtPDU1PhasesTablecurrentValue 3 }



edPowerMgmtPDU1PhasesTableApearentEnergyPhase1 OBJECT-TYPE
        SYNTAX             Integer32
         ACCESS         read-only
        STATUS             mandatory
        DESCRIPTION
        "ApearentEnergy(KVaHr) of R Phase if recieved 23024 then actual value in decimal willbe 2.3024 KVaHr , if recieved 12
	   then 0.0012 KVaHr. Returns 0 if not supported."
::= { edPowerMgmtPDU1PhasesTableApearentEnergyValue 1 }


edPowerMgmtPDU1PhasesTableApearentEnergyPhase2 OBJECT-TYPE
        SYNTAX             Integer32
         ACCESS         read-only
        STATUS             mandatory
        DESCRIPTION
         "ApearentEnergy(KVaHr) of Y Phase if recieved 23024 then actual value in decimal willbe 2.3024 KVaHr , if recieved 12
	   then 0.0012 KVaHr. Returns 0 if not supported."
::= { edPowerMgmtPDU1PhasesTableApearentEnergyValue 2 }

edPowerMgmtPDU1PhasesTableApearentEnergyPhase3 OBJECT-TYPE
        SYNTAX             Integer32
         ACCESS         read-only
        STATUS             mandatory
        DESCRIPTION
        "ApearentEnergy(KVaHr) of B Phase if recieved 23024 then actual value in decimal willbe 2.3024 KVaHr , if recieved 12
	   then 0.0012 KVaHr. Returns 0 if not supported."
::= { edPowerMgmtPDU1PhasesTableApearentEnergyValue 3 }


edPowerMgmtPDU1PhasesTableReactiveEnergyPhase1 OBJECT-TYPE
        SYNTAX             Integer32
         ACCESS         read-only
        STATUS             mandatory
        DESCRIPTION
        "ReactiveEnergy(KVarHr) of R Phase if recieved 23024 then actual value in decimal willbe 2.3024 KVaHr , if recieved 12
	   then 0.0012 KVaHr. Returns 0 if not supported."
::= { edPowerMgmtPDU1PhasesTableReactiveEnergyValue 1 }



edPowerMgmtPDU1PhasesTableReactiveEnergyPhase2 OBJECT-TYPE
        SYNTAX             Integer32
         ACCESS         read-only
        STATUS             mandatory
        DESCRIPTION
           "ReactiveEnergy(KVarHr) of Y Phase if recieved 23024 then actual value in decimal willbe 2.3024 KVaHr , if recieved 12
	   then 0.0012 KVaHr. Returns 0 if not supported."
::= { edPowerMgmtPDU1PhasesTableReactiveEnergyValue 2 }



edPowerMgmtPDU1PhasesTableReactiveEnergyPhase3 OBJECT-TYPE
        SYNTAX             Integer32
         ACCESS         read-only
        STATUS             mandatory
        DESCRIPTION
        "ReactiveEnergy(KVarHr) of B Phase if recieved 23024 then actual value in decimal willbe 2.3024 KVaHr , if recieved 12
	   then 0.0012 KVaHr. Returns 0 if not supported."
::= { edPowerMgmtPDU1PhasesTableReactiveEnergyValue 3 }

edPowerMgmtPDU1PhasesTableActiveEnergyPhase1 OBJECT-TYPE
        SYNTAX             Integer32
         ACCESS         read-only
        STATUS             mandatory
        DESCRIPTION
        "ActiveEnergy(KWattHr) of R Phase if recieved 23024 then actual value in decimal willbe 2.3024 KVaHr , if recieved 12
	   then 0.0012 KVaHr. Returns 0 if not supported."
::= { edPowerMgmtPDU1PhasesTableActiveEnergyValue 1 }

edPowerMgmtPDU1PhasesTableActiveEnergyPhase2 OBJECT-TYPE
        SYNTAX             Integer32
         ACCESS         read-only
        STATUS             mandatory
        DESCRIPTION
         "ActiveEnergy(KWattHr) of Y Phase if recieved 23024 then actual value in decimal willbe 2.3024 KVaHr , if recieved 12
	   then 0.0012 KVaHr. Returns 0 if not supported."
::= { edPowerMgmtPDU1PhasesTableActiveEnergyValue 2 }

edPowerMgmtPDU1PhasesTableActiveEnergyPhase3 OBJECT-TYPE
        SYNTAX             Integer32
         ACCESS         read-only
        STATUS             mandatory
        DESCRIPTION
        "ActiveEnergy(KWattHr) of B Phase if recieved 23024 then actual value in decimal willbe 2.3024 KVaHr , if recieved 12
	   then 0.0012 KVaHr. Returns 0 if not supported."
::= { edPowerMgmtPDU1PhasesTableActiveEnergyValue 3 }


edPowerMgmtPDU1PhasesTableInstantaneousPowerPhase1 OBJECT-TYPE
        SYNTAX             Integer32
         ACCESS         read-only
        STATUS             mandatory
        DESCRIPTION
           "Instantaneous Power(KWatt) of R Phase if recieved 23024 then actual value in decimal willbe 2.3024 KVaHr , if recieved 12
	   then 0.0012 KVaHr. Returns 0 if not supported."
::= { edPowerMgmtPDU1PhasesTableInstantaneousPowerValue 1 }


edPowerMgmtPDU1PhasesTableInstantaneousPowerPhase2 OBJECT-TYPE
        SYNTAX             Integer32
         ACCESS         read-only
        STATUS             mandatory
        DESCRIPTION
           "Instantaneous Power(KWatt) of Y Phase if recieved 23024 then actual value in decimal willbe 2.3024 KVaHr , if recieved 12
	   then 0.0012 KVaHr. Returns 0 if not supported."
::= { edPowerMgmtPDU1PhasesTableInstantaneousPowerValue 2 }


edPowerMgmtPDU1PhasesTableInstantaneousPowerPhase3 OBJECT-TYPE
        SYNTAX             Integer32
         ACCESS         read-only
        STATUS             mandatory
        DESCRIPTION
          "Instantaneous Power(KWatt) of B Phase if recieved 23024 then actual value in decimal willbe 2.3024 KVaHr , if recieved 12
	   then 0.0012 KVaHr. Returns 0 if not supported."
::= { edPowerMgmtPDU1PhasesTableInstantaneousPowerValue 3 }


edPowerMgmtPDU1PhasesTablePowerFactorPhase1 OBJECT-TYPE
        SYNTAX             Integer32
         ACCESS         read-only
        STATUS             mandatory
        DESCRIPTION
        "average of powerfactor(pF) R Phase.The recieved value 
		if 9999 then actual value in decimal willbe 99.99 pf , if recieved 12
		then 0.12 pf. Returns 0 if not supported."
::= { edPowerMgmtPDU1PhasesTablePowerFactorValue 1 }

edPowerMgmtPDU1PhasesTablePowerFactorPhase2 OBJECT-TYPE
        SYNTAX             Integer32
         ACCESS         read-only
        STATUS             mandatory
        DESCRIPTION
         "average of powerfactor(pF) Y Phase.The recieved value 
		if 9999 then actual value in decimal willbe 99.99 pf , if recieved 12
		then 0.12 pf. Returns 0 if not supported."
::= { edPowerMgmtPDU1PhasesTablePowerFactorValue 2 }

edPowerMgmtPDU1PhasesTablePowerFactorPhase3 OBJECT-TYPE
        SYNTAX             Integer32
         ACCESS         read-only
        STATUS             mandatory
        DESCRIPTION
        "average of powerfactor(pF) B Phase.The recieved value 
		if 9999 then actual value in decimal willbe 99.99 pf , if recieved 12
		then 0.12 pf. Returns 0 if not supported."
::= { edPowerMgmtPDU1PhasesTablePowerFactorValue 3 }


edPowerMgmtPDU1TotalNumberOfSensor OBJECT-TYPE
        SYNTAX             Integer32
         ACCESS         read-only
        STATUS             mandatory
        DESCRIPTION
        "Number of Sensors managed by the appliance."
::= { edConectedPdu1Data 7 }


edPowerMgmtPDU1SensorsTable OBJECT IDENTIFIER ::= { edConectedPdu1Data 8 }

edPowerMgmtPDU1SensorsData OBJECT IDENTIFIER ::= { edPowerMgmtPDU1SensorsTable 1 }

edPowerMgmtPDU1SensorsTableNumber OBJECT IDENTIFIER ::= { edPowerMgmtPDU1SensorsData 1 }
edPowerMgmtPDU1SensorsTableSensorType OBJECT IDENTIFIER ::= { edPowerMgmtPDU1SensorsData 2 }
edPowerMgmtPDU1SensorsTableSensorValue OBJECT IDENTIFIER::= { edPowerMgmtPDU1SensorsData 3 }

edPowerMgmtPDU1SensorsTableSensor1 OBJECT-TYPE
        SYNTAX             Integer32
         ACCESS         read-only
        STATUS             mandatory
        DESCRIPTION
        "Number of the sensor in the PDU."
::= { edPowerMgmtPDU1SensorsTableNumber 1 }


edPowerMgmtPDU1SensorsTableSensor2 OBJECT-TYPE
        SYNTAX             Integer32
         ACCESS         read-only
        STATUS             mandatory
        DESCRIPTION
        "Number of the sensor in the PDU."
::= { edPowerMgmtPDU1SensorsTableNumber 2 }


edPowerMgmtPDU1SensorsTableSensor3 OBJECT-TYPE
        SYNTAX             Integer32
         ACCESS         read-only
        STATUS             mandatory
        DESCRIPTION
        "Number of the sensor in the PDU."
::= { edPowerMgmtPDU1SensorsTableNumber 3 }

edPowerMgmtPDU1SensorsTableSensor4 OBJECT-TYPE
        SYNTAX             Integer32
         ACCESS         read-only
        STATUS             mandatory
        DESCRIPTION
        "Number of the sensor in the PDU."
::= { edPowerMgmtPDU1SensorsTableNumber 4 }

edPowerMgmtPDU1SensorsTableSensorType1 OBJECT-TYPE
        SYNTAX INTEGER {
		humidity     (2),    			
		temprature   (1),
		nosens      (0)  
		
		}
         ACCESS         read-only
        STATUS             mandatory
        DESCRIPTION
        "returns value displaying type of Sensor."
::= { edPowerMgmtPDU1SensorsTableSensorType 1 }

edPowerMgmtPDU1SensorsTableSensorType2 OBJECT-TYPE
         SYNTAX INTEGER {
		humidity     (2),    			
		temprature   (1),
		nosens      (0)  
		
		}
         ACCESS         read-only
        STATUS             mandatory
        DESCRIPTION
        "returns value displaying type of Sensor."
::= { edPowerMgmtPDU1SensorsTableSensorType 2 }

edPowerMgmtPDU1SensorsTableSensorType3 OBJECT-TYPE
         SYNTAX INTEGER {
		humidity     (2),    			
		temprature   (1),
		nosens      (0)  
		
		}
         ACCESS         read-only
        STATUS             mandatory
        DESCRIPTION
        "returns value displaying type of Sensor."
::= { edPowerMgmtPDU1SensorsTableSensorType 3 }


edPowerMgmtPDU1SensorsTableSensorType4 OBJECT-TYPE
         SYNTAX INTEGER {
		humidity     (2),    			
		temprature   (1),
		nosens      (0)  
		
		}
         ACCESS         read-only
        STATUS             mandatory
        DESCRIPTION
        "returns value displaying type of Sensor."
::= { edPowerMgmtPDU1SensorsTableSensorType 4 }



edPowerMgmtPDU1SensorsTableSensorValueSensor1 OBJECT-TYPE
        SYNTAX             Integer32
         ACCESS         read-only
        STATUS             mandatory
        DESCRIPTION
        "returns value of Sensor
         Returns 0 if not supported."
::= { edPowerMgmtPDU1SensorsTableSensorValue 1 }

edPowerMgmtPDU1SensorsTableSensorValueSensor2 OBJECT-TYPE
        SYNTAX             Integer32
         ACCESS         read-only
        STATUS             mandatory
        DESCRIPTION
        "returns value of Sensor
         Returns 0 if not supported."
::= { edPowerMgmtPDU1SensorsTableSensorValue 2 }

edPowerMgmtPDU1SensorsTableSensorValueSensor3 OBJECT-TYPE
        SYNTAX             Integer32
         ACCESS         read-only
        STATUS             mandatory
        DESCRIPTION
        "returns value of Sensor
         Returns 0 if not supported."
::= { edPowerMgmtPDU1SensorsTableSensorValue 3 }

edPowerMgmtPDU1SensorsTableSensorValueSensor4 OBJECT-TYPE
        SYNTAX             Integer32
         ACCESS         read-only
        STATUS             mandatory
        DESCRIPTION
        "returns value of Sensor
         Returns 0 if not supported."
::= { edPowerMgmtPDU1SensorsTableSensorValue 4 }

----------- Daisy Chaining pduData 1 Ends ----------------------

----------- Daisy Chaining pduData 2  ----------------------




edConectedPdu2Data OBJECT IDENTIFIER::= { edConnectedPduMgmt 2 }

edPowerMgmtPDU2TableData OBJECT IDENTIFIER::= { edConectedPdu2Data 1 }

edPowerMgmtPDU2TableNumber       OBJECT-TYPE
        SYNTAX             Integer32
         ACCESS         read-only
        STATUS             mandatory
        DESCRIPTION
        "Index Number"
::= { edPowerMgmtPDU2TableData 1 }

edPowerMgmtPDU2TableProductCode      OBJECT-TYPE
        SYNTAX             DisplayString
         ACCESS         read-only
        STATUS             mandatory
        DESCRIPTION
        "Version of the PDU firmware.
         Returns N/A if not applicable."
::= { edPowerMgmtPDU2TableData 2 }



edPowerMgmtPDU2TableSerialNumber OBJECT-TYPE
        SYNTAX             Integer32
         ACCESS         read-only
        STATUS             mandatory
        DESCRIPTION
        "Number of outlets of the PDU."
::= { edPowerMgmtPDU2TableData 3 }

edPowerMgmtPDU2TableFirmwareVersion       OBJECT-TYPE
        SYNTAX             DisplayString
         ACCESS         read-only
        STATUS             mandatory
        DESCRIPTION
        "Version of the PDU firmware.
         Returns N/A if not applicable."
::= { edPowerMgmtPDU2TableData 4 }



edPowerMgmtPDU2TableNumberOfOutlets OBJECT-TYPE
        SYNTAX             Integer32
         ACCESS         read-only
        STATUS             mandatory
        DESCRIPTION
        "Number of outlets of the PDU."
::= { edPowerMgmtPDU2TableData 5 }

edPowerMgmtPDU2TableNumberOfPhases OBJECT-TYPE
        SYNTAX             Integer32
         ACCESS         read-only
        STATUS             mandatory
        DESCRIPTION
        "Number of phases of the PDU."
::= { edPowerMgmtPDU2TableData 6 }


edPowerMgmtPDU2TableNumberOfSensors OBJECT-TYPE
        SYNTAX             Integer32
         ACCESS         read-only
        STATUS             mandatory
        DESCRIPTION
        "Number of sensors in the PDU."
::= { edPowerMgmtPDU2TableData 7 }



edPowerMgmtPDU2TableVendor   OBJECT-TYPE
        SYNTAX             DisplayString
         ACCESS         	  read-only
        STATUS             mandatory
        DESCRIPTION
        "Vendor of the PDU.
         Returns N/A if not applicable."
::= { edPowerMgmtPDU2TableData 8 }


edPowerMgmtPDU2AggrInfoTable OBJECT IDENTIFIER::= { edConectedPdu2Data 2 }

edPowerMgmtPDU2AggrsData OBJECT IDENTIFIER::= { edPowerMgmtPDU2AggrInfoTable 1 }


edPowerMgmtPDU2AggrInfoNumber       OBJECT-TYPE
        SYNTAX             		Integer32
         ACCESS         			read-only
        STATUS             		mandatory
        DESCRIPTION
        "Index Number"
::= { edPowerMgmtPDU2AggrsData 1 }
 


edPowerMgmtPDU2AggrInfoTableVoltageValue OBJECT-TYPE
        SYNTAX             Integer32
         ACCESS         read-only
        STATUS             mandatory
        DESCRIPTION
		"Aggrgate voltage of phase is (if vRphase R > vYphase && vRphase R > vBphase) 
		aggregate voltage of R Phase .The recieved value 
		if 23024 then actual value in decimal willbe 230.24 Volts ,
		if recieved 12 then 0.12 Volt. Returns 0 if not supported."
::= { edPowerMgmtPDU2AggrsData 2 }


edPowerMgmtPDU2AggrInfoTableCurrentValue OBJECT-TYPE
        SYNTAX             Integer32
         ACCESS         read-only
        STATUS             mandatory
        DESCRIPTION
        "Addition of mandatory of all Outlet.The recieved value 
		if 1234 then actual value in decimal willbe 12.34 Amp, if recieved 
		value is 12 then 0.12 Amp .Returns 0 if not supported."
::= { edPowerMgmtPDU2AggrsData 3 }


edPowerMgmtPDU2AggrInfoTableApearentEnergyValue OBJECT-TYPE
        SYNTAX             Integer32
         ACCESS         read-only
        STATUS             mandatory
        DESCRIPTION
       "addition of ApearentEnergy(KVaHr) of all outlet.The recieved value
	   if 23024 then actual value in decimal willbe 2.3024 KVaHr , if recieved 12
	   then 0.0012 KVaHr. Returns 0 if not supported."
::= { edPowerMgmtPDU2AggrsData 4 }


edPowerMgmtPDU2AggrInfoTableReactiveEnergyValue OBJECT-TYPE
        SYNTAX             Integer32
         ACCESS         read-only
        STATUS             mandatory
        DESCRIPTION
         "addition of ReactiveEnergy(KVarHr) of all outlet.The recieved value 
		 if 23024 then actual value in decimal willbe 2.3024 KVarHr , if recieved 12 
		 then 0.0012 KVarHr. Returns 0 if not supported."
::= { edPowerMgmtPDU2AggrsData 5 }

edPowerMgmtPDU2AggrInfoTableActiveEnergyValue OBJECT-TYPE
        SYNTAX             Integer32
         ACCESS         read-only
        STATUS             mandatory
        DESCRIPTION
      "addition of ActiveEnergy(KWattHr) of all outlets.The recieved value 
	  if 23024 then actual value in decimal willbe 2.3024 KWattHr , if recieved 12
	  then 0.0012 KWattHr. Returns 0 if not supported."
::= { edPowerMgmtPDU2AggrsData 6 }


edPowerMgmtPDU2AggrInfoTableInstantaneousPowerValue OBJECT-TYPE
        SYNTAX             Integer32
         ACCESS         read-only
        STATUS             mandatory
        DESCRIPTION
      "addition of  Instantaneous Power(KWatt) of all outlet.The recieved value 
	  if 230 then actual value in decimal willbe 2.30 KWatt , if recieved 12 
	  then 0.12 KWatt. Returns 0 if not supported."
::= { edPowerMgmtPDU2AggrsData 7 }

edPowerMgmtPDU2AggrInfoTablePowerFactorValue OBJECT-TYPE
        SYNTAX             Integer32
         ACCESS         read-only
        STATUS             mandatory
        DESCRIPTION
      	"average of powerfactor(pF) of all outlet.The recieved value 
		if 9999 then actual value in decimal willbe 99.99 pf , if recieved 12
		then 0.12 pf. Returns 0 if not supported."

::= { edPowerMgmtPDU2AggrsData 8 }


edPowerMgmtPDU2TotalNumberOfOutlets OBJECT-TYPE
        SYNTAX             Integer32
         ACCESS         read-only
        STATUS             mandatory
        DESCRIPTION
        "Number of outlets managed by the appliance."
::= { edConectedPdu2Data 3 }
 


edPowerMgmtPDU2OutletsTable OBJECT IDENTIFIER::= { edConectedPdu2Data 4 }

edPowerMgmtPDU2OutletData OBJECT IDENTIFIER::= { edPowerMgmtPDU2OutletsTable 1 }

edPowerMgmtPDU2OutletsTableIndex        			OBJECT IDENTIFIER::= { edPowerMgmtPDU2OutletData 1 }
edPowerMgmtPDU2OutletsTableIndexNumber        		OBJECT IDENTIFIER::= { edPowerMgmtPDU2OutletsTableIndex 1 }

edPowerMgmtPDU2OutletsTableVoltage        			OBJECT IDENTIFIER::= { edPowerMgmtPDU2OutletData 2 }
edPowerMgmtPDU2OutletsTableVoltageValue        		OBJECT IDENTIFIER::= { edPowerMgmtPDU2OutletsTableVoltage 1 }
edPowerMgmtPDU2OutletsTableCurrent       	 		OBJECT IDENTIFIER::= { edPowerMgmtPDU2OutletData 3 }
edPowerMgmtPDU2OutletsTableCurrentValue        		OBJECT IDENTIFIER::= { edPowerMgmtPDU2OutletsTableCurrent 1 }
edPowerMgmtPDU2OutletsTableApearentEnergy   		OBJECT IDENTIFIER::= { edPowerMgmtPDU2OutletData 4 }
edPowerMgmtPDU2OutletsTableApearentEnergyValue      OBJECT IDENTIFIER::= { edPowerMgmtPDU2OutletsTableApearentEnergy 1 }
edPowerMgmtPDU2OutletsTableReactiveEnergy      		OBJECT IDENTIFIER::= { edPowerMgmtPDU2OutletData 5 }
edPowerMgmtPDU2OutletsTableReactiveEnergyValue      OBJECT IDENTIFIER::= { edPowerMgmtPDU2OutletsTableReactiveEnergy 1 }
edPowerMgmtPDU2OutletsTableActiveEnergy  			OBJECT IDENTIFIER::= { edPowerMgmtPDU2OutletData 6 }
edPowerMgmtPDU2OutletsTableActiveEnergyValue        OBJECT IDENTIFIER::= { edPowerMgmtPDU2OutletsTableActiveEnergy 1 }
edPowerMgmtPDU2OutletsTableInstantaneousPower  		OBJECT IDENTIFIER::= { edPowerMgmtPDU2OutletData 7 }
edPowerMgmtPDU2OutletsTableInstantaneousPowerValue  OBJECT IDENTIFIER::= { edPowerMgmtPDU2OutletsTableInstantaneousPower 1 }
edPowerMgmtPDU2OutletsTablePowerFactor    			OBJECT IDENTIFIER::= { edPowerMgmtPDU2OutletData 8 }
edPowerMgmtPDU2OutletsTablePowerFactorValue        	OBJECT IDENTIFIER::= { edPowerMgmtPDU2OutletsTablePowerFactor 1 }
edPowerMgmtPDU2OutletsTableFreq    					OBJECT IDENTIFIER::= { edPowerMgmtPDU2OutletData 9 }
edPowerMgmtPDU2OutletsTableFreqValue        		OBJECT IDENTIFIER::= { edPowerMgmtPDU2OutletsTableFreq 1 }
edPowerMgmtPDU2OutletsTableOutletswitching        	OBJECT IDENTIFIER::= { edPowerMgmtPDU2OutletData 10 }
edPowerMgmtPDU2OutletsTableOutletControl        	OBJECT IDENTIFIER::= { edPowerMgmtPDU2OutletsTableOutletswitching 1 }





edPowerMgmtPDU2OutletsTableIndexNumber1 OBJECT-TYPE
        SYNTAX             Integer32
         ACCESS         read-only
        STATUS             mandatory
        DESCRIPTION
         "Index Number of the outlet in the PDU."
::= { edPowerMgmtPDU2OutletsTableIndexNumber 1 }


edPowerMgmtPDU2OutletsTableIndexNumber2 OBJECT-TYPE
        SYNTAX             Integer32
         ACCESS         read-only
        STATUS             mandatory
        DESCRIPTION
         "Index Number of the outlet in the PDU."
::= { edPowerMgmtPDU2OutletsTableIndexNumber 2 }

edPowerMgmtPDU2OutletsTableIndexNumber3 OBJECT-TYPE
        SYNTAX             Integer32
         ACCESS         read-only
        STATUS             mandatory
        DESCRIPTION
        "Index Number of the outlet in the PDU."
::= { edPowerMgmtPDU2OutletsTableIndexNumber 3 }


edPowerMgmtPDU2OutletsTableIndexNumber4 OBJECT-TYPE
        SYNTAX             Integer32
         ACCESS         read-only
        STATUS             mandatory
        DESCRIPTION
        "Index Number of the outlet in the PDU."
::= { edPowerMgmtPDU2OutletsTableIndexNumber 4 }


edPowerMgmtPDU2OutletsTableIndexNumber5 OBJECT-TYPE
        SYNTAX             Integer32
         ACCESS         read-only
        STATUS             mandatory
        DESCRIPTION
        "Index Number of the outlet in the PDU."
::= { edPowerMgmtPDU2OutletsTableIndexNumber 5 }


edPowerMgmtPDU2OutletsTableIndexNumber6 OBJECT-TYPE
        SYNTAX             Integer32
         ACCESS         read-only
        STATUS             mandatory
        DESCRIPTION
         "Index Number of the outlet in the PDU."
::= { edPowerMgmtPDU2OutletsTableIndexNumber 6 }


edPowerMgmtPDU2OutletsTableIndexNumber7 OBJECT-TYPE
        SYNTAX             Integer32
         ACCESS         read-only
        STATUS             mandatory
        DESCRIPTION
        "Index Number of the outlet in the PDU."
::= { edPowerMgmtPDU2OutletsTableIndexNumber 7 }


edPowerMgmtPDU2OutletsTableIndexNumber8 OBJECT-TYPE
        SYNTAX             Integer32
         ACCESS         read-only
        STATUS             mandatory
        DESCRIPTION
       "Index Number of the outlet in the PDU."
::= { edPowerMgmtPDU2OutletsTableIndexNumber 8 }


edPowerMgmtPDU2OutletsTableIndexNumber9 OBJECT-TYPE
        SYNTAX             Integer32
         ACCESS         read-only
        STATUS             mandatory
        DESCRIPTION
         "Index Number of the outlet in the PDU."
::= { edPowerMgmtPDU2OutletsTableIndexNumber 9 }


edPowerMgmtPDU2OutletsTableIndexNumber10 OBJECT-TYPE
        SYNTAX             Integer32
         ACCESS         read-only
        STATUS             mandatory
        DESCRIPTION
        "Index Number of the outlet in the PDU."
::= { edPowerMgmtPDU2OutletsTableIndexNumber 10 }


edPowerMgmtPDU2OutletsTableIndexNumber11 OBJECT-TYPE
        SYNTAX             Integer32
         ACCESS         read-only
        STATUS             mandatory
        DESCRIPTION
      "Index Number of the outlet in the PDU."
::= { edPowerMgmtPDU2OutletsTableIndexNumber 11 }


edPowerMgmtPDU2OutletsTableIndexNumber12 OBJECT-TYPE
        SYNTAX             Integer32
         ACCESS         read-only
        STATUS             mandatory
        DESCRIPTION
       "Index Number of the outlet in the PDU."
::= { edPowerMgmtPDU2OutletsTableIndexNumber 12 }


edPowerMgmtPDU2OutletsTableIndexNumber13 OBJECT-TYPE
        SYNTAX             Integer32
         ACCESS         read-only
        STATUS             mandatory
        DESCRIPTION
        "Index Number of the outlet in the PDU."
::= { edPowerMgmtPDU2OutletsTableIndexNumber 13 }


edPowerMgmtPDU2OutletsTableIndexNumber14 OBJECT-TYPE
        SYNTAX             Integer32
         ACCESS         read-only
        STATUS             mandatory
        DESCRIPTION
       "Index Number of the outlet in the PDU."
::= { edPowerMgmtPDU2OutletsTableIndexNumber 14 }


edPowerMgmtPDU2OutletsTableIndexNumber15 OBJECT-TYPE
        SYNTAX             Integer32
         ACCESS         read-only
        STATUS             mandatory
        DESCRIPTION
       "Index Number of the outlet in the PDU."
::= { edPowerMgmtPDU2OutletsTableIndexNumber 15 }


edPowerMgmtPDU2OutletsTableIndexNumber16 OBJECT-TYPE
        SYNTAX             Integer32
         ACCESS         read-only
        STATUS             mandatory
        DESCRIPTION
      "Index Number of the outlet in the PDU."
::= { edPowerMgmtPDU2OutletsTableIndexNumber 16 }


edPowerMgmtPDU2OutletsTableIndexNumber17 OBJECT-TYPE
        SYNTAX             Integer32
         ACCESS         read-only
        STATUS             mandatory
        DESCRIPTION
       "Index Number of the outlet in the PDU."
::= { edPowerMgmtPDU2OutletsTableIndexNumber 17 }


edPowerMgmtPDU2OutletsTableIndexNumber18 OBJECT-TYPE
        SYNTAX             Integer32
         ACCESS         read-only
        STATUS             mandatory
        DESCRIPTION
          "Index Number of the outlet in the PDU."
::= { edPowerMgmtPDU2OutletsTableIndexNumber 18 }


edPowerMgmtPDU2OutletsTableIndexNumber19 OBJECT-TYPE
        SYNTAX             Integer32
         ACCESS         read-only
        STATUS             mandatory
        DESCRIPTION
          "Index Number of the outlet in the PDU."
::= { edPowerMgmtPDU2OutletsTableIndexNumber 19 }


edPowerMgmtPDU2OutletsTableIndexNumber20 OBJECT-TYPE
        SYNTAX             Integer32
         ACCESS         read-only
        STATUS             mandatory
        DESCRIPTION
          "Index Number of the outlet in the PDU."
::= { edPowerMgmtPDU2OutletsTableIndexNumber 20 }


edPowerMgmtPDU2OutletsTableIndexNumber21 OBJECT-TYPE
        SYNTAX             Integer32
         ACCESS         read-only
        STATUS             mandatory
        DESCRIPTION
          "Index Number of the outlet in the PDU."
::= { edPowerMgmtPDU2OutletsTableIndexNumber 21 }


edPowerMgmtPDU2OutletsTableIndexNumber22 OBJECT-TYPE
        SYNTAX             Integer32
         ACCESS         read-only
        STATUS             mandatory
        DESCRIPTION
          "Index Number of the outlet in the PDU."
::= { edPowerMgmtPDU2OutletsTableIndexNumber 22 }


edPowerMgmtPDU2OutletsTableIndexNumber23 OBJECT-TYPE
        SYNTAX             Integer32
         ACCESS         read-only
        STATUS             mandatory
        DESCRIPTION
          "Index Number of the outlet in the PDU."
::= { edPowerMgmtPDU2OutletsTableIndexNumber 23 }


edPowerMgmtPDU2OutletsTableIndexNumber24 OBJECT-TYPE
        SYNTAX             Integer32
         ACCESS         read-only
        STATUS             mandatory
        DESCRIPTION
          "Index Number of the outlet in the PDU."
::= { edPowerMgmtPDU2OutletsTableIndexNumber 24 }

edPowerMgmtPDU2OutletsTableIndexNumber25 OBJECT-TYPE
        SYNTAX             Integer32
         ACCESS         read-only
        STATUS             mandatory
        DESCRIPTION
          "Index Number of the outlet in the PDU."
::= { edPowerMgmtPDU2OutletsTableIndexNumber 25 }


edPowerMgmtPDU2OutletsTableIndexNumber26 OBJECT-TYPE
        SYNTAX             Integer32
         ACCESS         read-only
        STATUS             mandatory
        DESCRIPTION
          "Index Number of the outlet in the PDU."
::= { edPowerMgmtPDU2OutletsTableIndexNumber 26 }


edPowerMgmtPDU2OutletsTableIndexNumber27 OBJECT-TYPE
        SYNTAX             Integer32
         ACCESS         read-only
        STATUS             mandatory
        DESCRIPTION
          "Index Number of the outlet in the PDU."
::= { edPowerMgmtPDU2OutletsTableIndexNumber 27 }

edPowerMgmtPDU2OutletsTableIndexNumber28 OBJECT-TYPE
        SYNTAX             Integer32
         ACCESS         read-only
        STATUS             mandatory
        DESCRIPTION
          "Index Number of the outlet in the PDU."
::= { edPowerMgmtPDU2OutletsTableIndexNumber 28 }

edPowerMgmtPDU2OutletsTableIndexNumber29 OBJECT-TYPE
        SYNTAX             Integer32
         ACCESS         read-only
        STATUS             mandatory
        DESCRIPTION
          "Index Number of the outlet in the PDU."
::= { edPowerMgmtPDU2OutletsTableIndexNumber 29 }

edPowerMgmtPDU2OutletsTableIndexNumber30 OBJECT-TYPE
        SYNTAX             Integer32
         ACCESS         read-only
        STATUS             mandatory
        DESCRIPTION
          "Index Number of the outlet in the PDU."
::= { edPowerMgmtPDU2OutletsTableIndexNumber 30 }

edPowerMgmtPDU2OutletsTableIndexNumber31 OBJECT-TYPE
        SYNTAX             Integer32
         ACCESS         read-only
        STATUS             mandatory
        DESCRIPTION
          "Index Number of the outlet in the PDU."
::= { edPowerMgmtPDU2OutletsTableIndexNumber 31 }

edPowerMgmtPDU2OutletsTableIndexNumber32 OBJECT-TYPE
        SYNTAX             Integer32
         ACCESS         read-only
        STATUS             mandatory
        DESCRIPTION
          "Index Number of the outlet in the PDU."
::= { edPowerMgmtPDU2OutletsTableIndexNumber 32 }

edPowerMgmtPDU2OutletsTableIndexNumber33 OBJECT-TYPE
        SYNTAX             Integer32
         ACCESS         read-only
        STATUS             mandatory
        DESCRIPTION
          "Index Number of the outlet in the PDU."
::= { edPowerMgmtPDU2OutletsTableIndexNumber 33 }

edPowerMgmtPDU2OutletsTableIndexNumber34 OBJECT-TYPE
        SYNTAX             Integer32
         ACCESS         read-only
        STATUS             mandatory
        DESCRIPTION
          "Index Number of the outlet in the PDU."
::= { edPowerMgmtPDU2OutletsTableIndexNumber 34 }


edPowerMgmtPDU2OutletsTableIndexNumber35 OBJECT-TYPE
        SYNTAX             Integer32
         ACCESS         read-only
        STATUS             mandatory
        DESCRIPTION
          "Index Number of the outlet in the PDU."
::= { edPowerMgmtPDU2OutletsTableIndexNumber 35 }


edPowerMgmtPDU2OutletsTableIndexNumber36 OBJECT-TYPE
        SYNTAX             Integer32
         ACCESS         read-only
        STATUS             mandatory
        DESCRIPTION
          "Index Number of the outlet in the PDU."
::= { edPowerMgmtPDU2OutletsTableIndexNumber 36 }


edPowerMgmtPDU2OutletsTableIndexNumber37 OBJECT-TYPE
        SYNTAX             Integer32
         ACCESS         read-only
        STATUS             mandatory
        DESCRIPTION
          "Index Number of the outlet in the PDU."
::= { edPowerMgmtPDU2OutletsTableIndexNumber 37 }


edPowerMgmtPDU2OutletsTableIndexNumber38 OBJECT-TYPE
        SYNTAX             Integer32
         ACCESS         read-only
        STATUS             mandatory
        DESCRIPTION
          "Index Number of the outlet in the PDU."
::= { edPowerMgmtPDU2OutletsTableIndexNumber 38 }


edPowerMgmtPDU2OutletsTableIndexNumber39 OBJECT-TYPE
        SYNTAX             Integer32
         ACCESS         read-only
        STATUS             mandatory
        DESCRIPTION
          "Index Number of the outlet in the PDU."
::= { edPowerMgmtPDU2OutletsTableIndexNumber 39 }


edPowerMgmtPDU2OutletsTableIndexNumber40 OBJECT-TYPE
        SYNTAX             Integer32
         ACCESS         read-only
        STATUS             mandatory
        DESCRIPTION
          "Index Number of the outlet in the PDU."
::= { edPowerMgmtPDU2OutletsTableIndexNumber 40 }


edPowerMgmtPDU2OutletsTableIndexNumber41 OBJECT-TYPE
        SYNTAX             Integer32
         ACCESS         		read-only
        STATUS             mandatory
        DESCRIPTION
          "Index Number of the outlet in the PDU."
::= { edPowerMgmtPDU2OutletsTableIndexNumber 41 }


edPowerMgmtPDU2OutletsTableIndexNumber42 OBJECT-TYPE
        SYNTAX             Integer32
         ACCESS         read-only
        STATUS             mandatory
        DESCRIPTION
          "Index Number of the outlet in the PDU."
::= { edPowerMgmtPDU2OutletsTableIndexNumber 42 }







edPowerMgmtPDU2OutletsTableVoltageOutlet1 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 1 }


edPowerMgmtPDU2OutletsTableVoltageOutlet2 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 2 }

edPowerMgmtPDU2OutletsTableVoltageOutlet3 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 3 }


edPowerMgmtPDU2OutletsTableVoltageOutlet4 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 4 }


edPowerMgmtPDU2OutletsTableVoltageOutlet5 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 5 }


edPowerMgmtPDU2OutletsTableVoltageOutlet6 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 6 }


edPowerMgmtPDU2OutletsTableVoltageOutlet7 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 7 }


edPowerMgmtPDU2OutletsTableVoltageOutlet8 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 8 }


edPowerMgmtPDU2OutletsTableVoltageOutlet9 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 9 }


edPowerMgmtPDU2OutletsTableVoltageOutlet10 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 10 }


edPowerMgmtPDU2OutletsTableVoltageOutlet11 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 11 }


edPowerMgmtPDU2OutletsTableVoltageOutlet12 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 12 }


edPowerMgmtPDU2OutletsTableVoltageOutlet13 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 13 }


edPowerMgmtPDU2OutletsTableVoltageOutlet14 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 14 }


edPowerMgmtPDU2OutletsTableVoltageOutlet15 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 15 }


edPowerMgmtPDU2OutletsTableVoltageOutlet16 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 16 }


edPowerMgmtPDU2OutletsTableVoltageOutlet17 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 17 }


edPowerMgmtPDU2OutletsTableVoltageOutlet18 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 18 }


edPowerMgmtPDU2OutletsTableVoltageOutlet19 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 19 }


edPowerMgmtPDU2OutletsTableVoltageOutlet20 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 20 }


edPowerMgmtPDU2OutletsTableVoltageOutlet21 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 21 }


edPowerMgmtPDU2OutletsTableVoltageOutlet22 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 22 }


edPowerMgmtPDU2OutletsTableVoltageOutlet23 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 23 }


edPowerMgmtPDU2OutletsTableVoltageOutlet24 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 24 }

edPowerMgmtPDU2OutletsTableVoltageOutlet25 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 25 }


edPowerMgmtPDU2OutletsTableVoltageOutlet26 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 26 }


edPowerMgmtPDU2OutletsTableVoltageOutlet27 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 27 }

edPowerMgmtPDU2OutletsTableVoltageOutlet28 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 28 }

edPowerMgmtPDU2OutletsTableVoltageOutlet29 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 29 }

edPowerMgmtPDU2OutletsTableVoltageOutlet30 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 30 }

edPowerMgmtPDU2OutletsTableVoltageOutlet31 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 31 }

edPowerMgmtPDU2OutletsTableVoltageOutlet32 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 32 }

edPowerMgmtPDU2OutletsTableVoltageOutlet33 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 33 }

edPowerMgmtPDU2OutletsTableVoltageOutlet34 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 34 }


edPowerMgmtPDU2OutletsTableVoltageOutlet35 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 35 }


edPowerMgmtPDU2OutletsTableVoltageOutlet36 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 36 }


edPowerMgmtPDU2OutletsTableVoltageOutlet37 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 37 }


edPowerMgmtPDU2OutletsTableVoltageOutlet38 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 38 }


edPowerMgmtPDU2OutletsTableVoltageOutlet39 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 39 }


edPowerMgmtPDU2OutletsTableVoltageOutlet40 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 40 }


edPowerMgmtPDU2OutletsTableVoltageOutlet41 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 41 }


edPowerMgmtPDU2OutletsTableVoltageOutlet42 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU2OutletsTableVoltageValue 42 }








edPowerMgmtPDU2OutletsTableCurrentOutlet1 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU2OutletsTableCurrentValue 1 }


edPowerMgmtPDU2OutletsTableCurrentOutlet2 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU2OutletsTableCurrentValue 2 }

edPowerMgmtPDU2OutletsTableCurrentOutlet3 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU2OutletsTableCurrentValue 3 }


edPowerMgmtPDU2OutletsTableCurrentOutlet4 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU2OutletsTableCurrentValue 4 }


edPowerMgmtPDU2OutletsTableCurrentOutlet5 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU2OutletsTableCurrentValue 5 }


edPowerMgmtPDU2OutletsTableCurrentOutlet6 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU2OutletsTableCurrentValue 6 }


edPowerMgmtPDU2OutletsTableCurrentOutlet7 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU2OutletsTableCurrentValue 7 }


edPowerMgmtPDU2OutletsTableCurrentOutlet8 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU2OutletsTableCurrentValue 8 }


edPowerMgmtPDU2OutletsTableCurrentOutlet9 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU2OutletsTableCurrentValue 9 }


edPowerMgmtPDU2OutletsTableCurrentOutlet10 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU2OutletsTableCurrentValue 10 }


edPowerMgmtPDU2OutletsTableCurrentOutlet11 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU2OutletsTableCurrentValue 11 }


edPowerMgmtPDU2OutletsTableCurrentOutlet12 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU2OutletsTableCurrentValue 12 }


edPowerMgmtPDU2OutletsTableCurrentOutlet13 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU2OutletsTableCurrentValue 13 }


edPowerMgmtPDU2OutletsTableCurrentOutlet14 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU2OutletsTableCurrentValue 14 }


edPowerMgmtPDU2OutletsTableCurrentOutlet15 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU2OutletsTableCurrentValue 15 }


edPowerMgmtPDU2OutletsTableCurrentOutlet16 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU2OutletsTableCurrentValue 16 }


edPowerMgmtPDU2OutletsTableCurrentOutlet17 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU2OutletsTableCurrentValue 17 }


edPowerMgmtPDU2OutletsTableCurrentOutlet18 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU2OutletsTableCurrentValue 18 }


edPowerMgmtPDU2OutletsTableCurrentOutlet19 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU2OutletsTableCurrentValue 19 }


edPowerMgmtPDU2OutletsTableCurrentOutlet20 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU2OutletsTableCurrentValue 20 }


edPowerMgmtPDU2OutletsTableCurrentOutlet21 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU2OutletsTableCurrentValue 21 }


edPowerMgmtPDU2OutletsTableCurrentOutlet22 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU2OutletsTableCurrentValue 22 }


edPowerMgmtPDU2OutletsTableCurrentOutlet23 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU2OutletsTableCurrentValue 23 }


edPowerMgmtPDU2OutletsTableCurrentOutlet24 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU2OutletsTableCurrentValue 24 }

edPowerMgmtPDU2OutletsTableCurrentOutlet25 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU2OutletsTableCurrentValue 25 }


edPowerMgmtPDU2OutletsTableCurrentOutlet26 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU2OutletsTableCurrentValue 26 }


edPowerMgmtPDU2OutletsTableCurrentOutlet27 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU2OutletsTableCurrentValue 27 }

edPowerMgmtPDU2OutletsTableCurrentOutlet28 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU2OutletsTableCurrentValue 28 }

edPowerMgmtPDU2OutletsTableCurrentOutlet29 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU2OutletsTableCurrentValue 29 }

edPowerMgmtPDU2OutletsTableCurrentOutlet30 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU2OutletsTableCurrentValue 30 }

edPowerMgmtPDU2OutletsTableCurrentOutlet31 OBJECT-TYPE
        SYNTAX             Integer32
         ACCESS         read-only
        STATUS             mandatory
        DESCRIPTION
      "Actual value of Current for the outlet(Amp).The recieved value 
		if 1234 then actual value in decimal willbe 12.34 Amp, if recieved 
		value is 12 then 0.12 Amp .Returns 0 if not supported."
::= { edPowerMgmtPDU2OutletsTableCurrentValue 31 }

edPowerMgmtPDU2OutletsTableCurrentOutlet32 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU2OutletsTableCurrentValue 32 }

edPowerMgmtPDU2OutletsTableCurrentOutlet33 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU2OutletsTableCurrentValue 33 }

edPowerMgmtPDU2OutletsTableCurrentOutlet34 OBJECT-TYPE
        SYNTAX             Integer32
         ACCESS         read-only
        STATUS             mandatory
        DESCRIPTION
       "Actual value of Current for the outlet(Amp).The recieved value 
		if 1234 then actual value in decimal willbe 12.34 Amp, if recieved 
		value is 12 then 0.12 Amp .Returns 0 if not supported."
::= { edPowerMgmtPDU2OutletsTableCurrentValue 34 }


edPowerMgmtPDU2OutletsTableCurrentOutlet35 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU2OutletsTableCurrentValue 35 }


edPowerMgmtPDU2OutletsTableCurrentOutlet36 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU2OutletsTableCurrentValue 36 }


edPowerMgmtPDU2OutletsTableCurrentOutlet37 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU2OutletsTableCurrentValue 37 }


edPowerMgmtPDU2OutletsTableCurrentOutlet38 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU2OutletsTableCurrentValue 38 }


edPowerMgmtPDU2OutletsTableCurrentOutlet39 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU2OutletsTableCurrentValue 39 }


edPowerMgmtPDU2OutletsTableCurrentOutlet40 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU2OutletsTableCurrentValue 40 }


edPowerMgmtPDU2OutletsTableCurrentOutlet41 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU2OutletsTableCurrentValue 41 }


edPowerMgmtPDU2OutletsTableCurrentOutlet42 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU2OutletsTableCurrentValue 42 }









edPowerMgmtPDU2OutletsTableApearentEnergyOutlet1 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 1 }


edPowerMgmtPDU2OutletsTableApearentEnergyOutlet2 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 2 }

edPowerMgmtPDU2OutletsTableApearentEnergyOutlet3 OBJECT-TYPE
        SYNTAX             Integer32
         ACCESS         read-only
        STATUS             mandatory
        DESCRIPTION
      "Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 3 }


edPowerMgmtPDU2OutletsTableApearentEnergyOutlet4 OBJECT-TYPE
        SYNTAX             Integer32
         ACCESS         read-only
        STATUS             mandatory
        DESCRIPTION
      "Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 4 }


edPowerMgmtPDU2OutletsTableApearentEnergyOutlet5 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 5 }


edPowerMgmtPDU2OutletsTableApearentEnergyOutlet6 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 6 }


edPowerMgmtPDU2OutletsTableApearentEnergyOutlet7 OBJECT-TYPE
        SYNTAX             Integer32
         ACCESS         read-only
        STATUS             mandatory
        DESCRIPTION
        "Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 7 }


edPowerMgmtPDU2OutletsTableApearentEnergyOutlet8 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 8 }


edPowerMgmtPDU2OutletsTableApearentEnergyOutlet9 OBJECT-TYPE
        SYNTAX             Integer32
         ACCESS         read-only
        STATUS             mandatory
        DESCRIPTION
     "Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 9 }


edPowerMgmtPDU2OutletsTableApearentEnergyOutlet10 OBJECT-TYPE
        SYNTAX             Integer32
         ACCESS         read-only
        STATUS             mandatory
        DESCRIPTION
     "Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 10 }


edPowerMgmtPDU2OutletsTableApearentEnergyOutlet11 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 11 }


edPowerMgmtPDU2OutletsTableApearentEnergyOutlet12 OBJECT-TYPE
        SYNTAX             Integer32
         ACCESS         read-only
        STATUS             mandatory
        DESCRIPTION
   "Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 12 }


edPowerMgmtPDU2OutletsTableApearentEnergyOutlet13 OBJECT-TYPE
        SYNTAX             Integer32
         ACCESS         read-only
        STATUS             mandatory
        DESCRIPTION
      "Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 13 }


edPowerMgmtPDU2OutletsTableApearentEnergyOutlet14 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 14 }


edPowerMgmtPDU2OutletsTableApearentEnergyOutlet15 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 15 }


edPowerMgmtPDU2OutletsTableApearentEnergyOutlet16 OBJECT-TYPE
        SYNTAX             Integer32
         ACCESS         read-only
        STATUS             mandatory
        DESCRIPTION
          "Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 16 }


edPowerMgmtPDU2OutletsTableApearentEnergyOutlet17 OBJECT-TYPE
        SYNTAX             Integer32
         ACCESS         read-only
        STATUS             mandatory
        DESCRIPTION
          "Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 17 }


edPowerMgmtPDU2OutletsTableApearentEnergyOutlet18 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 18 }


edPowerMgmtPDU2OutletsTableApearentEnergyOutlet19 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 19 }


edPowerMgmtPDU2OutletsTableApearentEnergyOutlet20 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 20 }


edPowerMgmtPDU2OutletsTableApearentEnergyOutlet21 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 21 }


edPowerMgmtPDU2OutletsTableApearentEnergyOutlet22 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 22 }


edPowerMgmtPDU2OutletsTableApearentEnergyOutlet23 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 23 }


edPowerMgmtPDU2OutletsTableApearentEnergyOutlet24 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 24 }

edPowerMgmtPDU2OutletsTableApearentEnergyOutlet25 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 25 }


edPowerMgmtPDU2OutletsTableApearentEnergyOutlet26 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 26 }


edPowerMgmtPDU2OutletsTableApearentEnergyOutlet27 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 27 }

edPowerMgmtPDU2OutletsTableApearentEnergyOutlet28 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 28 }

edPowerMgmtPDU2OutletsTableApearentEnergyOutlet29 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 29 }

edPowerMgmtPDU2OutletsTableApearentEnergyOutlet30 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 30 }

edPowerMgmtPDU2OutletsTableApearentEnergyOutlet31 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 31 }

edPowerMgmtPDU2OutletsTableApearentEnergyOutlet32 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 32 }

edPowerMgmtPDU2OutletsTableApearentEnergyOutlet33 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 33 }

edPowerMgmtPDU2OutletsTableApearentEnergyOutlet34 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 34 }


edPowerMgmtPDU2OutletsTableApearentEnergyOutlet35 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 35 }


edPowerMgmtPDU2OutletsTableApearentEnergyOutlet36 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 36 }


edPowerMgmtPDU2OutletsTableApearentEnergyOutlet37 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 37 }


edPowerMgmtPDU2OutletsTableApearentEnergyOutlet38 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 38 }


edPowerMgmtPDU2OutletsTableApearentEnergyOutlet39 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 39 }


edPowerMgmtPDU2OutletsTableApearentEnergyOutlet40 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 40 }


edPowerMgmtPDU2OutletsTableApearentEnergyOutlet41 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 41 }


edPowerMgmtPDU2OutletsTableApearentEnergyOutlet42 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU2OutletsTableApearentEnergyValue 42 }





edPowerMgmtPDU2OutletsTableReactiveEnergyOutlet1 OBJECT-TYPE
        SYNTAX             Integer32
         ACCESS         read-only
        STATUS             mandatory
        DESCRIPTION
		"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 1 }


edPowerMgmtPDU2OutletsTableReactiveEnergyOutlet2 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 2 }

edPowerMgmtPDU2OutletsTableReactiveEnergyOutlet3 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 3 }


edPowerMgmtPDU2OutletsTableReactiveEnergyOutlet4 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 4 }


edPowerMgmtPDU2OutletsTableReactiveEnergyOutlet5 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 5 }


edPowerMgmtPDU2OutletsTableReactiveEnergyOutlet6 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 6 }


edPowerMgmtPDU2OutletsTableReactiveEnergyOutlet7 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 7 }


edPowerMgmtPDU2OutletsTableReactiveEnergyOutlet8 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 8 }


edPowerMgmtPDU2OutletsTableReactiveEnergyOutlet9 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 9 }


edPowerMgmtPDU2OutletsTableReactiveEnergyOutlet10 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 10 }


edPowerMgmtPDU2OutletsTableReactiveEnergyOutlet11 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 11 }


edPowerMgmtPDU2OutletsTableReactiveEnergyOutlet12 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 12 }


edPowerMgmtPDU2OutletsTableReactiveEnergyOutlet13 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 13 }


edPowerMgmtPDU2OutletsTableReactiveEnergyOutlet14 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 14 }


edPowerMgmtPDU2OutletsTableReactiveEnergyOutlet15 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 15 }


edPowerMgmtPDU2OutletsTableReactiveEnergyOutlet16 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 16 }


edPowerMgmtPDU2OutletsTableReactiveEnergyOutlet17 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 17 }


edPowerMgmtPDU2OutletsTableReactiveEnergyOutlet18 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 18 }


edPowerMgmtPDU2OutletsTableReactiveEnergyOutlet19 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 19 }


edPowerMgmtPDU2OutletsTableReactiveEnergyOutlet20 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 20 }


edPowerMgmtPDU2OutletsTableReactiveEnergyOutlet21 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 21 }


edPowerMgmtPDU2OutletsTableReactiveEnergyOutlet22 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 22 }


edPowerMgmtPDU2OutletsTableReactiveEnergyOutlet23 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 23 }


edPowerMgmtPDU2OutletsTableReactiveEnergyOutlet24 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 24 }

edPowerMgmtPDU2OutletsTableReactiveEnergyOutlet25 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 25 }


edPowerMgmtPDU2OutletsTableReactiveEnergyOutlet26 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 26 }


edPowerMgmtPDU2OutletsTableReactiveEnergyOutlet27 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 27 }

edPowerMgmtPDU2OutletsTableReactiveEnergyOutlet28 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 28 }

edPowerMgmtPDU2OutletsTableReactiveEnergyOutlet29 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 29 }

edPowerMgmtPDU2OutletsTableReactiveEnergyOutlet30 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 30 }

edPowerMgmtPDU2OutletsTableReactiveEnergyOutlet31 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 31 }

edPowerMgmtPDU2OutletsTableReactiveEnergyOutlet32 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 32 }

edPowerMgmtPDU2OutletsTableReactiveEnergyOutlet33 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 33 }

edPowerMgmtPDU2OutletsTableReactiveEnergyOutlet34 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 34 }


edPowerMgmtPDU2OutletsTableReactiveEnergyOutlet35 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 35 }


edPowerMgmtPDU2OutletsTableReactiveEnergyOutlet36 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 36 }


edPowerMgmtPDU2OutletsTableReactiveEnergyOutlet37 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 37 }


edPowerMgmtPDU2OutletsTableReactiveEnergyOutlet38 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 38 }


edPowerMgmtPDU2OutletsTableReactiveEnergyOutlet39 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 39 }


edPowerMgmtPDU2OutletsTableReactiveEnergyOutlet40 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 40 }


edPowerMgmtPDU2OutletsTableReactiveEnergyOutlet41 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 41 }


edPowerMgmtPDU2OutletsTableReactiveEnergyOutlet42 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU2OutletsTableReactiveEnergyValue 42 }




edPowerMgmtPDU2OutletsTableActiveEnergyOutlet1 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 1 }


edPowerMgmtPDU2OutletsTableActiveEnergyOutlet2 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 2 }

edPowerMgmtPDU2OutletsTableActiveEnergyOutlet3 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 3 }


edPowerMgmtPDU2OutletsTableActiveEnergyOutlet4 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 4 }


edPowerMgmtPDU2OutletsTableActiveEnergyOutlet5 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 5 }


edPowerMgmtPDU2OutletsTableActiveEnergyOutlet6 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 6 }


edPowerMgmtPDU2OutletsTableActiveEnergyOutlet7 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 7 }


edPowerMgmtPDU2OutletsTableActiveEnergyOutlet8 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 8 }


edPowerMgmtPDU2OutletsTableActiveEnergyOutlet9 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 9 }


edPowerMgmtPDU2OutletsTableActiveEnergyOutlet10 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 10 }


edPowerMgmtPDU2OutletsTableActiveEnergyOutlet11 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 11 }


edPowerMgmtPDU2OutletsTableActiveEnergyOutlet12 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 12 }


edPowerMgmtPDU2OutletsTableActiveEnergyOutlet13 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 13 }


edPowerMgmtPDU2OutletsTableActiveEnergyOutlet14 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 14 }


edPowerMgmtPDU2OutletsTableActiveEnergyOutlet15 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 15 }


edPowerMgmtPDU2OutletsTableActiveEnergyOutlet16 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 16 }


edPowerMgmtPDU2OutletsTableActiveEnergyOutlet17 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 17 }


edPowerMgmtPDU2OutletsTableActiveEnergyOutlet18 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 18 }


edPowerMgmtPDU2OutletsTableActiveEnergyOutlet19 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 19 }


edPowerMgmtPDU2OutletsTableActiveEnergyOutlet20 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 20 }


edPowerMgmtPDU2OutletsTableActiveEnergyOutlet21 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 21 }


edPowerMgmtPDU2OutletsTableActiveEnergyOutlet22 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 22 }


edPowerMgmtPDU2OutletsTableActiveEnergyOutlet23 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 23 }


edPowerMgmtPDU2OutletsTableActiveEnergyOutlet24 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 24 }

edPowerMgmtPDU2OutletsTableActiveEnergyOutlet25 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 25 }


edPowerMgmtPDU2OutletsTableActiveEnergyOutlet26 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 26 }


edPowerMgmtPDU2OutletsTableActiveEnergyOutlet27 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 27 }

edPowerMgmtPDU2OutletsTableActiveEnergyOutlet28 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 28 }

edPowerMgmtPDU2OutletsTableActiveEnergyOutlet29 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 29 }

edPowerMgmtPDU2OutletsTableActiveEnergyOutlet30 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 30 }

edPowerMgmtPDU2OutletsTableActiveEnergyOutlet31 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 31 }

edPowerMgmtPDU2OutletsTableActiveEnergyOutlet32 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 32 }

edPowerMgmtPDU2OutletsTableActiveEnergyOutlet33 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 33 }

edPowerMgmtPDU2OutletsTableActiveEnergyOutlet34 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 34 }


edPowerMgmtPDU2OutletsTableActiveEnergyOutlet35 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 35 }


edPowerMgmtPDU2OutletsTableActiveEnergyOutlet36 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 36 }


edPowerMgmtPDU2OutletsTableActiveEnergyOutlet37 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 37 }


edPowerMgmtPDU2OutletsTableActiveEnergyOutlet38 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 38 }


edPowerMgmtPDU2OutletsTableActiveEnergyOutlet39 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 39 }


edPowerMgmtPDU2OutletsTableActiveEnergyOutlet40 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 40 }


edPowerMgmtPDU2OutletsTableActiveEnergyOutlet41 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 41 }


edPowerMgmtPDU2OutletsTableActiveEnergyOutlet42 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU2OutletsTableActiveEnergyValue 42 }









edPowerMgmtPDU2OutletsTableInstantaneousPowerOutlet1 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 1 }


edPowerMgmtPDU2OutletsTableInstantaneousPowerOutlet2 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 2 }

edPowerMgmtPDU2OutletsTableInstantaneousPowerOutlet3 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 3 }


edPowerMgmtPDU2OutletsTableInstantaneousPowerOutlet4 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 4 }


edPowerMgmtPDU2OutletsTableInstantaneousPowerOutlet5 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 5 }


edPowerMgmtPDU2OutletsTableInstantaneousPowerOutlet6 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 6 }


edPowerMgmtPDU2OutletsTableInstantaneousPowerOutlet7 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 7 }


edPowerMgmtPDU2OutletsTableInstantaneousPowerOutlet8 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 8 }


edPowerMgmtPDU2OutletsTableInstantaneousPowerOutlet9 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 9 }


edPowerMgmtPDU2OutletsTableInstantaneousPowerOutlet10 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 10 }


edPowerMgmtPDU2OutletsTableInstantaneousPowerOutlet11 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 11 }


edPowerMgmtPDU2OutletsTableInstantaneousPowerOutlet12 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 12 }


edPowerMgmtPDU2OutletsTableInstantaneousPowerOutlet13 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 13 }


edPowerMgmtPDU2OutletsTableInstantaneousPowerOutlet14 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 14 }


edPowerMgmtPDU2OutletsTableInstantaneousPowerOutlet15 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 15 }


edPowerMgmtPDU2OutletsTableInstantaneousPowerOutlet16 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 16 }


edPowerMgmtPDU2OutletsTableInstantaneousPowerOutlet17 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 17 }


edPowerMgmtPDU2OutletsTableInstantaneousPowerOutlet18 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 18 }


edPowerMgmtPDU2OutletsTableInstantaneousPowerOutlet19 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 19 }


edPowerMgmtPDU2OutletsTableInstantaneousPowerOutlet20 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 20 }


edPowerMgmtPDU2OutletsTableInstantaneousPowerOutlet21 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 21 }


edPowerMgmtPDU2OutletsTableInstantaneousPowerOutlet22 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 22 }


edPowerMgmtPDU2OutletsTableInstantaneousPowerOutlet23 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 23 }


edPowerMgmtPDU2OutletsTableInstantaneousPowerOutlet24 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 24 }

edPowerMgmtPDU2OutletsTableInstantaneousPowerOutlet25 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 25 }


edPowerMgmtPDU2OutletsTableInstantaneousPowerOutlet26 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 26 }


edPowerMgmtPDU2OutletsTableInstantaneousPowerOutlet27 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 27 }

edPowerMgmtPDU2OutletsTableInstantaneousPowerOutlet28 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 28 }

edPowerMgmtPDU2OutletsTableInstantaneousPowerOutlet29 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 29 }

edPowerMgmtPDU2OutletsTableInstantaneousPowerOutlet30 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 30 }

edPowerMgmtPDU2OutletsTableInstantaneousPowerOutlet31 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 31 }

edPowerMgmtPDU2OutletsTableInstantaneousPowerOutlet32 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 32 }

edPowerMgmtPDU2OutletsTableInstantaneousPowerOutlet33 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 33 }

edPowerMgmtPDU2OutletsTableInstantaneousPowerOutlet34 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 34 }


edPowerMgmtPDU2OutletsTableInstantaneousPowerOutlet35 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 35 }


edPowerMgmtPDU2OutletsTableInstantaneousPowerOutlet36 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 36 }


edPowerMgmtPDU2OutletsTableInstantaneousPowerOutlet37 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 37 }


edPowerMgmtPDU2OutletsTableInstantaneousPowerOutlet38 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 38 }


edPowerMgmtPDU2OutletsTableInstantaneousPowerOutlet39 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 39 }


edPowerMgmtPDU2OutletsTableInstantaneousPowerOutlet40 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 40 }


edPowerMgmtPDU2OutletsTableInstantaneousPowerOutlet41 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 41 }


edPowerMgmtPDU2OutletsTableInstantaneousPowerOutlet42 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU2OutletsTableInstantaneousPowerValue 42 }







edPowerMgmtPDU2OutletsTablePowerFactorOutlet1 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 1 }


edPowerMgmtPDU2OutletsTablePowerFactorOutlet2 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 2 }

edPowerMgmtPDU2OutletsTablePowerFactorOutlet3 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 3 }


edPowerMgmtPDU2OutletsTablePowerFactorOutlet4 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 4 }


edPowerMgmtPDU2OutletsTablePowerFactorOutlet5 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 5 }


edPowerMgmtPDU2OutletsTablePowerFactorOutlet6 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 6 }


edPowerMgmtPDU2OutletsTablePowerFactorOutlet7 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 7 }


edPowerMgmtPDU2OutletsTablePowerFactorOutlet8 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 8 }


edPowerMgmtPDU2OutletsTablePowerFactorOutlet9 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 9 }


edPowerMgmtPDU2OutletsTablePowerFactorOutlet10 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 10 }


edPowerMgmtPDU2OutletsTablePowerFactorOutlet11 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 11 }


edPowerMgmtPDU2OutletsTablePowerFactorOutlet12 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 12 }


edPowerMgmtPDU2OutletsTablePowerFactorOutlet13 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 13 }


edPowerMgmtPDU2OutletsTablePowerFactorOutlet14 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 14 }


edPowerMgmtPDU2OutletsTablePowerFactorOutlet15 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 15 }


edPowerMgmtPDU2OutletsTablePowerFactorOutlet16 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 16 }


edPowerMgmtPDU2OutletsTablePowerFactorOutlet17 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 17 }


edPowerMgmtPDU2OutletsTablePowerFactorOutlet18 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 18 }


edPowerMgmtPDU2OutletsTablePowerFactorOutlet19 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 19 }


edPowerMgmtPDU2OutletsTablePowerFactorOutlet20 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 20 }


edPowerMgmtPDU2OutletsTablePowerFactorOutlet21 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 21 }


edPowerMgmtPDU2OutletsTablePowerFactorOutlet22 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 22 }


edPowerMgmtPDU2OutletsTablePowerFactorOutlet23 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 23 }


edPowerMgmtPDU2OutletsTablePowerFactorOutlet24 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 24 }

edPowerMgmtPDU2OutletsTablePowerFactorOutlet25 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 25 }


edPowerMgmtPDU2OutletsTablePowerFactorOutlet26 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 26 }


edPowerMgmtPDU2OutletsTablePowerFactorOutlet27 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 27 }

edPowerMgmtPDU2OutletsTablePowerFactorOutlet28 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 28 }

edPowerMgmtPDU2OutletsTablePowerFactorOutlet29 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 29 }

edPowerMgmtPDU2OutletsTablePowerFactorOutlet30 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 30 }

edPowerMgmtPDU2OutletsTablePowerFactorOutlet31 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 31 }

edPowerMgmtPDU2OutletsTablePowerFactorOutlet32 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 32 }

edPowerMgmtPDU2OutletsTablePowerFactorOutlet33 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 33 }

edPowerMgmtPDU2OutletsTablePowerFactorOutlet34 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 34 }


edPowerMgmtPDU2OutletsTablePowerFactorOutlet35 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 35 }


edPowerMgmtPDU2OutletsTablePowerFactorOutlet36 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 36 }


edPowerMgmtPDU2OutletsTablePowerFactorOutlet37 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 37 }


edPowerMgmtPDU2OutletsTablePowerFactorOutlet38 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 38 }


edPowerMgmtPDU2OutletsTablePowerFactorOutlet39 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 39 }


edPowerMgmtPDU2OutletsTablePowerFactorOutlet40 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 40 }


edPowerMgmtPDU2OutletsTablePowerFactorOutlet41 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 41 }


edPowerMgmtPDU2OutletsTablePowerFactorOutlet42 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU2OutletsTablePowerFactorValue 42 }







edPowerMgmtPDU2OutletsTableFreqOutlet1 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 1 }


edPowerMgmtPDU2OutletsTableFreqOutlet2 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 2 }

edPowerMgmtPDU2OutletsTableFreqOutlet3 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 3 }


edPowerMgmtPDU2OutletsTableFreqOutlet4 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 4 }


edPowerMgmtPDU2OutletsTableFreqOutlet5 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 5 }


edPowerMgmtPDU2OutletsTableFreqOutlet6 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 6 }


edPowerMgmtPDU2OutletsTableFreqOutlet7 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 7 }


edPowerMgmtPDU2OutletsTableFreqOutlet8 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 8 }


edPowerMgmtPDU2OutletsTableFreqOutlet9 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 9 }


edPowerMgmtPDU2OutletsTableFreqOutlet10 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 10 }


edPowerMgmtPDU2OutletsTableFreqOutlet11 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 11 }


edPowerMgmtPDU2OutletsTableFreqOutlet12 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 12 }


edPowerMgmtPDU2OutletsTableFreqOutlet13 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 13 }


edPowerMgmtPDU2OutletsTableFreqOutlet14 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 14 }


edPowerMgmtPDU2OutletsTableFreqOutlet15 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 15 }


edPowerMgmtPDU2OutletsTableFreqOutlet16 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 16 }


edPowerMgmtPDU2OutletsTableFreqOutlet17 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 17 }


edPowerMgmtPDU2OutletsTableFreqOutlet18 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 18 }


edPowerMgmtPDU2OutletsTableFreqOutlet19 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 19 }


edPowerMgmtPDU2OutletsTableFreqOutlet20 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 20 }


edPowerMgmtPDU2OutletsTableFreqOutlet21 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 21 }


edPowerMgmtPDU2OutletsTableFreqOutlet22 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 22 }


edPowerMgmtPDU2OutletsTableFreqOutlet23 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 23 }


edPowerMgmtPDU2OutletsTableFreqOutlet24 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 24 }

edPowerMgmtPDU2OutletsTableFreqOutlet25 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 25 }


edPowerMgmtPDU2OutletsTableFreqOutlet26 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 26 }


edPowerMgmtPDU2OutletsTableFreqOutlet27 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 27 }

edPowerMgmtPDU2OutletsTableFreqOutlet28 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 28 }

edPowerMgmtPDU2OutletsTableFreqOutlet29 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 29 }

edPowerMgmtPDU2OutletsTableFreqOutlet30 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 30 }

edPowerMgmtPDU2OutletsTableFreqOutlet31 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 31 }

edPowerMgmtPDU2OutletsTableFreqOutlet32 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 32 }

edPowerMgmtPDU2OutletsTableFreqOutlet33 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 33 }

edPowerMgmtPDU2OutletsTableFreqOutlet34 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 34 }


edPowerMgmtPDU2OutletsTableFreqOutlet35 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 35 }


edPowerMgmtPDU2OutletsTableFreqOutlet36 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 36 }


edPowerMgmtPDU2OutletsTableFreqOutlet37 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 37 }


edPowerMgmtPDU2OutletsTableFreqOutlet38 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 38 }


edPowerMgmtPDU2OutletsTableFreqOutlet39 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 39 }


edPowerMgmtPDU2OutletsTableFreqOutlet40 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 40 }


edPowerMgmtPDU2OutletsTableFreqOutlet41 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 41 }


edPowerMgmtPDU2OutletsTableFreqOutlet42 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU2OutletsTableFreqValue 42 }






edPowerMgmtPDU2OutletsTableControlOutlet1 OBJECT-TYPE
        SYNTAX INTEGER {
			switchingDisabled     (2),    			
			outletOn              (1),
			outletOff             (0)  
			
		}    
        ACCESS         read-write
        STATUS             mandatory
        DESCRIPTION
         "Getting this variable will return the outlet state. If 
       the outlet is on, the outletOn (1) value will be returned.
       If the outlet is off, the outletOff (0) value will be
       returned. and if returned 2 then switching is prohibited"
::= { edPowerMgmtPDU2OutletsTableOutletControl 1 }


edPowerMgmtPDU2OutletsTableControlOutlet2 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 2 }

edPowerMgmtPDU2OutletsTableControlOutlet3 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 3 }


edPowerMgmtPDU2OutletsTableControlOutlet4 OBJECT-TYPE
            SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 4 }


edPowerMgmtPDU2OutletsTableControlOutlet5 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 5 }


edPowerMgmtPDU2OutletsTableControlOutlet6 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 6 }


edPowerMgmtPDU2OutletsTableControlOutlet7 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 7 }


edPowerMgmtPDU2OutletsTableControlOutlet8 OBJECT-TYPE
            SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 8 }


edPowerMgmtPDU2OutletsTableControlOutlet9 OBJECT-TYPE
              SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 9 }


edPowerMgmtPDU2OutletsTableControlOutlet10 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 10 }


edPowerMgmtPDU2OutletsTableControlOutlet11 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 11 }


edPowerMgmtPDU2OutletsTableControlOutlet12 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 12 }


edPowerMgmtPDU2OutletsTableControlOutlet13 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 13 }


edPowerMgmtPDU2OutletsTableControlOutlet14 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 14 }


edPowerMgmtPDU2OutletsTableControlOutlet15 OBJECT-TYPE
           SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 15 }


edPowerMgmtPDU2OutletsTableControlOutlet16 OBJECT-TYPE
                SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 16 }


edPowerMgmtPDU2OutletsTableControlOutlet17 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 17 }


edPowerMgmtPDU2OutletsTableControlOutlet18 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 18 }


edPowerMgmtPDU2OutletsTableControlOutlet19 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 19 }


edPowerMgmtPDU2OutletsTableControlOutlet20 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 20 }


edPowerMgmtPDU2OutletsTableControlOutlet21 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 21 }


edPowerMgmtPDU2OutletsTableControlOutlet22 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 22 }


edPowerMgmtPDU2OutletsTableControlOutlet23 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 23 }


edPowerMgmtPDU2OutletsTableControlOutlet24 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 24 }

edPowerMgmtPDU2OutletsTableControlOutlet25 OBJECT-TYPE
           SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 25 }


edPowerMgmtPDU2OutletsTableControlOutlet26 OBJECT-TYPE
            SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 26 }


edPowerMgmtPDU2OutletsTableControlOutlet27 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 27 }

edPowerMgmtPDU2OutletsTableControlOutlet28 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 28 }

edPowerMgmtPDU2OutletsTableControlOutlet29 OBJECT-TYPE
                SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 29 }

edPowerMgmtPDU2OutletsTableControlOutlet30 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 30 }

edPowerMgmtPDU2OutletsTableControlOutlet31 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 31 }

edPowerMgmtPDU2OutletsTableControlOutlet32 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 32 }

edPowerMgmtPDU2OutletsTableControlOutlet33 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 33 }

edPowerMgmtPDU2OutletsTableControlOutlet34 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 34 }


edPowerMgmtPDU2OutletsTableControlOutlet35 OBJECT-TYPE
                SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 35 }


edPowerMgmtPDU2OutletsTableControlOutlet36 OBJECT-TYPE
                 SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 36 }


edPowerMgmtPDU2OutletsTableControlOutlet37 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 37 }


edPowerMgmtPDU2OutletsTableControlOutlet38 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 38 }


edPowerMgmtPDU2OutletsTableControlOutlet39 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 39 }


edPowerMgmtPDU2OutletsTableControlOutlet40 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 40 }


edPowerMgmtPDU2OutletsTableControlOutlet41 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 41 }


edPowerMgmtPDU2OutletsTableControlOutlet42 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU2OutletsTableOutletControl 42 }




edPowerMgmtPDU2TotalNumberOfPhases OBJECT-TYPE
        SYNTAX             Integer32
         ACCESS         		read-only
        STATUS             mandatory
        DESCRIPTION
        "Number of Phases managed by the appliance."
::= { edConectedPdu2Data 5 }

edPowerMgmtPDU2PhasesTable OBJECT IDENTIFIER::= { edConectedPdu2Data 6 }

edPowerMgmtPDU2PhasesData OBJECT IDENTIFIER::= { edPowerMgmtPDU2PhasesTable 1 }
edPowerMgmtPDU2PhasesTableIndexNumber OBJECT IDENTIFIER::= { edPowerMgmtPDU2PhasesData 1 }
edPowerMgmtPDU2PhasesTableVoltageValue OBJECT IDENTIFIER::= { edPowerMgmtPDU2PhasesData 2 }
edPowerMgmtPDU2PhasesTablecurrentValue OBJECT IDENTIFIER::= { edPowerMgmtPDU2PhasesData 3 }
edPowerMgmtPDU2PhasesTableApearentEnergyValue OBJECT IDENTIFIER::= { edPowerMgmtPDU2PhasesData 4 }
edPowerMgmtPDU2PhasesTableReactiveEnergyValue OBJECT IDENTIFIER::= { edPowerMgmtPDU2PhasesData 5 }
edPowerMgmtPDU2PhasesTableActiveEnergyValue OBJECT IDENTIFIER::= { edPowerMgmtPDU2PhasesData 6 }
edPowerMgmtPDU2PhasesTableInstantaneousPowerValue OBJECT IDENTIFIER::= { edPowerMgmtPDU2PhasesData 7 }
edPowerMgmtPDU2PhasesTablePowerFactorValue OBJECT IDENTIFIER::= { edPowerMgmtPDU2PhasesData 8 }

edPowerMgmtPDU2PhasesTableIndexNumber1 OBJECT-TYPE
        SYNTAX             Integer32
         ACCESS         read-only
        STATUS             mandatory
        DESCRIPTION
         "Index Number of the outlet in the PDU."
::= { edPowerMgmtPDU2PhasesTableIndexNumber 1 }

edPowerMgmtPDU2PhasesTableIndexNumber2 OBJECT-TYPE
        SYNTAX             Integer32
         ACCESS         read-only
        STATUS             mandatory
        DESCRIPTION
         "Index Number of the outlet in the PDU."
::= { edPowerMgmtPDU2PhasesTableIndexNumber 2 }


edPowerMgmtPDU2PhasesTableIndexNumber3 OBJECT-TYPE
        SYNTAX             Integer32
         ACCESS         read-only
        STATUS             mandatory
        DESCRIPTION
         "Index Number of the outlet in the PDU."
::= { edPowerMgmtPDU2PhasesTableIndexNumber 3 }


edPowerMgmtPDU2PhasesTableVoltageValuePhase1 OBJECT-TYPE
        SYNTAX             Integer32
         ACCESS         read-only
        STATUS             mandatory
        DESCRIPTION
        "Value of R Phase recieved from device.
		if recieved 23024 then actual value in decimal willbe 230.24 Volts ,
		if recieved 12 then 0.12 Volt. Returns 0 if not supported."
::= { edPowerMgmtPDU2PhasesTableVoltageValue 1 }

edPowerMgmtPDU2PhasesTableVoltageValuePhase2 OBJECT-TYPE
        SYNTAX             Integer32
         ACCESS         read-only
        STATUS             mandatory
        DESCRIPTION
        "Value of Y Phase recieved from device.
		if recieved 23024 then actual value in decimal willbe 230.24 Volts ,
		if recieved 12 then 0.12 Volt. Returns 0 if not supported."
::= { edPowerMgmtPDU2PhasesTableVoltageValue 2 }

edPowerMgmtPDU2PhasesTableVoltageValuePhase3 OBJECT-TYPE
        SYNTAX             Integer32
         ACCESS         read-only
        STATUS             mandatory
        DESCRIPTION
        "Value of B Phase recieved from device.
		if recieved 23024 then actual value in decimal willbe 230.24 Volts ,
		if recieved 12 then 0.12 Volt. Returns 0 if not supported."
::= { edPowerMgmtPDU2PhasesTableVoltageValue 3 }


edPowerMgmtPDU2PhasesTablecurrentPhase1 OBJECT-TYPE
        SYNTAX             Integer32
         ACCESS         read-only
        STATUS             mandatory
        DESCRIPTION
        "Current of R Phase in Ampere ,if recieved 1234 then actual value in decimal willbe 12.34 Amp, if recieved 
		value is 12 then 0.12 Amp .Returns 0 if not supported."
::= { edPowerMgmtPDU2PhasesTablecurrentValue 1 }


edPowerMgmtPDU2PhasesTablecurrentPhase2 OBJECT-TYPE
        SYNTAX             Integer32
         ACCESS         read-only
        STATUS             mandatory
        DESCRIPTION
        "Current of Y Phase in Ampere ,if recieved 1234 then actual value in decimal willbe 12.34 Amp, if recieved 
		value is 12 then 0.12 Amp .Returns 0 if not supported."
::= { edPowerMgmtPDU2PhasesTablecurrentValue 2 }



edPowerMgmtPDU2PhasesTablecurrentPhase3 OBJECT-TYPE
        SYNTAX             Integer32
         ACCESS         read-only
        STATUS             mandatory
        DESCRIPTION
        "Current of B Phase in Ampere ,if recieved 1234 then actual value in decimal willbe 12.34 Amp, if recieved 
		value is 12 then 0.12 Amp .Returns 0 if not supported."
::= { edPowerMgmtPDU2PhasesTablecurrentValue 3 }



edPowerMgmtPDU2PhasesTableApearentEnergyPhase1 OBJECT-TYPE
        SYNTAX             Integer32
         ACCESS         read-only
        STATUS             mandatory
        DESCRIPTION
        "ApearentEnergy(KVaHr) of R Phase if recieved 23024 then actual value in decimal willbe 2.3024 KVaHr , if recieved 12
	   then 0.0012 KVaHr. Returns 0 if not supported."
::= { edPowerMgmtPDU2PhasesTableApearentEnergyValue 1 }


edPowerMgmtPDU2PhasesTableApearentEnergyPhase2 OBJECT-TYPE
        SYNTAX             Integer32
         ACCESS         read-only
        STATUS             mandatory
        DESCRIPTION
        "ApearentEnergy(KVaHr) of Y Phase if recieved 23024 then actual value in decimal willbe 2.3024 KVaHr , if recieved 12
	   then 0.0012 KVaHr. Returns 0 if not supported."
::= { edPowerMgmtPDU2PhasesTableApearentEnergyValue 2 }

edPowerMgmtPDU2PhasesTableApearentEnergyPhase3 OBJECT-TYPE
        SYNTAX             Integer32
         ACCESS         read-only
        STATUS             mandatory
        DESCRIPTION
        "ApearentEnergy(KVaHr) of B Phase if recieved 23024 then actual value in decimal willbe 2.3024 KVaHr , if recieved 12
	   then 0.0012 KVaHr. Returns 0 if not supported."
::= { edPowerMgmtPDU2PhasesTableApearentEnergyValue 3 }


edPowerMgmtPDU2PhasesTableReactiveEnergyPhase1 OBJECT-TYPE
        SYNTAX             Integer32
         ACCESS         read-only
        STATUS             mandatory
        DESCRIPTION
        "ReactiveEnergy(KVarHr) of R Phase if recieved 23024 then actual value in decimal willbe 2.3024 KVaHr , if recieved 12
	   then 0.0012 KVaHr. Returns 0 if not supported."
::= { edPowerMgmtPDU2PhasesTableReactiveEnergyValue 1 }



edPowerMgmtPDU2PhasesTableReactiveEnergyPhase2 OBJECT-TYPE
        SYNTAX             Integer32
         ACCESS         read-only
        STATUS             mandatory
        DESCRIPTION
        "ReactiveEnergy(KVarHr) of Y Phase if recieved 23024 then actual value in decimal willbe 2.3024 KVaHr , if recieved 12
	   then 0.0012 KVaHr. Returns 0 if not supported."
::= { edPowerMgmtPDU2PhasesTableReactiveEnergyValue 2 }



edPowerMgmtPDU2PhasesTableReactiveEnergyPhase3 OBJECT-TYPE
        SYNTAX             Integer32
         ACCESS         read-only
        STATUS             mandatory
        DESCRIPTION
        "ReactiveEnergy(KVarHr) of B Phase if recieved 23024 then actual value in decimal willbe 2.3024 KVaHr , if recieved 12
	   then 0.0012 KVaHr. Returns 0 if not supported."
::= { edPowerMgmtPDU2PhasesTableReactiveEnergyValue 3 }

edPowerMgmtPDU2PhasesTableActiveEnergyPhase1 OBJECT-TYPE
        SYNTAX             Integer32
         ACCESS         read-only
        STATUS             mandatory
        DESCRIPTION
        "ActiveEnergy(KWattHr) of R Phase if recieved 23024 then actual value in decimal willbe 2.3024 KVaHr , if recieved 12
	   then 0.0012 KVaHr. Returns 0 if not supported."
::= { edPowerMgmtPDU2PhasesTableActiveEnergyValue 1 }

edPowerMgmtPDU2PhasesTableActiveEnergyPhase2 OBJECT-TYPE
        SYNTAX             Integer32
         ACCESS         read-only
        STATUS             mandatory
        DESCRIPTION
        "ActiveEnergy(KWattHr) of Y Phase if recieved 23024 then actual value in decimal willbe 2.3024 KVaHr , if recieved 12
	   then 0.0012 KVaHr. Returns 0 if not supported."
::= { edPowerMgmtPDU2PhasesTableActiveEnergyValue 2 }

edPowerMgmtPDU2PhasesTableActiveEnergyPhase3 OBJECT-TYPE
        SYNTAX             Integer32
         ACCESS         read-only
        STATUS             mandatory
        DESCRIPTION
        "ActiveEnergy(KWattHr) of B Phase if recieved 23024 then actual value in decimal willbe 2.3024 KVaHr , if recieved 12
	   then 0.0012 KVaHr. Returns 0 if not supported."
::= { edPowerMgmtPDU2PhasesTableActiveEnergyValue 3 }


edPowerMgmtPDU2PhasesTableInstantaneousPowerPhase1 OBJECT-TYPE
        SYNTAX             Integer32
         ACCESS         read-only
        STATUS             mandatory
        DESCRIPTION
        "Instantaneous Power(KWatt) of R Phase if recieved 23024 then actual value in decimal willbe 2.3024 KVaHr , if recieved 12
	   then 0.0012 KVaHr. Returns 0 if not supported."
::= { edPowerMgmtPDU2PhasesTableInstantaneousPowerValue 1 }


edPowerMgmtPDU2PhasesTableInstantaneousPowerPhase2 OBJECT-TYPE
        SYNTAX             Integer32
         ACCESS         read-only
        STATUS             mandatory
        DESCRIPTION
        "Instantaneous Power(KWatt) of Y Phase if recieved 23024 then actual value in decimal willbe 2.3024 KVaHr , if recieved 12
	   then 0.0012 KVaHr. Returns 0 if not supported."
::= { edPowerMgmtPDU2PhasesTableInstantaneousPowerValue 2 }


edPowerMgmtPDU2PhasesTableInstantaneousPowerPhase3 OBJECT-TYPE
        SYNTAX             Integer32
         ACCESS         read-only
        STATUS             mandatory
        DESCRIPTION
        "Instantaneous Power(KWatt) of B Phase if recieved 23024 then actual value in decimal willbe 2.3024 KVaHr , if recieved 12
	   then 0.0012 KVaHr. Returns 0 if not supported."
::= { edPowerMgmtPDU2PhasesTableInstantaneousPowerValue 3 }


edPowerMgmtPDU2PhasesTablePowerFactorPhase1 OBJECT-TYPE
        SYNTAX             Integer32
         ACCESS         read-only
        STATUS             mandatory
        DESCRIPTION
        "average of powerfactor(pF) R Phase.The recieved value 
		if 9999 then actual value in decimal willbe 99.99 pf , if recieved 12
		then 0.12 pf. Returns 0 if not supported."
::= { edPowerMgmtPDU2PhasesTablePowerFactorValue 1 }

edPowerMgmtPDU2PhasesTablePowerFactorPhase2 OBJECT-TYPE
        SYNTAX             Integer32
         ACCESS         read-only
        STATUS             mandatory
        DESCRIPTION
        "average of powerfactor(pF) Y Phase.The recieved value 
		if 9999 then actual value in decimal willbe 99.99 pf , if recieved 12
		then 0.12 pf. Returns 0 if not supported."
::= { edPowerMgmtPDU2PhasesTablePowerFactorValue 2 }

edPowerMgmtPDU2PhasesTablePowerFactorPhase3 OBJECT-TYPE
        SYNTAX             Integer32
         ACCESS         read-only
        STATUS             mandatory
        DESCRIPTION
        "average of powerfactor(pF) B Phase.The recieved value 
		if 9999 then actual value in decimal willbe 99.99 pf , if recieved 12
		then 0.12 pf. Returns 0 if not supported."
::= { edPowerMgmtPDU2PhasesTablePowerFactorValue 3 }


edPowerMgmtPDU2TotalNumberOfSensor OBJECT-TYPE
        SYNTAX             Integer32
         ACCESS         read-only
        STATUS             mandatory
        DESCRIPTION
        "Number of Sensors managed by the appliance."
::= { edConectedPdu2Data 7 }


edPowerMgmtPDU2SensorsTable OBJECT IDENTIFIER ::= { edConectedPdu2Data 8 }

edPowerMgmtPDU2SensorsData OBJECT IDENTIFIER ::= { edPowerMgmtPDU2SensorsTable 1 }

edPowerMgmtPDU2SensorsTableNumber OBJECT IDENTIFIER ::= { edPowerMgmtPDU2SensorsData 1 }
edPowerMgmtPDU2SensorsTableSensorType OBJECT IDENTIFIER ::= { edPowerMgmtPDU2SensorsData 2 }
edPowerMgmtPDU2SensorsTableSensorValue OBJECT IDENTIFIER::= { edPowerMgmtPDU2SensorsData 3 }

edPowerMgmtPDU2SensorsTableSensor1 OBJECT-TYPE
        SYNTAX             Integer32
         ACCESS         read-only
        STATUS             mandatory
        DESCRIPTION
        "Number of the sensor in the PDU."
::= { edPowerMgmtPDU2SensorsTableNumber 1 }


edPowerMgmtPDU2SensorsTableSensor2 OBJECT-TYPE
        SYNTAX             Integer32
         ACCESS         read-only
        STATUS             mandatory
        DESCRIPTION
        "Number of the sensor in the PDU."
::= { edPowerMgmtPDU2SensorsTableNumber 2 }


edPowerMgmtPDU2SensorsTableSensor3 OBJECT-TYPE
        SYNTAX             Integer32
         ACCESS         read-only
        STATUS             mandatory
        DESCRIPTION
        "Number of the sensor in the PDU."
::= { edPowerMgmtPDU2SensorsTableNumber 3 }

edPowerMgmtPDU2SensorsTableSensor4 OBJECT-TYPE
        SYNTAX             Integer32
         ACCESS         read-only
        STATUS             mandatory
        DESCRIPTION
        "Number of the sensor in the PDU."
::= { edPowerMgmtPDU2SensorsTableNumber 4 }

edPowerMgmtPDU2SensorsTableSensorType1 OBJECT-TYPE
         SYNTAX INTEGER {
		humidity     (2),    			
		temprature   (1),
		nosens      (0)  
		
		}
         ACCESS         read-only
        STATUS             mandatory
        DESCRIPTION
        "returns value displaying type of Sensor."
::= { edPowerMgmtPDU2SensorsTableSensorType 1 }

edPowerMgmtPDU2SensorsTableSensorType2 OBJECT-TYPE
         SYNTAX INTEGER {
		humidity     (2),    			
		temprature   (1),
		nosens      (0)  
		
		}
         ACCESS         read-only
        STATUS             mandatory
        DESCRIPTION
        "returns value displaying type of Sensor."
::= { edPowerMgmtPDU2SensorsTableSensorType 2 }

edPowerMgmtPDU2SensorsTableSensorType3 OBJECT-TYPE
         SYNTAX INTEGER {
		humidity     (2),    			
		temprature   (1),
		nosens      (0)  
		
		}
         ACCESS         read-only
        STATUS             mandatory
        DESCRIPTION
        "returns value displaying type of Sensor."
::= { edPowerMgmtPDU2SensorsTableSensorType 3 }


edPowerMgmtPDU2SensorsTableSensorType4 OBJECT-TYPE
         SYNTAX INTEGER {
		humidity     (2),    			
		temprature   (1),
		nosens      (0)  
		
		}
         ACCESS         read-only
        STATUS             mandatory
        DESCRIPTION
        "returns value displaying type of Sensor."
::= { edPowerMgmtPDU2SensorsTableSensorType 4 }



edPowerMgmtPDU2SensorsTableSensorValueSensor1 OBJECT-TYPE
        SYNTAX             Integer32
         ACCESS         read-only
        STATUS             mandatory
        DESCRIPTION
        "returns value of Sensor
         Returns 0 if not supported."
::= { edPowerMgmtPDU2SensorsTableSensorValue 1 }

edPowerMgmtPDU2SensorsTableSensorValueSensor2 OBJECT-TYPE
        SYNTAX             Integer32
         ACCESS         read-only
        STATUS             mandatory
        DESCRIPTION
        "returns value of Sensor
         Returns 0 if not supported."
::= { edPowerMgmtPDU2SensorsTableSensorValue 2 }

edPowerMgmtPDU2SensorsTableSensorValueSensor3 OBJECT-TYPE
        SYNTAX             Integer32
         ACCESS         read-only
        STATUS             mandatory
        DESCRIPTION
        "returns value of Sensor
         Returns 0 if not supported."
::= { edPowerMgmtPDU2SensorsTableSensorValue 3 }

edPowerMgmtPDU2SensorsTableSensorValueSensor4 OBJECT-TYPE
        SYNTAX             Integer32
         ACCESS         read-only
        STATUS             mandatory
        DESCRIPTION
        "returns value of Sensor
         Returns 0 if not supported."
::= { edPowerMgmtPDU2SensorsTableSensorValue 4 }



----------- Daisy Chaining pduData 2 Ends ----------------------

----------- Daisy Chaining pduData 3  ----------------------

edConectedPdu3Data OBJECT IDENTIFIER::= { edConnectedPduMgmt 3 }

edPowerMgmtPDU3TableData OBJECT IDENTIFIER::= { edConectedPdu3Data 1 }

edPowerMgmtPDU3TableNumber       OBJECT-TYPE
        SYNTAX             Integer32
         ACCESS         read-only
        STATUS             mandatory
        DESCRIPTION
        "Index Number"
::= { edPowerMgmtPDU3TableData 1 }



edPowerMgmtPDU3TableProductCode      OBJECT-TYPE
        SYNTAX             DisplayString
         ACCESS         read-only
        STATUS             mandatory
        DESCRIPTION
        "Version of the PDU firmware.
         Returns N/A if not applicable."
::= { edPowerMgmtPDU3TableData 2 }



edPowerMgmtPDU3TableSerialNumber OBJECT-TYPE
        SYNTAX             Integer32
         ACCESS         read-only
        STATUS             mandatory
        DESCRIPTION
        "Number of outlets of the PDU."
::= { edPowerMgmtPDU3TableData 3 }


edPowerMgmtPDU3TableFirmwareVersion       OBJECT-TYPE
        SYNTAX             DisplayString
         ACCESS         read-only
        STATUS             mandatory
        DESCRIPTION
        "Version of the PDU firmware.
         Returns N/A if not applicable."
::= { edPowerMgmtPDU3TableData 4 }



edPowerMgmtPDU3TableNumberOfOutlets OBJECT-TYPE
        SYNTAX             Integer32
         ACCESS         read-only
        STATUS             mandatory
        DESCRIPTION
        "Number of outlets of the PDU."
::= { edPowerMgmtPDU3TableData 5 }

edPowerMgmtPDU3TableNumberOfPhases OBJECT-TYPE
        SYNTAX             Integer32
         ACCESS         read-only
        STATUS             mandatory
        DESCRIPTION
        "Number of phases of the PDU."
::= { edPowerMgmtPDU3TableData 6 }


edPowerMgmtPDU3TableNumberOfSensors OBJECT-TYPE
        SYNTAX             Integer32
         ACCESS         read-only
        STATUS             mandatory
        DESCRIPTION
        "Number of sensors in the PDU."
::= { edPowerMgmtPDU3TableData 7 }



edPowerMgmtPDU3TableVendor   OBJECT-TYPE
        SYNTAX             DisplayString
         ACCESS         	  read-only
        STATUS             mandatory
        DESCRIPTION
        "Vendor of the PDU.
         Returns N/A if not applicable."
::= { edPowerMgmtPDU3TableData 8 }


edPowerMgmtPDU3AggrInfoTable OBJECT IDENTIFIER::= { edConectedPdu3Data 2 }

edPowerMgmtPDU3AggrsData OBJECT IDENTIFIER::= { edPowerMgmtPDU3AggrInfoTable 1 }


edPowerMgmtPDU3AggrInfoNumber       OBJECT-TYPE
        SYNTAX             		Integer32
         ACCESS         			read-only
        STATUS             		mandatory
        DESCRIPTION
        "Index Number"
::= { edPowerMgmtPDU3AggrsData 1 }
 


edPowerMgmtPDU3AggrInfoTableVoltageValue OBJECT-TYPE
        SYNTAX             Integer32
         ACCESS         read-only
        STATUS             mandatory
        DESCRIPTION
		"Aggrgate voltage of phase is (if vRphase R > vYphase && vRphase R > vBphase) 
		aggregate voltage of R Phase .The recieved value 
		if 23024 then actual value in decimal willbe 230.24 Volts ,
		if recieved 12 then 0.12 Volt. Returns 0 if not supported."
::= { edPowerMgmtPDU3AggrsData 2 }


edPowerMgmtPDU3AggrInfoTableCurrentValue OBJECT-TYPE
        SYNTAX             Integer32
         ACCESS         read-only
        STATUS             mandatory
        DESCRIPTION
        "Addition of mandatory of all Outlet.The recieved value 
		if 1234 then actual value in decimal willbe 12.34 Amp, if recieved 
		value is 12 then 0.12 Amp .Returns 0 if not supported."
::= { edPowerMgmtPDU3AggrsData 3 }


edPowerMgmtPDU3AggrInfoTableApearentEnergyValue OBJECT-TYPE
        SYNTAX             Integer32
         ACCESS         read-only
        STATUS             mandatory
        DESCRIPTION
       "addition of ApearentEnergy(KVaHr) of all outlet.The recieved value
	   if 23024 then actual value in decimal willbe 2.3024 KVaHr , if recieved 12
	   then 0.0012 KVaHr. Returns 0 if not supported."
::= { edPowerMgmtPDU3AggrsData 4 }


edPowerMgmtPDU3AggrInfoTableReactiveEnergyValue OBJECT-TYPE
        SYNTAX             Integer32
         ACCESS         read-only
        STATUS             mandatory
        DESCRIPTION
         "addition of ReactiveEnergy(KVarHr) of all outlet.The recieved value 
		 if 23024 then actual value in decimal willbe 2.3024 KVarHr , if recieved 12 
		 then 0.0012 KVarHr. Returns 0 if not supported."
::= { edPowerMgmtPDU3AggrsData 5 }

edPowerMgmtPDU3AggrInfoTableActiveEnergyValue OBJECT-TYPE
        SYNTAX             Integer32
         ACCESS         read-only
        STATUS             mandatory
        DESCRIPTION
      "addition of ActiveEnergy(KWattHr) of all outlets.The recieved value 
	  if 23024 then actual value in decimal willbe 2.3024 KWattHr , if recieved 12
	  then 0.0012 KWattHr. Returns 0 if not supported."
::= { edPowerMgmtPDU3AggrsData 6 }


edPowerMgmtPDU3AggrInfoTableInstantaneousPowerValue OBJECT-TYPE
        SYNTAX             Integer32
         ACCESS         read-only
        STATUS             mandatory
        DESCRIPTION
      "addition of  Instantaneous Power(KWatt) of all outlet.The recieved value 
	  if 230 then actual value in decimal willbe 2.30 KWatt , if recieved 12 
	  then 0.12 KWatt. Returns 0 if not supported."
::= { edPowerMgmtPDU3AggrsData 7 }

edPowerMgmtPDU3AggrInfoTablePowerFactorValue OBJECT-TYPE
        SYNTAX             Integer32
         ACCESS         read-only
        STATUS             mandatory
        DESCRIPTION
      	"average of powerfactor(pF) of all outlet.The recieved value 
		if 9999 then actual value in decimal willbe 99.99 pf , if recieved 12
		then 0.12 pf. Returns 0 if not supported."

::= { edPowerMgmtPDU3AggrsData 8 }


edPowerMgmtPDU3TotalNumberOfOutlets OBJECT-TYPE
        SYNTAX             Integer32
         ACCESS         read-only
        STATUS             mandatory
        DESCRIPTION
        "Number of outlets managed by the appliance."
::= { edConectedPdu3Data 3 }
 


edPowerMgmtPDU3OutletsTable OBJECT IDENTIFIER::= { edConectedPdu3Data 4 }

edPowerMgmtPDU3OutletData OBJECT IDENTIFIER::= { edPowerMgmtPDU3OutletsTable 1 }

edPowerMgmtPDU3OutletsTableIndex        			OBJECT IDENTIFIER::= { edPowerMgmtPDU3OutletData 1 }
edPowerMgmtPDU3OutletsTableIndexNumber        		OBJECT IDENTIFIER::= { edPowerMgmtPDU3OutletsTableIndex 1 }

edPowerMgmtPDU3OutletsTableVoltage        			OBJECT IDENTIFIER::= { edPowerMgmtPDU3OutletData 2 }
edPowerMgmtPDU3OutletsTableVoltageValue        		OBJECT IDENTIFIER::= { edPowerMgmtPDU3OutletsTableVoltage 1 }
edPowerMgmtPDU3OutletsTableCurrent       	 		OBJECT IDENTIFIER::= { edPowerMgmtPDU3OutletData 3 }
edPowerMgmtPDU3OutletsTableCurrentValue        		OBJECT IDENTIFIER::= { edPowerMgmtPDU3OutletsTableCurrent 1 }
edPowerMgmtPDU3OutletsTableApearentEnergy   		OBJECT IDENTIFIER::= { edPowerMgmtPDU3OutletData 4 }
edPowerMgmtPDU3OutletsTableApearentEnergyValue      OBJECT IDENTIFIER::= { edPowerMgmtPDU3OutletsTableApearentEnergy 1 }
edPowerMgmtPDU3OutletsTableReactiveEnergy      		OBJECT IDENTIFIER::= { edPowerMgmtPDU3OutletData 5 }
edPowerMgmtPDU3OutletsTableReactiveEnergyValue      OBJECT IDENTIFIER::= { edPowerMgmtPDU3OutletsTableReactiveEnergy 1 }
edPowerMgmtPDU3OutletsTableActiveEnergy  			OBJECT IDENTIFIER::= { edPowerMgmtPDU3OutletData 6 }
edPowerMgmtPDU3OutletsTableActiveEnergyValue        OBJECT IDENTIFIER::= { edPowerMgmtPDU3OutletsTableActiveEnergy 1 }
edPowerMgmtPDU3OutletsTableInstantaneousPower  		OBJECT IDENTIFIER::= { edPowerMgmtPDU3OutletData 7 }
edPowerMgmtPDU3OutletsTableInstantaneousPowerValue  OBJECT IDENTIFIER::= { edPowerMgmtPDU3OutletsTableInstantaneousPower 1 }
edPowerMgmtPDU3OutletsTablePowerFactor    			OBJECT IDENTIFIER::= { edPowerMgmtPDU3OutletData 8 }
edPowerMgmtPDU3OutletsTablePowerFactorValue        	OBJECT IDENTIFIER::= { edPowerMgmtPDU3OutletsTablePowerFactor 1 }
edPowerMgmtPDU3OutletsTableFreq    					OBJECT IDENTIFIER::= { edPowerMgmtPDU3OutletData 9 }
edPowerMgmtPDU3OutletsTableFreqValue        		OBJECT IDENTIFIER::= { edPowerMgmtPDU3OutletsTableFreq 1 }
edPowerMgmtPDU3OutletsTableOutletswitching        	OBJECT IDENTIFIER::= { edPowerMgmtPDU3OutletData 10 }
edPowerMgmtPDU3OutletsTableOutletControl        	OBJECT IDENTIFIER::= { edPowerMgmtPDU3OutletsTableOutletswitching 1 }





edPowerMgmtPDU3OutletsTableIndexNumber1 OBJECT-TYPE
        SYNTAX             Integer32
         ACCESS         read-only
        STATUS             mandatory
        DESCRIPTION
         "Index Number of the outlet in the PDU."
::= { edPowerMgmtPDU3OutletsTableIndexNumber 1 }


edPowerMgmtPDU3OutletsTableIndexNumber2 OBJECT-TYPE
        SYNTAX             Integer32
         ACCESS         read-only
        STATUS             mandatory
        DESCRIPTION
         "Index Number of the outlet in the PDU."
::= { edPowerMgmtPDU3OutletsTableIndexNumber 2 }

edPowerMgmtPDU3OutletsTableIndexNumber3 OBJECT-TYPE
        SYNTAX             Integer32
         ACCESS         read-only
        STATUS             mandatory
        DESCRIPTION
        "Index Number of the outlet in the PDU."
::= { edPowerMgmtPDU3OutletsTableIndexNumber 3 }


edPowerMgmtPDU3OutletsTableIndexNumber4 OBJECT-TYPE
        SYNTAX             Integer32
         ACCESS         read-only
        STATUS             mandatory
        DESCRIPTION
        "Index Number of the outlet in the PDU."
::= { edPowerMgmtPDU3OutletsTableIndexNumber 4 }


edPowerMgmtPDU3OutletsTableIndexNumber5 OBJECT-TYPE
        SYNTAX             Integer32
         ACCESS         read-only
        STATUS             mandatory
        DESCRIPTION
        "Index Number of the outlet in the PDU."
::= { edPowerMgmtPDU3OutletsTableIndexNumber 5 }


edPowerMgmtPDU3OutletsTableIndexNumber6 OBJECT-TYPE
        SYNTAX             Integer32
         ACCESS         read-only
        STATUS             mandatory
        DESCRIPTION
         "Index Number of the outlet in the PDU."
::= { edPowerMgmtPDU3OutletsTableIndexNumber 6 }


edPowerMgmtPDU3OutletsTableIndexNumber7 OBJECT-TYPE
        SYNTAX             Integer32
         ACCESS         read-only
        STATUS             mandatory
        DESCRIPTION
        "Index Number of the outlet in the PDU."
::= { edPowerMgmtPDU3OutletsTableIndexNumber 7 }


edPowerMgmtPDU3OutletsTableIndexNumber8 OBJECT-TYPE
        SYNTAX             Integer32
         ACCESS         read-only
        STATUS             mandatory
        DESCRIPTION
       "Index Number of the outlet in the PDU."
::= { edPowerMgmtPDU3OutletsTableIndexNumber 8 }


edPowerMgmtPDU3OutletsTableIndexNumber9 OBJECT-TYPE
        SYNTAX             Integer32
         ACCESS         read-only
        STATUS             mandatory
        DESCRIPTION
         "Index Number of the outlet in the PDU."
::= { edPowerMgmtPDU3OutletsTableIndexNumber 9 }


edPowerMgmtPDU3OutletsTableIndexNumber10 OBJECT-TYPE
        SYNTAX             Integer32
         ACCESS         read-only
        STATUS             mandatory
        DESCRIPTION
        "Index Number of the outlet in the PDU."
::= { edPowerMgmtPDU3OutletsTableIndexNumber 10 }


edPowerMgmtPDU3OutletsTableIndexNumber11 OBJECT-TYPE
        SYNTAX             Integer32
         ACCESS         read-only
        STATUS             mandatory
        DESCRIPTION
      "Index Number of the outlet in the PDU."
::= { edPowerMgmtPDU3OutletsTableIndexNumber 11 }


edPowerMgmtPDU3OutletsTableIndexNumber12 OBJECT-TYPE
        SYNTAX             Integer32
         ACCESS         read-only
        STATUS             mandatory
        DESCRIPTION
       "Index Number of the outlet in the PDU."
::= { edPowerMgmtPDU3OutletsTableIndexNumber 12 }


edPowerMgmtPDU3OutletsTableIndexNumber13 OBJECT-TYPE
        SYNTAX             Integer32
         ACCESS         read-only
        STATUS             mandatory
        DESCRIPTION
        "Index Number of the outlet in the PDU."
::= { edPowerMgmtPDU3OutletsTableIndexNumber 13 }


edPowerMgmtPDU3OutletsTableIndexNumber14 OBJECT-TYPE
        SYNTAX             Integer32
         ACCESS         read-only
        STATUS             mandatory
        DESCRIPTION
       "Index Number of the outlet in the PDU."
::= { edPowerMgmtPDU3OutletsTableIndexNumber 14 }


edPowerMgmtPDU3OutletsTableIndexNumber15 OBJECT-TYPE
        SYNTAX             Integer32
         ACCESS         read-only
        STATUS             mandatory
        DESCRIPTION
       "Index Number of the outlet in the PDU."
::= { edPowerMgmtPDU3OutletsTableIndexNumber 15 }


edPowerMgmtPDU3OutletsTableIndexNumber16 OBJECT-TYPE
        SYNTAX             Integer32
         ACCESS         read-only
        STATUS             mandatory
        DESCRIPTION
      "Index Number of the outlet in the PDU."
::= { edPowerMgmtPDU3OutletsTableIndexNumber 16 }


edPowerMgmtPDU3OutletsTableIndexNumber17 OBJECT-TYPE
        SYNTAX             Integer32
         ACCESS         read-only
        STATUS             mandatory
        DESCRIPTION
       "Index Number of the outlet in the PDU."
::= { edPowerMgmtPDU3OutletsTableIndexNumber 17 }


edPowerMgmtPDU3OutletsTableIndexNumber18 OBJECT-TYPE
        SYNTAX             Integer32
         ACCESS         read-only
        STATUS             mandatory
        DESCRIPTION
          "Index Number of the outlet in the PDU."
::= { edPowerMgmtPDU3OutletsTableIndexNumber 18 }


edPowerMgmtPDU3OutletsTableIndexNumber19 OBJECT-TYPE
        SYNTAX             Integer32
         ACCESS         read-only
        STATUS             mandatory
        DESCRIPTION
          "Index Number of the outlet in the PDU."
::= { edPowerMgmtPDU3OutletsTableIndexNumber 19 }


edPowerMgmtPDU3OutletsTableIndexNumber20 OBJECT-TYPE
        SYNTAX             Integer32
         ACCESS         read-only
        STATUS             mandatory
        DESCRIPTION
          "Index Number of the outlet in the PDU."
::= { edPowerMgmtPDU3OutletsTableIndexNumber 20 }


edPowerMgmtPDU3OutletsTableIndexNumber21 OBJECT-TYPE
        SYNTAX             Integer32
         ACCESS         read-only
        STATUS             mandatory
        DESCRIPTION
          "Index Number of the outlet in the PDU."
::= { edPowerMgmtPDU3OutletsTableIndexNumber 21 }


edPowerMgmtPDU3OutletsTableIndexNumber22 OBJECT-TYPE
        SYNTAX             Integer32
         ACCESS         read-only
        STATUS             mandatory
        DESCRIPTION
          "Index Number of the outlet in the PDU."
::= { edPowerMgmtPDU3OutletsTableIndexNumber 22 }


edPowerMgmtPDU3OutletsTableIndexNumber23 OBJECT-TYPE
        SYNTAX             Integer32
         ACCESS         read-only
        STATUS             mandatory
        DESCRIPTION
          "Index Number of the outlet in the PDU."
::= { edPowerMgmtPDU3OutletsTableIndexNumber 23 }


edPowerMgmtPDU3OutletsTableIndexNumber24 OBJECT-TYPE
        SYNTAX             Integer32
         ACCESS         read-only
        STATUS             mandatory
        DESCRIPTION
          "Index Number of the outlet in the PDU."
::= { edPowerMgmtPDU3OutletsTableIndexNumber 24 }

edPowerMgmtPDU3OutletsTableIndexNumber25 OBJECT-TYPE
        SYNTAX             Integer32
         ACCESS         read-only
        STATUS             mandatory
        DESCRIPTION
          "Index Number of the outlet in the PDU."
::= { edPowerMgmtPDU3OutletsTableIndexNumber 25 }


edPowerMgmtPDU3OutletsTableIndexNumber26 OBJECT-TYPE
        SYNTAX             Integer32
         ACCESS         read-only
        STATUS             mandatory
        DESCRIPTION
          "Index Number of the outlet in the PDU."
::= { edPowerMgmtPDU3OutletsTableIndexNumber 26 }


edPowerMgmtPDU3OutletsTableIndexNumber27 OBJECT-TYPE
        SYNTAX             Integer32
         ACCESS         read-only
        STATUS             mandatory
        DESCRIPTION
          "Index Number of the outlet in the PDU."
::= { edPowerMgmtPDU3OutletsTableIndexNumber 27 }

edPowerMgmtPDU3OutletsTableIndexNumber28 OBJECT-TYPE
        SYNTAX             Integer32
         ACCESS         read-only
        STATUS             mandatory
        DESCRIPTION
          "Index Number of the outlet in the PDU."
::= { edPowerMgmtPDU3OutletsTableIndexNumber 28 }

edPowerMgmtPDU3OutletsTableIndexNumber29 OBJECT-TYPE
        SYNTAX             Integer32
         ACCESS         read-only
        STATUS             mandatory
        DESCRIPTION
          "Index Number of the outlet in the PDU."
::= { edPowerMgmtPDU3OutletsTableIndexNumber 29 }

edPowerMgmtPDU3OutletsTableIndexNumber30 OBJECT-TYPE
        SYNTAX             Integer32
         ACCESS         read-only
        STATUS             mandatory
        DESCRIPTION
          "Index Number of the outlet in the PDU."
::= { edPowerMgmtPDU3OutletsTableIndexNumber 30 }

edPowerMgmtPDU3OutletsTableIndexNumber31 OBJECT-TYPE
        SYNTAX             Integer32
         ACCESS         read-only
        STATUS             mandatory
        DESCRIPTION
          "Index Number of the outlet in the PDU."
::= { edPowerMgmtPDU3OutletsTableIndexNumber 31 }

edPowerMgmtPDU3OutletsTableIndexNumber32 OBJECT-TYPE
        SYNTAX             Integer32
         ACCESS         read-only
        STATUS             mandatory
        DESCRIPTION
          "Index Number of the outlet in the PDU."
::= { edPowerMgmtPDU3OutletsTableIndexNumber 32 }

edPowerMgmtPDU3OutletsTableIndexNumber33 OBJECT-TYPE
        SYNTAX             Integer32
         ACCESS         read-only
        STATUS             mandatory
        DESCRIPTION
          "Index Number of the outlet in the PDU."
::= { edPowerMgmtPDU3OutletsTableIndexNumber 33 }

edPowerMgmtPDU3OutletsTableIndexNumber34 OBJECT-TYPE
        SYNTAX             Integer32
         ACCESS         read-only
        STATUS             mandatory
        DESCRIPTION
          "Index Number of the outlet in the PDU."
::= { edPowerMgmtPDU3OutletsTableIndexNumber 34 }


edPowerMgmtPDU3OutletsTableIndexNumber35 OBJECT-TYPE
        SYNTAX             Integer32
         ACCESS         read-only
        STATUS             mandatory
        DESCRIPTION
          "Index Number of the outlet in the PDU."
::= { edPowerMgmtPDU3OutletsTableIndexNumber 35 }


edPowerMgmtPDU3OutletsTableIndexNumber36 OBJECT-TYPE
        SYNTAX             Integer32
         ACCESS         read-only
        STATUS             mandatory
        DESCRIPTION
          "Index Number of the outlet in the PDU."
::= { edPowerMgmtPDU3OutletsTableIndexNumber 36 }


edPowerMgmtPDU3OutletsTableIndexNumber37 OBJECT-TYPE
        SYNTAX             Integer32
         ACCESS         read-only
        STATUS             mandatory
        DESCRIPTION
          "Index Number of the outlet in the PDU."
::= { edPowerMgmtPDU3OutletsTableIndexNumber 37 }


edPowerMgmtPDU3OutletsTableIndexNumber38 OBJECT-TYPE
        SYNTAX             Integer32
         ACCESS         read-only
        STATUS             mandatory
        DESCRIPTION
          "Index Number of the outlet in the PDU."
::= { edPowerMgmtPDU3OutletsTableIndexNumber 38 }


edPowerMgmtPDU3OutletsTableIndexNumber39 OBJECT-TYPE
        SYNTAX             Integer32
         ACCESS         read-only
        STATUS             mandatory
        DESCRIPTION
          "Index Number of the outlet in the PDU."
::= { edPowerMgmtPDU3OutletsTableIndexNumber 39 }


edPowerMgmtPDU3OutletsTableIndexNumber40 OBJECT-TYPE
        SYNTAX             Integer32
         ACCESS         read-only
        STATUS             mandatory
        DESCRIPTION
          "Index Number of the outlet in the PDU."
::= { edPowerMgmtPDU3OutletsTableIndexNumber 40 }


edPowerMgmtPDU3OutletsTableIndexNumber41 OBJECT-TYPE
        SYNTAX             Integer32
         ACCESS         		read-only
        STATUS             mandatory
        DESCRIPTION
          "Index Number of the outlet in the PDU."
::= { edPowerMgmtPDU3OutletsTableIndexNumber 41 }


edPowerMgmtPDU3OutletsTableIndexNumber42 OBJECT-TYPE
        SYNTAX             Integer32
         ACCESS         read-only
        STATUS             mandatory
        DESCRIPTION
          "Index Number of the outlet in the PDU."
::= { edPowerMgmtPDU3OutletsTableIndexNumber 42 }







edPowerMgmtPDU3OutletsTableVoltageOutlet1 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 1 }


edPowerMgmtPDU3OutletsTableVoltageOutlet2 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 2 }

edPowerMgmtPDU3OutletsTableVoltageOutlet3 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 3 }


edPowerMgmtPDU3OutletsTableVoltageOutlet4 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 4 }


edPowerMgmtPDU3OutletsTableVoltageOutlet5 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 5 }


edPowerMgmtPDU3OutletsTableVoltageOutlet6 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 6 }


edPowerMgmtPDU3OutletsTableVoltageOutlet7 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 7 }


edPowerMgmtPDU3OutletsTableVoltageOutlet8 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 8 }


edPowerMgmtPDU3OutletsTableVoltageOutlet9 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 9 }


edPowerMgmtPDU3OutletsTableVoltageOutlet10 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 10 }


edPowerMgmtPDU3OutletsTableVoltageOutlet11 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 11 }


edPowerMgmtPDU3OutletsTableVoltageOutlet12 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 12 }


edPowerMgmtPDU3OutletsTableVoltageOutlet13 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 13 }


edPowerMgmtPDU3OutletsTableVoltageOutlet14 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 14 }


edPowerMgmtPDU3OutletsTableVoltageOutlet15 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 15 }


edPowerMgmtPDU3OutletsTableVoltageOutlet16 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 16 }


edPowerMgmtPDU3OutletsTableVoltageOutlet17 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 17 }


edPowerMgmtPDU3OutletsTableVoltageOutlet18 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 18 }


edPowerMgmtPDU3OutletsTableVoltageOutlet19 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 19 }


edPowerMgmtPDU3OutletsTableVoltageOutlet20 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 20 }


edPowerMgmtPDU3OutletsTableVoltageOutlet21 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 21 }


edPowerMgmtPDU3OutletsTableVoltageOutlet22 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 22 }


edPowerMgmtPDU3OutletsTableVoltageOutlet23 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 23 }


edPowerMgmtPDU3OutletsTableVoltageOutlet24 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 24 }

edPowerMgmtPDU3OutletsTableVoltageOutlet25 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 25 }


edPowerMgmtPDU3OutletsTableVoltageOutlet26 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 26 }


edPowerMgmtPDU3OutletsTableVoltageOutlet27 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 27 }

edPowerMgmtPDU3OutletsTableVoltageOutlet28 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 28 }

edPowerMgmtPDU3OutletsTableVoltageOutlet29 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 29 }

edPowerMgmtPDU3OutletsTableVoltageOutlet30 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 30 }

edPowerMgmtPDU3OutletsTableVoltageOutlet31 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 31 }

edPowerMgmtPDU3OutletsTableVoltageOutlet32 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 32 }

edPowerMgmtPDU3OutletsTableVoltageOutlet33 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 33 }

edPowerMgmtPDU3OutletsTableVoltageOutlet34 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 34 }


edPowerMgmtPDU3OutletsTableVoltageOutlet35 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 35 }


edPowerMgmtPDU3OutletsTableVoltageOutlet36 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 36 }


edPowerMgmtPDU3OutletsTableVoltageOutlet37 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 37 }


edPowerMgmtPDU3OutletsTableVoltageOutlet38 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 38 }


edPowerMgmtPDU3OutletsTableVoltageOutlet39 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 39 }


edPowerMgmtPDU3OutletsTableVoltageOutlet40 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 40 }


edPowerMgmtPDU3OutletsTableVoltageOutlet41 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 41 }


edPowerMgmtPDU3OutletsTableVoltageOutlet42 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU3OutletsTableVoltageValue 42 }








edPowerMgmtPDU3OutletsTableCurrentOutlet1 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU3OutletsTableCurrentValue 1 }


edPowerMgmtPDU3OutletsTableCurrentOutlet2 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU3OutletsTableCurrentValue 2 }

edPowerMgmtPDU3OutletsTableCurrentOutlet3 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU3OutletsTableCurrentValue 3 }


edPowerMgmtPDU3OutletsTableCurrentOutlet4 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU3OutletsTableCurrentValue 4 }


edPowerMgmtPDU3OutletsTableCurrentOutlet5 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU3OutletsTableCurrentValue 5 }


edPowerMgmtPDU3OutletsTableCurrentOutlet6 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU3OutletsTableCurrentValue 6 }


edPowerMgmtPDU3OutletsTableCurrentOutlet7 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU3OutletsTableCurrentValue 7 }


edPowerMgmtPDU3OutletsTableCurrentOutlet8 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU3OutletsTableCurrentValue 8 }


edPowerMgmtPDU3OutletsTableCurrentOutlet9 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU3OutletsTableCurrentValue 9 }


edPowerMgmtPDU3OutletsTableCurrentOutlet10 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU3OutletsTableCurrentValue 10 }


edPowerMgmtPDU3OutletsTableCurrentOutlet11 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU3OutletsTableCurrentValue 11 }


edPowerMgmtPDU3OutletsTableCurrentOutlet12 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU3OutletsTableCurrentValue 12 }


edPowerMgmtPDU3OutletsTableCurrentOutlet13 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU3OutletsTableCurrentValue 13 }


edPowerMgmtPDU3OutletsTableCurrentOutlet14 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU3OutletsTableCurrentValue 14 }


edPowerMgmtPDU3OutletsTableCurrentOutlet15 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU3OutletsTableCurrentValue 15 }


edPowerMgmtPDU3OutletsTableCurrentOutlet16 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU3OutletsTableCurrentValue 16 }


edPowerMgmtPDU3OutletsTableCurrentOutlet17 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU3OutletsTableCurrentValue 17 }


edPowerMgmtPDU3OutletsTableCurrentOutlet18 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU3OutletsTableCurrentValue 18 }


edPowerMgmtPDU3OutletsTableCurrentOutlet19 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU3OutletsTableCurrentValue 19 }


edPowerMgmtPDU3OutletsTableCurrentOutlet20 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU3OutletsTableCurrentValue 20 }


edPowerMgmtPDU3OutletsTableCurrentOutlet21 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU3OutletsTableCurrentValue 21 }


edPowerMgmtPDU3OutletsTableCurrentOutlet22 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU3OutletsTableCurrentValue 22 }


edPowerMgmtPDU3OutletsTableCurrentOutlet23 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU3OutletsTableCurrentValue 23 }


edPowerMgmtPDU3OutletsTableCurrentOutlet24 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU3OutletsTableCurrentValue 24 }

edPowerMgmtPDU3OutletsTableCurrentOutlet25 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU3OutletsTableCurrentValue 25 }


edPowerMgmtPDU3OutletsTableCurrentOutlet26 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU3OutletsTableCurrentValue 26 }


edPowerMgmtPDU3OutletsTableCurrentOutlet27 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU3OutletsTableCurrentValue 27 }

edPowerMgmtPDU3OutletsTableCurrentOutlet28 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU3OutletsTableCurrentValue 28 }

edPowerMgmtPDU3OutletsTableCurrentOutlet29 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU3OutletsTableCurrentValue 29 }

edPowerMgmtPDU3OutletsTableCurrentOutlet30 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU3OutletsTableCurrentValue 30 }

edPowerMgmtPDU3OutletsTableCurrentOutlet31 OBJECT-TYPE
        SYNTAX             Integer32
         ACCESS         read-only
        STATUS             mandatory
        DESCRIPTION
      "Actual value of Current for the outlet(Amp).The recieved value 
		if 1234 then actual value in decimal willbe 12.34 Amp, if recieved 
		value is 12 then 0.12 Amp .Returns 0 if not supported."
::= { edPowerMgmtPDU3OutletsTableCurrentValue 31 }

edPowerMgmtPDU3OutletsTableCurrentOutlet32 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU3OutletsTableCurrentValue 32 }

edPowerMgmtPDU3OutletsTableCurrentOutlet33 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU3OutletsTableCurrentValue 33 }

edPowerMgmtPDU3OutletsTableCurrentOutlet34 OBJECT-TYPE
        SYNTAX             Integer32
         ACCESS         read-only
        STATUS             mandatory
        DESCRIPTION
       "Actual value of Current for the outlet(Amp).The recieved value 
		if 1234 then actual value in decimal willbe 12.34 Amp, if recieved 
		value is 12 then 0.12 Amp .Returns 0 if not supported."
::= { edPowerMgmtPDU3OutletsTableCurrentValue 34 }


edPowerMgmtPDU3OutletsTableCurrentOutlet35 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU3OutletsTableCurrentValue 35 }


edPowerMgmtPDU3OutletsTableCurrentOutlet36 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU3OutletsTableCurrentValue 36 }


edPowerMgmtPDU3OutletsTableCurrentOutlet37 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU3OutletsTableCurrentValue 37 }


edPowerMgmtPDU3OutletsTableCurrentOutlet38 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU3OutletsTableCurrentValue 38 }


edPowerMgmtPDU3OutletsTableCurrentOutlet39 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU3OutletsTableCurrentValue 39 }


edPowerMgmtPDU3OutletsTableCurrentOutlet40 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU3OutletsTableCurrentValue 40 }


edPowerMgmtPDU3OutletsTableCurrentOutlet41 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU3OutletsTableCurrentValue 41 }


edPowerMgmtPDU3OutletsTableCurrentOutlet42 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU3OutletsTableCurrentValue 42 }









edPowerMgmtPDU3OutletsTableApearentEnergyOutlet1 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 1 }


edPowerMgmtPDU3OutletsTableApearentEnergyOutlet2 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 2 }

edPowerMgmtPDU3OutletsTableApearentEnergyOutlet3 OBJECT-TYPE
        SYNTAX             Integer32
         ACCESS         read-only
        STATUS             mandatory
        DESCRIPTION
      "Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 3 }


edPowerMgmtPDU3OutletsTableApearentEnergyOutlet4 OBJECT-TYPE
        SYNTAX             Integer32
         ACCESS         read-only
        STATUS             mandatory
        DESCRIPTION
      "Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 4 }


edPowerMgmtPDU3OutletsTableApearentEnergyOutlet5 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 5 }


edPowerMgmtPDU3OutletsTableApearentEnergyOutlet6 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 6 }


edPowerMgmtPDU3OutletsTableApearentEnergyOutlet7 OBJECT-TYPE
        SYNTAX             Integer32
         ACCESS         read-only
        STATUS             mandatory
        DESCRIPTION
        "Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 7 }


edPowerMgmtPDU3OutletsTableApearentEnergyOutlet8 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 8 }


edPowerMgmtPDU3OutletsTableApearentEnergyOutlet9 OBJECT-TYPE
        SYNTAX             Integer32
         ACCESS         read-only
        STATUS             mandatory
        DESCRIPTION
     "Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 9 }


edPowerMgmtPDU3OutletsTableApearentEnergyOutlet10 OBJECT-TYPE
        SYNTAX             Integer32
         ACCESS         read-only
        STATUS             mandatory
        DESCRIPTION
     "Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 10 }


edPowerMgmtPDU3OutletsTableApearentEnergyOutlet11 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 11 }


edPowerMgmtPDU3OutletsTableApearentEnergyOutlet12 OBJECT-TYPE
        SYNTAX             Integer32
         ACCESS         read-only
        STATUS             mandatory
        DESCRIPTION
   "Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 12 }


edPowerMgmtPDU3OutletsTableApearentEnergyOutlet13 OBJECT-TYPE
        SYNTAX             Integer32
         ACCESS         read-only
        STATUS             mandatory
        DESCRIPTION
      "Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 13 }


edPowerMgmtPDU3OutletsTableApearentEnergyOutlet14 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 14 }


edPowerMgmtPDU3OutletsTableApearentEnergyOutlet15 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 15 }


edPowerMgmtPDU3OutletsTableApearentEnergyOutlet16 OBJECT-TYPE
        SYNTAX             Integer32
         ACCESS         read-only
        STATUS             mandatory
        DESCRIPTION
          "Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 16 }


edPowerMgmtPDU3OutletsTableApearentEnergyOutlet17 OBJECT-TYPE
        SYNTAX             Integer32
         ACCESS         read-only
        STATUS             mandatory
        DESCRIPTION
          "Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 17 }


edPowerMgmtPDU3OutletsTableApearentEnergyOutlet18 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 18 }


edPowerMgmtPDU3OutletsTableApearentEnergyOutlet19 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 19 }


edPowerMgmtPDU3OutletsTableApearentEnergyOutlet20 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 20 }


edPowerMgmtPDU3OutletsTableApearentEnergyOutlet21 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 21 }


edPowerMgmtPDU3OutletsTableApearentEnergyOutlet22 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 22 }


edPowerMgmtPDU3OutletsTableApearentEnergyOutlet23 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 23 }


edPowerMgmtPDU3OutletsTableApearentEnergyOutlet24 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 24 }

edPowerMgmtPDU3OutletsTableApearentEnergyOutlet25 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 25 }


edPowerMgmtPDU3OutletsTableApearentEnergyOutlet26 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 26 }


edPowerMgmtPDU3OutletsTableApearentEnergyOutlet27 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 27 }

edPowerMgmtPDU3OutletsTableApearentEnergyOutlet28 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 28 }

edPowerMgmtPDU3OutletsTableApearentEnergyOutlet29 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 29 }

edPowerMgmtPDU3OutletsTableApearentEnergyOutlet30 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 30 }

edPowerMgmtPDU3OutletsTableApearentEnergyOutlet31 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 31 }

edPowerMgmtPDU3OutletsTableApearentEnergyOutlet32 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 32 }

edPowerMgmtPDU3OutletsTableApearentEnergyOutlet33 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 33 }

edPowerMgmtPDU3OutletsTableApearentEnergyOutlet34 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 34 }


edPowerMgmtPDU3OutletsTableApearentEnergyOutlet35 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 35 }


edPowerMgmtPDU3OutletsTableApearentEnergyOutlet36 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 36 }


edPowerMgmtPDU3OutletsTableApearentEnergyOutlet37 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 37 }


edPowerMgmtPDU3OutletsTableApearentEnergyOutlet38 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 38 }


edPowerMgmtPDU3OutletsTableApearentEnergyOutlet39 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 39 }


edPowerMgmtPDU3OutletsTableApearentEnergyOutlet40 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 40 }


edPowerMgmtPDU3OutletsTableApearentEnergyOutlet41 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 41 }


edPowerMgmtPDU3OutletsTableApearentEnergyOutlet42 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU3OutletsTableApearentEnergyValue 42 }





edPowerMgmtPDU3OutletsTableReactiveEnergyOutlet1 OBJECT-TYPE
        SYNTAX             Integer32
         ACCESS         read-only
        STATUS             mandatory
        DESCRIPTION
		"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 1 }


edPowerMgmtPDU3OutletsTableReactiveEnergyOutlet2 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 2 }

edPowerMgmtPDU3OutletsTableReactiveEnergyOutlet3 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 3 }


edPowerMgmtPDU3OutletsTableReactiveEnergyOutlet4 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 4 }


edPowerMgmtPDU3OutletsTableReactiveEnergyOutlet5 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 5 }


edPowerMgmtPDU3OutletsTableReactiveEnergyOutlet6 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 6 }


edPowerMgmtPDU3OutletsTableReactiveEnergyOutlet7 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 7 }


edPowerMgmtPDU3OutletsTableReactiveEnergyOutlet8 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 8 }


edPowerMgmtPDU3OutletsTableReactiveEnergyOutlet9 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 9 }


edPowerMgmtPDU3OutletsTableReactiveEnergyOutlet10 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 10 }


edPowerMgmtPDU3OutletsTableReactiveEnergyOutlet11 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 11 }


edPowerMgmtPDU3OutletsTableReactiveEnergyOutlet12 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 12 }


edPowerMgmtPDU3OutletsTableReactiveEnergyOutlet13 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 13 }


edPowerMgmtPDU3OutletsTableReactiveEnergyOutlet14 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 14 }


edPowerMgmtPDU3OutletsTableReactiveEnergyOutlet15 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 15 }


edPowerMgmtPDU3OutletsTableReactiveEnergyOutlet16 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 16 }


edPowerMgmtPDU3OutletsTableReactiveEnergyOutlet17 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 17 }


edPowerMgmtPDU3OutletsTableReactiveEnergyOutlet18 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 18 }


edPowerMgmtPDU3OutletsTableReactiveEnergyOutlet19 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 19 }


edPowerMgmtPDU3OutletsTableReactiveEnergyOutlet20 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 20 }


edPowerMgmtPDU3OutletsTableReactiveEnergyOutlet21 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 21 }


edPowerMgmtPDU3OutletsTableReactiveEnergyOutlet22 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 22 }


edPowerMgmtPDU3OutletsTableReactiveEnergyOutlet23 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 23 }


edPowerMgmtPDU3OutletsTableReactiveEnergyOutlet24 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 24 }

edPowerMgmtPDU3OutletsTableReactiveEnergyOutlet25 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 25 }


edPowerMgmtPDU3OutletsTableReactiveEnergyOutlet26 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 26 }


edPowerMgmtPDU3OutletsTableReactiveEnergyOutlet27 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 27 }

edPowerMgmtPDU3OutletsTableReactiveEnergyOutlet28 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 28 }

edPowerMgmtPDU3OutletsTableReactiveEnergyOutlet29 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 29 }

edPowerMgmtPDU3OutletsTableReactiveEnergyOutlet30 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 30 }

edPowerMgmtPDU3OutletsTableReactiveEnergyOutlet31 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 31 }

edPowerMgmtPDU3OutletsTableReactiveEnergyOutlet32 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 32 }

edPowerMgmtPDU3OutletsTableReactiveEnergyOutlet33 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 33 }

edPowerMgmtPDU3OutletsTableReactiveEnergyOutlet34 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 34 }


edPowerMgmtPDU3OutletsTableReactiveEnergyOutlet35 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 35 }


edPowerMgmtPDU3OutletsTableReactiveEnergyOutlet36 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 36 }


edPowerMgmtPDU3OutletsTableReactiveEnergyOutlet37 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 37 }


edPowerMgmtPDU3OutletsTableReactiveEnergyOutlet38 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 38 }


edPowerMgmtPDU3OutletsTableReactiveEnergyOutlet39 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 39 }


edPowerMgmtPDU3OutletsTableReactiveEnergyOutlet40 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 40 }


edPowerMgmtPDU3OutletsTableReactiveEnergyOutlet41 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 41 }


edPowerMgmtPDU3OutletsTableReactiveEnergyOutlet42 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU3OutletsTableReactiveEnergyValue 42 }




edPowerMgmtPDU3OutletsTableActiveEnergyOutlet1 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 1 }


edPowerMgmtPDU3OutletsTableActiveEnergyOutlet2 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 2 }

edPowerMgmtPDU3OutletsTableActiveEnergyOutlet3 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 3 }


edPowerMgmtPDU3OutletsTableActiveEnergyOutlet4 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 4 }


edPowerMgmtPDU3OutletsTableActiveEnergyOutlet5 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 5 }


edPowerMgmtPDU3OutletsTableActiveEnergyOutlet6 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 6 }


edPowerMgmtPDU3OutletsTableActiveEnergyOutlet7 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 7 }


edPowerMgmtPDU3OutletsTableActiveEnergyOutlet8 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 8 }


edPowerMgmtPDU3OutletsTableActiveEnergyOutlet9 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 9 }


edPowerMgmtPDU3OutletsTableActiveEnergyOutlet10 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 10 }


edPowerMgmtPDU3OutletsTableActiveEnergyOutlet11 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 11 }


edPowerMgmtPDU3OutletsTableActiveEnergyOutlet12 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 12 }


edPowerMgmtPDU3OutletsTableActiveEnergyOutlet13 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 13 }


edPowerMgmtPDU3OutletsTableActiveEnergyOutlet14 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 14 }


edPowerMgmtPDU3OutletsTableActiveEnergyOutlet15 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 15 }


edPowerMgmtPDU3OutletsTableActiveEnergyOutlet16 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 16 }


edPowerMgmtPDU3OutletsTableActiveEnergyOutlet17 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 17 }


edPowerMgmtPDU3OutletsTableActiveEnergyOutlet18 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 18 }


edPowerMgmtPDU3OutletsTableActiveEnergyOutlet19 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 19 }


edPowerMgmtPDU3OutletsTableActiveEnergyOutlet20 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 20 }


edPowerMgmtPDU3OutletsTableActiveEnergyOutlet21 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 21 }


edPowerMgmtPDU3OutletsTableActiveEnergyOutlet22 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 22 }


edPowerMgmtPDU3OutletsTableActiveEnergyOutlet23 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 23 }


edPowerMgmtPDU3OutletsTableActiveEnergyOutlet24 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 24 }

edPowerMgmtPDU3OutletsTableActiveEnergyOutlet25 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 25 }


edPowerMgmtPDU3OutletsTableActiveEnergyOutlet26 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 26 }


edPowerMgmtPDU3OutletsTableActiveEnergyOutlet27 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 27 }

edPowerMgmtPDU3OutletsTableActiveEnergyOutlet28 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 28 }

edPowerMgmtPDU3OutletsTableActiveEnergyOutlet29 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 29 }

edPowerMgmtPDU3OutletsTableActiveEnergyOutlet30 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 30 }

edPowerMgmtPDU3OutletsTableActiveEnergyOutlet31 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 31 }

edPowerMgmtPDU3OutletsTableActiveEnergyOutlet32 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 32 }

edPowerMgmtPDU3OutletsTableActiveEnergyOutlet33 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 33 }

edPowerMgmtPDU3OutletsTableActiveEnergyOutlet34 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 34 }


edPowerMgmtPDU3OutletsTableActiveEnergyOutlet35 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 35 }


edPowerMgmtPDU3OutletsTableActiveEnergyOutlet36 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 36 }


edPowerMgmtPDU3OutletsTableActiveEnergyOutlet37 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 37 }


edPowerMgmtPDU3OutletsTableActiveEnergyOutlet38 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 38 }


edPowerMgmtPDU3OutletsTableActiveEnergyOutlet39 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 39 }


edPowerMgmtPDU3OutletsTableActiveEnergyOutlet40 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 40 }


edPowerMgmtPDU3OutletsTableActiveEnergyOutlet41 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 41 }


edPowerMgmtPDU3OutletsTableActiveEnergyOutlet42 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU3OutletsTableActiveEnergyValue 42 }









edPowerMgmtPDU3OutletsTableInstantaneousPowerOutlet1 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 1 }


edPowerMgmtPDU3OutletsTableInstantaneousPowerOutlet2 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 2 }

edPowerMgmtPDU3OutletsTableInstantaneousPowerOutlet3 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 3 }


edPowerMgmtPDU3OutletsTableInstantaneousPowerOutlet4 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 4 }


edPowerMgmtPDU3OutletsTableInstantaneousPowerOutlet5 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 5 }


edPowerMgmtPDU3OutletsTableInstantaneousPowerOutlet6 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 6 }


edPowerMgmtPDU3OutletsTableInstantaneousPowerOutlet7 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 7 }


edPowerMgmtPDU3OutletsTableInstantaneousPowerOutlet8 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 8 }


edPowerMgmtPDU3OutletsTableInstantaneousPowerOutlet9 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 9 }


edPowerMgmtPDU3OutletsTableInstantaneousPowerOutlet10 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 10 }


edPowerMgmtPDU3OutletsTableInstantaneousPowerOutlet11 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 11 }


edPowerMgmtPDU3OutletsTableInstantaneousPowerOutlet12 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 12 }


edPowerMgmtPDU3OutletsTableInstantaneousPowerOutlet13 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 13 }


edPowerMgmtPDU3OutletsTableInstantaneousPowerOutlet14 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 14 }


edPowerMgmtPDU3OutletsTableInstantaneousPowerOutlet15 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 15 }


edPowerMgmtPDU3OutletsTableInstantaneousPowerOutlet16 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 16 }


edPowerMgmtPDU3OutletsTableInstantaneousPowerOutlet17 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 17 }


edPowerMgmtPDU3OutletsTableInstantaneousPowerOutlet18 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 18 }


edPowerMgmtPDU3OutletsTableInstantaneousPowerOutlet19 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 19 }


edPowerMgmtPDU3OutletsTableInstantaneousPowerOutlet20 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 20 }


edPowerMgmtPDU3OutletsTableInstantaneousPowerOutlet21 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 21 }


edPowerMgmtPDU3OutletsTableInstantaneousPowerOutlet22 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 22 }


edPowerMgmtPDU3OutletsTableInstantaneousPowerOutlet23 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 23 }


edPowerMgmtPDU3OutletsTableInstantaneousPowerOutlet24 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 24 }

edPowerMgmtPDU3OutletsTableInstantaneousPowerOutlet25 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 25 }


edPowerMgmtPDU3OutletsTableInstantaneousPowerOutlet26 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 26 }


edPowerMgmtPDU3OutletsTableInstantaneousPowerOutlet27 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 27 }

edPowerMgmtPDU3OutletsTableInstantaneousPowerOutlet28 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 28 }

edPowerMgmtPDU3OutletsTableInstantaneousPowerOutlet29 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 29 }

edPowerMgmtPDU3OutletsTableInstantaneousPowerOutlet30 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 30 }

edPowerMgmtPDU3OutletsTableInstantaneousPowerOutlet31 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 31 }

edPowerMgmtPDU3OutletsTableInstantaneousPowerOutlet32 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 32 }

edPowerMgmtPDU3OutletsTableInstantaneousPowerOutlet33 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 33 }

edPowerMgmtPDU3OutletsTableInstantaneousPowerOutlet34 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 34 }


edPowerMgmtPDU3OutletsTableInstantaneousPowerOutlet35 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 35 }


edPowerMgmtPDU3OutletsTableInstantaneousPowerOutlet36 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 36 }


edPowerMgmtPDU3OutletsTableInstantaneousPowerOutlet37 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 37 }


edPowerMgmtPDU3OutletsTableInstantaneousPowerOutlet38 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 38 }


edPowerMgmtPDU3OutletsTableInstantaneousPowerOutlet39 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 39 }


edPowerMgmtPDU3OutletsTableInstantaneousPowerOutlet40 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 40 }


edPowerMgmtPDU3OutletsTableInstantaneousPowerOutlet41 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 41 }


edPowerMgmtPDU3OutletsTableInstantaneousPowerOutlet42 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU3OutletsTableInstantaneousPowerValue 42 }







edPowerMgmtPDU3OutletsTablePowerFactorOutlet1 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 1 }


edPowerMgmtPDU3OutletsTablePowerFactorOutlet2 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 2 }

edPowerMgmtPDU3OutletsTablePowerFactorOutlet3 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 3 }


edPowerMgmtPDU3OutletsTablePowerFactorOutlet4 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 4 }


edPowerMgmtPDU3OutletsTablePowerFactorOutlet5 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 5 }


edPowerMgmtPDU3OutletsTablePowerFactorOutlet6 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 6 }


edPowerMgmtPDU3OutletsTablePowerFactorOutlet7 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 7 }


edPowerMgmtPDU3OutletsTablePowerFactorOutlet8 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 8 }


edPowerMgmtPDU3OutletsTablePowerFactorOutlet9 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 9 }


edPowerMgmtPDU3OutletsTablePowerFactorOutlet10 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 10 }


edPowerMgmtPDU3OutletsTablePowerFactorOutlet11 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 11 }


edPowerMgmtPDU3OutletsTablePowerFactorOutlet12 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 12 }


edPowerMgmtPDU3OutletsTablePowerFactorOutlet13 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 13 }


edPowerMgmtPDU3OutletsTablePowerFactorOutlet14 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 14 }


edPowerMgmtPDU3OutletsTablePowerFactorOutlet15 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 15 }


edPowerMgmtPDU3OutletsTablePowerFactorOutlet16 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 16 }


edPowerMgmtPDU3OutletsTablePowerFactorOutlet17 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 17 }


edPowerMgmtPDU3OutletsTablePowerFactorOutlet18 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 18 }


edPowerMgmtPDU3OutletsTablePowerFactorOutlet19 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 19 }


edPowerMgmtPDU3OutletsTablePowerFactorOutlet20 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 20 }


edPowerMgmtPDU3OutletsTablePowerFactorOutlet21 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 21 }


edPowerMgmtPDU3OutletsTablePowerFactorOutlet22 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 22 }


edPowerMgmtPDU3OutletsTablePowerFactorOutlet23 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 23 }


edPowerMgmtPDU3OutletsTablePowerFactorOutlet24 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 24 }

edPowerMgmtPDU3OutletsTablePowerFactorOutlet25 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 25 }


edPowerMgmtPDU3OutletsTablePowerFactorOutlet26 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 26 }


edPowerMgmtPDU3OutletsTablePowerFactorOutlet27 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 27 }

edPowerMgmtPDU3OutletsTablePowerFactorOutlet28 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 28 }

edPowerMgmtPDU3OutletsTablePowerFactorOutlet29 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 29 }

edPowerMgmtPDU3OutletsTablePowerFactorOutlet30 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 30 }

edPowerMgmtPDU3OutletsTablePowerFactorOutlet31 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 31 }

edPowerMgmtPDU3OutletsTablePowerFactorOutlet32 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 32 }

edPowerMgmtPDU3OutletsTablePowerFactorOutlet33 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 33 }

edPowerMgmtPDU3OutletsTablePowerFactorOutlet34 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 34 }


edPowerMgmtPDU3OutletsTablePowerFactorOutlet35 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 35 }


edPowerMgmtPDU3OutletsTablePowerFactorOutlet36 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 36 }


edPowerMgmtPDU3OutletsTablePowerFactorOutlet37 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 37 }


edPowerMgmtPDU3OutletsTablePowerFactorOutlet38 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 38 }


edPowerMgmtPDU3OutletsTablePowerFactorOutlet39 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 39 }


edPowerMgmtPDU3OutletsTablePowerFactorOutlet40 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 40 }


edPowerMgmtPDU3OutletsTablePowerFactorOutlet41 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 41 }


edPowerMgmtPDU3OutletsTablePowerFactorOutlet42 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU3OutletsTablePowerFactorValue 42 }







edPowerMgmtPDU3OutletsTableFreqOutlet1 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 1 }


edPowerMgmtPDU3OutletsTableFreqOutlet2 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 2 }

edPowerMgmtPDU3OutletsTableFreqOutlet3 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 3 }


edPowerMgmtPDU3OutletsTableFreqOutlet4 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 4 }


edPowerMgmtPDU3OutletsTableFreqOutlet5 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 5 }


edPowerMgmtPDU3OutletsTableFreqOutlet6 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 6 }


edPowerMgmtPDU3OutletsTableFreqOutlet7 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 7 }


edPowerMgmtPDU3OutletsTableFreqOutlet8 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 8 }


edPowerMgmtPDU3OutletsTableFreqOutlet9 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 9 }


edPowerMgmtPDU3OutletsTableFreqOutlet10 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 10 }


edPowerMgmtPDU3OutletsTableFreqOutlet11 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 11 }


edPowerMgmtPDU3OutletsTableFreqOutlet12 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 12 }


edPowerMgmtPDU3OutletsTableFreqOutlet13 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 13 }


edPowerMgmtPDU3OutletsTableFreqOutlet14 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 14 }


edPowerMgmtPDU3OutletsTableFreqOutlet15 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 15 }


edPowerMgmtPDU3OutletsTableFreqOutlet16 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 16 }


edPowerMgmtPDU3OutletsTableFreqOutlet17 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 17 }


edPowerMgmtPDU3OutletsTableFreqOutlet18 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 18 }


edPowerMgmtPDU3OutletsTableFreqOutlet19 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 19 }


edPowerMgmtPDU3OutletsTableFreqOutlet20 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 20 }


edPowerMgmtPDU3OutletsTableFreqOutlet21 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 21 }


edPowerMgmtPDU3OutletsTableFreqOutlet22 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 22 }


edPowerMgmtPDU3OutletsTableFreqOutlet23 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 23 }


edPowerMgmtPDU3OutletsTableFreqOutlet24 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 24 }

edPowerMgmtPDU3OutletsTableFreqOutlet25 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 25 }


edPowerMgmtPDU3OutletsTableFreqOutlet26 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 26 }


edPowerMgmtPDU3OutletsTableFreqOutlet27 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 27 }

edPowerMgmtPDU3OutletsTableFreqOutlet28 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 28 }

edPowerMgmtPDU3OutletsTableFreqOutlet29 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 29 }

edPowerMgmtPDU3OutletsTableFreqOutlet30 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 30 }

edPowerMgmtPDU3OutletsTableFreqOutlet31 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 31 }

edPowerMgmtPDU3OutletsTableFreqOutlet32 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 32 }

edPowerMgmtPDU3OutletsTableFreqOutlet33 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 33 }

edPowerMgmtPDU3OutletsTableFreqOutlet34 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 34 }


edPowerMgmtPDU3OutletsTableFreqOutlet35 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 35 }


edPowerMgmtPDU3OutletsTableFreqOutlet36 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 36 }


edPowerMgmtPDU3OutletsTableFreqOutlet37 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 37 }


edPowerMgmtPDU3OutletsTableFreqOutlet38 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 38 }


edPowerMgmtPDU3OutletsTableFreqOutlet39 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 39 }


edPowerMgmtPDU3OutletsTableFreqOutlet40 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 40 }


edPowerMgmtPDU3OutletsTableFreqOutlet41 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 41 }


edPowerMgmtPDU3OutletsTableFreqOutlet42 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU3OutletsTableFreqValue 42 }






edPowerMgmtPDU3OutletsTableControlOutlet1 OBJECT-TYPE
        SYNTAX INTEGER {
			switchingDisabled     (2),    			
			outletOn              (1),
			outletOff             (0)  
			
		}    
        ACCESS         read-write
        STATUS             mandatory
        DESCRIPTION
         "Getting this variable will return the outlet state. If 
       the outlet is on, the outletOn (1) value will be returned.
       If the outlet is off, the outletOff (0) value will be
       returned. and if returned 2 then switching is prohibited"
::= { edPowerMgmtPDU3OutletsTableOutletControl 1 }


edPowerMgmtPDU3OutletsTableControlOutlet2 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 2 }

edPowerMgmtPDU3OutletsTableControlOutlet3 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 3 }


edPowerMgmtPDU3OutletsTableControlOutlet4 OBJECT-TYPE
            SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 4 }


edPowerMgmtPDU3OutletsTableControlOutlet5 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 5 }


edPowerMgmtPDU3OutletsTableControlOutlet6 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 6 }


edPowerMgmtPDU3OutletsTableControlOutlet7 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 7 }


edPowerMgmtPDU3OutletsTableControlOutlet8 OBJECT-TYPE
            SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 8 }


edPowerMgmtPDU3OutletsTableControlOutlet9 OBJECT-TYPE
              SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 9 }


edPowerMgmtPDU3OutletsTableControlOutlet10 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 10 }


edPowerMgmtPDU3OutletsTableControlOutlet11 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 11 }


edPowerMgmtPDU3OutletsTableControlOutlet12 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 12 }


edPowerMgmtPDU3OutletsTableControlOutlet13 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 13 }


edPowerMgmtPDU3OutletsTableControlOutlet14 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 14 }


edPowerMgmtPDU3OutletsTableControlOutlet15 OBJECT-TYPE
           SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 15 }


edPowerMgmtPDU3OutletsTableControlOutlet16 OBJECT-TYPE
                SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 16 }


edPowerMgmtPDU3OutletsTableControlOutlet17 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 17 }


edPowerMgmtPDU3OutletsTableControlOutlet18 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 18 }


edPowerMgmtPDU3OutletsTableControlOutlet19 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 19 }


edPowerMgmtPDU3OutletsTableControlOutlet20 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 20 }


edPowerMgmtPDU3OutletsTableControlOutlet21 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 21 }


edPowerMgmtPDU3OutletsTableControlOutlet22 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 22 }


edPowerMgmtPDU3OutletsTableControlOutlet23 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 23 }


edPowerMgmtPDU3OutletsTableControlOutlet24 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 24 }

edPowerMgmtPDU3OutletsTableControlOutlet25 OBJECT-TYPE
           SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 25 }


edPowerMgmtPDU3OutletsTableControlOutlet26 OBJECT-TYPE
            SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 26 }


edPowerMgmtPDU3OutletsTableControlOutlet27 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 27 }

edPowerMgmtPDU3OutletsTableControlOutlet28 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 28 }

edPowerMgmtPDU3OutletsTableControlOutlet29 OBJECT-TYPE
                SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 29 }

edPowerMgmtPDU3OutletsTableControlOutlet30 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 30 }

edPowerMgmtPDU3OutletsTableControlOutlet31 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 31 }

edPowerMgmtPDU3OutletsTableControlOutlet32 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 32 }

edPowerMgmtPDU3OutletsTableControlOutlet33 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 33 }

edPowerMgmtPDU3OutletsTableControlOutlet34 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 34 }


edPowerMgmtPDU3OutletsTableControlOutlet35 OBJECT-TYPE
                SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 35 }


edPowerMgmtPDU3OutletsTableControlOutlet36 OBJECT-TYPE
                 SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 36 }


edPowerMgmtPDU3OutletsTableControlOutlet37 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 37 }


edPowerMgmtPDU3OutletsTableControlOutlet38 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 38 }


edPowerMgmtPDU3OutletsTableControlOutlet39 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 39 }


edPowerMgmtPDU3OutletsTableControlOutlet40 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 40 }


edPowerMgmtPDU3OutletsTableControlOutlet41 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 41 }


edPowerMgmtPDU3OutletsTableControlOutlet42 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU3OutletsTableOutletControl 42 }




edPowerMgmtPDU3TotalNumberOfPhases OBJECT-TYPE
        SYNTAX             Integer32
         ACCESS         		read-only
        STATUS             mandatory
        DESCRIPTION
        "Number of Phases managed by the appliance."
::= { edConectedPdu3Data 5 }

edPowerMgmtPDU3PhasesTable OBJECT IDENTIFIER::= { edConectedPdu3Data 6 }

edPowerMgmtPDU3PhasesData OBJECT IDENTIFIER::= { edPowerMgmtPDU3PhasesTable 1 }
edPowerMgmtPDU3PhasesTableIndexNumber OBJECT IDENTIFIER::= { edPowerMgmtPDU3PhasesData 1 }
edPowerMgmtPDU3PhasesTableVoltageValue OBJECT IDENTIFIER::= { edPowerMgmtPDU3PhasesData 2 }
edPowerMgmtPDU3PhasesTablecurrentValue OBJECT IDENTIFIER::= { edPowerMgmtPDU3PhasesData 3 }
edPowerMgmtPDU3PhasesTableApearentEnergyValue OBJECT IDENTIFIER::= { edPowerMgmtPDU3PhasesData 4 }
edPowerMgmtPDU3PhasesTableReactiveEnergyValue OBJECT IDENTIFIER::= { edPowerMgmtPDU3PhasesData 5 }
edPowerMgmtPDU3PhasesTableActiveEnergyValue OBJECT IDENTIFIER::= { edPowerMgmtPDU3PhasesData 6 }
edPowerMgmtPDU3PhasesTableInstantaneousPowerValue OBJECT IDENTIFIER::= { edPowerMgmtPDU3PhasesData 7 }
edPowerMgmtPDU3PhasesTablePowerFactorValue OBJECT IDENTIFIER::= { edPowerMgmtPDU3PhasesData 8 }

edPowerMgmtPDU3PhasesTableIndexNumber1 OBJECT-TYPE
        SYNTAX             Integer32
         ACCESS         read-only
        STATUS             mandatory
        DESCRIPTION
         "Index Number of the outlet in the PDU."
::= { edPowerMgmtPDU3PhasesTableIndexNumber 1 }

edPowerMgmtPDU3PhasesTableIndexNumber2 OBJECT-TYPE
        SYNTAX             Integer32
         ACCESS         read-only
        STATUS             mandatory
        DESCRIPTION
         "Index Number of the outlet in the PDU."
::= { edPowerMgmtPDU3PhasesTableIndexNumber 2 }


edPowerMgmtPDU3PhasesTableIndexNumber3 OBJECT-TYPE
        SYNTAX             Integer32
         ACCESS         read-only
        STATUS             mandatory
        DESCRIPTION
         "Index Number of the outlet in the PDU."
::= { edPowerMgmtPDU3PhasesTableIndexNumber 3 }


edPowerMgmtPDU3PhasesTableVoltageValuePhase1 OBJECT-TYPE
        SYNTAX             Integer32
         ACCESS         read-only
        STATUS             mandatory
        DESCRIPTION
        "Value of R Phase recieved from device.
		if recieved 23024 then actual value in decimal willbe 230.24 Volts ,
		if recieved 12 then 0.12 Volt. Returns 0 if not supported."
::= { edPowerMgmtPDU3PhasesTableVoltageValue 1 }

edPowerMgmtPDU3PhasesTableVoltageValuePhase2 OBJECT-TYPE
        SYNTAX             Integer32
         ACCESS         read-only
        STATUS             mandatory
        DESCRIPTION
        "Value of Y Phase recieved from device.
		if recieved 23024 then actual value in decimal willbe 230.24 Volts ,
		if recieved 12 then 0.12 Volt. Returns 0 if not supported."
::= { edPowerMgmtPDU3PhasesTableVoltageValue 2 }

edPowerMgmtPDU3PhasesTableVoltageValuePhase3 OBJECT-TYPE
        SYNTAX             Integer32
         ACCESS         read-only
        STATUS             mandatory
        DESCRIPTION
        "Value of B Phase recieved from device.
		if recieved 23024 then actual value in decimal willbe 230.24 Volts ,
		if recieved 12 then 0.12 Volt. Returns 0 if not supported."
::= { edPowerMgmtPDU3PhasesTableVoltageValue 3 }


edPowerMgmtPDU3PhasesTablecurrentPhase1 OBJECT-TYPE
        SYNTAX             Integer32
         ACCESS         read-only
        STATUS             mandatory
        DESCRIPTION
        "Current of R Phase in Ampere ,if recieved 1234 then actual value in decimal willbe 12.34 Amp, if recieved 
		value is 12 then 0.12 Amp .Returns 0 if not supported."
::= { edPowerMgmtPDU3PhasesTablecurrentValue 1 }


edPowerMgmtPDU3PhasesTablecurrentPhase2 OBJECT-TYPE
        SYNTAX             Integer32
         ACCESS         read-only
        STATUS             mandatory
        DESCRIPTION
        "Current of Y Phase in Ampere ,if recieved 1234 then actual value in decimal willbe 12.34 Amp, if recieved 
		value is 12 then 0.12 Amp .Returns 0 if not supported."
::= { edPowerMgmtPDU3PhasesTablecurrentValue 2 }



edPowerMgmtPDU3PhasesTablecurrentPhase3 OBJECT-TYPE
        SYNTAX             Integer32
         ACCESS         read-only
        STATUS             mandatory
        DESCRIPTION
        "Current of B Phase in Ampere ,if recieved 1234 then actual value in decimal willbe 12.34 Amp, if recieved 
		value is 12 then 0.12 Amp .Returns 0 if not supported."
::= { edPowerMgmtPDU3PhasesTablecurrentValue 3 }



edPowerMgmtPDU3PhasesTableApearentEnergyPhase1 OBJECT-TYPE
        SYNTAX             Integer32
         ACCESS         read-only
        STATUS             mandatory
        DESCRIPTION
        "ApearentEnergy(KVaHr) of R Phase if recieved 23024 then actual value in decimal willbe 2.3024 KVaHr , if recieved 12
	   then 0.0012 KVaHr. Returns 0 if not supported."
::= { edPowerMgmtPDU3PhasesTableApearentEnergyValue 1 }


edPowerMgmtPDU3PhasesTableApearentEnergyPhase2 OBJECT-TYPE
        SYNTAX             Integer32
         ACCESS         read-only
        STATUS             mandatory
        DESCRIPTION
        "ApearentEnergy(KVaHr) of Y Phase if recieved 23024 then actual value in decimal willbe 2.3024 KVaHr , if recieved 12
	   then 0.0012 KVaHr. Returns 0 if not supported."
::= { edPowerMgmtPDU3PhasesTableApearentEnergyValue 2 }

edPowerMgmtPDU3PhasesTableApearentEnergyPhase3 OBJECT-TYPE
        SYNTAX             Integer32
         ACCESS         read-only
        STATUS             mandatory
        DESCRIPTION
        "ApearentEnergy(KVaHr) of B Phase if recieved 23024 then actual value in decimal willbe 2.3024 KVaHr , if recieved 12
	   then 0.0012 KVaHr. Returns 0 if not supported."
::= { edPowerMgmtPDU3PhasesTableApearentEnergyValue 3 }


edPowerMgmtPDU3PhasesTableReactiveEnergyPhase1 OBJECT-TYPE
        SYNTAX             Integer32
         ACCESS         read-only
        STATUS             mandatory
        DESCRIPTION
        "ReactiveEnergy(KVarHr) of R Phase if recieved 23024 then actual value in decimal willbe 2.3024 KVaHr , if recieved 12
	   then 0.0012 KVaHr. Returns 0 if not supported."
::= { edPowerMgmtPDU3PhasesTableReactiveEnergyValue 1 }



edPowerMgmtPDU3PhasesTableReactiveEnergyPhase2 OBJECT-TYPE
        SYNTAX             Integer32
         ACCESS         read-only
        STATUS             mandatory
        DESCRIPTION
        "ReactiveEnergy(KVarHr) of Y Phase if recieved 23024 then actual value in decimal willbe 2.3024 KVaHr , if recieved 12
	   then 0.0012 KVaHr. Returns 0 if not supported."
::= { edPowerMgmtPDU3PhasesTableReactiveEnergyValue 2 }



edPowerMgmtPDU3PhasesTableReactiveEnergyPhase3 OBJECT-TYPE
        SYNTAX             Integer32
         ACCESS         read-only
        STATUS             mandatory
        DESCRIPTION
        "ReactiveEnergy(KVarHr) of B Phase if recieved 23024 then actual value in decimal willbe 2.3024 KVaHr , if recieved 12
	   then 0.0012 KVaHr. Returns 0 if not supported."
::= { edPowerMgmtPDU3PhasesTableReactiveEnergyValue 3 }

edPowerMgmtPDU3PhasesTableActiveEnergyPhase1 OBJECT-TYPE
        SYNTAX             Integer32
         ACCESS         read-only
        STATUS             mandatory
        DESCRIPTION
        "ActiveEnergy(KWattHr) of R Phase if recieved 23024 then actual value in decimal willbe 2.3024 KVaHr , if recieved 12
	   then 0.0012 KVaHr. Returns 0 if not supported."
::= { edPowerMgmtPDU3PhasesTableActiveEnergyValue 1 }

edPowerMgmtPDU3PhasesTableActiveEnergyPhase2 OBJECT-TYPE
        SYNTAX             Integer32
         ACCESS         read-only
        STATUS             mandatory
        DESCRIPTION
        "ActiveEnergy(KWattHr) of Y Phase if recieved 23024 then actual value in decimal willbe 2.3024 KVaHr , if recieved 12
	   then 0.0012 KVaHr. Returns 0 if not supported."
::= { edPowerMgmtPDU3PhasesTableActiveEnergyValue 2 }

edPowerMgmtPDU3PhasesTableActiveEnergyPhase3 OBJECT-TYPE
        SYNTAX             Integer32
         ACCESS         read-only
        STATUS             mandatory
        DESCRIPTION
        "ActiveEnergy(KWattHr) of B Phase if recieved 23024 then actual value in decimal willbe 2.3024 KVaHr , if recieved 12
	   then 0.0012 KVaHr. Returns 0 if not supported."
::= { edPowerMgmtPDU3PhasesTableActiveEnergyValue 3 }


edPowerMgmtPDU3PhasesTableInstantaneousPowerPhase1 OBJECT-TYPE
        SYNTAX             Integer32
         ACCESS         read-only
        STATUS             mandatory
        DESCRIPTION
        "Instantaneous Power(KWatt) of R Phase if recieved 23024 then actual value in decimal willbe 2.3024 KVaHr , if recieved 12
	   then 0.0012 KVaHr. Returns 0 if not supported."
::= { edPowerMgmtPDU3PhasesTableInstantaneousPowerValue 1 }


edPowerMgmtPDU3PhasesTableInstantaneousPowerPhase2 OBJECT-TYPE
        SYNTAX             Integer32
         ACCESS         read-only
        STATUS             mandatory
        DESCRIPTION
        "Instantaneous Power(KWatt) of Y Phase if recieved 23024 then actual value in decimal willbe 2.3024 KVaHr , if recieved 12
	   then 0.0012 KVaHr. Returns 0 if not supported."
::= { edPowerMgmtPDU3PhasesTableInstantaneousPowerValue 2 }


edPowerMgmtPDU3PhasesTableInstantaneousPowerPhase3 OBJECT-TYPE
        SYNTAX             Integer32
         ACCESS         read-only
        STATUS             mandatory
        DESCRIPTION
        "Instantaneous Power(KWatt) of B Phase if recieved 23024 then actual value in decimal willbe 2.3024 KVaHr , if recieved 12
	   then 0.0012 KVaHr. Returns 0 if not supported."
::= { edPowerMgmtPDU3PhasesTableInstantaneousPowerValue 3 }


edPowerMgmtPDU3PhasesTablePowerFactorPhase1 OBJECT-TYPE
        SYNTAX             Integer32
         ACCESS         read-only
        STATUS             mandatory
        DESCRIPTION
        "average of powerfactor(pF) R Phase.The recieved value 
		if 9999 then actual value in decimal willbe 99.99 pf , if recieved 12
		then 0.12 pf. Returns 0 if not supported."
::= { edPowerMgmtPDU3PhasesTablePowerFactorValue 1 }

edPowerMgmtPDU3PhasesTablePowerFactorPhase2 OBJECT-TYPE
        SYNTAX             Integer32
         ACCESS         read-only
        STATUS             mandatory
        DESCRIPTION
        "average of powerfactor(pF) Y Phase.The recieved value 
		if 9999 then actual value in decimal willbe 99.99 pf , if recieved 12
		then 0.12 pf. Returns 0 if not supported."
::= { edPowerMgmtPDU3PhasesTablePowerFactorValue 2 }

edPowerMgmtPDU3PhasesTablePowerFactorPhase3 OBJECT-TYPE
        SYNTAX             Integer32
         ACCESS         read-only
        STATUS             mandatory
        DESCRIPTION
        "average of powerfactor(pF) B Phase.The recieved value 
		if 9999 then actual value in decimal willbe 99.99 pf , if recieved 12
		then 0.12 pf. Returns 0 if not supported."
::= { edPowerMgmtPDU3PhasesTablePowerFactorValue 3 }


edPowerMgmtPDU3TotalNumberOfSensor OBJECT-TYPE
        SYNTAX             Integer32
         ACCESS         read-only
        STATUS             mandatory
        DESCRIPTION
        "Number of Sensors managed by the appliance."
::= { edConectedPdu3Data 7 }


edPowerMgmtPDU3SensorsTable OBJECT IDENTIFIER ::= { edConectedPdu3Data 8 }

edPowerMgmtPDU3SensorsData OBJECT IDENTIFIER ::= { edPowerMgmtPDU3SensorsTable 1 }

edPowerMgmtPDU3SensorsTableNumber OBJECT IDENTIFIER ::= { edPowerMgmtPDU3SensorsData 1 }
edPowerMgmtPDU3SensorsTableSensorType OBJECT IDENTIFIER ::= { edPowerMgmtPDU3SensorsData 2 }
edPowerMgmtPDU3SensorsTableSensorValue OBJECT IDENTIFIER::= { edPowerMgmtPDU3SensorsData 3 }

edPowerMgmtPDU3SensorsTableSensor1 OBJECT-TYPE
        SYNTAX             Integer32
         ACCESS         read-only
        STATUS             mandatory
        DESCRIPTION
        "Number of the sensor in the PDU."
::= { edPowerMgmtPDU3SensorsTableNumber 1 }


edPowerMgmtPDU3SensorsTableSensor2 OBJECT-TYPE
        SYNTAX             Integer32
         ACCESS         read-only
        STATUS             mandatory
        DESCRIPTION
        "Number of the sensor in the PDU."
::= { edPowerMgmtPDU3SensorsTableNumber 2 }


edPowerMgmtPDU3SensorsTableSensor3 OBJECT-TYPE
        SYNTAX             Integer32
         ACCESS         read-only
        STATUS             mandatory
        DESCRIPTION
        "Number of the sensor in the PDU."
::= { edPowerMgmtPDU3SensorsTableNumber 3 }

edPowerMgmtPDU3SensorsTableSensor4 OBJECT-TYPE
        SYNTAX             Integer32
         ACCESS         read-only
        STATUS             mandatory
        DESCRIPTION
        "Number of the sensor in the PDU."
::= { edPowerMgmtPDU3SensorsTableNumber 4 }

edPowerMgmtPDU3SensorsTableSensorType1 OBJECT-TYPE
         SYNTAX INTEGER {
		humidity     (2),    			
		temprature   (1),
		nosens      (0)  
		
		}
         ACCESS         read-only
        STATUS             mandatory
        DESCRIPTION
        "returns value displaying type of Sensor."
::= { edPowerMgmtPDU3SensorsTableSensorType 1 }

edPowerMgmtPDU3SensorsTableSensorType2 OBJECT-TYPE
         SYNTAX INTEGER {
		humidity     (2),    			
		temprature   (1),
		nosens      (0)  
		
		}
         ACCESS         read-only
        STATUS             mandatory
        DESCRIPTION
        "returns value displaying type of Sensor."
::= { edPowerMgmtPDU3SensorsTableSensorType 2 }

edPowerMgmtPDU3SensorsTableSensorType3 OBJECT-TYPE
         SYNTAX INTEGER {
		humidity     (2),    			
		temprature   (1),
		nosens      (0)  
		
		}
         ACCESS         read-only
        STATUS             mandatory
        DESCRIPTION
        "returns value displaying type of Sensor."
::= { edPowerMgmtPDU3SensorsTableSensorType 3 }


edPowerMgmtPDU3SensorsTableSensorType4 OBJECT-TYPE
        SYNTAX INTEGER {
		humidity     (2),    			
		temprature   (1),
		nosens      (0)  
		
		}
         ACCESS         read-only
        STATUS             mandatory
        DESCRIPTION
        "returns value displaying type of Sensor."
::= { edPowerMgmtPDU3SensorsTableSensorType 4 }



edPowerMgmtPDU3SensorsTableSensorValueSensor1 OBJECT-TYPE
        SYNTAX             Integer32
         ACCESS         read-only
        STATUS             mandatory
        DESCRIPTION
        "returns value of Sensor
         Returns 0 if not supported."
::= { edPowerMgmtPDU3SensorsTableSensorValue 1 }

edPowerMgmtPDU3SensorsTableSensorValueSensor2 OBJECT-TYPE
        SYNTAX             Integer32
         ACCESS         read-only
        STATUS             mandatory
        DESCRIPTION
        "returns value of Sensor
         Returns 0 if not supported."
::= { edPowerMgmtPDU3SensorsTableSensorValue 2 }

edPowerMgmtPDU3SensorsTableSensorValueSensor3 OBJECT-TYPE
        SYNTAX             Integer32
         ACCESS         read-only
        STATUS             mandatory
        DESCRIPTION
        "returns value of Sensor
         Returns 0 if not supported."
::= { edPowerMgmtPDU3SensorsTableSensorValue 3 }

edPowerMgmtPDU3SensorsTableSensorValueSensor4 OBJECT-TYPE
        SYNTAX             Integer32
         ACCESS         read-only
        STATUS             mandatory
        DESCRIPTION
        "returns value of Sensor
         Returns 0 if not supported."
::= { edPowerMgmtPDU3SensorsTableSensorValue 4 }






----------- Daisy Chaining pduData 3 Ends ----------------------

----------- Daisy Chaining pduData  4 ----------------------


edConectedPdu4Data OBJECT IDENTIFIER::= { edConnectedPduMgmt 4 }

edPowerMgmtPDU4TableData OBJECT IDENTIFIER::= { edConectedPdu4Data 1 }

edPowerMgmtPDU4TableNumber       OBJECT-TYPE
        SYNTAX             Integer32
         ACCESS         read-only
        STATUS             mandatory
        DESCRIPTION
        "Index Number"
::= { edPowerMgmtPDU4TableData 1 }

edPowerMgmtPDU4TableProductCode      OBJECT-TYPE
        SYNTAX             DisplayString
         ACCESS         read-only
        STATUS             mandatory
        DESCRIPTION
        "Version of the PDU firmware.
         Returns N/A if not applicable."
::= { edPowerMgmtPDU4TableData 2 }



edPowerMgmtPDU4TableSerialNumber OBJECT-TYPE
        SYNTAX             Integer32
         ACCESS         read-only
        STATUS             mandatory
        DESCRIPTION
        "Number of outlets of the PDU."
::= { edPowerMgmtPDU4TableData 3 }



edPowerMgmtPDU4TableFirmwareVersion       OBJECT-TYPE
        SYNTAX             DisplayString
         ACCESS         read-only
        STATUS             mandatory
        DESCRIPTION
        "Version of the PDU firmware.
         Returns N/A if not applicable."
::= { edPowerMgmtPDU4TableData 4 }



edPowerMgmtPDU4TableNumberOfOutlets OBJECT-TYPE
        SYNTAX             Integer32
         ACCESS         read-only
        STATUS             mandatory
        DESCRIPTION
        "Number of outlets of the PDU."
::= { edPowerMgmtPDU4TableData 5 }

edPowerMgmtPDU4TableNumberOfPhases OBJECT-TYPE
        SYNTAX             Integer32
         ACCESS         read-only
        STATUS             mandatory
        DESCRIPTION
        "Number of phases of the PDU."
::= { edPowerMgmtPDU4TableData 6 }


edPowerMgmtPDU4TableNumberOfSensors OBJECT-TYPE
        SYNTAX             Integer32
         ACCESS         read-only
        STATUS             mandatory
        DESCRIPTION
        "Number of sensors in the PDU."
::= { edPowerMgmtPDU4TableData 7 }



edPowerMgmtPDU4TableVendor   OBJECT-TYPE
        SYNTAX             DisplayString
         ACCESS         	  read-only
        STATUS             mandatory
        DESCRIPTION
        "Vendor of the PDU.
         Returns N/A if not applicable."
::= { edPowerMgmtPDU4TableData 8 }


edPowerMgmtPDU4AggrInfoTable OBJECT IDENTIFIER::= { edConectedPdu4Data 2 }

edPowerMgmtPDU4AggrsData OBJECT IDENTIFIER::= { edPowerMgmtPDU4AggrInfoTable 1 }


edPowerMgmtPDU4AggrInfoNumber       OBJECT-TYPE
        SYNTAX             		Integer32
         ACCESS         			read-only
        STATUS             		mandatory
        DESCRIPTION
        "Index Number"
::= { edPowerMgmtPDU4AggrsData 1 }
 


edPowerMgmtPDU4AggrInfoTableVoltageValue OBJECT-TYPE
        SYNTAX             Integer32
         ACCESS         read-only
        STATUS             mandatory
        DESCRIPTION
		"Aggrgate voltage of phase is (if vRphase R > vYphase && vRphase R > vBphase) 
		aggregate voltage of R Phase .The recieved value 
		if 23024 then actual value in decimal willbe 230.24 Volts ,
		if recieved 12 then 0.12 Volt. Returns 0 if not supported."
::= { edPowerMgmtPDU4AggrsData 2 }


edPowerMgmtPDU4AggrInfoTableCurrentValue OBJECT-TYPE
        SYNTAX             Integer32
         ACCESS         read-only
        STATUS             mandatory
        DESCRIPTION
        "Addition of mandatory of all Outlet.The recieved value 
		if 1234 then actual value in decimal willbe 12.34 Amp, if recieved 
		value is 12 then 0.12 Amp .Returns 0 if not supported."
::= { edPowerMgmtPDU4AggrsData 3 }


edPowerMgmtPDU4AggrInfoTableApearentEnergyValue OBJECT-TYPE
        SYNTAX             Integer32
         ACCESS         read-only
        STATUS             mandatory
        DESCRIPTION
       "addition of ApearentEnergy(KVaHr) of all outlet.The recieved value
	   if 23024 then actual value in decimal willbe 2.3024 KVaHr , if recieved 12
	   then 0.0012 KVaHr. Returns 0 if not supported."
::= { edPowerMgmtPDU4AggrsData 4 }


edPowerMgmtPDU4AggrInfoTableReactiveEnergyValue OBJECT-TYPE
        SYNTAX             Integer32
         ACCESS         read-only
        STATUS             mandatory
        DESCRIPTION
         "addition of ReactiveEnergy(KVarHr) of all outlet.The recieved value 
		 if 23024 then actual value in decimal willbe 2.3024 KVarHr , if recieved 12 
		 then 0.0012 KVarHr. Returns 0 if not supported."
::= { edPowerMgmtPDU4AggrsData 5 }

edPowerMgmtPDU4AggrInfoTableActiveEnergyValue OBJECT-TYPE
        SYNTAX             Integer32
         ACCESS         read-only
        STATUS             mandatory
        DESCRIPTION
      "addition of ActiveEnergy(KWattHr) of all outlets.The recieved value 
	  if 23024 then actual value in decimal willbe 2.3024 KWattHr , if recieved 12
	  then 0.0012 KWattHr. Returns 0 if not supported."
::= { edPowerMgmtPDU4AggrsData 6 }


edPowerMgmtPDU4AggrInfoTableInstantaneousPowerValue OBJECT-TYPE
        SYNTAX             Integer32
         ACCESS         read-only
        STATUS             mandatory
        DESCRIPTION
      "addition of  Instantaneous Power(KWatt) of all outlet.The recieved value 
	  if 230 then actual value in decimal willbe 2.30 KWatt , if recieved 12 
	  then 0.12 KWatt. Returns 0 if not supported."
::= { edPowerMgmtPDU4AggrsData 7 }

edPowerMgmtPDU4AggrInfoTablePowerFactorValue OBJECT-TYPE
        SYNTAX             Integer32
         ACCESS         read-only
        STATUS             mandatory
        DESCRIPTION
      	"average of powerfactor(pF) of all outlet.The recieved value 
		if 9999 then actual value in decimal willbe 99.99 pf , if recieved 12
		then 0.12 pf. Returns 0 if not supported."

::= { edPowerMgmtPDU4AggrsData 8 }


edPowerMgmtPDU4TotalNumberOfOutlets OBJECT-TYPE
        SYNTAX             Integer32
         ACCESS         read-only
        STATUS             mandatory
        DESCRIPTION
        "Number of outlets managed by the appliance."
::= { edConectedPdu4Data 3 }
 


edPowerMgmtPDU4OutletsTable OBJECT IDENTIFIER::= { edConectedPdu4Data 4 }

edPowerMgmtPDU4OutletData OBJECT IDENTIFIER::= { edPowerMgmtPDU4OutletsTable 1 }

edPowerMgmtPDU4OutletsTableIndex        			OBJECT IDENTIFIER::= { edPowerMgmtPDU4OutletData 1 }
edPowerMgmtPDU4OutletsTableIndexNumber        		OBJECT IDENTIFIER::= { edPowerMgmtPDU4OutletsTableIndex 1 }

edPowerMgmtPDU4OutletsTableVoltage        			OBJECT IDENTIFIER::= { edPowerMgmtPDU4OutletData 2 }
edPowerMgmtPDU4OutletsTableVoltageValue        		OBJECT IDENTIFIER::= { edPowerMgmtPDU4OutletsTableVoltage 1 }
edPowerMgmtPDU4OutletsTableCurrent       	 		OBJECT IDENTIFIER::= { edPowerMgmtPDU4OutletData 3 }
edPowerMgmtPDU4OutletsTableCurrentValue        		OBJECT IDENTIFIER::= { edPowerMgmtPDU4OutletsTableCurrent 1 }
edPowerMgmtPDU4OutletsTableApearentEnergy   		OBJECT IDENTIFIER::= { edPowerMgmtPDU4OutletData 4 }
edPowerMgmtPDU4OutletsTableApearentEnergyValue      OBJECT IDENTIFIER::= { edPowerMgmtPDU4OutletsTableApearentEnergy 1 }
edPowerMgmtPDU4OutletsTableReactiveEnergy      		OBJECT IDENTIFIER::= { edPowerMgmtPDU4OutletData 5 }
edPowerMgmtPDU4OutletsTableReactiveEnergyValue      OBJECT IDENTIFIER::= { edPowerMgmtPDU4OutletsTableReactiveEnergy 1 }
edPowerMgmtPDU4OutletsTableActiveEnergy  			OBJECT IDENTIFIER::= { edPowerMgmtPDU4OutletData 6 }
edPowerMgmtPDU4OutletsTableActiveEnergyValue        OBJECT IDENTIFIER::= { edPowerMgmtPDU4OutletsTableActiveEnergy 1 }
edPowerMgmtPDU4OutletsTableInstantaneousPower  		OBJECT IDENTIFIER::= { edPowerMgmtPDU4OutletData 7 }
edPowerMgmtPDU4OutletsTableInstantaneousPowerValue  OBJECT IDENTIFIER::= { edPowerMgmtPDU4OutletsTableInstantaneousPower 1 }
edPowerMgmtPDU4OutletsTablePowerFactor    			OBJECT IDENTIFIER::= { edPowerMgmtPDU4OutletData 8 }
edPowerMgmtPDU4OutletsTablePowerFactorValue        	OBJECT IDENTIFIER::= { edPowerMgmtPDU4OutletsTablePowerFactor 1 }
edPowerMgmtPDU4OutletsTableFreq    					OBJECT IDENTIFIER::= { edPowerMgmtPDU4OutletData 9 }
edPowerMgmtPDU4OutletsTableFreqValue        		OBJECT IDENTIFIER::= { edPowerMgmtPDU4OutletsTableFreq 1 }
edPowerMgmtPDU4OutletsTableOutletswitching        	OBJECT IDENTIFIER::= { edPowerMgmtPDU4OutletData 10 }
edPowerMgmtPDU4OutletsTableOutletControl        	OBJECT IDENTIFIER::= { edPowerMgmtPDU4OutletsTableOutletswitching 1 }





edPowerMgmtPDU4OutletsTableIndexNumber1 OBJECT-TYPE
        SYNTAX             Integer32
         ACCESS         read-only
        STATUS             mandatory
        DESCRIPTION
         "Index Number of the outlet in the PDU."
::= { edPowerMgmtPDU4OutletsTableIndexNumber 1 }


edPowerMgmtPDU4OutletsTableIndexNumber2 OBJECT-TYPE
        SYNTAX             Integer32
         ACCESS         read-only
        STATUS             mandatory
        DESCRIPTION
         "Index Number of the outlet in the PDU."
::= { edPowerMgmtPDU4OutletsTableIndexNumber 2 }

edPowerMgmtPDU4OutletsTableIndexNumber3 OBJECT-TYPE
        SYNTAX             Integer32
         ACCESS         read-only
        STATUS             mandatory
        DESCRIPTION
        "Index Number of the outlet in the PDU."
::= { edPowerMgmtPDU4OutletsTableIndexNumber 3 }


edPowerMgmtPDU4OutletsTableIndexNumber4 OBJECT-TYPE
        SYNTAX             Integer32
         ACCESS         read-only
        STATUS             mandatory
        DESCRIPTION
        "Index Number of the outlet in the PDU."
::= { edPowerMgmtPDU4OutletsTableIndexNumber 4 }


edPowerMgmtPDU4OutletsTableIndexNumber5 OBJECT-TYPE
        SYNTAX             Integer32
         ACCESS         read-only
        STATUS             mandatory
        DESCRIPTION
        "Index Number of the outlet in the PDU."
::= { edPowerMgmtPDU4OutletsTableIndexNumber 5 }


edPowerMgmtPDU4OutletsTableIndexNumber6 OBJECT-TYPE
        SYNTAX             Integer32
         ACCESS         read-only
        STATUS             mandatory
        DESCRIPTION
         "Index Number of the outlet in the PDU."
::= { edPowerMgmtPDU4OutletsTableIndexNumber 6 }


edPowerMgmtPDU4OutletsTableIndexNumber7 OBJECT-TYPE
        SYNTAX             Integer32
         ACCESS         read-only
        STATUS             mandatory
        DESCRIPTION
        "Index Number of the outlet in the PDU."
::= { edPowerMgmtPDU4OutletsTableIndexNumber 7 }


edPowerMgmtPDU4OutletsTableIndexNumber8 OBJECT-TYPE
        SYNTAX             Integer32
         ACCESS         read-only
        STATUS             mandatory
        DESCRIPTION
       "Index Number of the outlet in the PDU."
::= { edPowerMgmtPDU4OutletsTableIndexNumber 8 }


edPowerMgmtPDU4OutletsTableIndexNumber9 OBJECT-TYPE
        SYNTAX             Integer32
         ACCESS         read-only
        STATUS             mandatory
        DESCRIPTION
         "Index Number of the outlet in the PDU."
::= { edPowerMgmtPDU4OutletsTableIndexNumber 9 }


edPowerMgmtPDU4OutletsTableIndexNumber10 OBJECT-TYPE
        SYNTAX             Integer32
         ACCESS         read-only
        STATUS             mandatory
        DESCRIPTION
        "Index Number of the outlet in the PDU."
::= { edPowerMgmtPDU4OutletsTableIndexNumber 10 }


edPowerMgmtPDU4OutletsTableIndexNumber11 OBJECT-TYPE
        SYNTAX             Integer32
         ACCESS         read-only
        STATUS             mandatory
        DESCRIPTION
      "Index Number of the outlet in the PDU."
::= { edPowerMgmtPDU4OutletsTableIndexNumber 11 }


edPowerMgmtPDU4OutletsTableIndexNumber12 OBJECT-TYPE
        SYNTAX             Integer32
         ACCESS         read-only
        STATUS             mandatory
        DESCRIPTION
       "Index Number of the outlet in the PDU."
::= { edPowerMgmtPDU4OutletsTableIndexNumber 12 }


edPowerMgmtPDU4OutletsTableIndexNumber13 OBJECT-TYPE
        SYNTAX             Integer32
         ACCESS         read-only
        STATUS             mandatory
        DESCRIPTION
        "Index Number of the outlet in the PDU."
::= { edPowerMgmtPDU4OutletsTableIndexNumber 13 }


edPowerMgmtPDU4OutletsTableIndexNumber14 OBJECT-TYPE
        SYNTAX             Integer32
         ACCESS         read-only
        STATUS             mandatory
        DESCRIPTION
       "Index Number of the outlet in the PDU."
::= { edPowerMgmtPDU4OutletsTableIndexNumber 14 }


edPowerMgmtPDU4OutletsTableIndexNumber15 OBJECT-TYPE
        SYNTAX             Integer32
         ACCESS         read-only
        STATUS             mandatory
        DESCRIPTION
       "Index Number of the outlet in the PDU."
::= { edPowerMgmtPDU4OutletsTableIndexNumber 15 }


edPowerMgmtPDU4OutletsTableIndexNumber16 OBJECT-TYPE
        SYNTAX             Integer32
         ACCESS         read-only
        STATUS             mandatory
        DESCRIPTION
      "Index Number of the outlet in the PDU."
::= { edPowerMgmtPDU4OutletsTableIndexNumber 16 }


edPowerMgmtPDU4OutletsTableIndexNumber17 OBJECT-TYPE
        SYNTAX             Integer32
         ACCESS         read-only
        STATUS             mandatory
        DESCRIPTION
       "Index Number of the outlet in the PDU."
::= { edPowerMgmtPDU4OutletsTableIndexNumber 17 }


edPowerMgmtPDU4OutletsTableIndexNumber18 OBJECT-TYPE
        SYNTAX             Integer32
         ACCESS         read-only
        STATUS             mandatory
        DESCRIPTION
          "Index Number of the outlet in the PDU."
::= { edPowerMgmtPDU4OutletsTableIndexNumber 18 }


edPowerMgmtPDU4OutletsTableIndexNumber19 OBJECT-TYPE
        SYNTAX             Integer32
         ACCESS         read-only
        STATUS             mandatory
        DESCRIPTION
          "Index Number of the outlet in the PDU."
::= { edPowerMgmtPDU4OutletsTableIndexNumber 19 }


edPowerMgmtPDU4OutletsTableIndexNumber20 OBJECT-TYPE
        SYNTAX             Integer32
         ACCESS         read-only
        STATUS             mandatory
        DESCRIPTION
          "Index Number of the outlet in the PDU."
::= { edPowerMgmtPDU4OutletsTableIndexNumber 20 }


edPowerMgmtPDU4OutletsTableIndexNumber21 OBJECT-TYPE
        SYNTAX             Integer32
         ACCESS         read-only
        STATUS             mandatory
        DESCRIPTION
          "Index Number of the outlet in the PDU."
::= { edPowerMgmtPDU4OutletsTableIndexNumber 21 }


edPowerMgmtPDU4OutletsTableIndexNumber22 OBJECT-TYPE
        SYNTAX             Integer32
         ACCESS         read-only
        STATUS             mandatory
        DESCRIPTION
          "Index Number of the outlet in the PDU."
::= { edPowerMgmtPDU4OutletsTableIndexNumber 22 }


edPowerMgmtPDU4OutletsTableIndexNumber23 OBJECT-TYPE
        SYNTAX             Integer32
         ACCESS         read-only
        STATUS             mandatory
        DESCRIPTION
          "Index Number of the outlet in the PDU."
::= { edPowerMgmtPDU4OutletsTableIndexNumber 23 }


edPowerMgmtPDU4OutletsTableIndexNumber24 OBJECT-TYPE
        SYNTAX             Integer32
         ACCESS         read-only
        STATUS             mandatory
        DESCRIPTION
          "Index Number of the outlet in the PDU."
::= { edPowerMgmtPDU4OutletsTableIndexNumber 24 }

edPowerMgmtPDU4OutletsTableIndexNumber25 OBJECT-TYPE
        SYNTAX             Integer32
         ACCESS         read-only
        STATUS             mandatory
        DESCRIPTION
          "Index Number of the outlet in the PDU."
::= { edPowerMgmtPDU4OutletsTableIndexNumber 25 }


edPowerMgmtPDU4OutletsTableIndexNumber26 OBJECT-TYPE
        SYNTAX             Integer32
         ACCESS         read-only
        STATUS             mandatory
        DESCRIPTION
          "Index Number of the outlet in the PDU."
::= { edPowerMgmtPDU4OutletsTableIndexNumber 26 }


edPowerMgmtPDU4OutletsTableIndexNumber27 OBJECT-TYPE
        SYNTAX             Integer32
         ACCESS         read-only
        STATUS             mandatory
        DESCRIPTION
          "Index Number of the outlet in the PDU."
::= { edPowerMgmtPDU4OutletsTableIndexNumber 27 }

edPowerMgmtPDU4OutletsTableIndexNumber28 OBJECT-TYPE
        SYNTAX             Integer32
         ACCESS         read-only
        STATUS             mandatory
        DESCRIPTION
          "Index Number of the outlet in the PDU."
::= { edPowerMgmtPDU4OutletsTableIndexNumber 28 }

edPowerMgmtPDU4OutletsTableIndexNumber29 OBJECT-TYPE
        SYNTAX             Integer32
         ACCESS         read-only
        STATUS             mandatory
        DESCRIPTION
          "Index Number of the outlet in the PDU."
::= { edPowerMgmtPDU4OutletsTableIndexNumber 29 }

edPowerMgmtPDU4OutletsTableIndexNumber30 OBJECT-TYPE
        SYNTAX             Integer32
         ACCESS         read-only
        STATUS             mandatory
        DESCRIPTION
          "Index Number of the outlet in the PDU."
::= { edPowerMgmtPDU4OutletsTableIndexNumber 30 }

edPowerMgmtPDU4OutletsTableIndexNumber31 OBJECT-TYPE
        SYNTAX             Integer32
         ACCESS         read-only
        STATUS             mandatory
        DESCRIPTION
          "Index Number of the outlet in the PDU."
::= { edPowerMgmtPDU4OutletsTableIndexNumber 31 }

edPowerMgmtPDU4OutletsTableIndexNumber32 OBJECT-TYPE
        SYNTAX             Integer32
         ACCESS         read-only
        STATUS             mandatory
        DESCRIPTION
          "Index Number of the outlet in the PDU."
::= { edPowerMgmtPDU4OutletsTableIndexNumber 32 }

edPowerMgmtPDU4OutletsTableIndexNumber33 OBJECT-TYPE
        SYNTAX             Integer32
         ACCESS         read-only
        STATUS             mandatory
        DESCRIPTION
          "Index Number of the outlet in the PDU."
::= { edPowerMgmtPDU4OutletsTableIndexNumber 33 }

edPowerMgmtPDU4OutletsTableIndexNumber34 OBJECT-TYPE
        SYNTAX             Integer32
         ACCESS         read-only
        STATUS             mandatory
        DESCRIPTION
          "Index Number of the outlet in the PDU."
::= { edPowerMgmtPDU4OutletsTableIndexNumber 34 }


edPowerMgmtPDU4OutletsTableIndexNumber35 OBJECT-TYPE
        SYNTAX             Integer32
         ACCESS         read-only
        STATUS             mandatory
        DESCRIPTION
          "Index Number of the outlet in the PDU."
::= { edPowerMgmtPDU4OutletsTableIndexNumber 35 }


edPowerMgmtPDU4OutletsTableIndexNumber36 OBJECT-TYPE
        SYNTAX             Integer32
         ACCESS         read-only
        STATUS             mandatory
        DESCRIPTION
          "Index Number of the outlet in the PDU."
::= { edPowerMgmtPDU4OutletsTableIndexNumber 36 }


edPowerMgmtPDU4OutletsTableIndexNumber37 OBJECT-TYPE
        SYNTAX             Integer32
         ACCESS         read-only
        STATUS             mandatory
        DESCRIPTION
          "Index Number of the outlet in the PDU."
::= { edPowerMgmtPDU4OutletsTableIndexNumber 37 }


edPowerMgmtPDU4OutletsTableIndexNumber38 OBJECT-TYPE
        SYNTAX             Integer32
         ACCESS         read-only
        STATUS             mandatory
        DESCRIPTION
          "Index Number of the outlet in the PDU."
::= { edPowerMgmtPDU4OutletsTableIndexNumber 38 }


edPowerMgmtPDU4OutletsTableIndexNumber39 OBJECT-TYPE
        SYNTAX             Integer32
         ACCESS         read-only
        STATUS             mandatory
        DESCRIPTION
          "Index Number of the outlet in the PDU."
::= { edPowerMgmtPDU4OutletsTableIndexNumber 39 }


edPowerMgmtPDU4OutletsTableIndexNumber40 OBJECT-TYPE
        SYNTAX             Integer32
         ACCESS         read-only
        STATUS             mandatory
        DESCRIPTION
          "Index Number of the outlet in the PDU."
::= { edPowerMgmtPDU4OutletsTableIndexNumber 40 }


edPowerMgmtPDU4OutletsTableIndexNumber41 OBJECT-TYPE
        SYNTAX             Integer32
         ACCESS         		read-only
        STATUS             mandatory
        DESCRIPTION
          "Index Number of the outlet in the PDU."
::= { edPowerMgmtPDU4OutletsTableIndexNumber 41 }


edPowerMgmtPDU4OutletsTableIndexNumber42 OBJECT-TYPE
        SYNTAX             Integer32
         ACCESS         read-only
        STATUS             mandatory
        DESCRIPTION
          "Index Number of the outlet in the PDU."
::= { edPowerMgmtPDU4OutletsTableIndexNumber 42 }







edPowerMgmtPDU4OutletsTableVoltageOutlet1 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 1 }


edPowerMgmtPDU4OutletsTableVoltageOutlet2 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 2 }

edPowerMgmtPDU4OutletsTableVoltageOutlet3 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 3 }


edPowerMgmtPDU4OutletsTableVoltageOutlet4 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 4 }


edPowerMgmtPDU4OutletsTableVoltageOutlet5 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 5 }


edPowerMgmtPDU4OutletsTableVoltageOutlet6 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 6 }


edPowerMgmtPDU4OutletsTableVoltageOutlet7 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 7 }


edPowerMgmtPDU4OutletsTableVoltageOutlet8 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 8 }


edPowerMgmtPDU4OutletsTableVoltageOutlet9 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 9 }


edPowerMgmtPDU4OutletsTableVoltageOutlet10 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 10 }


edPowerMgmtPDU4OutletsTableVoltageOutlet11 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 11 }


edPowerMgmtPDU4OutletsTableVoltageOutlet12 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 12 }


edPowerMgmtPDU4OutletsTableVoltageOutlet13 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 13 }


edPowerMgmtPDU4OutletsTableVoltageOutlet14 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 14 }


edPowerMgmtPDU4OutletsTableVoltageOutlet15 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 15 }


edPowerMgmtPDU4OutletsTableVoltageOutlet16 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 16 }


edPowerMgmtPDU4OutletsTableVoltageOutlet17 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 17 }


edPowerMgmtPDU4OutletsTableVoltageOutlet18 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 18 }


edPowerMgmtPDU4OutletsTableVoltageOutlet19 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 19 }


edPowerMgmtPDU4OutletsTableVoltageOutlet20 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 20 }


edPowerMgmtPDU4OutletsTableVoltageOutlet21 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 21 }


edPowerMgmtPDU4OutletsTableVoltageOutlet22 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 22 }


edPowerMgmtPDU4OutletsTableVoltageOutlet23 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 23 }


edPowerMgmtPDU4OutletsTableVoltageOutlet24 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 24 }

edPowerMgmtPDU4OutletsTableVoltageOutlet25 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 25 }


edPowerMgmtPDU4OutletsTableVoltageOutlet26 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 26 }


edPowerMgmtPDU4OutletsTableVoltageOutlet27 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 27 }

edPowerMgmtPDU4OutletsTableVoltageOutlet28 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 28 }

edPowerMgmtPDU4OutletsTableVoltageOutlet29 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 29 }

edPowerMgmtPDU4OutletsTableVoltageOutlet30 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 30 }

edPowerMgmtPDU4OutletsTableVoltageOutlet31 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 31 }

edPowerMgmtPDU4OutletsTableVoltageOutlet32 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 32 }

edPowerMgmtPDU4OutletsTableVoltageOutlet33 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 33 }

edPowerMgmtPDU4OutletsTableVoltageOutlet34 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 34 }


edPowerMgmtPDU4OutletsTableVoltageOutlet35 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 35 }


edPowerMgmtPDU4OutletsTableVoltageOutlet36 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 36 }


edPowerMgmtPDU4OutletsTableVoltageOutlet37 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 37 }


edPowerMgmtPDU4OutletsTableVoltageOutlet38 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 38 }


edPowerMgmtPDU4OutletsTableVoltageOutlet39 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 39 }


edPowerMgmtPDU4OutletsTableVoltageOutlet40 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 40 }


edPowerMgmtPDU4OutletsTableVoltageOutlet41 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 41 }


edPowerMgmtPDU4OutletsTableVoltageOutlet42 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU4OutletsTableVoltageValue 42 }








edPowerMgmtPDU4OutletsTableCurrentOutlet1 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU4OutletsTableCurrentValue 1 }


edPowerMgmtPDU4OutletsTableCurrentOutlet2 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU4OutletsTableCurrentValue 2 }

edPowerMgmtPDU4OutletsTableCurrentOutlet3 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU4OutletsTableCurrentValue 3 }


edPowerMgmtPDU4OutletsTableCurrentOutlet4 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU4OutletsTableCurrentValue 4 }


edPowerMgmtPDU4OutletsTableCurrentOutlet5 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU4OutletsTableCurrentValue 5 }


edPowerMgmtPDU4OutletsTableCurrentOutlet6 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU4OutletsTableCurrentValue 6 }


edPowerMgmtPDU4OutletsTableCurrentOutlet7 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU4OutletsTableCurrentValue 7 }


edPowerMgmtPDU4OutletsTableCurrentOutlet8 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU4OutletsTableCurrentValue 8 }


edPowerMgmtPDU4OutletsTableCurrentOutlet9 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU4OutletsTableCurrentValue 9 }


edPowerMgmtPDU4OutletsTableCurrentOutlet10 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU4OutletsTableCurrentValue 10 }


edPowerMgmtPDU4OutletsTableCurrentOutlet11 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU4OutletsTableCurrentValue 11 }


edPowerMgmtPDU4OutletsTableCurrentOutlet12 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU4OutletsTableCurrentValue 12 }


edPowerMgmtPDU4OutletsTableCurrentOutlet13 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU4OutletsTableCurrentValue 13 }


edPowerMgmtPDU4OutletsTableCurrentOutlet14 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU4OutletsTableCurrentValue 14 }


edPowerMgmtPDU4OutletsTableCurrentOutlet15 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU4OutletsTableCurrentValue 15 }


edPowerMgmtPDU4OutletsTableCurrentOutlet16 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU4OutletsTableCurrentValue 16 }


edPowerMgmtPDU4OutletsTableCurrentOutlet17 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU4OutletsTableCurrentValue 17 }


edPowerMgmtPDU4OutletsTableCurrentOutlet18 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU4OutletsTableCurrentValue 18 }


edPowerMgmtPDU4OutletsTableCurrentOutlet19 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU4OutletsTableCurrentValue 19 }


edPowerMgmtPDU4OutletsTableCurrentOutlet20 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU4OutletsTableCurrentValue 20 }


edPowerMgmtPDU4OutletsTableCurrentOutlet21 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU4OutletsTableCurrentValue 21 }


edPowerMgmtPDU4OutletsTableCurrentOutlet22 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU4OutletsTableCurrentValue 22 }


edPowerMgmtPDU4OutletsTableCurrentOutlet23 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU4OutletsTableCurrentValue 23 }


edPowerMgmtPDU4OutletsTableCurrentOutlet24 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU4OutletsTableCurrentValue 24 }

edPowerMgmtPDU4OutletsTableCurrentOutlet25 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU4OutletsTableCurrentValue 25 }


edPowerMgmtPDU4OutletsTableCurrentOutlet26 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU4OutletsTableCurrentValue 26 }


edPowerMgmtPDU4OutletsTableCurrentOutlet27 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU4OutletsTableCurrentValue 27 }

edPowerMgmtPDU4OutletsTableCurrentOutlet28 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU4OutletsTableCurrentValue 28 }

edPowerMgmtPDU4OutletsTableCurrentOutlet29 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU4OutletsTableCurrentValue 29 }

edPowerMgmtPDU4OutletsTableCurrentOutlet30 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU4OutletsTableCurrentValue 30 }

edPowerMgmtPDU4OutletsTableCurrentOutlet31 OBJECT-TYPE
        SYNTAX             Integer32
         ACCESS         read-only
        STATUS             mandatory
        DESCRIPTION
      "Actual value of Current for the outlet(Amp).The recieved value 
		if 1234 then actual value in decimal willbe 12.34 Amp, if recieved 
		value is 12 then 0.12 Amp .Returns 0 if not supported."
::= { edPowerMgmtPDU4OutletsTableCurrentValue 31 }

edPowerMgmtPDU4OutletsTableCurrentOutlet32 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU4OutletsTableCurrentValue 32 }

edPowerMgmtPDU4OutletsTableCurrentOutlet33 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU4OutletsTableCurrentValue 33 }

edPowerMgmtPDU4OutletsTableCurrentOutlet34 OBJECT-TYPE
        SYNTAX             Integer32
         ACCESS         read-only
        STATUS             mandatory
        DESCRIPTION
       "Actual value of Current for the outlet(Amp).The recieved value 
		if 1234 then actual value in decimal willbe 12.34 Amp, if recieved 
		value is 12 then 0.12 Amp .Returns 0 if not supported."
::= { edPowerMgmtPDU4OutletsTableCurrentValue 34 }


edPowerMgmtPDU4OutletsTableCurrentOutlet35 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU4OutletsTableCurrentValue 35 }


edPowerMgmtPDU4OutletsTableCurrentOutlet36 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU4OutletsTableCurrentValue 36 }


edPowerMgmtPDU4OutletsTableCurrentOutlet37 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU4OutletsTableCurrentValue 37 }


edPowerMgmtPDU4OutletsTableCurrentOutlet38 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU4OutletsTableCurrentValue 38 }


edPowerMgmtPDU4OutletsTableCurrentOutlet39 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU4OutletsTableCurrentValue 39 }


edPowerMgmtPDU4OutletsTableCurrentOutlet40 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU4OutletsTableCurrentValue 40 }


edPowerMgmtPDU4OutletsTableCurrentOutlet41 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU4OutletsTableCurrentValue 41 }


edPowerMgmtPDU4OutletsTableCurrentOutlet42 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU4OutletsTableCurrentValue 42 }









edPowerMgmtPDU4OutletsTableApearentEnergyOutlet1 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 1 }


edPowerMgmtPDU4OutletsTableApearentEnergyOutlet2 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 2 }

edPowerMgmtPDU4OutletsTableApearentEnergyOutlet3 OBJECT-TYPE
        SYNTAX             Integer32
         ACCESS         read-only
        STATUS             mandatory
        DESCRIPTION
      "Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 3 }


edPowerMgmtPDU4OutletsTableApearentEnergyOutlet4 OBJECT-TYPE
        SYNTAX             Integer32
         ACCESS         read-only
        STATUS             mandatory
        DESCRIPTION
      "Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 4 }


edPowerMgmtPDU4OutletsTableApearentEnergyOutlet5 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 5 }


edPowerMgmtPDU4OutletsTableApearentEnergyOutlet6 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 6 }


edPowerMgmtPDU4OutletsTableApearentEnergyOutlet7 OBJECT-TYPE
        SYNTAX             Integer32
         ACCESS         read-only
        STATUS             mandatory
        DESCRIPTION
        "Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 7 }


edPowerMgmtPDU4OutletsTableApearentEnergyOutlet8 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 8 }


edPowerMgmtPDU4OutletsTableApearentEnergyOutlet9 OBJECT-TYPE
        SYNTAX             Integer32
         ACCESS         read-only
        STATUS             mandatory
        DESCRIPTION
     "Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 9 }


edPowerMgmtPDU4OutletsTableApearentEnergyOutlet10 OBJECT-TYPE
        SYNTAX             Integer32
         ACCESS         read-only
        STATUS             mandatory
        DESCRIPTION
     "Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 10 }


edPowerMgmtPDU4OutletsTableApearentEnergyOutlet11 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 11 }


edPowerMgmtPDU4OutletsTableApearentEnergyOutlet12 OBJECT-TYPE
        SYNTAX             Integer32
         ACCESS         read-only
        STATUS             mandatory
        DESCRIPTION
   "Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 12 }


edPowerMgmtPDU4OutletsTableApearentEnergyOutlet13 OBJECT-TYPE
        SYNTAX             Integer32
         ACCESS         read-only
        STATUS             mandatory
        DESCRIPTION
      "Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 13 }


edPowerMgmtPDU4OutletsTableApearentEnergyOutlet14 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 14 }


edPowerMgmtPDU4OutletsTableApearentEnergyOutlet15 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 15 }


edPowerMgmtPDU4OutletsTableApearentEnergyOutlet16 OBJECT-TYPE
        SYNTAX             Integer32
         ACCESS         read-only
        STATUS             mandatory
        DESCRIPTION
          "Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 16 }


edPowerMgmtPDU4OutletsTableApearentEnergyOutlet17 OBJECT-TYPE
        SYNTAX             Integer32
         ACCESS         read-only
        STATUS             mandatory
        DESCRIPTION
          "Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 17 }


edPowerMgmtPDU4OutletsTableApearentEnergyOutlet18 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 18 }


edPowerMgmtPDU4OutletsTableApearentEnergyOutlet19 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 19 }


edPowerMgmtPDU4OutletsTableApearentEnergyOutlet20 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 20 }


edPowerMgmtPDU4OutletsTableApearentEnergyOutlet21 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 21 }


edPowerMgmtPDU4OutletsTableApearentEnergyOutlet22 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 22 }


edPowerMgmtPDU4OutletsTableApearentEnergyOutlet23 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 23 }


edPowerMgmtPDU4OutletsTableApearentEnergyOutlet24 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 24 }

edPowerMgmtPDU4OutletsTableApearentEnergyOutlet25 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 25 }


edPowerMgmtPDU4OutletsTableApearentEnergyOutlet26 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 26 }


edPowerMgmtPDU4OutletsTableApearentEnergyOutlet27 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 27 }

edPowerMgmtPDU4OutletsTableApearentEnergyOutlet28 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 28 }

edPowerMgmtPDU4OutletsTableApearentEnergyOutlet29 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 29 }

edPowerMgmtPDU4OutletsTableApearentEnergyOutlet30 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 30 }

edPowerMgmtPDU4OutletsTableApearentEnergyOutlet31 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 31 }

edPowerMgmtPDU4OutletsTableApearentEnergyOutlet32 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 32 }

edPowerMgmtPDU4OutletsTableApearentEnergyOutlet33 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 33 }

edPowerMgmtPDU4OutletsTableApearentEnergyOutlet34 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 34 }


edPowerMgmtPDU4OutletsTableApearentEnergyOutlet35 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 35 }


edPowerMgmtPDU4OutletsTableApearentEnergyOutlet36 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 36 }


edPowerMgmtPDU4OutletsTableApearentEnergyOutlet37 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 37 }


edPowerMgmtPDU4OutletsTableApearentEnergyOutlet38 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 38 }


edPowerMgmtPDU4OutletsTableApearentEnergyOutlet39 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 39 }


edPowerMgmtPDU4OutletsTableApearentEnergyOutlet40 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 40 }


edPowerMgmtPDU4OutletsTableApearentEnergyOutlet41 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 41 }


edPowerMgmtPDU4OutletsTableApearentEnergyOutlet42 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU4OutletsTableApearentEnergyValue 42 }





edPowerMgmtPDU4OutletsTableReactiveEnergyOutlet1 OBJECT-TYPE
        SYNTAX             Integer32
         ACCESS         read-only
        STATUS             mandatory
        DESCRIPTION
		"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 1 }


edPowerMgmtPDU4OutletsTableReactiveEnergyOutlet2 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 2 }

edPowerMgmtPDU4OutletsTableReactiveEnergyOutlet3 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 3 }


edPowerMgmtPDU4OutletsTableReactiveEnergyOutlet4 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 4 }


edPowerMgmtPDU4OutletsTableReactiveEnergyOutlet5 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 5 }


edPowerMgmtPDU4OutletsTableReactiveEnergyOutlet6 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 6 }


edPowerMgmtPDU4OutletsTableReactiveEnergyOutlet7 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 7 }


edPowerMgmtPDU4OutletsTableReactiveEnergyOutlet8 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 8 }


edPowerMgmtPDU4OutletsTableReactiveEnergyOutlet9 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 9 }


edPowerMgmtPDU4OutletsTableReactiveEnergyOutlet10 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 10 }


edPowerMgmtPDU4OutletsTableReactiveEnergyOutlet11 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 11 }


edPowerMgmtPDU4OutletsTableReactiveEnergyOutlet12 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 12 }


edPowerMgmtPDU4OutletsTableReactiveEnergyOutlet13 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 13 }


edPowerMgmtPDU4OutletsTableReactiveEnergyOutlet14 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 14 }


edPowerMgmtPDU4OutletsTableReactiveEnergyOutlet15 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 15 }


edPowerMgmtPDU4OutletsTableReactiveEnergyOutlet16 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 16 }


edPowerMgmtPDU4OutletsTableReactiveEnergyOutlet17 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 17 }


edPowerMgmtPDU4OutletsTableReactiveEnergyOutlet18 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 18 }


edPowerMgmtPDU4OutletsTableReactiveEnergyOutlet19 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 19 }


edPowerMgmtPDU4OutletsTableReactiveEnergyOutlet20 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 20 }


edPowerMgmtPDU4OutletsTableReactiveEnergyOutlet21 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 21 }


edPowerMgmtPDU4OutletsTableReactiveEnergyOutlet22 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 22 }


edPowerMgmtPDU4OutletsTableReactiveEnergyOutlet23 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 23 }


edPowerMgmtPDU4OutletsTableReactiveEnergyOutlet24 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 24 }

edPowerMgmtPDU4OutletsTableReactiveEnergyOutlet25 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 25 }


edPowerMgmtPDU4OutletsTableReactiveEnergyOutlet26 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 26 }


edPowerMgmtPDU4OutletsTableReactiveEnergyOutlet27 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 27 }

edPowerMgmtPDU4OutletsTableReactiveEnergyOutlet28 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 28 }

edPowerMgmtPDU4OutletsTableReactiveEnergyOutlet29 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 29 }

edPowerMgmtPDU4OutletsTableReactiveEnergyOutlet30 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 30 }

edPowerMgmtPDU4OutletsTableReactiveEnergyOutlet31 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 31 }

edPowerMgmtPDU4OutletsTableReactiveEnergyOutlet32 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 32 }

edPowerMgmtPDU4OutletsTableReactiveEnergyOutlet33 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 33 }

edPowerMgmtPDU4OutletsTableReactiveEnergyOutlet34 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 34 }


edPowerMgmtPDU4OutletsTableReactiveEnergyOutlet35 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 35 }


edPowerMgmtPDU4OutletsTableReactiveEnergyOutlet36 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 36 }


edPowerMgmtPDU4OutletsTableReactiveEnergyOutlet37 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 37 }


edPowerMgmtPDU4OutletsTableReactiveEnergyOutlet38 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 38 }


edPowerMgmtPDU4OutletsTableReactiveEnergyOutlet39 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 39 }


edPowerMgmtPDU4OutletsTableReactiveEnergyOutlet40 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 40 }


edPowerMgmtPDU4OutletsTableReactiveEnergyOutlet41 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 41 }


edPowerMgmtPDU4OutletsTableReactiveEnergyOutlet42 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU4OutletsTableReactiveEnergyValue 42 }




edPowerMgmtPDU4OutletsTableActiveEnergyOutlet1 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 1 }


edPowerMgmtPDU4OutletsTableActiveEnergyOutlet2 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 2 }

edPowerMgmtPDU4OutletsTableActiveEnergyOutlet3 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 3 }


edPowerMgmtPDU4OutletsTableActiveEnergyOutlet4 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 4 }


edPowerMgmtPDU4OutletsTableActiveEnergyOutlet5 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 5 }


edPowerMgmtPDU4OutletsTableActiveEnergyOutlet6 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 6 }


edPowerMgmtPDU4OutletsTableActiveEnergyOutlet7 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 7 }


edPowerMgmtPDU4OutletsTableActiveEnergyOutlet8 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 8 }


edPowerMgmtPDU4OutletsTableActiveEnergyOutlet9 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 9 }


edPowerMgmtPDU4OutletsTableActiveEnergyOutlet10 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 10 }


edPowerMgmtPDU4OutletsTableActiveEnergyOutlet11 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 11 }


edPowerMgmtPDU4OutletsTableActiveEnergyOutlet12 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 12 }


edPowerMgmtPDU4OutletsTableActiveEnergyOutlet13 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 13 }


edPowerMgmtPDU4OutletsTableActiveEnergyOutlet14 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 14 }


edPowerMgmtPDU4OutletsTableActiveEnergyOutlet15 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 15 }


edPowerMgmtPDU4OutletsTableActiveEnergyOutlet16 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 16 }


edPowerMgmtPDU4OutletsTableActiveEnergyOutlet17 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 17 }


edPowerMgmtPDU4OutletsTableActiveEnergyOutlet18 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 18 }


edPowerMgmtPDU4OutletsTableActiveEnergyOutlet19 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 19 }


edPowerMgmtPDU4OutletsTableActiveEnergyOutlet20 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 20 }


edPowerMgmtPDU4OutletsTableActiveEnergyOutlet21 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 21 }


edPowerMgmtPDU4OutletsTableActiveEnergyOutlet22 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 22 }


edPowerMgmtPDU4OutletsTableActiveEnergyOutlet23 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 23 }


edPowerMgmtPDU4OutletsTableActiveEnergyOutlet24 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 24 }

edPowerMgmtPDU4OutletsTableActiveEnergyOutlet25 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 25 }


edPowerMgmtPDU4OutletsTableActiveEnergyOutlet26 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 26 }


edPowerMgmtPDU4OutletsTableActiveEnergyOutlet27 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 27 }

edPowerMgmtPDU4OutletsTableActiveEnergyOutlet28 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 28 }

edPowerMgmtPDU4OutletsTableActiveEnergyOutlet29 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 29 }

edPowerMgmtPDU4OutletsTableActiveEnergyOutlet30 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 30 }

edPowerMgmtPDU4OutletsTableActiveEnergyOutlet31 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 31 }

edPowerMgmtPDU4OutletsTableActiveEnergyOutlet32 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 32 }

edPowerMgmtPDU4OutletsTableActiveEnergyOutlet33 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 33 }

edPowerMgmtPDU4OutletsTableActiveEnergyOutlet34 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 34 }


edPowerMgmtPDU4OutletsTableActiveEnergyOutlet35 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 35 }


edPowerMgmtPDU4OutletsTableActiveEnergyOutlet36 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 36 }


edPowerMgmtPDU4OutletsTableActiveEnergyOutlet37 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 37 }


edPowerMgmtPDU4OutletsTableActiveEnergyOutlet38 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 38 }


edPowerMgmtPDU4OutletsTableActiveEnergyOutlet39 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 39 }


edPowerMgmtPDU4OutletsTableActiveEnergyOutlet40 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 40 }


edPowerMgmtPDU4OutletsTableActiveEnergyOutlet41 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 41 }


edPowerMgmtPDU4OutletsTableActiveEnergyOutlet42 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU4OutletsTableActiveEnergyValue 42 }









edPowerMgmtPDU4OutletsTableInstantaneousPowerOutlet1 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 1 }


edPowerMgmtPDU4OutletsTableInstantaneousPowerOutlet2 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 2 }

edPowerMgmtPDU4OutletsTableInstantaneousPowerOutlet3 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 3 }


edPowerMgmtPDU4OutletsTableInstantaneousPowerOutlet4 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 4 }


edPowerMgmtPDU4OutletsTableInstantaneousPowerOutlet5 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 5 }


edPowerMgmtPDU4OutletsTableInstantaneousPowerOutlet6 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 6 }


edPowerMgmtPDU4OutletsTableInstantaneousPowerOutlet7 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 7 }


edPowerMgmtPDU4OutletsTableInstantaneousPowerOutlet8 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 8 }


edPowerMgmtPDU4OutletsTableInstantaneousPowerOutlet9 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 9 }


edPowerMgmtPDU4OutletsTableInstantaneousPowerOutlet10 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 10 }


edPowerMgmtPDU4OutletsTableInstantaneousPowerOutlet11 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 11 }


edPowerMgmtPDU4OutletsTableInstantaneousPowerOutlet12 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 12 }


edPowerMgmtPDU4OutletsTableInstantaneousPowerOutlet13 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 13 }


edPowerMgmtPDU4OutletsTableInstantaneousPowerOutlet14 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 14 }


edPowerMgmtPDU4OutletsTableInstantaneousPowerOutlet15 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 15 }


edPowerMgmtPDU4OutletsTableInstantaneousPowerOutlet16 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 16 }


edPowerMgmtPDU4OutletsTableInstantaneousPowerOutlet17 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 17 }


edPowerMgmtPDU4OutletsTableInstantaneousPowerOutlet18 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 18 }


edPowerMgmtPDU4OutletsTableInstantaneousPowerOutlet19 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 19 }


edPowerMgmtPDU4OutletsTableInstantaneousPowerOutlet20 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 20 }


edPowerMgmtPDU4OutletsTableInstantaneousPowerOutlet21 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 21 }


edPowerMgmtPDU4OutletsTableInstantaneousPowerOutlet22 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 22 }


edPowerMgmtPDU4OutletsTableInstantaneousPowerOutlet23 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 23 }


edPowerMgmtPDU4OutletsTableInstantaneousPowerOutlet24 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 24 }

edPowerMgmtPDU4OutletsTableInstantaneousPowerOutlet25 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 25 }


edPowerMgmtPDU4OutletsTableInstantaneousPowerOutlet26 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 26 }


edPowerMgmtPDU4OutletsTableInstantaneousPowerOutlet27 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 27 }

edPowerMgmtPDU4OutletsTableInstantaneousPowerOutlet28 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 28 }

edPowerMgmtPDU4OutletsTableInstantaneousPowerOutlet29 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 29 }

edPowerMgmtPDU4OutletsTableInstantaneousPowerOutlet30 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 30 }

edPowerMgmtPDU4OutletsTableInstantaneousPowerOutlet31 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 31 }

edPowerMgmtPDU4OutletsTableInstantaneousPowerOutlet32 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 32 }

edPowerMgmtPDU4OutletsTableInstantaneousPowerOutlet33 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 33 }

edPowerMgmtPDU4OutletsTableInstantaneousPowerOutlet34 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 34 }


edPowerMgmtPDU4OutletsTableInstantaneousPowerOutlet35 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 35 }


edPowerMgmtPDU4OutletsTableInstantaneousPowerOutlet36 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 36 }


edPowerMgmtPDU4OutletsTableInstantaneousPowerOutlet37 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 37 }


edPowerMgmtPDU4OutletsTableInstantaneousPowerOutlet38 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 38 }


edPowerMgmtPDU4OutletsTableInstantaneousPowerOutlet39 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 39 }


edPowerMgmtPDU4OutletsTableInstantaneousPowerOutlet40 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 40 }


edPowerMgmtPDU4OutletsTableInstantaneousPowerOutlet41 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 41 }


edPowerMgmtPDU4OutletsTableInstantaneousPowerOutlet42 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU4OutletsTableInstantaneousPowerValue 42 }







edPowerMgmtPDU4OutletsTablePowerFactorOutlet1 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 1 }


edPowerMgmtPDU4OutletsTablePowerFactorOutlet2 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 2 }

edPowerMgmtPDU4OutletsTablePowerFactorOutlet3 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 3 }


edPowerMgmtPDU4OutletsTablePowerFactorOutlet4 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 4 }


edPowerMgmtPDU4OutletsTablePowerFactorOutlet5 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 5 }


edPowerMgmtPDU4OutletsTablePowerFactorOutlet6 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 6 }


edPowerMgmtPDU4OutletsTablePowerFactorOutlet7 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 7 }


edPowerMgmtPDU4OutletsTablePowerFactorOutlet8 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 8 }


edPowerMgmtPDU4OutletsTablePowerFactorOutlet9 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 9 }


edPowerMgmtPDU4OutletsTablePowerFactorOutlet10 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 10 }


edPowerMgmtPDU4OutletsTablePowerFactorOutlet11 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 11 }


edPowerMgmtPDU4OutletsTablePowerFactorOutlet12 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 12 }


edPowerMgmtPDU4OutletsTablePowerFactorOutlet13 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 13 }


edPowerMgmtPDU4OutletsTablePowerFactorOutlet14 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 14 }


edPowerMgmtPDU4OutletsTablePowerFactorOutlet15 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 15 }


edPowerMgmtPDU4OutletsTablePowerFactorOutlet16 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 16 }


edPowerMgmtPDU4OutletsTablePowerFactorOutlet17 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 17 }


edPowerMgmtPDU4OutletsTablePowerFactorOutlet18 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 18 }


edPowerMgmtPDU4OutletsTablePowerFactorOutlet19 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 19 }


edPowerMgmtPDU4OutletsTablePowerFactorOutlet20 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 20 }


edPowerMgmtPDU4OutletsTablePowerFactorOutlet21 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 21 }


edPowerMgmtPDU4OutletsTablePowerFactorOutlet22 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 22 }


edPowerMgmtPDU4OutletsTablePowerFactorOutlet23 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 23 }


edPowerMgmtPDU4OutletsTablePowerFactorOutlet24 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 24 }

edPowerMgmtPDU4OutletsTablePowerFactorOutlet25 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 25 }


edPowerMgmtPDU4OutletsTablePowerFactorOutlet26 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 26 }


edPowerMgmtPDU4OutletsTablePowerFactorOutlet27 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 27 }

edPowerMgmtPDU4OutletsTablePowerFactorOutlet28 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 28 }

edPowerMgmtPDU4OutletsTablePowerFactorOutlet29 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 29 }

edPowerMgmtPDU4OutletsTablePowerFactorOutlet30 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 30 }

edPowerMgmtPDU4OutletsTablePowerFactorOutlet31 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 31 }

edPowerMgmtPDU4OutletsTablePowerFactorOutlet32 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 32 }

edPowerMgmtPDU4OutletsTablePowerFactorOutlet33 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 33 }

edPowerMgmtPDU4OutletsTablePowerFactorOutlet34 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 34 }


edPowerMgmtPDU4OutletsTablePowerFactorOutlet35 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 35 }


edPowerMgmtPDU4OutletsTablePowerFactorOutlet36 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 36 }


edPowerMgmtPDU4OutletsTablePowerFactorOutlet37 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 37 }


edPowerMgmtPDU4OutletsTablePowerFactorOutlet38 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 38 }


edPowerMgmtPDU4OutletsTablePowerFactorOutlet39 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 39 }


edPowerMgmtPDU4OutletsTablePowerFactorOutlet40 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 40 }


edPowerMgmtPDU4OutletsTablePowerFactorOutlet41 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 41 }


edPowerMgmtPDU4OutletsTablePowerFactorOutlet42 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU4OutletsTablePowerFactorValue 42 }







edPowerMgmtPDU4OutletsTableFreqOutlet1 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 1 }


edPowerMgmtPDU4OutletsTableFreqOutlet2 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 2 }

edPowerMgmtPDU4OutletsTableFreqOutlet3 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 3 }


edPowerMgmtPDU4OutletsTableFreqOutlet4 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 4 }


edPowerMgmtPDU4OutletsTableFreqOutlet5 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 5 }


edPowerMgmtPDU4OutletsTableFreqOutlet6 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 6 }


edPowerMgmtPDU4OutletsTableFreqOutlet7 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 7 }


edPowerMgmtPDU4OutletsTableFreqOutlet8 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 8 }


edPowerMgmtPDU4OutletsTableFreqOutlet9 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 9 }


edPowerMgmtPDU4OutletsTableFreqOutlet10 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 10 }


edPowerMgmtPDU4OutletsTableFreqOutlet11 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 11 }


edPowerMgmtPDU4OutletsTableFreqOutlet12 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 12 }


edPowerMgmtPDU4OutletsTableFreqOutlet13 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 13 }


edPowerMgmtPDU4OutletsTableFreqOutlet14 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 14 }


edPowerMgmtPDU4OutletsTableFreqOutlet15 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 15 }


edPowerMgmtPDU4OutletsTableFreqOutlet16 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 16 }


edPowerMgmtPDU4OutletsTableFreqOutlet17 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 17 }


edPowerMgmtPDU4OutletsTableFreqOutlet18 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 18 }


edPowerMgmtPDU4OutletsTableFreqOutlet19 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 19 }


edPowerMgmtPDU4OutletsTableFreqOutlet20 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 20 }


edPowerMgmtPDU4OutletsTableFreqOutlet21 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 21 }


edPowerMgmtPDU4OutletsTableFreqOutlet22 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 22 }


edPowerMgmtPDU4OutletsTableFreqOutlet23 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 23 }


edPowerMgmtPDU4OutletsTableFreqOutlet24 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 24 }

edPowerMgmtPDU4OutletsTableFreqOutlet25 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 25 }


edPowerMgmtPDU4OutletsTableFreqOutlet26 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 26 }


edPowerMgmtPDU4OutletsTableFreqOutlet27 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 27 }

edPowerMgmtPDU4OutletsTableFreqOutlet28 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 28 }

edPowerMgmtPDU4OutletsTableFreqOutlet29 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 29 }

edPowerMgmtPDU4OutletsTableFreqOutlet30 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 30 }

edPowerMgmtPDU4OutletsTableFreqOutlet31 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 31 }

edPowerMgmtPDU4OutletsTableFreqOutlet32 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 32 }

edPowerMgmtPDU4OutletsTableFreqOutlet33 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 33 }

edPowerMgmtPDU4OutletsTableFreqOutlet34 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 34 }


edPowerMgmtPDU4OutletsTableFreqOutlet35 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 35 }


edPowerMgmtPDU4OutletsTableFreqOutlet36 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 36 }


edPowerMgmtPDU4OutletsTableFreqOutlet37 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 37 }


edPowerMgmtPDU4OutletsTableFreqOutlet38 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 38 }


edPowerMgmtPDU4OutletsTableFreqOutlet39 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 39 }


edPowerMgmtPDU4OutletsTableFreqOutlet40 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 40 }


edPowerMgmtPDU4OutletsTableFreqOutlet41 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 41 }


edPowerMgmtPDU4OutletsTableFreqOutlet42 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU4OutletsTableFreqValue 42 }






edPowerMgmtPDU4OutletsTableControlOutlet1 OBJECT-TYPE
        SYNTAX INTEGER {
			switchingDisabled     (2),    			
			outletOn              (1),
			outletOff             (0)  
			
		}    
        ACCESS         read-write
        STATUS             mandatory
        DESCRIPTION
         "Getting this variable will return the outlet state. If 
       the outlet is on, the outletOn (1) value will be returned.
       If the outlet is off, the outletOff (0) value will be
       returned. and if returned 2 then switching is prohibited"
::= { edPowerMgmtPDU4OutletsTableOutletControl 1 }


edPowerMgmtPDU4OutletsTableControlOutlet2 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 2 }

edPowerMgmtPDU4OutletsTableControlOutlet3 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 3 }


edPowerMgmtPDU4OutletsTableControlOutlet4 OBJECT-TYPE
            SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 4 }


edPowerMgmtPDU4OutletsTableControlOutlet5 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 5 }


edPowerMgmtPDU4OutletsTableControlOutlet6 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 6 }


edPowerMgmtPDU4OutletsTableControlOutlet7 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 7 }


edPowerMgmtPDU4OutletsTableControlOutlet8 OBJECT-TYPE
            SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 8 }


edPowerMgmtPDU4OutletsTableControlOutlet9 OBJECT-TYPE
              SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 9 }


edPowerMgmtPDU4OutletsTableControlOutlet10 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 10 }


edPowerMgmtPDU4OutletsTableControlOutlet11 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 11 }


edPowerMgmtPDU4OutletsTableControlOutlet12 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 12 }


edPowerMgmtPDU4OutletsTableControlOutlet13 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 13 }


edPowerMgmtPDU4OutletsTableControlOutlet14 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 14 }


edPowerMgmtPDU4OutletsTableControlOutlet15 OBJECT-TYPE
           SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 15 }


edPowerMgmtPDU4OutletsTableControlOutlet16 OBJECT-TYPE
                SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 16 }


edPowerMgmtPDU4OutletsTableControlOutlet17 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 17 }


edPowerMgmtPDU4OutletsTableControlOutlet18 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 18 }


edPowerMgmtPDU4OutletsTableControlOutlet19 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 19 }


edPowerMgmtPDU4OutletsTableControlOutlet20 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 20 }


edPowerMgmtPDU4OutletsTableControlOutlet21 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 21 }


edPowerMgmtPDU4OutletsTableControlOutlet22 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 22 }


edPowerMgmtPDU4OutletsTableControlOutlet23 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 23 }


edPowerMgmtPDU4OutletsTableControlOutlet24 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 24 }

edPowerMgmtPDU4OutletsTableControlOutlet25 OBJECT-TYPE
           SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 25 }


edPowerMgmtPDU4OutletsTableControlOutlet26 OBJECT-TYPE
            SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 26 }


edPowerMgmtPDU4OutletsTableControlOutlet27 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 27 }

edPowerMgmtPDU4OutletsTableControlOutlet28 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 28 }

edPowerMgmtPDU4OutletsTableControlOutlet29 OBJECT-TYPE
                SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 29 }

edPowerMgmtPDU4OutletsTableControlOutlet30 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 30 }

edPowerMgmtPDU4OutletsTableControlOutlet31 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 31 }

edPowerMgmtPDU4OutletsTableControlOutlet32 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 32 }

edPowerMgmtPDU4OutletsTableControlOutlet33 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 33 }

edPowerMgmtPDU4OutletsTableControlOutlet34 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 34 }


edPowerMgmtPDU4OutletsTableControlOutlet35 OBJECT-TYPE
                SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 35 }


edPowerMgmtPDU4OutletsTableControlOutlet36 OBJECT-TYPE
                 SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 36 }


edPowerMgmtPDU4OutletsTableControlOutlet37 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 37 }


edPowerMgmtPDU4OutletsTableControlOutlet38 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 38 }


edPowerMgmtPDU4OutletsTableControlOutlet39 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 39 }


edPowerMgmtPDU4OutletsTableControlOutlet40 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 40 }


edPowerMgmtPDU4OutletsTableControlOutlet41 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 41 }


edPowerMgmtPDU4OutletsTableControlOutlet42 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU4OutletsTableOutletControl 42 }




edPowerMgmtPDU4TotalNumberOfPhases OBJECT-TYPE
        SYNTAX             Integer32
         ACCESS         		read-only
        STATUS             mandatory
        DESCRIPTION
        "Number of Phases managed by the appliance."
::= { edConectedPdu4Data 5 }

edPowerMgmtPDU4PhasesTable OBJECT IDENTIFIER::= { edConectedPdu4Data 6 }

edPowerMgmtPDU4PhasesData OBJECT IDENTIFIER::= { edPowerMgmtPDU4PhasesTable 1 }
edPowerMgmtPDU4PhasesTableIndexNumber OBJECT IDENTIFIER::= { edPowerMgmtPDU4PhasesData 1 }
edPowerMgmtPDU4PhasesTableVoltageValue OBJECT IDENTIFIER::= { edPowerMgmtPDU4PhasesData 2 }
edPowerMgmtPDU4PhasesTablecurrentValue OBJECT IDENTIFIER::= { edPowerMgmtPDU4PhasesData 3 }
edPowerMgmtPDU4PhasesTableApearentEnergyValue OBJECT IDENTIFIER::= { edPowerMgmtPDU4PhasesData 4 }
edPowerMgmtPDU4PhasesTableReactiveEnergyValue OBJECT IDENTIFIER::= { edPowerMgmtPDU4PhasesData 5 }
edPowerMgmtPDU4PhasesTableActiveEnergyValue OBJECT IDENTIFIER::= { edPowerMgmtPDU4PhasesData 6 }
edPowerMgmtPDU4PhasesTableInstantaneousPowerValue OBJECT IDENTIFIER::= { edPowerMgmtPDU4PhasesData 7 }
edPowerMgmtPDU4PhasesTablePowerFactorValue OBJECT IDENTIFIER::= { edPowerMgmtPDU4PhasesData 8 }

edPowerMgmtPDU4PhasesTableIndexNumber1 OBJECT-TYPE
        SYNTAX             Integer32
         ACCESS         read-only
        STATUS             mandatory
        DESCRIPTION
         "Index Number of the outlet in the PDU."
::= { edPowerMgmtPDU4PhasesTableIndexNumber 1 }

edPowerMgmtPDU4PhasesTableIndexNumber2 OBJECT-TYPE
        SYNTAX             Integer32
         ACCESS         read-only
        STATUS             mandatory
        DESCRIPTION
         "Index Number of the outlet in the PDU."
::= { edPowerMgmtPDU4PhasesTableIndexNumber 2 }


edPowerMgmtPDU4PhasesTableIndexNumber3 OBJECT-TYPE
        SYNTAX             Integer32
         ACCESS         read-only
        STATUS             mandatory
        DESCRIPTION
         "Index Number of the outlet in the PDU."
::= { edPowerMgmtPDU4PhasesTableIndexNumber 3 }


edPowerMgmtPDU4PhasesTableVoltageValuePhase1 OBJECT-TYPE
        SYNTAX             Integer32
         ACCESS         read-only
        STATUS             mandatory
        DESCRIPTION
        "Value of R Phase recieved from device.
		if recieved 23024 then actual value in decimal willbe 230.24 Volts ,
		if recieved 12 then 0.12 Volt. Returns 0 if not supported."
::= { edPowerMgmtPDU4PhasesTableVoltageValue 1 }

edPowerMgmtPDU4PhasesTableVoltageValuePhase2 OBJECT-TYPE
        SYNTAX             Integer32
         ACCESS         read-only
        STATUS             mandatory
        DESCRIPTION
        "Value of Y Phase recieved from device.
		if recieved 23024 then actual value in decimal willbe 230.24 Volts ,
		if recieved 12 then 0.12 Volt. Returns 0 if not supported."
::= { edPowerMgmtPDU4PhasesTableVoltageValue 2 }

edPowerMgmtPDU4PhasesTableVoltageValuePhase3 OBJECT-TYPE
        SYNTAX             Integer32
         ACCESS         read-only
        STATUS             mandatory
        DESCRIPTION
        "Value of B Phase recieved from device.
		if recieved 23024 then actual value in decimal willbe 230.24 Volts ,
		if recieved 12 then 0.12 Volt. Returns 0 if not supported."
::= { edPowerMgmtPDU4PhasesTableVoltageValue 3 }


edPowerMgmtPDU4PhasesTablecurrentPhase1 OBJECT-TYPE
        SYNTAX             Integer32
         ACCESS         read-only
        STATUS             mandatory
        DESCRIPTION
        "Current of R Phase in Ampere ,if recieved 1234 then actual value in decimal willbe 12.34 Amp, if recieved 
		value is 12 then 0.12 Amp .Returns 0 if not supported."
::= { edPowerMgmtPDU4PhasesTablecurrentValue 1 }


edPowerMgmtPDU4PhasesTablecurrentPhase2 OBJECT-TYPE
        SYNTAX             Integer32
         ACCESS         read-only
        STATUS             mandatory
        DESCRIPTION
        "Current of Y Phase in Ampere ,if recieved 1234 then actual value in decimal willbe 12.34 Amp, if recieved 
		value is 12 then 0.12 Amp .Returns 0 if not supported."
::= { edPowerMgmtPDU4PhasesTablecurrentValue 2 }



edPowerMgmtPDU4PhasesTablecurrentPhase3 OBJECT-TYPE
        SYNTAX             Integer32
         ACCESS         read-only
        STATUS             mandatory
        DESCRIPTION
        "Current of B Phase in Ampere ,if recieved 1234 then actual value in decimal willbe 12.34 Amp, if recieved 
		value is 12 then 0.12 Amp .Returns 0 if not supported."
::= { edPowerMgmtPDU4PhasesTablecurrentValue 3 }



edPowerMgmtPDU4PhasesTableApearentEnergyPhase1 OBJECT-TYPE
        SYNTAX             Integer32
         ACCESS         read-only
        STATUS             mandatory
        DESCRIPTION
        "ApearentEnergy(KVaHr) of R Phase if recieved 23024 then actual value in decimal willbe 2.3024 KVaHr , if recieved 12
	   then 0.0012 KVaHr. Returns 0 if not supported."
::= { edPowerMgmtPDU4PhasesTableApearentEnergyValue 1 }


edPowerMgmtPDU4PhasesTableApearentEnergyPhase2 OBJECT-TYPE
        SYNTAX             Integer32
         ACCESS         read-only
        STATUS             mandatory
        DESCRIPTION
        "ApearentEnergy(KVaHr) of Y Phase if recieved 23024 then actual value in decimal willbe 2.3024 KVaHr , if recieved 12
	   then 0.0012 KVaHr. Returns 0 if not supported."
::= { edPowerMgmtPDU4PhasesTableApearentEnergyValue 2 }

edPowerMgmtPDU4PhasesTableApearentEnergyPhase3 OBJECT-TYPE
        SYNTAX             Integer32
         ACCESS         read-only
        STATUS             mandatory
        DESCRIPTION
        "ApearentEnergy(KVaHr) of B Phase if recieved 23024 then actual value in decimal willbe 2.3024 KVaHr , if recieved 12
	   then 0.0012 KVaHr. Returns 0 if not supported."
::= { edPowerMgmtPDU4PhasesTableApearentEnergyValue 3 }


edPowerMgmtPDU4PhasesTableReactiveEnergyPhase1 OBJECT-TYPE
        SYNTAX             Integer32
         ACCESS         read-only
        STATUS             mandatory
        DESCRIPTION
        "ReactiveEnergy(KVarHr) of R Phase if recieved 23024 then actual value in decimal willbe 2.3024 KVaHr , if recieved 12
	   then 0.0012 KVaHr. Returns 0 if not supported."
::= { edPowerMgmtPDU4PhasesTableReactiveEnergyValue 1 }



edPowerMgmtPDU4PhasesTableReactiveEnergyPhase2 OBJECT-TYPE
        SYNTAX             Integer32
         ACCESS         read-only
        STATUS             mandatory
        DESCRIPTION
        "ReactiveEnergy(KVarHr) of Y Phase if recieved 23024 then actual value in decimal willbe 2.3024 KVaHr , if recieved 12
	   then 0.0012 KVaHr. Returns 0 if not supported."
::= { edPowerMgmtPDU4PhasesTableReactiveEnergyValue 2 }



edPowerMgmtPDU4PhasesTableReactiveEnergyPhase3 OBJECT-TYPE
        SYNTAX             Integer32
         ACCESS         read-only
        STATUS             mandatory
        DESCRIPTION
        "ReactiveEnergy(KVarHr) of B Phase if recieved 23024 then actual value in decimal willbe 2.3024 KVaHr , if recieved 12
	   then 0.0012 KVaHr. Returns 0 if not supported."
::= { edPowerMgmtPDU4PhasesTableReactiveEnergyValue 3 }

edPowerMgmtPDU4PhasesTableActiveEnergyPhase1 OBJECT-TYPE
        SYNTAX             Integer32
         ACCESS         read-only
        STATUS             mandatory
        DESCRIPTION
        "ActiveEnergy(KWattHr) of R Phase if recieved 23024 then actual value in decimal willbe 2.3024 KVaHr , if recieved 12
	   then 0.0012 KVaHr. Returns 0 if not supported."
::= { edPowerMgmtPDU4PhasesTableActiveEnergyValue 1 }

edPowerMgmtPDU4PhasesTableActiveEnergyPhase2 OBJECT-TYPE
        SYNTAX             Integer32
         ACCESS         read-only
        STATUS             mandatory
        DESCRIPTION
        "ActiveEnergy(KWattHr) of Y Phase if recieved 23024 then actual value in decimal willbe 2.3024 KVaHr , if recieved 12
	   then 0.0012 KVaHr. Returns 0 if not supported."
::= { edPowerMgmtPDU4PhasesTableActiveEnergyValue 2 }

edPowerMgmtPDU4PhasesTableActiveEnergyPhase3 OBJECT-TYPE
        SYNTAX             Integer32
         ACCESS         read-only
        STATUS             mandatory
        DESCRIPTION
        "ActiveEnergy(KWattHr) of B Phase if recieved 23024 then actual value in decimal willbe 2.3024 KVaHr , if recieved 12
	   then 0.0012 KVaHr. Returns 0 if not supported."
::= { edPowerMgmtPDU4PhasesTableActiveEnergyValue 3 }


edPowerMgmtPDU4PhasesTableInstantaneousPowerPhase1 OBJECT-TYPE
        SYNTAX             Integer32
         ACCESS         read-only
        STATUS             mandatory
        DESCRIPTION
        "Instantaneous Power(KWatt) of R Phase if recieved 23024 then actual value in decimal willbe 2.3024 KVaHr , if recieved 12
	   then 0.0012 KVaHr. Returns 0 if not supported."
::= { edPowerMgmtPDU4PhasesTableInstantaneousPowerValue 1 }


edPowerMgmtPDU4PhasesTableInstantaneousPowerPhase2 OBJECT-TYPE
        SYNTAX             Integer32
         ACCESS         read-only
        STATUS             mandatory
        DESCRIPTION
        "Instantaneous Power(KWatt) of Y Phase if recieved 23024 then actual value in decimal willbe 2.3024 KVaHr , if recieved 12
	   then 0.0012 KVaHr. Returns 0 if not supported."
::= { edPowerMgmtPDU4PhasesTableInstantaneousPowerValue 2 }


edPowerMgmtPDU4PhasesTableInstantaneousPowerPhase3 OBJECT-TYPE
        SYNTAX             Integer32
         ACCESS         read-only
        STATUS             mandatory
        DESCRIPTION
        "Instantaneous Power(KWatt) of B Phase if recieved 23024 then actual value in decimal willbe 2.3024 KVaHr , if recieved 12
	   then 0.0012 KVaHr. Returns 0 if not supported."
::= { edPowerMgmtPDU4PhasesTableInstantaneousPowerValue 3 }


edPowerMgmtPDU4PhasesTablePowerFactorPhase1 OBJECT-TYPE
        SYNTAX             Integer32
         ACCESS         read-only
        STATUS             mandatory
        DESCRIPTION
        "average of powerfactor(pF) R Phase.The recieved value 
		if 9999 then actual value in decimal willbe 99.99 pf , if recieved 12
		then 0.12 pf. Returns 0 if not supported."
::= { edPowerMgmtPDU4PhasesTablePowerFactorValue 1 }

edPowerMgmtPDU4PhasesTablePowerFactorPhase2 OBJECT-TYPE
        SYNTAX             Integer32
         ACCESS         read-only
        STATUS             mandatory
        DESCRIPTION
        "average of powerfactor(pF) Y Phase.The recieved value 
		if 9999 then actual value in decimal willbe 99.99 pf , if recieved 12
		then 0.12 pf. Returns 0 if not supported."
::= { edPowerMgmtPDU4PhasesTablePowerFactorValue 2 }

edPowerMgmtPDU4PhasesTablePowerFactorPhase3 OBJECT-TYPE
        SYNTAX             Integer32
         ACCESS         read-only
        STATUS             mandatory
        DESCRIPTION
        "average of powerfactor(pF) B Phase.The recieved value 
		if 9999 then actual value in decimal willbe 99.99 pf , if recieved 12
		then 0.12 pf. Returns 0 if not supported."
::= { edPowerMgmtPDU4PhasesTablePowerFactorValue 3 }


edPowerMgmtPDU4TotalNumberOfSensor OBJECT-TYPE
        SYNTAX             Integer32
         ACCESS         read-only
        STATUS             mandatory
        DESCRIPTION
        "Number of Sensors managed by the appliance."
::= { edConectedPdu4Data 7 }


edPowerMgmtPDU4SensorsTable OBJECT IDENTIFIER ::= { edConectedPdu4Data 8 }

edPowerMgmtPDU4SensorsData OBJECT IDENTIFIER ::= { edPowerMgmtPDU4SensorsTable 1 }

edPowerMgmtPDU4SensorsTableNumber OBJECT IDENTIFIER ::= { edPowerMgmtPDU4SensorsData 1 }
edPowerMgmtPDU4SensorsTableSensorType OBJECT IDENTIFIER ::= { edPowerMgmtPDU4SensorsData 2 }
edPowerMgmtPDU4SensorsTableSensorValue OBJECT IDENTIFIER::= { edPowerMgmtPDU4SensorsData 3 }

edPowerMgmtPDU4SensorsTableSensor1 OBJECT-TYPE
        SYNTAX             Integer32
         ACCESS         read-only
        STATUS             mandatory
        DESCRIPTION
        "Number of the sensor in the PDU."
::= { edPowerMgmtPDU4SensorsTableNumber 1 }


edPowerMgmtPDU4SensorsTableSensor2 OBJECT-TYPE
        SYNTAX             Integer32
         ACCESS         read-only
        STATUS             mandatory
        DESCRIPTION
        "Number of the sensor in the PDU."
::= { edPowerMgmtPDU4SensorsTableNumber 2 }


edPowerMgmtPDU4SensorsTableSensor3 OBJECT-TYPE
        SYNTAX             Integer32
         ACCESS         read-only
        STATUS             mandatory
        DESCRIPTION
        "Number of the sensor in the PDU."
::= { edPowerMgmtPDU4SensorsTableNumber 3 }

edPowerMgmtPDU4SensorsTableSensor4 OBJECT-TYPE
        SYNTAX             Integer32
         ACCESS         read-only
        STATUS             mandatory
        DESCRIPTION
        "Number of the sensor in the PDU."
::= { edPowerMgmtPDU4SensorsTableNumber 4 }

edPowerMgmtPDU4SensorsTableSensorType1 OBJECT-TYPE
         SYNTAX INTEGER {
		humidity     (2),    			
		temprature   (1),
		nosens      (0)  
		
		}
         ACCESS         read-only
        STATUS             mandatory
        DESCRIPTION
        "returns value displaying type of Sensor."
::= { edPowerMgmtPDU4SensorsTableSensorType 1 }

edPowerMgmtPDU4SensorsTableSensorType2 OBJECT-TYPE
        SYNTAX INTEGER {
		humidity     (2),    			
		temprature   (1),
		nosens      (0)  
		
		}
         ACCESS         read-only
        STATUS             mandatory
        DESCRIPTION
        "returns value displaying type of Sensor."
::= { edPowerMgmtPDU4SensorsTableSensorType 2 }

edPowerMgmtPDU4SensorsTableSensorType3 OBJECT-TYPE
         SYNTAX INTEGER {
		humidity     (2),    			
		temprature   (1),
		nosens      (0)  
		
		}
         ACCESS         read-only
        STATUS             mandatory
        DESCRIPTION
        "returns value displaying type of Sensor."
::= { edPowerMgmtPDU4SensorsTableSensorType 3 }


edPowerMgmtPDU4SensorsTableSensorType4 OBJECT-TYPE
         SYNTAX INTEGER {
		humidity     (2),    			
		temprature   (1),
		nosens      (0)  
		
		}
         ACCESS         read-only
        STATUS             mandatory
        DESCRIPTION
        "returns value displaying type of Sensor."
::= { edPowerMgmtPDU4SensorsTableSensorType 4 }



edPowerMgmtPDU4SensorsTableSensorValueSensor1 OBJECT-TYPE
        SYNTAX             Integer32
         ACCESS         read-only
        STATUS             mandatory
        DESCRIPTION
        "returns value of Sensor
         Returns 0 if not supported."
::= { edPowerMgmtPDU4SensorsTableSensorValue 1 }

edPowerMgmtPDU4SensorsTableSensorValueSensor2 OBJECT-TYPE
        SYNTAX             Integer32
         ACCESS         read-only
        STATUS             mandatory
        DESCRIPTION
        "returns value of Sensor
         Returns 0 if not supported."
::= { edPowerMgmtPDU4SensorsTableSensorValue 2 }

edPowerMgmtPDU4SensorsTableSensorValueSensor3 OBJECT-TYPE
        SYNTAX             Integer32
         ACCESS         read-only
        STATUS             mandatory
        DESCRIPTION
        "returns value of Sensor
         Returns 0 if not supported."
::= { edPowerMgmtPDU4SensorsTableSensorValue 3 }

edPowerMgmtPDU4SensorsTableSensorValueSensor4 OBJECT-TYPE
        SYNTAX             Integer32
         ACCESS         read-only
        STATUS             mandatory
        DESCRIPTION
        "returns value of Sensor
         Returns 0 if not supported."
::= { edPowerMgmtPDU4SensorsTableSensorValue 4 }





----------- Daisy Chaining pduData  4 Ends ----------------------

----------- Daisy Chaining pduData  5 ----------------------


edConectedPdu5Data OBJECT IDENTIFIER::= { edConnectedPduMgmt 5 }

edPowerMgmtPDU5TableData OBJECT IDENTIFIER::= { edConectedPdu5Data 1 }

edPowerMgmtPDU5TableNumber       OBJECT-TYPE
        SYNTAX             Integer32
         ACCESS         read-only
        STATUS             mandatory
        DESCRIPTION
        "Index Number"
::= { edPowerMgmtPDU5TableData 1 }

edPowerMgmtPDU5TableProductCode      OBJECT-TYPE
        SYNTAX             DisplayString
         ACCESS         read-only
        STATUS             mandatory
        DESCRIPTION
        "Version of the PDU firmware.
         Returns N/A if not applicable."
::= { edPowerMgmtPDU5TableData 2 }



edPowerMgmtPDU5TableSerialNumber OBJECT-TYPE
        SYNTAX             Integer32
         ACCESS         read-only
        STATUS             mandatory
        DESCRIPTION
        "Number of outlets of the PDU."
::= { edPowerMgmtPDU5TableData 3 }


edPowerMgmtPDU5TableFirmwareVersion       OBJECT-TYPE
        SYNTAX             DisplayString
         ACCESS         read-only
        STATUS             mandatory
        DESCRIPTION
        "Version of the PDU firmware.
         Returns N/A if not applicable."
::= { edPowerMgmtPDU5TableData 4 }



edPowerMgmtPDU5TableNumberOfOutlets OBJECT-TYPE
        SYNTAX             Integer32
         ACCESS         read-only
        STATUS             mandatory
        DESCRIPTION
        "Number of outlets of the PDU."
::= { edPowerMgmtPDU5TableData 5 }

edPowerMgmtPDU5TableNumberOfPhases OBJECT-TYPE
        SYNTAX             Integer32
         ACCESS         read-only
        STATUS             mandatory
        DESCRIPTION
        "Number of phases of the PDU."
::= { edPowerMgmtPDU5TableData 6 }


edPowerMgmtPDU5TableNumberOfSensors OBJECT-TYPE
        SYNTAX             Integer32
         ACCESS         read-only
        STATUS             mandatory
        DESCRIPTION
        "Number of sensors in the PDU."
::= { edPowerMgmtPDU5TableData 7 }



edPowerMgmtPDU5TableVendor   OBJECT-TYPE
        SYNTAX             DisplayString
         ACCESS         	  read-only
        STATUS             mandatory
        DESCRIPTION
        "Vendor of the PDU.
         Returns N/A if not applicable."
::= { edPowerMgmtPDU5TableData 8 }


edPowerMgmtPDU5AggrInfoTable OBJECT IDENTIFIER::= { edConectedPdu5Data 2 }

edPowerMgmtPDU5AggrsData OBJECT IDENTIFIER::= { edPowerMgmtPDU5AggrInfoTable 1 }


edPowerMgmtPDU5AggrInfoNumber       OBJECT-TYPE
        SYNTAX             		Integer32
         ACCESS         			read-only
        STATUS             		mandatory
        DESCRIPTION
        "Index Number"
::= { edPowerMgmtPDU5AggrsData 1 }
 


edPowerMgmtPDU5AggrInfoTableVoltageValue OBJECT-TYPE
        SYNTAX             Integer32
         ACCESS         read-only
        STATUS             mandatory
        DESCRIPTION
		"Aggrgate voltage of phase is (if vRphase R > vYphase && vRphase R > vBphase) 
		aggregate voltage of R Phase .The recieved value 
		if 23024 then actual value in decimal willbe 230.24 Volts ,
		if recieved 12 then 0.12 Volt. Returns 0 if not supported."
::= { edPowerMgmtPDU5AggrsData 2 }


edPowerMgmtPDU5AggrInfoTableCurrentValue OBJECT-TYPE
        SYNTAX             Integer32
         ACCESS         read-only
        STATUS             mandatory
        DESCRIPTION
        "Addition of mandatory of all Outlet.The recieved value 
		if 1234 then actual value in decimal willbe 12.34 Amp, if recieved 
		value is 12 then 0.12 Amp .Returns 0 if not supported."
::= { edPowerMgmtPDU5AggrsData 3 }


edPowerMgmtPDU5AggrInfoTableApearentEnergyValue OBJECT-TYPE
        SYNTAX             Integer32
         ACCESS         read-only
        STATUS             mandatory
        DESCRIPTION
       "addition of ApearentEnergy(KVaHr) of all outlet.The recieved value
	   if 23024 then actual value in decimal willbe 2.3024 KVaHr , if recieved 12
	   then 0.0012 KVaHr. Returns 0 if not supported."
::= { edPowerMgmtPDU5AggrsData 4 }


edPowerMgmtPDU5AggrInfoTableReactiveEnergyValue OBJECT-TYPE
        SYNTAX             Integer32
         ACCESS         read-only
        STATUS             mandatory
        DESCRIPTION
         "addition of ReactiveEnergy(KVarHr) of all outlet.The recieved value 
		 if 23024 then actual value in decimal willbe 2.3024 KVarHr , if recieved 12 
		 then 0.0012 KVarHr. Returns 0 if not supported."
::= { edPowerMgmtPDU5AggrsData 5 }

edPowerMgmtPDU5AggrInfoTableActiveEnergyValue OBJECT-TYPE
        SYNTAX             Integer32
         ACCESS         read-only
        STATUS             mandatory
        DESCRIPTION
      "addition of ActiveEnergy(KWattHr) of all outlets.The recieved value 
	  if 23024 then actual value in decimal willbe 2.3024 KWattHr , if recieved 12
	  then 0.0012 KWattHr. Returns 0 if not supported."
::= { edPowerMgmtPDU5AggrsData 6 }


edPowerMgmtPDU5AggrInfoTableInstantaneousPowerValue OBJECT-TYPE
        SYNTAX             Integer32
         ACCESS         read-only
        STATUS             mandatory
        DESCRIPTION
      "addition of  Instantaneous Power(KWatt) of all outlet.The recieved value 
	  if 230 then actual value in decimal willbe 2.30 KWatt , if recieved 12 
	  then 0.12 KWatt. Returns 0 if not supported."
::= { edPowerMgmtPDU5AggrsData 7 }

edPowerMgmtPDU5AggrInfoTablePowerFactorValue OBJECT-TYPE
        SYNTAX             Integer32
         ACCESS         read-only
        STATUS             mandatory
        DESCRIPTION
      	"average of powerfactor(pF) of all outlet.The recieved value 
		if 9999 then actual value in decimal willbe 99.99 pf , if recieved 12
		then 0.12 pf. Returns 0 if not supported."

::= { edPowerMgmtPDU5AggrsData 8 }


edPowerMgmtPDU5TotalNumberOfOutlets OBJECT-TYPE
        SYNTAX             Integer32
         ACCESS         read-only
        STATUS             mandatory
        DESCRIPTION
        "Number of outlets managed by the appliance."
::= { edConectedPdu5Data 3 }
 


edPowerMgmtPDU5OutletsTable OBJECT IDENTIFIER::= { edConectedPdu5Data 4 }

edPowerMgmtPDU5OutletData OBJECT IDENTIFIER::= { edPowerMgmtPDU5OutletsTable 1 }

edPowerMgmtPDU5OutletsTableIndex        			OBJECT IDENTIFIER::= { edPowerMgmtPDU5OutletData 1 }
edPowerMgmtPDU5OutletsTableIndexNumber        		OBJECT IDENTIFIER::= { edPowerMgmtPDU5OutletsTableIndex 1 }

edPowerMgmtPDU5OutletsTableVoltage        			OBJECT IDENTIFIER::= { edPowerMgmtPDU5OutletData 2 }
edPowerMgmtPDU5OutletsTableVoltageValue        		OBJECT IDENTIFIER::= { edPowerMgmtPDU5OutletsTableVoltage 1 }
edPowerMgmtPDU5OutletsTableCurrent       	 		OBJECT IDENTIFIER::= { edPowerMgmtPDU5OutletData 3 }
edPowerMgmtPDU5OutletsTableCurrentValue        		OBJECT IDENTIFIER::= { edPowerMgmtPDU5OutletsTableCurrent 1 }
edPowerMgmtPDU5OutletsTableApearentEnergy   		OBJECT IDENTIFIER::= { edPowerMgmtPDU5OutletData 4 }
edPowerMgmtPDU5OutletsTableApearentEnergyValue      OBJECT IDENTIFIER::= { edPowerMgmtPDU5OutletsTableApearentEnergy 1 }
edPowerMgmtPDU5OutletsTableReactiveEnergy      		OBJECT IDENTIFIER::= { edPowerMgmtPDU5OutletData 5 }
edPowerMgmtPDU5OutletsTableReactiveEnergyValue      OBJECT IDENTIFIER::= { edPowerMgmtPDU5OutletsTableReactiveEnergy 1 }
edPowerMgmtPDU5OutletsTableActiveEnergy  			OBJECT IDENTIFIER::= { edPowerMgmtPDU5OutletData 6 }
edPowerMgmtPDU5OutletsTableActiveEnergyValue        OBJECT IDENTIFIER::= { edPowerMgmtPDU5OutletsTableActiveEnergy 1 }
edPowerMgmtPDU5OutletsTableInstantaneousPower  		OBJECT IDENTIFIER::= { edPowerMgmtPDU5OutletData 7 }
edPowerMgmtPDU5OutletsTableInstantaneousPowerValue  OBJECT IDENTIFIER::= { edPowerMgmtPDU5OutletsTableInstantaneousPower 1 }
edPowerMgmtPDU5OutletsTablePowerFactor    			OBJECT IDENTIFIER::= { edPowerMgmtPDU5OutletData 8 }
edPowerMgmtPDU5OutletsTablePowerFactorValue        	OBJECT IDENTIFIER::= { edPowerMgmtPDU5OutletsTablePowerFactor 1 }
edPowerMgmtPDU5OutletsTableFreq    					OBJECT IDENTIFIER::= { edPowerMgmtPDU5OutletData 9 }
edPowerMgmtPDU5OutletsTableFreqValue        		OBJECT IDENTIFIER::= { edPowerMgmtPDU5OutletsTableFreq 1 }
edPowerMgmtPDU5OutletsTableOutletswitching        	OBJECT IDENTIFIER::= { edPowerMgmtPDU5OutletData 10 }
edPowerMgmtPDU5OutletsTableOutletControl        	OBJECT IDENTIFIER::= { edPowerMgmtPDU5OutletsTableOutletswitching 1 }





edPowerMgmtPDU5OutletsTableIndexNumber1 OBJECT-TYPE
        SYNTAX             Integer32
         ACCESS         read-only
        STATUS             mandatory
        DESCRIPTION
         "Index Number of the outlet in the PDU."
::= { edPowerMgmtPDU5OutletsTableIndexNumber 1 }


edPowerMgmtPDU5OutletsTableIndexNumber2 OBJECT-TYPE
        SYNTAX             Integer32
         ACCESS         read-only
        STATUS             mandatory
        DESCRIPTION
         "Index Number of the outlet in the PDU."
::= { edPowerMgmtPDU5OutletsTableIndexNumber 2 }

edPowerMgmtPDU5OutletsTableIndexNumber3 OBJECT-TYPE
        SYNTAX             Integer32
         ACCESS         read-only
        STATUS             mandatory
        DESCRIPTION
        "Index Number of the outlet in the PDU."
::= { edPowerMgmtPDU5OutletsTableIndexNumber 3 }


edPowerMgmtPDU5OutletsTableIndexNumber4 OBJECT-TYPE
        SYNTAX             Integer32
         ACCESS         read-only
        STATUS             mandatory
        DESCRIPTION
        "Index Number of the outlet in the PDU."
::= { edPowerMgmtPDU5OutletsTableIndexNumber 4 }


edPowerMgmtPDU5OutletsTableIndexNumber5 OBJECT-TYPE
        SYNTAX             Integer32
         ACCESS         read-only
        STATUS             mandatory
        DESCRIPTION
        "Index Number of the outlet in the PDU."
::= { edPowerMgmtPDU5OutletsTableIndexNumber 5 }


edPowerMgmtPDU5OutletsTableIndexNumber6 OBJECT-TYPE
        SYNTAX             Integer32
         ACCESS         read-only
        STATUS             mandatory
        DESCRIPTION
         "Index Number of the outlet in the PDU."
::= { edPowerMgmtPDU5OutletsTableIndexNumber 6 }


edPowerMgmtPDU5OutletsTableIndexNumber7 OBJECT-TYPE
        SYNTAX             Integer32
         ACCESS         read-only
        STATUS             mandatory
        DESCRIPTION
        "Index Number of the outlet in the PDU."
::= { edPowerMgmtPDU5OutletsTableIndexNumber 7 }


edPowerMgmtPDU5OutletsTableIndexNumber8 OBJECT-TYPE
        SYNTAX             Integer32
         ACCESS         read-only
        STATUS             mandatory
        DESCRIPTION
       "Index Number of the outlet in the PDU."
::= { edPowerMgmtPDU5OutletsTableIndexNumber 8 }


edPowerMgmtPDU5OutletsTableIndexNumber9 OBJECT-TYPE
        SYNTAX             Integer32
         ACCESS         read-only
        STATUS             mandatory
        DESCRIPTION
         "Index Number of the outlet in the PDU."
::= { edPowerMgmtPDU5OutletsTableIndexNumber 9 }


edPowerMgmtPDU5OutletsTableIndexNumber10 OBJECT-TYPE
        SYNTAX             Integer32
         ACCESS         read-only
        STATUS             mandatory
        DESCRIPTION
        "Index Number of the outlet in the PDU."
::= { edPowerMgmtPDU5OutletsTableIndexNumber 10 }


edPowerMgmtPDU5OutletsTableIndexNumber11 OBJECT-TYPE
        SYNTAX             Integer32
         ACCESS         read-only
        STATUS             mandatory
        DESCRIPTION
      "Index Number of the outlet in the PDU."
::= { edPowerMgmtPDU5OutletsTableIndexNumber 11 }


edPowerMgmtPDU5OutletsTableIndexNumber12 OBJECT-TYPE
        SYNTAX             Integer32
         ACCESS         read-only
        STATUS             mandatory
        DESCRIPTION
       "Index Number of the outlet in the PDU."
::= { edPowerMgmtPDU5OutletsTableIndexNumber 12 }


edPowerMgmtPDU5OutletsTableIndexNumber13 OBJECT-TYPE
        SYNTAX             Integer32
         ACCESS         read-only
        STATUS             mandatory
        DESCRIPTION
        "Index Number of the outlet in the PDU."
::= { edPowerMgmtPDU5OutletsTableIndexNumber 13 }


edPowerMgmtPDU5OutletsTableIndexNumber14 OBJECT-TYPE
        SYNTAX             Integer32
         ACCESS         read-only
        STATUS             mandatory
        DESCRIPTION
       "Index Number of the outlet in the PDU."
::= { edPowerMgmtPDU5OutletsTableIndexNumber 14 }


edPowerMgmtPDU5OutletsTableIndexNumber15 OBJECT-TYPE
        SYNTAX             Integer32
         ACCESS         read-only
        STATUS             mandatory
        DESCRIPTION
       "Index Number of the outlet in the PDU."
::= { edPowerMgmtPDU5OutletsTableIndexNumber 15 }


edPowerMgmtPDU5OutletsTableIndexNumber16 OBJECT-TYPE
        SYNTAX             Integer32
         ACCESS         read-only
        STATUS             mandatory
        DESCRIPTION
      "Index Number of the outlet in the PDU."
::= { edPowerMgmtPDU5OutletsTableIndexNumber 16 }


edPowerMgmtPDU5OutletsTableIndexNumber17 OBJECT-TYPE
        SYNTAX             Integer32
         ACCESS         read-only
        STATUS             mandatory
        DESCRIPTION
       "Index Number of the outlet in the PDU."
::= { edPowerMgmtPDU5OutletsTableIndexNumber 17 }


edPowerMgmtPDU5OutletsTableIndexNumber18 OBJECT-TYPE
        SYNTAX             Integer32
         ACCESS         read-only
        STATUS             mandatory
        DESCRIPTION
          "Index Number of the outlet in the PDU."
::= { edPowerMgmtPDU5OutletsTableIndexNumber 18 }


edPowerMgmtPDU5OutletsTableIndexNumber19 OBJECT-TYPE
        SYNTAX             Integer32
         ACCESS         read-only
        STATUS             mandatory
        DESCRIPTION
          "Index Number of the outlet in the PDU."
::= { edPowerMgmtPDU5OutletsTableIndexNumber 19 }


edPowerMgmtPDU5OutletsTableIndexNumber20 OBJECT-TYPE
        SYNTAX             Integer32
         ACCESS         read-only
        STATUS             mandatory
        DESCRIPTION
          "Index Number of the outlet in the PDU."
::= { edPowerMgmtPDU5OutletsTableIndexNumber 20 }


edPowerMgmtPDU5OutletsTableIndexNumber21 OBJECT-TYPE
        SYNTAX             Integer32
         ACCESS         read-only
        STATUS             mandatory
        DESCRIPTION
          "Index Number of the outlet in the PDU."
::= { edPowerMgmtPDU5OutletsTableIndexNumber 21 }


edPowerMgmtPDU5OutletsTableIndexNumber22 OBJECT-TYPE
        SYNTAX             Integer32
         ACCESS         read-only
        STATUS             mandatory
        DESCRIPTION
          "Index Number of the outlet in the PDU."
::= { edPowerMgmtPDU5OutletsTableIndexNumber 22 }


edPowerMgmtPDU5OutletsTableIndexNumber23 OBJECT-TYPE
        SYNTAX             Integer32
         ACCESS         read-only
        STATUS             mandatory
        DESCRIPTION
          "Index Number of the outlet in the PDU."
::= { edPowerMgmtPDU5OutletsTableIndexNumber 23 }


edPowerMgmtPDU5OutletsTableIndexNumber24 OBJECT-TYPE
        SYNTAX             Integer32
         ACCESS         read-only
        STATUS             mandatory
        DESCRIPTION
          "Index Number of the outlet in the PDU."
::= { edPowerMgmtPDU5OutletsTableIndexNumber 24 }

edPowerMgmtPDU5OutletsTableIndexNumber25 OBJECT-TYPE
        SYNTAX             Integer32
         ACCESS         read-only
        STATUS             mandatory
        DESCRIPTION
          "Index Number of the outlet in the PDU."
::= { edPowerMgmtPDU5OutletsTableIndexNumber 25 }


edPowerMgmtPDU5OutletsTableIndexNumber26 OBJECT-TYPE
        SYNTAX             Integer32
         ACCESS         read-only
        STATUS             mandatory
        DESCRIPTION
          "Index Number of the outlet in the PDU."
::= { edPowerMgmtPDU5OutletsTableIndexNumber 26 }


edPowerMgmtPDU5OutletsTableIndexNumber27 OBJECT-TYPE
        SYNTAX             Integer32
         ACCESS         read-only
        STATUS             mandatory
        DESCRIPTION
          "Index Number of the outlet in the PDU."
::= { edPowerMgmtPDU5OutletsTableIndexNumber 27 }

edPowerMgmtPDU5OutletsTableIndexNumber28 OBJECT-TYPE
        SYNTAX             Integer32
         ACCESS         read-only
        STATUS             mandatory
        DESCRIPTION
          "Index Number of the outlet in the PDU."
::= { edPowerMgmtPDU5OutletsTableIndexNumber 28 }

edPowerMgmtPDU5OutletsTableIndexNumber29 OBJECT-TYPE
        SYNTAX             Integer32
         ACCESS         read-only
        STATUS             mandatory
        DESCRIPTION
          "Index Number of the outlet in the PDU."
::= { edPowerMgmtPDU5OutletsTableIndexNumber 29 }

edPowerMgmtPDU5OutletsTableIndexNumber30 OBJECT-TYPE
        SYNTAX             Integer32
         ACCESS         read-only
        STATUS             mandatory
        DESCRIPTION
          "Index Number of the outlet in the PDU."
::= { edPowerMgmtPDU5OutletsTableIndexNumber 30 }

edPowerMgmtPDU5OutletsTableIndexNumber31 OBJECT-TYPE
        SYNTAX             Integer32
         ACCESS         read-only
        STATUS             mandatory
        DESCRIPTION
          "Index Number of the outlet in the PDU."
::= { edPowerMgmtPDU5OutletsTableIndexNumber 31 }

edPowerMgmtPDU5OutletsTableIndexNumber32 OBJECT-TYPE
        SYNTAX             Integer32
         ACCESS         read-only
        STATUS             mandatory
        DESCRIPTION
          "Index Number of the outlet in the PDU."
::= { edPowerMgmtPDU5OutletsTableIndexNumber 32 }

edPowerMgmtPDU5OutletsTableIndexNumber33 OBJECT-TYPE
        SYNTAX             Integer32
         ACCESS         read-only
        STATUS             mandatory
        DESCRIPTION
          "Index Number of the outlet in the PDU."
::= { edPowerMgmtPDU5OutletsTableIndexNumber 33 }

edPowerMgmtPDU5OutletsTableIndexNumber34 OBJECT-TYPE
        SYNTAX             Integer32
         ACCESS         read-only
        STATUS             mandatory
        DESCRIPTION
          "Index Number of the outlet in the PDU."
::= { edPowerMgmtPDU5OutletsTableIndexNumber 34 }


edPowerMgmtPDU5OutletsTableIndexNumber35 OBJECT-TYPE
        SYNTAX             Integer32
         ACCESS         read-only
        STATUS             mandatory
        DESCRIPTION
          "Index Number of the outlet in the PDU."
::= { edPowerMgmtPDU5OutletsTableIndexNumber 35 }


edPowerMgmtPDU5OutletsTableIndexNumber36 OBJECT-TYPE
        SYNTAX             Integer32
         ACCESS         read-only
        STATUS             mandatory
        DESCRIPTION
          "Index Number of the outlet in the PDU."
::= { edPowerMgmtPDU5OutletsTableIndexNumber 36 }


edPowerMgmtPDU5OutletsTableIndexNumber37 OBJECT-TYPE
        SYNTAX             Integer32
         ACCESS         read-only
        STATUS             mandatory
        DESCRIPTION
          "Index Number of the outlet in the PDU."
::= { edPowerMgmtPDU5OutletsTableIndexNumber 37 }


edPowerMgmtPDU5OutletsTableIndexNumber38 OBJECT-TYPE
        SYNTAX             Integer32
         ACCESS         read-only
        STATUS             mandatory
        DESCRIPTION
          "Index Number of the outlet in the PDU."
::= { edPowerMgmtPDU5OutletsTableIndexNumber 38 }


edPowerMgmtPDU5OutletsTableIndexNumber39 OBJECT-TYPE
        SYNTAX             Integer32
         ACCESS         read-only
        STATUS             mandatory
        DESCRIPTION
          "Index Number of the outlet in the PDU."
::= { edPowerMgmtPDU5OutletsTableIndexNumber 39 }


edPowerMgmtPDU5OutletsTableIndexNumber40 OBJECT-TYPE
        SYNTAX             Integer32
         ACCESS         read-only
        STATUS             mandatory
        DESCRIPTION
          "Index Number of the outlet in the PDU."
::= { edPowerMgmtPDU5OutletsTableIndexNumber 40 }


edPowerMgmtPDU5OutletsTableIndexNumber41 OBJECT-TYPE
        SYNTAX             Integer32
         ACCESS         		read-only
        STATUS             mandatory
        DESCRIPTION
          "Index Number of the outlet in the PDU."
::= { edPowerMgmtPDU5OutletsTableIndexNumber 41 }


edPowerMgmtPDU5OutletsTableIndexNumber42 OBJECT-TYPE
        SYNTAX             Integer32
         ACCESS         read-only
        STATUS             mandatory
        DESCRIPTION
          "Index Number of the outlet in the PDU."
::= { edPowerMgmtPDU5OutletsTableIndexNumber 42 }







edPowerMgmtPDU5OutletsTableVoltageOutlet1 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 1 }


edPowerMgmtPDU5OutletsTableVoltageOutlet2 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 2 }

edPowerMgmtPDU5OutletsTableVoltageOutlet3 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 3 }


edPowerMgmtPDU5OutletsTableVoltageOutlet4 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 4 }


edPowerMgmtPDU5OutletsTableVoltageOutlet5 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 5 }


edPowerMgmtPDU5OutletsTableVoltageOutlet6 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 6 }


edPowerMgmtPDU5OutletsTableVoltageOutlet7 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 7 }


edPowerMgmtPDU5OutletsTableVoltageOutlet8 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 8 }


edPowerMgmtPDU5OutletsTableVoltageOutlet9 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 9 }


edPowerMgmtPDU5OutletsTableVoltageOutlet10 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 10 }


edPowerMgmtPDU5OutletsTableVoltageOutlet11 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 11 }


edPowerMgmtPDU5OutletsTableVoltageOutlet12 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 12 }


edPowerMgmtPDU5OutletsTableVoltageOutlet13 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 13 }


edPowerMgmtPDU5OutletsTableVoltageOutlet14 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 14 }


edPowerMgmtPDU5OutletsTableVoltageOutlet15 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 15 }


edPowerMgmtPDU5OutletsTableVoltageOutlet16 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 16 }


edPowerMgmtPDU5OutletsTableVoltageOutlet17 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 17 }


edPowerMgmtPDU5OutletsTableVoltageOutlet18 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 18 }


edPowerMgmtPDU5OutletsTableVoltageOutlet19 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 19 }


edPowerMgmtPDU5OutletsTableVoltageOutlet20 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 20 }


edPowerMgmtPDU5OutletsTableVoltageOutlet21 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 21 }


edPowerMgmtPDU5OutletsTableVoltageOutlet22 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 22 }


edPowerMgmtPDU5OutletsTableVoltageOutlet23 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 23 }


edPowerMgmtPDU5OutletsTableVoltageOutlet24 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 24 }

edPowerMgmtPDU5OutletsTableVoltageOutlet25 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 25 }


edPowerMgmtPDU5OutletsTableVoltageOutlet26 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 26 }


edPowerMgmtPDU5OutletsTableVoltageOutlet27 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 27 }

edPowerMgmtPDU5OutletsTableVoltageOutlet28 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 28 }

edPowerMgmtPDU5OutletsTableVoltageOutlet29 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 29 }

edPowerMgmtPDU5OutletsTableVoltageOutlet30 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 30 }

edPowerMgmtPDU5OutletsTableVoltageOutlet31 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 31 }

edPowerMgmtPDU5OutletsTableVoltageOutlet32 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 32 }

edPowerMgmtPDU5OutletsTableVoltageOutlet33 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 33 }

edPowerMgmtPDU5OutletsTableVoltageOutlet34 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 34 }


edPowerMgmtPDU5OutletsTableVoltageOutlet35 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 35 }


edPowerMgmtPDU5OutletsTableVoltageOutlet36 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 36 }


edPowerMgmtPDU5OutletsTableVoltageOutlet37 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 37 }


edPowerMgmtPDU5OutletsTableVoltageOutlet38 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 38 }


edPowerMgmtPDU5OutletsTableVoltageOutlet39 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 39 }


edPowerMgmtPDU5OutletsTableVoltageOutlet40 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 40 }


edPowerMgmtPDU5OutletsTableVoltageOutlet41 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 41 }


edPowerMgmtPDU5OutletsTableVoltageOutlet42 OBJECT-TYPE
        SYNTAX             Integer32
         ACCESS         read-only
        STATUS             mandatory
        DESCRIPTION
        "Actual value of Voltage for the outlet.The recieved value
		if 23024 then actual value in decimal willbe 230.24 Volts ,
		if recieved 12 then 0.12 Volt. Returns 0 if not supported."
::= { edPowerMgmtPDU5OutletsTableVoltageValue 42 }








edPowerMgmtPDU5OutletsTableCurrentOutlet1 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU5OutletsTableCurrentValue 1 }


edPowerMgmtPDU5OutletsTableCurrentOutlet2 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU5OutletsTableCurrentValue 2 }

edPowerMgmtPDU5OutletsTableCurrentOutlet3 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU5OutletsTableCurrentValue 3 }


edPowerMgmtPDU5OutletsTableCurrentOutlet4 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU5OutletsTableCurrentValue 4 }


edPowerMgmtPDU5OutletsTableCurrentOutlet5 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU5OutletsTableCurrentValue 5 }


edPowerMgmtPDU5OutletsTableCurrentOutlet6 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU5OutletsTableCurrentValue 6 }


edPowerMgmtPDU5OutletsTableCurrentOutlet7 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU5OutletsTableCurrentValue 7 }


edPowerMgmtPDU5OutletsTableCurrentOutlet8 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU5OutletsTableCurrentValue 8 }


edPowerMgmtPDU5OutletsTableCurrentOutlet9 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU5OutletsTableCurrentValue 9 }


edPowerMgmtPDU5OutletsTableCurrentOutlet10 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU5OutletsTableCurrentValue 10 }


edPowerMgmtPDU5OutletsTableCurrentOutlet11 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU5OutletsTableCurrentValue 11 }


edPowerMgmtPDU5OutletsTableCurrentOutlet12 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU5OutletsTableCurrentValue 12 }


edPowerMgmtPDU5OutletsTableCurrentOutlet13 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU5OutletsTableCurrentValue 13 }


edPowerMgmtPDU5OutletsTableCurrentOutlet14 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU5OutletsTableCurrentValue 14 }


edPowerMgmtPDU5OutletsTableCurrentOutlet15 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU5OutletsTableCurrentValue 15 }


edPowerMgmtPDU5OutletsTableCurrentOutlet16 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU5OutletsTableCurrentValue 16 }


edPowerMgmtPDU5OutletsTableCurrentOutlet17 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU5OutletsTableCurrentValue 17 }


edPowerMgmtPDU5OutletsTableCurrentOutlet18 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU5OutletsTableCurrentValue 18 }


edPowerMgmtPDU5OutletsTableCurrentOutlet19 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU5OutletsTableCurrentValue 19 }


edPowerMgmtPDU5OutletsTableCurrentOutlet20 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU5OutletsTableCurrentValue 20 }


edPowerMgmtPDU5OutletsTableCurrentOutlet21 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU5OutletsTableCurrentValue 21 }


edPowerMgmtPDU5OutletsTableCurrentOutlet22 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU5OutletsTableCurrentValue 22 }


edPowerMgmtPDU5OutletsTableCurrentOutlet23 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU5OutletsTableCurrentValue 23 }


edPowerMgmtPDU5OutletsTableCurrentOutlet24 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU5OutletsTableCurrentValue 24 }

edPowerMgmtPDU5OutletsTableCurrentOutlet25 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU5OutletsTableCurrentValue 25 }


edPowerMgmtPDU5OutletsTableCurrentOutlet26 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU5OutletsTableCurrentValue 26 }


edPowerMgmtPDU5OutletsTableCurrentOutlet27 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU5OutletsTableCurrentValue 27 }

edPowerMgmtPDU5OutletsTableCurrentOutlet28 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU5OutletsTableCurrentValue 28 }

edPowerMgmtPDU5OutletsTableCurrentOutlet29 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU5OutletsTableCurrentValue 29 }

edPowerMgmtPDU5OutletsTableCurrentOutlet30 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU5OutletsTableCurrentValue 30 }

edPowerMgmtPDU5OutletsTableCurrentOutlet31 OBJECT-TYPE
        SYNTAX             Integer32
         ACCESS         read-only
        STATUS             mandatory
        DESCRIPTION
      "Actual value of Current for the outlet(Amp).The recieved value 
		if 1234 then actual value in decimal willbe 12.34 Amp, if recieved 
		value is 12 then 0.12 Amp .Returns 0 if not supported."
::= { edPowerMgmtPDU5OutletsTableCurrentValue 31 }

edPowerMgmtPDU5OutletsTableCurrentOutlet32 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU5OutletsTableCurrentValue 32 }

edPowerMgmtPDU5OutletsTableCurrentOutlet33 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU5OutletsTableCurrentValue 33 }

edPowerMgmtPDU5OutletsTableCurrentOutlet34 OBJECT-TYPE
        SYNTAX             Integer32
         ACCESS         read-only
        STATUS             mandatory
        DESCRIPTION
       "Actual value of Current for the outlet(Amp).The recieved value 
		if 1234 then actual value in decimal willbe 12.34 Amp, if recieved 
		value is 12 then 0.12 Amp .Returns 0 if not supported."
::= { edPowerMgmtPDU5OutletsTableCurrentValue 34 }


edPowerMgmtPDU5OutletsTableCurrentOutlet35 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU5OutletsTableCurrentValue 35 }


edPowerMgmtPDU5OutletsTableCurrentOutlet36 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU5OutletsTableCurrentValue 36 }


edPowerMgmtPDU5OutletsTableCurrentOutlet37 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU5OutletsTableCurrentValue 37 }


edPowerMgmtPDU5OutletsTableCurrentOutlet38 OBJECT-TYPE
        SYNTAX             Integer32
         ACCESS         read-only
        STATUS             mandatory
        DESCRIPTION
         "Actual value of Current for the outlet(Amp).The recieved value 
		if 1234 then actual value in decimal willbe 12.34 Amp, if recieved 
		value is 12 then 0.12 Amp .Returns 0 if not supported."
::= { edPowerMgmtPDU5OutletsTableCurrentValue 38 }


edPowerMgmtPDU5OutletsTableCurrentOutlet39 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU5OutletsTableCurrentValue 39 }


edPowerMgmtPDU5OutletsTableCurrentOutlet40 OBJECT-TYPE
        SYNTAX             Integer32
         ACCESS         read-only
        STATUS             mandatory
        DESCRIPTION
        "Actual value of Current for the outlet(Amp).The recieved value 
		if 1234 then actual value in decimal willbe 12.34 Amp, if recieved 
		value is 12 then 0.12 Amp .Returns 0 if not supported."
::= { edPowerMgmtPDU5OutletsTableCurrentValue 40 }


edPowerMgmtPDU5OutletsTableCurrentOutlet41 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU5OutletsTableCurrentValue 41 }


edPowerMgmtPDU5OutletsTableCurrentOutlet42 OBJECT-TYPE
        SYNTAX             Integer32
         ACCESS         read-only
        STATUS             mandatory
        DESCRIPTION
          "Actual value of Current for the outlet(Amp).The recieved value 
		if 1234 then actual value in decimal willbe 12.34 Amp, if recieved 
		value is 12 then 0.12 Amp .Returns 0 if not supported."
::= { edPowerMgmtPDU5OutletsTableCurrentValue 42 }









edPowerMgmtPDU5OutletsTableApearentEnergyOutlet1 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 1 }


edPowerMgmtPDU5OutletsTableApearentEnergyOutlet2 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 2 }

edPowerMgmtPDU5OutletsTableApearentEnergyOutlet3 OBJECT-TYPE
        SYNTAX             Integer32
         ACCESS         read-only
        STATUS             mandatory
        DESCRIPTION
      "Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 3 }


edPowerMgmtPDU5OutletsTableApearentEnergyOutlet4 OBJECT-TYPE
        SYNTAX             Integer32
         ACCESS         read-only
        STATUS             mandatory
        DESCRIPTION
      "Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 4 }


edPowerMgmtPDU5OutletsTableApearentEnergyOutlet5 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 5 }


edPowerMgmtPDU5OutletsTableApearentEnergyOutlet6 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 6 }


edPowerMgmtPDU5OutletsTableApearentEnergyOutlet7 OBJECT-TYPE
        SYNTAX             Integer32
         ACCESS         read-only
        STATUS             mandatory
        DESCRIPTION
        "Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 7 }


edPowerMgmtPDU5OutletsTableApearentEnergyOutlet8 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 8 }


edPowerMgmtPDU5OutletsTableApearentEnergyOutlet9 OBJECT-TYPE
        SYNTAX             Integer32
         ACCESS         read-only
        STATUS             mandatory
        DESCRIPTION
     "Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 9 }


edPowerMgmtPDU5OutletsTableApearentEnergyOutlet10 OBJECT-TYPE
        SYNTAX             Integer32
         ACCESS         read-only
        STATUS             mandatory
        DESCRIPTION
     "Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 10 }


edPowerMgmtPDU5OutletsTableApearentEnergyOutlet11 OBJECT-TYPE
        SYNTAX             Integer32
         ACCESS         read-only
        STATUS             mandatory
        DESCRIPTION
       "Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 11 }


edPowerMgmtPDU5OutletsTableApearentEnergyOutlet12 OBJECT-TYPE
        SYNTAX             Integer32
         ACCESS         read-only
        STATUS             mandatory
        DESCRIPTION
   "Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 12 }


edPowerMgmtPDU5OutletsTableApearentEnergyOutlet13 OBJECT-TYPE
        SYNTAX             Integer32
         ACCESS         read-only
        STATUS             mandatory
        DESCRIPTION
      "Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 13 }


edPowerMgmtPDU5OutletsTableApearentEnergyOutlet14 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 14 }


edPowerMgmtPDU5OutletsTableApearentEnergyOutlet15 OBJECT-TYPE
        SYNTAX             Integer32
         ACCESS         read-only
        STATUS             mandatory
        DESCRIPTION
         "Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 15 }


edPowerMgmtPDU5OutletsTableApearentEnergyOutlet16 OBJECT-TYPE
        SYNTAX             Integer32
         ACCESS         read-only
        STATUS             mandatory
        DESCRIPTION
          "Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 16 }


edPowerMgmtPDU5OutletsTableApearentEnergyOutlet17 OBJECT-TYPE
        SYNTAX             Integer32
         ACCESS         read-only
        STATUS             mandatory
        DESCRIPTION
          "Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 17 }


edPowerMgmtPDU5OutletsTableApearentEnergyOutlet18 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 18 }


edPowerMgmtPDU5OutletsTableApearentEnergyOutlet19 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 19 }


edPowerMgmtPDU5OutletsTableApearentEnergyOutlet20 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 20 }


edPowerMgmtPDU5OutletsTableApearentEnergyOutlet21 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 21 }


edPowerMgmtPDU5OutletsTableApearentEnergyOutlet22 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 22 }


edPowerMgmtPDU5OutletsTableApearentEnergyOutlet23 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 23 }


edPowerMgmtPDU5OutletsTableApearentEnergyOutlet24 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 24 }

edPowerMgmtPDU5OutletsTableApearentEnergyOutlet25 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 25 }


edPowerMgmtPDU5OutletsTableApearentEnergyOutlet26 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 26 }


edPowerMgmtPDU5OutletsTableApearentEnergyOutlet27 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 27 }

edPowerMgmtPDU5OutletsTableApearentEnergyOutlet28 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 28 }

edPowerMgmtPDU5OutletsTableApearentEnergyOutlet29 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 29 }

edPowerMgmtPDU5OutletsTableApearentEnergyOutlet30 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 30 }

edPowerMgmtPDU5OutletsTableApearentEnergyOutlet31 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 31 }

edPowerMgmtPDU5OutletsTableApearentEnergyOutlet32 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 32 }

edPowerMgmtPDU5OutletsTableApearentEnergyOutlet33 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 33 }

edPowerMgmtPDU5OutletsTableApearentEnergyOutlet34 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 34 }


edPowerMgmtPDU5OutletsTableApearentEnergyOutlet35 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 35 }


edPowerMgmtPDU5OutletsTableApearentEnergyOutlet36 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 36 }


edPowerMgmtPDU5OutletsTableApearentEnergyOutlet37 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 37 }


edPowerMgmtPDU5OutletsTableApearentEnergyOutlet38 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 38 }


edPowerMgmtPDU5OutletsTableApearentEnergyOutlet39 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 39 }


edPowerMgmtPDU5OutletsTableApearentEnergyOutlet40 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 40 }


edPowerMgmtPDU5OutletsTableApearentEnergyOutlet41 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 41 }


edPowerMgmtPDU5OutletsTableApearentEnergyOutlet42 OBJECT-TYPE
        SYNTAX             Integer32
         ACCESS         read-only
        STATUS             mandatory
        DESCRIPTION
		"Actual value of ApearentEnergy(KVaHr) for the outlet.The recieved value
		if 23024 then actual value in decimal willbe 2.3024 KVaHr , if recieved 12
		then 0.0012 KVaHr. Returns 0 if not supported."
::= { edPowerMgmtPDU5OutletsTableApearentEnergyValue 42 }





edPowerMgmtPDU5OutletsTableReactiveEnergyOutlet1 OBJECT-TYPE
        SYNTAX             Integer32
         ACCESS         read-only
        STATUS             mandatory
        DESCRIPTION
		"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 1 }


edPowerMgmtPDU5OutletsTableReactiveEnergyOutlet2 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 2 }

edPowerMgmtPDU5OutletsTableReactiveEnergyOutlet3 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 3 }


edPowerMgmtPDU5OutletsTableReactiveEnergyOutlet4 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 4 }


edPowerMgmtPDU5OutletsTableReactiveEnergyOutlet5 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 5 }


edPowerMgmtPDU5OutletsTableReactiveEnergyOutlet6 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 6 }


edPowerMgmtPDU5OutletsTableReactiveEnergyOutlet7 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 7 }


edPowerMgmtPDU5OutletsTableReactiveEnergyOutlet8 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 8 }


edPowerMgmtPDU5OutletsTableReactiveEnergyOutlet9 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 9 }


edPowerMgmtPDU5OutletsTableReactiveEnergyOutlet10 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 10 }


edPowerMgmtPDU5OutletsTableReactiveEnergyOutlet11 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 11 }


edPowerMgmtPDU5OutletsTableReactiveEnergyOutlet12 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 12 }


edPowerMgmtPDU5OutletsTableReactiveEnergyOutlet13 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 13 }


edPowerMgmtPDU5OutletsTableReactiveEnergyOutlet14 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 14 }


edPowerMgmtPDU5OutletsTableReactiveEnergyOutlet15 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 15 }


edPowerMgmtPDU5OutletsTableReactiveEnergyOutlet16 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 16 }


edPowerMgmtPDU5OutletsTableReactiveEnergyOutlet17 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 17 }


edPowerMgmtPDU5OutletsTableReactiveEnergyOutlet18 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 18 }


edPowerMgmtPDU5OutletsTableReactiveEnergyOutlet19 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 19 }


edPowerMgmtPDU5OutletsTableReactiveEnergyOutlet20 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 20 }


edPowerMgmtPDU5OutletsTableReactiveEnergyOutlet21 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 21 }


edPowerMgmtPDU5OutletsTableReactiveEnergyOutlet22 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 22 }


edPowerMgmtPDU5OutletsTableReactiveEnergyOutlet23 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 23 }


edPowerMgmtPDU5OutletsTableReactiveEnergyOutlet24 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 24 }

edPowerMgmtPDU5OutletsTableReactiveEnergyOutlet25 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 25 }


edPowerMgmtPDU5OutletsTableReactiveEnergyOutlet26 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 26 }


edPowerMgmtPDU5OutletsTableReactiveEnergyOutlet27 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 27 }

edPowerMgmtPDU5OutletsTableReactiveEnergyOutlet28 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 28 }

edPowerMgmtPDU5OutletsTableReactiveEnergyOutlet29 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 29 }

edPowerMgmtPDU5OutletsTableReactiveEnergyOutlet30 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 30 }

edPowerMgmtPDU5OutletsTableReactiveEnergyOutlet31 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 31 }

edPowerMgmtPDU5OutletsTableReactiveEnergyOutlet32 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 32 }

edPowerMgmtPDU5OutletsTableReactiveEnergyOutlet33 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 33 }

edPowerMgmtPDU5OutletsTableReactiveEnergyOutlet34 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 34 }


edPowerMgmtPDU5OutletsTableReactiveEnergyOutlet35 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 35 }


edPowerMgmtPDU5OutletsTableReactiveEnergyOutlet36 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 36 }


edPowerMgmtPDU5OutletsTableReactiveEnergyOutlet37 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 37 }


edPowerMgmtPDU5OutletsTableReactiveEnergyOutlet38 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 38 }


edPowerMgmtPDU5OutletsTableReactiveEnergyOutlet39 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 39 }


edPowerMgmtPDU5OutletsTableReactiveEnergyOutlet40 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 40 }


edPowerMgmtPDU5OutletsTableReactiveEnergyOutlet41 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 41 }


edPowerMgmtPDU5OutletsTableReactiveEnergyOutlet42 OBJECT-TYPE
        SYNTAX             Integer32
         ACCESS         read-only
        STATUS             mandatory
        DESCRIPTION
"Actual value of ReactiveEnergy(KVarHr) for the outlet.The recieved value 
		if 23024 then actual value in decimal willbe 2.3024 KVarHr , if recieved 12
		then 0.0012 KVarHr. Returns 0 if not supported."
::= { edPowerMgmtPDU5OutletsTableReactiveEnergyValue 42 }




edPowerMgmtPDU5OutletsTableActiveEnergyOutlet1 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 1 }


edPowerMgmtPDU5OutletsTableActiveEnergyOutlet2 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 2 }

edPowerMgmtPDU5OutletsTableActiveEnergyOutlet3 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 3 }


edPowerMgmtPDU5OutletsTableActiveEnergyOutlet4 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 4 }


edPowerMgmtPDU5OutletsTableActiveEnergyOutlet5 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 5 }


edPowerMgmtPDU5OutletsTableActiveEnergyOutlet6 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 6 }


edPowerMgmtPDU5OutletsTableActiveEnergyOutlet7 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 7 }


edPowerMgmtPDU5OutletsTableActiveEnergyOutlet8 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 8 }


edPowerMgmtPDU5OutletsTableActiveEnergyOutlet9 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 9 }


edPowerMgmtPDU5OutletsTableActiveEnergyOutlet10 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 10 }


edPowerMgmtPDU5OutletsTableActiveEnergyOutlet11 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 11 }


edPowerMgmtPDU5OutletsTableActiveEnergyOutlet12 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 12 }


edPowerMgmtPDU5OutletsTableActiveEnergyOutlet13 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 13 }


edPowerMgmtPDU5OutletsTableActiveEnergyOutlet14 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 14 }


edPowerMgmtPDU5OutletsTableActiveEnergyOutlet15 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 15 }


edPowerMgmtPDU5OutletsTableActiveEnergyOutlet16 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 16 }


edPowerMgmtPDU5OutletsTableActiveEnergyOutlet17 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 17 }


edPowerMgmtPDU5OutletsTableActiveEnergyOutlet18 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 18 }


edPowerMgmtPDU5OutletsTableActiveEnergyOutlet19 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 19 }


edPowerMgmtPDU5OutletsTableActiveEnergyOutlet20 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 20 }


edPowerMgmtPDU5OutletsTableActiveEnergyOutlet21 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 21 }


edPowerMgmtPDU5OutletsTableActiveEnergyOutlet22 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 22 }


edPowerMgmtPDU5OutletsTableActiveEnergyOutlet23 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 23 }


edPowerMgmtPDU5OutletsTableActiveEnergyOutlet24 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 24 }

edPowerMgmtPDU5OutletsTableActiveEnergyOutlet25 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 25 }


edPowerMgmtPDU5OutletsTableActiveEnergyOutlet26 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 26 }


edPowerMgmtPDU5OutletsTableActiveEnergyOutlet27 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 27 }

edPowerMgmtPDU5OutletsTableActiveEnergyOutlet28 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 28 }

edPowerMgmtPDU5OutletsTableActiveEnergyOutlet29 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 29 }

edPowerMgmtPDU5OutletsTableActiveEnergyOutlet30 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 30 }

edPowerMgmtPDU5OutletsTableActiveEnergyOutlet31 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 31 }

edPowerMgmtPDU5OutletsTableActiveEnergyOutlet32 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 32 }

edPowerMgmtPDU5OutletsTableActiveEnergyOutlet33 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 33 }

edPowerMgmtPDU5OutletsTableActiveEnergyOutlet34 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 34 }


edPowerMgmtPDU5OutletsTableActiveEnergyOutlet35 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 35 }


edPowerMgmtPDU5OutletsTableActiveEnergyOutlet36 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 36 }


edPowerMgmtPDU5OutletsTableActiveEnergyOutlet37 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 37 }


edPowerMgmtPDU5OutletsTableActiveEnergyOutlet38 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 38 }


edPowerMgmtPDU5OutletsTableActiveEnergyOutlet39 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 39 }


edPowerMgmtPDU5OutletsTableActiveEnergyOutlet40 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 40 }


edPowerMgmtPDU5OutletsTableActiveEnergyOutlet41 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 41 }


edPowerMgmtPDU5OutletsTableActiveEnergyOutlet42 OBJECT-TYPE
        SYNTAX             Integer32
         ACCESS         read-only
        STATUS             mandatory
        DESCRIPTION
		"Actual value of ActiveEnergy(KWattHr) for the outlet.The recieved value
		if 23024 then actual value in decimal willbe 2.3024 KWattHr , if recieved 12 
		then 0.0012 KWattHr. Returns 0 if not supported."
::= { edPowerMgmtPDU5OutletsTableActiveEnergyValue 42 }









edPowerMgmtPDU5OutletsTableInstantaneousPowerOutlet1 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 1 }


edPowerMgmtPDU5OutletsTableInstantaneousPowerOutlet2 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 2 }

edPowerMgmtPDU5OutletsTableInstantaneousPowerOutlet3 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 3 }


edPowerMgmtPDU5OutletsTableInstantaneousPowerOutlet4 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 4 }


edPowerMgmtPDU5OutletsTableInstantaneousPowerOutlet5 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 5 }


edPowerMgmtPDU5OutletsTableInstantaneousPowerOutlet6 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 6 }


edPowerMgmtPDU5OutletsTableInstantaneousPowerOutlet7 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 7 }


edPowerMgmtPDU5OutletsTableInstantaneousPowerOutlet8 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 8 }


edPowerMgmtPDU5OutletsTableInstantaneousPowerOutlet9 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 9 }


edPowerMgmtPDU5OutletsTableInstantaneousPowerOutlet10 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 10 }


edPowerMgmtPDU5OutletsTableInstantaneousPowerOutlet11 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 11 }


edPowerMgmtPDU5OutletsTableInstantaneousPowerOutlet12 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 12 }


edPowerMgmtPDU5OutletsTableInstantaneousPowerOutlet13 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 13 }


edPowerMgmtPDU5OutletsTableInstantaneousPowerOutlet14 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 14 }


edPowerMgmtPDU5OutletsTableInstantaneousPowerOutlet15 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 15 }


edPowerMgmtPDU5OutletsTableInstantaneousPowerOutlet16 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 16 }


edPowerMgmtPDU5OutletsTableInstantaneousPowerOutlet17 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 17 }


edPowerMgmtPDU5OutletsTableInstantaneousPowerOutlet18 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 18 }


edPowerMgmtPDU5OutletsTableInstantaneousPowerOutlet19 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 19 }


edPowerMgmtPDU5OutletsTableInstantaneousPowerOutlet20 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 20 }


edPowerMgmtPDU5OutletsTableInstantaneousPowerOutlet21 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 21 }


edPowerMgmtPDU5OutletsTableInstantaneousPowerOutlet22 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 22 }


edPowerMgmtPDU5OutletsTableInstantaneousPowerOutlet23 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 23 }


edPowerMgmtPDU5OutletsTableInstantaneousPowerOutlet24 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 24 }

edPowerMgmtPDU5OutletsTableInstantaneousPowerOutlet25 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 25 }


edPowerMgmtPDU5OutletsTableInstantaneousPowerOutlet26 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 26 }


edPowerMgmtPDU5OutletsTableInstantaneousPowerOutlet27 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 27 }

edPowerMgmtPDU5OutletsTableInstantaneousPowerOutlet28 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 28 }

edPowerMgmtPDU5OutletsTableInstantaneousPowerOutlet29 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 29 }

edPowerMgmtPDU5OutletsTableInstantaneousPowerOutlet30 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 30 }

edPowerMgmtPDU5OutletsTableInstantaneousPowerOutlet31 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 31 }

edPowerMgmtPDU5OutletsTableInstantaneousPowerOutlet32 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 32 }

edPowerMgmtPDU5OutletsTableInstantaneousPowerOutlet33 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 33 }

edPowerMgmtPDU5OutletsTableInstantaneousPowerOutlet34 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 34 }


edPowerMgmtPDU5OutletsTableInstantaneousPowerOutlet35 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 35 }


edPowerMgmtPDU5OutletsTableInstantaneousPowerOutlet36 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 36 }


edPowerMgmtPDU5OutletsTableInstantaneousPowerOutlet37 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 37 }


edPowerMgmtPDU5OutletsTableInstantaneousPowerOutlet38 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 38 }


edPowerMgmtPDU5OutletsTableInstantaneousPowerOutlet39 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 39 }


edPowerMgmtPDU5OutletsTableInstantaneousPowerOutlet40 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 40 }


edPowerMgmtPDU5OutletsTableInstantaneousPowerOutlet41 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 41 }


edPowerMgmtPDU5OutletsTableInstantaneousPowerOutlet42 OBJECT-TYPE
        SYNTAX             Integer32
         ACCESS         read-only
        STATUS             mandatory
        DESCRIPTION
       	"Actual value of InstantaneousPower(KWatt) for the outlet.The recieved value 
		if 230 then actual value in decimal willbe 2.30 KWatt , if recieved 12
		then 0.12 KWatt. Returns 0 if not supported."
::= { edPowerMgmtPDU5OutletsTableInstantaneousPowerValue 42 }







edPowerMgmtPDU5OutletsTablePowerFactorOutlet1 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 1 }


edPowerMgmtPDU5OutletsTablePowerFactorOutlet2 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 2 }

edPowerMgmtPDU5OutletsTablePowerFactorOutlet3 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 3 }


edPowerMgmtPDU5OutletsTablePowerFactorOutlet4 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 4 }


edPowerMgmtPDU5OutletsTablePowerFactorOutlet5 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 5 }


edPowerMgmtPDU5OutletsTablePowerFactorOutlet6 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 6 }


edPowerMgmtPDU5OutletsTablePowerFactorOutlet7 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 7 }


edPowerMgmtPDU5OutletsTablePowerFactorOutlet8 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 8 }


edPowerMgmtPDU5OutletsTablePowerFactorOutlet9 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 9 }


edPowerMgmtPDU5OutletsTablePowerFactorOutlet10 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 10 }


edPowerMgmtPDU5OutletsTablePowerFactorOutlet11 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 11 }


edPowerMgmtPDU5OutletsTablePowerFactorOutlet12 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 12 }


edPowerMgmtPDU5OutletsTablePowerFactorOutlet13 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 13 }


edPowerMgmtPDU5OutletsTablePowerFactorOutlet14 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 14 }


edPowerMgmtPDU5OutletsTablePowerFactorOutlet15 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 15 }


edPowerMgmtPDU5OutletsTablePowerFactorOutlet16 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 16 }


edPowerMgmtPDU5OutletsTablePowerFactorOutlet17 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 17 }


edPowerMgmtPDU5OutletsTablePowerFactorOutlet18 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 18 }


edPowerMgmtPDU5OutletsTablePowerFactorOutlet19 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 19 }


edPowerMgmtPDU5OutletsTablePowerFactorOutlet20 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 20 }


edPowerMgmtPDU5OutletsTablePowerFactorOutlet21 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 21 }


edPowerMgmtPDU5OutletsTablePowerFactorOutlet22 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 22 }


edPowerMgmtPDU5OutletsTablePowerFactorOutlet23 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 23 }


edPowerMgmtPDU5OutletsTablePowerFactorOutlet24 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 24 }

edPowerMgmtPDU5OutletsTablePowerFactorOutlet25 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 25 }


edPowerMgmtPDU5OutletsTablePowerFactorOutlet26 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 26 }


edPowerMgmtPDU5OutletsTablePowerFactorOutlet27 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 27 }

edPowerMgmtPDU5OutletsTablePowerFactorOutlet28 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 28 }

edPowerMgmtPDU5OutletsTablePowerFactorOutlet29 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 29 }

edPowerMgmtPDU5OutletsTablePowerFactorOutlet30 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 30 }

edPowerMgmtPDU5OutletsTablePowerFactorOutlet31 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 31 }

edPowerMgmtPDU5OutletsTablePowerFactorOutlet32 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 32 }

edPowerMgmtPDU5OutletsTablePowerFactorOutlet33 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 33 }

edPowerMgmtPDU5OutletsTablePowerFactorOutlet34 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 34 }


edPowerMgmtPDU5OutletsTablePowerFactorOutlet35 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 35 }


edPowerMgmtPDU5OutletsTablePowerFactorOutlet36 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 36 }


edPowerMgmtPDU5OutletsTablePowerFactorOutlet37 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 37 }


edPowerMgmtPDU5OutletsTablePowerFactorOutlet38 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 38 }


edPowerMgmtPDU5OutletsTablePowerFactorOutlet39 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 39 }


edPowerMgmtPDU5OutletsTablePowerFactorOutlet40 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 40 }


edPowerMgmtPDU5OutletsTablePowerFactorOutlet41 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 41 }


edPowerMgmtPDU5OutletsTablePowerFactorOutlet42 OBJECT-TYPE
        SYNTAX             Integer32
         ACCESS         read-only
        STATUS             mandatory
        DESCRIPTION
        "Actual value of PowerFactor(pF) for the outlet.The recieved value 
		if 9999 then actual value in decimal willbe 99.99 pf , if recieved 12 
		then 0.12 pf. Returns 0 if not supported."
::= { edPowerMgmtPDU5OutletsTablePowerFactorValue 42 }







edPowerMgmtPDU5OutletsTableFreqOutlet1 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 1 }


edPowerMgmtPDU5OutletsTableFreqOutlet2 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 2 }

edPowerMgmtPDU5OutletsTableFreqOutlet3 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 3 }


edPowerMgmtPDU5OutletsTableFreqOutlet4 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 4 }


edPowerMgmtPDU5OutletsTableFreqOutlet5 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 5 }


edPowerMgmtPDU5OutletsTableFreqOutlet6 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 6 }


edPowerMgmtPDU5OutletsTableFreqOutlet7 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 7 }


edPowerMgmtPDU5OutletsTableFreqOutlet8 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 8 }


edPowerMgmtPDU5OutletsTableFreqOutlet9 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 9 }


edPowerMgmtPDU5OutletsTableFreqOutlet10 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 10 }


edPowerMgmtPDU5OutletsTableFreqOutlet11 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 11 }


edPowerMgmtPDU5OutletsTableFreqOutlet12 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 12 }


edPowerMgmtPDU5OutletsTableFreqOutlet13 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 13 }


edPowerMgmtPDU5OutletsTableFreqOutlet14 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 14 }


edPowerMgmtPDU5OutletsTableFreqOutlet15 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 15 }


edPowerMgmtPDU5OutletsTableFreqOutlet16 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 16 }


edPowerMgmtPDU5OutletsTableFreqOutlet17 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 17 }


edPowerMgmtPDU5OutletsTableFreqOutlet18 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 18 }


edPowerMgmtPDU5OutletsTableFreqOutlet19 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 19 }


edPowerMgmtPDU5OutletsTableFreqOutlet20 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 20 }


edPowerMgmtPDU5OutletsTableFreqOutlet21 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 21 }


edPowerMgmtPDU5OutletsTableFreqOutlet22 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 22 }


edPowerMgmtPDU5OutletsTableFreqOutlet23 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 23 }


edPowerMgmtPDU5OutletsTableFreqOutlet24 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 24 }

edPowerMgmtPDU5OutletsTableFreqOutlet25 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 25 }


edPowerMgmtPDU5OutletsTableFreqOutlet26 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 26 }


edPowerMgmtPDU5OutletsTableFreqOutlet27 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 27 }

edPowerMgmtPDU5OutletsTableFreqOutlet28 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 28 }

edPowerMgmtPDU5OutletsTableFreqOutlet29 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 29 }

edPowerMgmtPDU5OutletsTableFreqOutlet30 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 30 }

edPowerMgmtPDU5OutletsTableFreqOutlet31 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 31 }

edPowerMgmtPDU5OutletsTableFreqOutlet32 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 32 }

edPowerMgmtPDU5OutletsTableFreqOutlet33 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 33 }

edPowerMgmtPDU5OutletsTableFreqOutlet34 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 34 }


edPowerMgmtPDU5OutletsTableFreqOutlet35 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 35 }


edPowerMgmtPDU5OutletsTableFreqOutlet36 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 36 }


edPowerMgmtPDU5OutletsTableFreqOutlet37 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 37 }


edPowerMgmtPDU5OutletsTableFreqOutlet38 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 38 }


edPowerMgmtPDU5OutletsTableFreqOutlet39 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 39 }


edPowerMgmtPDU5OutletsTableFreqOutlet40 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 40 }


edPowerMgmtPDU5OutletsTableFreqOutlet41 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 41 }


edPowerMgmtPDU5OutletsTableFreqOutlet42 OBJECT-TYPE
        SYNTAX             Integer32
         ACCESS         read-only
        STATUS             mandatory
        DESCRIPTION
       	"Actual value of Frequency for the outlet.The recieved value 
		if 4955 then actual value in decimal willbe 49.55 Hz  , if recieved 12 
		then 0.12 Hz. Returns 0 if not supported."
::= { edPowerMgmtPDU5OutletsTableFreqValue 42 }






edPowerMgmtPDU5OutletsTableControlOutlet1 OBJECT-TYPE
        SYNTAX INTEGER {
			switchingDisabled     (2),    			
			outletOn              (1),
			outletOff             (0)  
			
		}    
        ACCESS         read-write
        STATUS             mandatory
        DESCRIPTION
         "Getting this variable will return the outlet state. If 
       the outlet is on, the outletOn (1) value will be returned.
       If the outlet is off, the outletOff (0) value will be
       returned. and if returned 2 then switching is prohibited"
::= { edPowerMgmtPDU5OutletsTableOutletControl 1 }


edPowerMgmtPDU5OutletsTableControlOutlet2 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 2 }

edPowerMgmtPDU5OutletsTableControlOutlet3 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 3 }


edPowerMgmtPDU5OutletsTableControlOutlet4 OBJECT-TYPE
            SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 4 }


edPowerMgmtPDU5OutletsTableControlOutlet5 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 5 }


edPowerMgmtPDU5OutletsTableControlOutlet6 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 6 }


edPowerMgmtPDU5OutletsTableControlOutlet7 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 7 }


edPowerMgmtPDU5OutletsTableControlOutlet8 OBJECT-TYPE
            SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 8 }


edPowerMgmtPDU5OutletsTableControlOutlet9 OBJECT-TYPE
              SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 9 }


edPowerMgmtPDU5OutletsTableControlOutlet10 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 10 }


edPowerMgmtPDU5OutletsTableControlOutlet11 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 11 }


edPowerMgmtPDU5OutletsTableControlOutlet12 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 12 }


edPowerMgmtPDU5OutletsTableControlOutlet13 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 13 }


edPowerMgmtPDU5OutletsTableControlOutlet14 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 14 }


edPowerMgmtPDU5OutletsTableControlOutlet15 OBJECT-TYPE
           SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 15 }


edPowerMgmtPDU5OutletsTableControlOutlet16 OBJECT-TYPE
                SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 16 }


edPowerMgmtPDU5OutletsTableControlOutlet17 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 17 }


edPowerMgmtPDU5OutletsTableControlOutlet18 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 18 }


edPowerMgmtPDU5OutletsTableControlOutlet19 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 19 }


edPowerMgmtPDU5OutletsTableControlOutlet20 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 20 }


edPowerMgmtPDU5OutletsTableControlOutlet21 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 21 }


edPowerMgmtPDU5OutletsTableControlOutlet22 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 22 }


edPowerMgmtPDU5OutletsTableControlOutlet23 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 23 }


edPowerMgmtPDU5OutletsTableControlOutlet24 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 24 }

edPowerMgmtPDU5OutletsTableControlOutlet25 OBJECT-TYPE
           SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 25 }


edPowerMgmtPDU5OutletsTableControlOutlet26 OBJECT-TYPE
            SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 26 }


edPowerMgmtPDU5OutletsTableControlOutlet27 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 27 }

edPowerMgmtPDU5OutletsTableControlOutlet28 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 28 }

edPowerMgmtPDU5OutletsTableControlOutlet29 OBJECT-TYPE
                SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 29 }

edPowerMgmtPDU5OutletsTableControlOutlet30 OBJECT-TYPE
          SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 30 }

edPowerMgmtPDU5OutletsTableControlOutlet31 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 31 }

edPowerMgmtPDU5OutletsTableControlOutlet32 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 32 }

edPowerMgmtPDU5OutletsTableControlOutlet33 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 33 }

edPowerMgmtPDU5OutletsTableControlOutlet34 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 34 }


edPowerMgmtPDU5OutletsTableControlOutlet35 OBJECT-TYPE
                SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 35 }


edPowerMgmtPDU5OutletsTableControlOutlet36 OBJECT-TYPE
                 SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 36 }


edPowerMgmtPDU5OutletsTableControlOutlet37 OBJECT-TYPE
             SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 37 }


edPowerMgmtPDU5OutletsTableControlOutlet38 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 38 }


edPowerMgmtPDU5OutletsTableControlOutlet39 OBJECT-TYPE
               SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 39 }


edPowerMgmtPDU5OutletsTableControlOutlet40 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 40 }


edPowerMgmtPDU5OutletsTableControlOutlet41 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 41 }


edPowerMgmtPDU5OutletsTableControlOutlet42 OBJECT-TYPE
         SYNTAX INTEGER {
			switchingDisabled     (2),    			
			outletOn              (1),
			outletOff             (0)  
			
		}    
         ACCESS         read-write
        STATUS             mandatory
        DESCRIPTION
         "Getting this variable will return the outlet state. If 
       the outlet is on, the outletOn (1) value will be returned.
       If the outlet is off, the outletOff (0) value will be
       returned. and if returned 2 then switching is prohibited"

::= { edPowerMgmtPDU5OutletsTableOutletControl 42 }




edPowerMgmtPDU5TotalNumberOfPhases OBJECT-TYPE
        SYNTAX             Integer32
         ACCESS         		read-only
        STATUS             mandatory
        DESCRIPTION
        "Number of Phases managed by the appliance."
::= { edConectedPdu5Data 5 }

edPowerMgmtPDU5PhasesTable OBJECT IDENTIFIER::= { edConectedPdu5Data 6 }

edPowerMgmtPDU5PhasesData OBJECT IDENTIFIER::= { edPowerMgmtPDU5PhasesTable 1 }
edPowerMgmtPDU5PhasesTableIndexNumber OBJECT IDENTIFIER::= { edPowerMgmtPDU5PhasesData 1 }
edPowerMgmtPDU5PhasesTableVoltageValue OBJECT IDENTIFIER::= { edPowerMgmtPDU5PhasesData 2 }
edPowerMgmtPDU5PhasesTablecurrentValue OBJECT IDENTIFIER::= { edPowerMgmtPDU5PhasesData 3 }
edPowerMgmtPDU5PhasesTableApearentEnergyValue OBJECT IDENTIFIER::= { edPowerMgmtPDU5PhasesData 4 }
edPowerMgmtPDU5PhasesTableReactiveEnergyValue OBJECT IDENTIFIER::= { edPowerMgmtPDU5PhasesData 5 }
edPowerMgmtPDU5PhasesTableActiveEnergyValue OBJECT IDENTIFIER::= { edPowerMgmtPDU5PhasesData 6 }
edPowerMgmtPDU5PhasesTableInstantaneousPowerValue OBJECT IDENTIFIER::= { edPowerMgmtPDU5PhasesData 7 }
edPowerMgmtPDU5PhasesTablePowerFactorValue OBJECT IDENTIFIER::= { edPowerMgmtPDU5PhasesData 8 }

edPowerMgmtPDU5PhasesTableIndexNumber1 OBJECT-TYPE
        SYNTAX             Integer32
         ACCESS         read-only
        STATUS             mandatory
        DESCRIPTION
         "Index Number of the outlet in the PDU."
::= { edPowerMgmtPDU5PhasesTableIndexNumber 1 }

edPowerMgmtPDU5PhasesTableIndexNumber2 OBJECT-TYPE
        SYNTAX             Integer32
         ACCESS         read-only
        STATUS             mandatory
        DESCRIPTION
         "Index Number of the outlet in the PDU."
::= { edPowerMgmtPDU5PhasesTableIndexNumber 2 }


edPowerMgmtPDU5PhasesTableIndexNumber3 OBJECT-TYPE
        SYNTAX             Integer32
         ACCESS         read-only
        STATUS             mandatory
        DESCRIPTION
         "Index Number of the outlet in the PDU."
::= { edPowerMgmtPDU5PhasesTableIndexNumber 3 }


edPowerMgmtPDU5PhasesTableVoltageValuePhase1 OBJECT-TYPE
        SYNTAX             Integer32
         ACCESS         read-only
        STATUS             mandatory
        DESCRIPTION
        "Value of R Phase recieved from device.
		if recieved 23024 then actual value in decimal willbe 230.24 Volts ,
		if recieved 12 then 0.12 Volt. Returns 0 if not supported."
::= { edPowerMgmtPDU5PhasesTableVoltageValue 1 }

edPowerMgmtPDU5PhasesTableVoltageValuePhase2 OBJECT-TYPE
        SYNTAX             Integer32
         ACCESS         read-only
        STATUS             mandatory
        DESCRIPTION
        "Value of Y Phase recieved from device.
		if recieved 23024 then actual value in decimal willbe 230.24 Volts ,
		if recieved 12 then 0.12 Volt. Returns 0 if not supported."
::= { edPowerMgmtPDU5PhasesTableVoltageValue 2 }

edPowerMgmtPDU5PhasesTableVoltageValuePhase3 OBJECT-TYPE
        SYNTAX             Integer32
         ACCESS         read-only
        STATUS             mandatory
        DESCRIPTION
        "Value of B Phase recieved from device.
		if recieved 23024 then actual value in decimal willbe 230.24 Volts ,
		if recieved 12 then 0.12 Volt. Returns 0 if not supported."
::= { edPowerMgmtPDU5PhasesTableVoltageValue 3 }


edPowerMgmtPDU5PhasesTablecurrentPhase1 OBJECT-TYPE
        SYNTAX             Integer32
         ACCESS         read-only
        STATUS             mandatory
        DESCRIPTION
        "Current of R Phase in Ampere ,if recieved 1234 then actual value in decimal willbe 12.34 Amp, if recieved 
		value is 12 then 0.12 Amp .Returns 0 if not supported."
::= { edPowerMgmtPDU5PhasesTablecurrentValue 1 }


edPowerMgmtPDU5PhasesTablecurrentPhase2 OBJECT-TYPE
        SYNTAX             Integer32
         ACCESS         read-only
        STATUS             mandatory
        DESCRIPTION
        "Current of Y Phase in Ampere ,if recieved 1234 then actual value in decimal willbe 12.34 Amp, if recieved 
		value is 12 then 0.12 Amp .Returns 0 if not supported."
::= { edPowerMgmtPDU5PhasesTablecurrentValue 2 }



edPowerMgmtPDU5PhasesTablecurrentPhase3 OBJECT-TYPE
        SYNTAX             Integer32
         ACCESS         read-only
        STATUS             mandatory
        DESCRIPTION
        "Current of B Phase in Ampere ,if recieved 1234 then actual value in decimal willbe 12.34 Amp, if recieved 
		value is 12 then 0.12 Amp .Returns 0 if not supported."
::= { edPowerMgmtPDU5PhasesTablecurrentValue 3 }



edPowerMgmtPDU5PhasesTableApearentEnergyPhase1 OBJECT-TYPE
        SYNTAX             Integer32
         ACCESS         read-only
        STATUS             mandatory
        DESCRIPTION
        "ApearentEnergy(KVaHr) of R Phase if recieved 23024 then actual value in decimal willbe 2.3024 KVaHr , if recieved 12
	   then 0.0012 KVaHr. Returns 0 if not supported."
::= { edPowerMgmtPDU5PhasesTableApearentEnergyValue 1 }


edPowerMgmtPDU5PhasesTableApearentEnergyPhase2 OBJECT-TYPE
        SYNTAX             Integer32
         ACCESS         read-only
        STATUS             mandatory
        DESCRIPTION
        "ApearentEnergy(KVaHr) of Y Phase if recieved 23024 then actual value in decimal willbe 2.3024 KVaHr , if recieved 12
	   then 0.0012 KVaHr. Returns 0 if not supported."
::= { edPowerMgmtPDU5PhasesTableApearentEnergyValue 2 }

edPowerMgmtPDU5PhasesTableApearentEnergyPhase3 OBJECT-TYPE
        SYNTAX             Integer32
         ACCESS         read-only
        STATUS             mandatory
        DESCRIPTION
        "ApearentEnergy(KVaHr) of B Phase if recieved 23024 then actual value in decimal willbe 2.3024 KVaHr , if recieved 12
	   then 0.0012 KVaHr. Returns 0 if not supported."
::= { edPowerMgmtPDU5PhasesTableApearentEnergyValue 3 }


edPowerMgmtPDU5PhasesTableReactiveEnergyPhase1 OBJECT-TYPE
        SYNTAX             Integer32
         ACCESS         read-only
        STATUS             mandatory
        DESCRIPTION
        "ReactiveEnergy(KVarHr) of R Phase if recieved 23024 then actual value in decimal willbe 2.3024 KVaHr , if recieved 12
	   then 0.0012 KVaHr. Returns 0 if not supported."
::= { edPowerMgmtPDU5PhasesTableReactiveEnergyValue 1 }



edPowerMgmtPDU5PhasesTableReactiveEnergyPhase2 OBJECT-TYPE
        SYNTAX             Integer32
         ACCESS         read-only
        STATUS             mandatory
        DESCRIPTION
        "ReactiveEnergy(KVarHr) of Y Phase if recieved 23024 then actual value in decimal willbe 2.3024 KVaHr , if recieved 12
	   then 0.0012 KVaHr. Returns 0 if not supported."
::= { edPowerMgmtPDU5PhasesTableReactiveEnergyValue 2 }



edPowerMgmtPDU5PhasesTableReactiveEnergyPhase3 OBJECT-TYPE
        SYNTAX             Integer32
         ACCESS         read-only
        STATUS             mandatory
        DESCRIPTION
        "ReactiveEnergy(KVarHr) of B Phase if recieved 23024 then actual value in decimal willbe 2.3024 KVaHr , if recieved 12
	   then 0.0012 KVaHr. Returns 0 if not supported."
::= { edPowerMgmtPDU5PhasesTableReactiveEnergyValue 3 }

edPowerMgmtPDU5PhasesTableActiveEnergyPhase1 OBJECT-TYPE
        SYNTAX             Integer32
         ACCESS         read-only
        STATUS             mandatory
        DESCRIPTION
        "ActiveEnergy(KWattHr) of R Phase if recieved 23024 then actual value in decimal willbe 2.3024 KVaHr , if recieved 12
	   then 0.0012 KVaHr. Returns 0 if not supported."
::= { edPowerMgmtPDU5PhasesTableActiveEnergyValue 1 }

edPowerMgmtPDU5PhasesTableActiveEnergyPhase2 OBJECT-TYPE
        SYNTAX             Integer32
         ACCESS         read-only
        STATUS             mandatory
        DESCRIPTION
        "ActiveEnergy(KWattHr) of Y Phase if recieved 23024 then actual value in decimal willbe 2.3024 KVaHr , if recieved 12
	   then 0.0012 KVaHr. Returns 0 if not supported."
::= { edPowerMgmtPDU5PhasesTableActiveEnergyValue 2 }

edPowerMgmtPDU5PhasesTableActiveEnergyPhase3 OBJECT-TYPE
        SYNTAX             Integer32
         ACCESS         read-only
        STATUS             mandatory
        DESCRIPTION
        "ActiveEnergy(KWattHr) of B Phase if recieved 23024 then actual value in decimal willbe 2.3024 KVaHr , if recieved 12
	   then 0.0012 KVaHr. Returns 0 if not supported."
::= { edPowerMgmtPDU5PhasesTableActiveEnergyValue 3 }


edPowerMgmtPDU5PhasesTableInstantaneousPowerPhase1 OBJECT-TYPE
        SYNTAX             Integer32
         ACCESS         read-only
        STATUS             mandatory
        DESCRIPTION
        "Instantaneous Power(KWatt) of R Phase if recieved 23024 then actual value in decimal willbe 2.3024 KVaHr , if recieved 12
	   then 0.0012 KVaHr. Returns 0 if not supported."
::= { edPowerMgmtPDU5PhasesTableInstantaneousPowerValue 1 }


edPowerMgmtPDU5PhasesTableInstantaneousPowerPhase2 OBJECT-TYPE
        SYNTAX             Integer32
         ACCESS         read-only
        STATUS             mandatory
        DESCRIPTION
        "Instantaneous Power(KWatt) of Y Phase if recieved 23024 then actual value in decimal willbe 2.3024 KVaHr , if recieved 12
	   then 0.0012 KVaHr. Returns 0 if not supported."
::= { edPowerMgmtPDU5PhasesTableInstantaneousPowerValue 2 }


edPowerMgmtPDU5PhasesTableInstantaneousPowerPhase3 OBJECT-TYPE
        SYNTAX             Integer32
         ACCESS         read-only
        STATUS             mandatory
        DESCRIPTION
        "Instantaneous Power(KWatt) of B Phase if recieved 23024 then actual value in decimal willbe 2.3024 KVaHr , if recieved 12
	   then 0.0012 KVaHr. Returns 0 if not supported."
::= { edPowerMgmtPDU5PhasesTableInstantaneousPowerValue 3 }


edPowerMgmtPDU5PhasesTablePowerFactorPhase1 OBJECT-TYPE
        SYNTAX             Integer32
         ACCESS         read-only
        STATUS             mandatory
        DESCRIPTION
        "average of powerfactor(pF) R Phase.The recieved value 
		if 9999 then actual value in decimal willbe 99.99 pf , if recieved 12
		then 0.12 pf. Returns 0 if not supported."
::= { edPowerMgmtPDU5PhasesTablePowerFactorValue 1 }

edPowerMgmtPDU5PhasesTablePowerFactorPhase2 OBJECT-TYPE
        SYNTAX             Integer32
         ACCESS         read-only
        STATUS             mandatory
        DESCRIPTION
        "average of powerfactor(pF) Y Phase.The recieved value 
		if 9999 then actual value in decimal willbe 99.99 pf , if recieved 12
		then 0.12 pf. Returns 0 if not supported."
::= { edPowerMgmtPDU5PhasesTablePowerFactorValue 2 }

edPowerMgmtPDU5PhasesTablePowerFactorPhase3 OBJECT-TYPE
        SYNTAX             Integer32
         ACCESS         read-only
        STATUS             mandatory
        DESCRIPTION
        "average of powerfactor(pF) B Phase.The recieved value 
		if 9999 then actual value in decimal willbe 99.99 pf , if recieved 12
		then 0.12 pf. Returns 0 if not supported."
::= { edPowerMgmtPDU5PhasesTablePowerFactorValue 3 }


edPowerMgmtPDU5TotalNumberOfSensor OBJECT-TYPE
        SYNTAX             Integer32
         ACCESS         read-only
        STATUS             mandatory
        DESCRIPTION
        "Number of Sensors managed by the appliance."
::= { edConectedPdu5Data 7 }


edPowerMgmtPDU5SensorsTable OBJECT IDENTIFIER ::= { edConectedPdu5Data 8 }

edPowerMgmtPDU5SensorsData OBJECT IDENTIFIER ::= { edPowerMgmtPDU5SensorsTable 1 }

edPowerMgmtPDU5SensorsTableNumber OBJECT IDENTIFIER ::= { edPowerMgmtPDU5SensorsData 1 }
edPowerMgmtPDU5SensorsTableSensorType OBJECT IDENTIFIER ::= { edPowerMgmtPDU5SensorsData 2 }
edPowerMgmtPDU5SensorsTableSensorValue OBJECT IDENTIFIER::= { edPowerMgmtPDU5SensorsData 3 }

edPowerMgmtPDU5SensorsTableSensor1 OBJECT-TYPE
        SYNTAX             Integer32
         ACCESS         read-only
        STATUS             mandatory
        DESCRIPTION
        "Number of the sensor in the PDU."
::= { edPowerMgmtPDU5SensorsTableNumber 1 }


edPowerMgmtPDU5SensorsTableSensor2 OBJECT-TYPE
        SYNTAX             Integer32
         ACCESS         read-only
        STATUS             mandatory
        DESCRIPTION
        "Number of the sensor in the PDU."
::= { edPowerMgmtPDU5SensorsTableNumber 2 }


edPowerMgmtPDU5SensorsTableSensor3 OBJECT-TYPE
        SYNTAX             Integer32
         ACCESS         read-only
        STATUS             mandatory
        DESCRIPTION
        "Number of the sensor in the PDU."
::= { edPowerMgmtPDU5SensorsTableNumber 3 }

edPowerMgmtPDU5SensorsTableSensor4 OBJECT-TYPE
        SYNTAX             Integer32
         ACCESS         read-only
        STATUS             mandatory
        DESCRIPTION
        "Number of the sensor in the PDU."
::= { edPowerMgmtPDU5SensorsTableNumber 4 }

edPowerMgmtPDU5SensorsTableSensorType1 OBJECT-TYPE
         SYNTAX INTEGER {
		humidity     (2),    			
		temprature   (1),
		nosens      (0)  
		
		}
         ACCESS         read-only
        STATUS             mandatory
        DESCRIPTION
        "returns value displaying type of Sensor."
::= { edPowerMgmtPDU5SensorsTableSensorType 1 }

edPowerMgmtPDU5SensorsTableSensorType2 OBJECT-TYPE
         SYNTAX INTEGER {
		humidity     (2),    			
		temprature   (1),
		nosens      (0)  
		
		}
         ACCESS         read-only
        STATUS             mandatory
        DESCRIPTION
        "returns value displaying type of Sensor."
::= { edPowerMgmtPDU5SensorsTableSensorType 2 }

edPowerMgmtPDU5SensorsTableSensorType3 OBJECT-TYPE
         SYNTAX INTEGER {
		humidity     (2),    			
		temprature   (1),
		nosens      (0)  
		
		}
         ACCESS         read-only
        STATUS             mandatory
        DESCRIPTION
        "returns value displaying type of Sensor."
::= { edPowerMgmtPDU5SensorsTableSensorType 3 }


edPowerMgmtPDU5SensorsTableSensorType4 OBJECT-TYPE
         SYNTAX INTEGER {
		humidity     (2),    			
		temprature   (1),
		nosens      (0)  
		}
         ACCESS         read-only
        STATUS             mandatory
        DESCRIPTION
        "returns value displaying type of Sensor."
::= { edPowerMgmtPDU5SensorsTableSensorType 4 }



edPowerMgmtPDU5SensorsTableSensorValueSensor1 OBJECT-TYPE
        SYNTAX             Integer32
         ACCESS         read-only
        STATUS             mandatory
        DESCRIPTION
        "returns value of Sensor
         Returns 0 if not supported."
::= { edPowerMgmtPDU5SensorsTableSensorValue 1 }

edPowerMgmtPDU5SensorsTableSensorValueSensor2 OBJECT-TYPE
        SYNTAX             Integer32
         ACCESS         read-only
        STATUS             mandatory
        DESCRIPTION
        "returns value of Sensor
         Returns 0 if not supported."
::= { edPowerMgmtPDU5SensorsTableSensorValue 2 }

edPowerMgmtPDU5SensorsTableSensorValueSensor3 OBJECT-TYPE
        SYNTAX             Integer32
         ACCESS         read-only
        STATUS             mandatory
        DESCRIPTION
        "returns value of Sensor
         Returns 0 if not supported."
::= { edPowerMgmtPDU5SensorsTableSensorValue 3 }

edPowerMgmtPDU5SensorsTableSensorValueSensor4 OBJECT-TYPE
        SYNTAX             Integer32
         ACCESS         read-only
        STATUS             mandatory
        DESCRIPTION
        "returns value of Sensor
         Returns 0 if not supported."
::= { edPowerMgmtPDU5SensorsTableSensorValue 4 }




----------- Daisy Chaining pduData  5 Ends ----------------------



--
END


-- Traps
-- Annotations are provided for Novell's NMS product
--
-- Each trap has at least one variable (mtrapargsString) which always appears
-- as the last variable in the list. This variable contains either a static
-- or dynamically-constructed string which provides an enhanced description of
-- the trap's purpose and any pertinent information about the trap.
-- ElcomNet-MIB { iso org(3) dod(6) internet(1) private(4)
--    enterprises(1) elcom(40367) }

ElcomNet-MIB DEFINITIONS ::= BEGIN
IMPORTS
TRAP-TYPE                                           FROM RFC-1215 ;                                          FROM RFC-1215 ;

lowLoadR TRAP-TYPE
   ENTERPRISE elcom
   VARIABLES {edPowerMgmtOutletsTableCurrentValue}
   DESCRIPTION
      "WARNING: A Rack PDU has violated the low load threshold."
       --#SEVERITY SEVERE
   ::= 1


nearOverloadR TRAP-TYPE
   ENTERPRISE elcom
   VARIABLES {edPowerMgmtOutletsTableCurrentValue  }
   DESCRIPTION
      "WARNING: A Rack PDU is near an overload condition."
   ::= 2

overloadR TRAP-TYPE
   ENTERPRISE elcom
   VARIABLES { edPowerMgmtOutletsTableCurrentValue  }
   DESCRIPTION
      "SEVERE: A Rack PDU is in an overload condition."
   ::= 3

lowLoadY TRAP-TYPE
   ENTERPRISE elcom
   VARIABLES {edPowerMgmtOutletsTableCurrentValue }
   DESCRIPTION
      "WARNING: A Rack PDU has violated the low load threshold."
   ::= 4


nearOverloadY TRAP-TYPE
   ENTERPRISE elcom
   VARIABLES {edPowerMgmtOutletsTableCurrentValue  }
   DESCRIPTION
      "WARNING: A Rack PDU is near an overload condition."
   ::= 5

overloadY TRAP-TYPE
   ENTERPRISE elcom
   VARIABLES { edPowerMgmtOutletsTableCurrentValue  }
   DESCRIPTION
      "SEVERE: A Rack PDU is in an overload condition."
   ::= 6

lowLoadB TRAP-TYPE
   ENTERPRISE elcom
   VARIABLES {edPowerMgmtOutletsTableCurrentValue  }
   DESCRIPTION
      "WARNING: A Rack PDU has violated the low load threshold."
   ::= 7


nearOverloadB TRAP-TYPE
   ENTERPRISE elcom
   VARIABLES {edPowerMgmtOutletsTableCurrentValue  }
   DESCRIPTION
      "WARNING: A Rack PDU is near an overload condition."
 
   ::= 8

overloadB TRAP-TYPE
   ENTERPRISE elcom
   VARIABLES { edPowerMgmtOutletsTableCurrentValue  }
   DESCRIPTION
      "SEVERE: A Rack PDU is in an overload condition."

   ::= 9
   
lowLoad TRAP-TYPE
   ENTERPRISE elcom
   VARIABLES {edPowerMgmtAggrInfoTableCurrentValue }
   DESCRIPTION
      "WARNING: A Rack PDU has violated the low load threshold."
   ::= 10
   
nearOverload TRAP-TYPE
   ENTERPRISE elcom
   VARIABLES {edPowerMgmtAggrInfoTableCurrentValue  }
   DESCRIPTION
      "WARNING: A Rack PDU is near an overload condition."
   ::= 11

overload TRAP-TYPE
   ENTERPRISE elcom
   VARIABLES { edPowerMgmtAggrInfoTableCurrentValue  }
   DESCRIPTION
      "SEVERE: A Rack PDU is in an overload condition."
   ::= 12





humLowCutoff TRAP-TYPE
   ENTERPRISE elcom
   VARIABLES { edPowerMgmtSensorsTableSensorValue}
   DESCRIPTION
      "SEVERE: The Humidity of the PDU is below  the lower thershold value ."
   ::= 13

humHighCutoff TRAP-TYPE
   ENTERPRISE elcom
   VARIABLES { edPowerMgmtSensorsTableSensorValue}
   DESCRIPTION
      "SEVERE: The Humidity of the PDU has exceeded the higher thershold value ."
   ::= 14
   
tempLowCutoff TRAP-TYPE
   ENTERPRISE elcom
   VARIABLES { edPowerMgmtSensorsTableSensorValue }
   DESCRIPTION
      "SEVERE: The temperature of the PDU has gone below the lower thershold value ."
   ::= 15

tempHighCutoff TRAP-TYPE
   ENTERPRISE elcom
   VARIABLES { edPowerMgmtSensorsTableSensorValue }
   DESCRIPTION
      "SEVERE: The temperature of the PDU has exceeded the higher thershold value ."
   ::= 16


   
   
WaterSensorMoistureDetect TRAP-TYPE
   ENTERPRISE elcom
   VARIABLES { edPowerMgmtSensorsTableSensorType}
   DESCRIPTION
      "SEVERE: The water sensor has detected Moisture along the length of Sensing cable ."
  
   ::= 17


WaterSensorLeakDetect TRAP-TYPE
   ENTERPRISE elcom
   VARIABLES { edPowerMgmtSensorsTableSensorType}
   DESCRIPTION
      "SEVERE: The Water sensor has detected a leackage along the length of Sensing cable ."
 
   ::= 18





-- MasterSwitch Vm Traps


-- MasterSwitch plus (MSP) Traps















-- Switched and Metered Rack PDU Traps


-- xPDU Traps (part 1)







   



-- xPDU Traps (part 2)








END
