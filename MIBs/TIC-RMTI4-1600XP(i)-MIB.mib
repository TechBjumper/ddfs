-- Toshiba MIB
-- UPS MIB for Toshiba 1600XP-i Uninterruptible Power Systems with RemotEye 4
--
--{iso(1) org(3) dod(6) internet(1) private(4) enterprises(1) toshiba(186) 
-- equ(1) equups(19) ticups(2) rmti4 (5) ups1600XP-i(2)}
--=============================================================================

TIC-RMTI4-1600XP-i-MIB DEFINITIONS ::= BEGIN

--=============================================================================
-- Update : October 4, 2016
-- By     : Edwin Rubio, Toshiba International Corp.
-- Revised: Changed TIC-RMTI4-1600XP(i)-MIB DEFINITIONS to TIC-RMTI4-1600XP-i-MIB DEFINITIONS
--		  : Removed the 'a' character from the second line title
--=============================================================================
-- Update : July 29, 2015
-- By     : Ming Lu, Toshiba International Corp.
-- Revised: upsOutputVoltageAdjust changed description and SYNTAX 
--=============================================================================
-- Update : May 28, 2015
-- By     : Edwin Rubio, Toshiba International Corp.
-- Revised: Change object name from upsTrapDCBusUnderVoltAtTest to upsTrapDCBusUnderVoltAtBattTest.
--		  : Added in description warning for upsTrapOnBypass, upsTrapOnBypassClear and upsAlarmOnBypass.
--=============================================================================
-- Update : March 19, 2015
-- By     : Edwin Rubio, Toshiba International Corp.
-- Revised: Added upsStsCtlCfgUserDefinedOverloadSetPoint.
--		  : Added upsAlarmUserDefinedOverloadWarning
--		  : Added upsTrapUserDefinedOverloadWarning
--		  : Added upsTrapUserDefinedOverloadWarningClear
--=============================================================================
-- Update : February 3, 2015
-- By     : Edwin Rubio, Toshiba International Corp.
-- Revised: Changed upsStsCtlCfgSecurityLevel access level to read-only.
--=============================================================================
-- Update : September 25, 2014
-- By     : Edwin Rubio, Toshiba International Corp.
-- Revised: Changed upsStsCtlCfgChangeSecurityLevel access level to read-only.
--=============================================================================
-- Update : July 16, 2014
-- By     : Edwin Rubio, Toshiba International.
-- For    : 1600XP MIB Draft 4.0 for RemotEye 4
-- Revised: Changed OID upsStsCtlCfgServicePortCommStatus SYNTAX INTEGER off(3) to idle(3)
--=============================================================================
-- Update : Apr 27, 2014
-- By     : Edwin Rubio, Toshiba International.
-- Revised: Changed OID upsBatteryNumStrings to upsBatteryInParallel
--        : Changed OID upsBatteryExtNumStrings to upsBatteryExtInParallel
--=============================================================================
-- Update : Apr 21, 2014
-- By     : Hung Huynh, Toshiba International.
-- Revised: upsHistorySysOperationTime: Changed units from DHM to Hours
--	  	  : upsHistoryInverterOperationTime: Changed units from DHM to Hours 
--	  	  : upsHistoryBackupOperationTime: Changed units from Minutes to Seconds
--=============================================================================
-- Update : Jan 02, 2014
-- By     : Edwin Rubio, Toshiba International.
-- Revised: upsIdent 1: Changed size from (0..16) to (0..31)
--	  	  : upsInput 3: Changed description. 
--	  	  : upsInput 8: Changed OID Name from "upsInputOverVoltage" to "upsInputOverVoltageDetectLevel"
--	  	  : upsInput 9: Changed OID Name from "upsInputOverVoltageRecoverylevel" to "upsInputOverVoltageRecoveryLevel"
--	  	  : upsInput 12: Changed OID Name from "upsInputUnderVoltageDetectlevel" to "upsInputUnderVoltageDetectLevel"
--	  	  : upsInput 13: Changed OID Name from "upsInputUnderVoltageRecoverylevel" to "upsInputUnderVltageRecoveryLevel"
--	  	  : upsInput 14: Changed description.
--	  	  : upsOutput 6: Changed OID Name from "upsOutputUndervoltagelevel" to "upsOutputUnderVoltageDetectLevel"
--	  	  : upsOutput 7: Changed OID Name from "upsOutputOverVoltagelevel" to "upsOutputOverVoltageDetectLevel"
--	  	  : upsBypass 5: Changed OID Name from "upsBypassUnderVoltageDetectionlevel" to "upsBypassUnderVoltageDetectLevel"
--	  	  : upsBypass 6: Changed OID Name from "upsBypassUnderVoltageRecoverylevel" to "upsBypassUnderVoltageRecoveryLevel"
--	  	  : upsBypass 7: Changed OID Name from "upsBypassOverVoltageDetectionlevel" to "upsBypassOverVoltageDetectLevel"
--	  	  : upsBypass 8: Changed OID Name from "upsBypassOverVoltageRecoverylevel" to "upsBypassOverVoltageRecoveryLevel"
--	  	  : upsBattery 7: Changed OID Name from "upsBatteryNumberofDischarge" to "upsBatteryNumberOfDischarge"
--	  	  : UpsBatteryExtEntry: Changed Object Name from "upsBatteryExtInParallel" to "upsBatteryExtNumStrings"
--	  	  : upsStsCtlCfg 31: Changed OID Name from "upsStsCtlCfgAutoRetransferDelay" to "upsStsCtlCfgAutoTransferDelay"
--	  	  : upsHistory 16: Changed OID Name from "upsHistoryTotalNumSystemSettingsChanged" to "upsHistoryTotalNumSystemSettingsChange"
--	  	  : upsAlarm 1: Changed description. 
--	  	  : upsWellKnownAlarms 5: Changed OID Name from "upsAlarmDCOverVoltage" to "upsAlarmDCBusOverVoltage"
--	  	  : upsWellKnownAlarms 9: Changed OID Name from "upsAlarmHeatSinkOverheat" to "upsAlarmUPSOverheat"
--	  	  : upsWellKnownAlarms 13: Changed OID Name from "upsAlarmDCUnderVoltAtBoostUp" to "upsAlarmDCBusUnderVoltAtBoostUp"
--	  	  : upsWellKnownAlarms 24: Changed OID Name from "upsAlarmDCUnderVoltAtBattTest" to "upsAlarmDCBusUnderVoltAtBattTest"
--	  	  : upsWellKnownAlarms 40: Changed OID Name from "upsAlarmRMTICommError" to "upsAlarmRemotEyeCommError"
--	  	  : upsWellKnownAlarms 41: Changed OID Name from "upsAlarmRMTIUplinkCommError" to "upsAlarmRemotEyeUplinkCommError"
--	  	  : upsWellKnownAlarms 45: CHanged OID Name from "upsAlarmBypassOn" to"upsOnBypass"
--	  	  : upsWellKnownAlarms 61: Changed OID Name from "upsAlarmExtBattCab1LossCommunication" to "upsAlarmExtBattCab1LostCommunication"
--	  	  : upsWellKnownAlarms 71: Changed OID Name from "upsAlarmExtBattCab2LossCommunication" to "upsAlarmExtBattCab2LostCommunication"
--	  	  : upsTrap 9: Changed OID Name from "upsTrapDCBusOverVoltage" to "upsTrapDCBusOverVoltage"
--	  	  : upsTrap 17 & 18: Changed OID Name from "upsTrapHeatSinkOverheat/upsTrapHeatSinkOverheatClear" to "upsTrapUPSOverheat/upsTrapUPSOverheatClear"
--	  	  : upsTrap 25 & 26: Changed OID Name from "upsTrapDCUnderVoltageAtBoostUp/upsTrapDCUnderVoltageAtBoostUpClear" to "upsTrapDCBusUnderVoltAtBoostUp/upsTrapDCBusUnderVoltAtBoostUpClear"
--	  	  : upsTrap 27 & 28: Changed OID Name from "upsTrapDCUnderVoltageAtCharge/upsTrapDCUnderVoltageAtChargeClear" to "upsTrapDCBusUnderVoltAtCharge/upsTrapDCBusUnderVoltAtChargeClear"
--	  	  : upsTrap 47 & 48: Changed OID Name from "upsTrapDCUnderVoltageAtTest/upsTrapDCUnderVoltageAtTestClear" to "upsTrapDCBusUnderVoltAtTest/upsTrapDCBusUnderVoltAtTestClear"
--	  	  : upsTrap 51 & 42: Changed OID Name from "upsTrapBatteryAtShutdownlevel/upsTrapBatteryAtShutdownlevelClear" to "upsTrapBatteryAtShutdownLevel/upsTrapBatteryAtShutdownLevelClear"
--	  	  : upsTrap 79 & 80: Changed OID Name from "upsTrapRMTICommError/upsTrapRMTICommErrorClear" to "upsTrapRemotEyeCommError/upsTrapRemotEyeCommErrorClear"
--	  	  : upsTrap 81 & 82: Changed OID Name from "upsTrapRMTIUplinkCommError/upsTrapRMTIUplinkCommErrorClear" to "upsTrapRemotEyeUplinkCommError/upsTrapRemotEyeUplinkCommErrorClear"
--	  	  : upsTrap 121 & 122: Changed OID Name from "upsTrapExtBattCab1LossCommunication/upsTrapExtBattCab1LossCommunicationClear" to "upsTrapExtBattCab1LostCommunication/upsTrapExtBattCab1LostCommunicationClear"
--	  	  : upsTrap 141 & 142: Changed OID Name from "upsTrapExtBattCab2LossCommunication/upsTrapExtBattCab2LossCommunicationClear" to "upsTrapExtBattCab2LostCommunication/upsTrapExtBattCab2LostCommunicationClear"
--=============================================================================
-- Update : Dec 26, 2013
-- By     : Tiffany Tye, Toshiba International.
-- Revised: (2.2) upsInputNumLines changed to upsInputNumOfPhases 
--        : (3.2) upsOutputNumLines changed to upsOutputNumOfPhases
--        : (4.2) upsBypassNumLines changed to upsBypassNumOfPhases
--        : (6.1) batteryFailure” changed to “batteryTestFailure” on upsBatteryStatus
--        : (6.2) upsSecondsOnBattery changed to upsElapsedTimeonBatteryPower
--        : (6.3) upsEstimatedMinutesRemaing changed to upsEstimatedBatteryRuntime
--        : (6.8) upsBatteryCalculatedShutdownVoltage changed to upsBatteryRatedShutdownVoltage
--        : (6.9) upsBatteryLifeRemaining changed to upsBatteryEstimatedLifeRemaining
--        : (6.12) upsBatteryInParallel changed to upsBatteryNumStrings
--        : (6.13) upsBatteryInstallationDate SYNTAX DisplayString (SIZE(0..8)) changed to SYNTAX DisplayString (SIZE(10))
--        : (6.15.2) upsBatteryExtInstallStatus change to upsBatteryExtInstallationStatus
--        : (6.15.4) upsBatteryExtInParallel changed to upsBatteryExtNumStrings
--        : (6.15.7) upsBatteryExtInstallDate SYNTAX DisplayString (SIZE(0..8)) changed to SYNTAX DisplayString (SIZE(10))
--        : (6.15.7) upsBatteryExtInstallDate change to upsBatteryExtInstallationDate 
--        : (6.16) upsBatteryLowBattLevel changed to upsBatteryRatedLowBattLevelPercent 
--        : (6.17) exchange OID of upsBatteryChargerOverVoltageDelay and upsBatteryCalcLBLevel 
--        : (6.17) upsBatteryCalcLBLevel change to upsBatteryRatedLowBattLevel 
--        : (8.1-8.4) Units Changed for upsHistorySysOperationTime, upsHIstoryInverterOperationTime, upsHistoryBackupOperationTime, and upsHistoryLifetimeRemaining
--        : (8.5 & 8.7) upsHistoryHighestSystemTempC and upHistoryHighestBatteryTempC were added to the MIB
--        : (9.7) sound(3) changed to alarm(3) in upsDisplayBuzzerStatus
--        : (9.9) upsDisplayRMTIInstallDate change to upsDisplayRMTIInstallationDate 
--        : (9.11) upsDisplayRMTIInstallStatus change to upsDisplayRMTIInstallationStatus
--        : (10.51) upsAlarmBatteryOn changed to upsAlarmOnBattery
--        : (12.89) upsTrapBypassOn changed to upsTrapOnBypass
--        : (12.90) upsTrapBypassOnClear changed to upsTrapOnBypassClear
--        : (12.101) upsTrapBatteryOn changed to upsTrapOnBattery
--        : (12.102) upsTrapBatteryOnClear changed to upsTrapOnBatteryClear
--=============================================================================
-- Update : Dec 22, 2013
-- By     : Tiffany Tye, Toshiba International.
-- Revised: upsInputPowerSupplyConfiguration Remove 120V 60Hz & 50Hz
--        : upsInputFreqWithErr add units 0.1Hertz
--        : upsBatteryLifeRemaining change units from hours to month
--        : upsBatteryExtEntry 10-13, 16-19 add units
--=============================================================================
-- Update : July 30, 2013
-- By     : Edwin Rubio, Toshiba International.
-- Revised: 1600XP First Draft MIB for RemotEye 4
--=============================================================================

IMPORTS
  DisplayString, TimeStamp, TimeInterval, TestAndIncr, AutonomousType
    FROM SNMPv2-TC
  enterprises
    FROM RFC1155-SMI
  OBJECT-TYPE
    FROM RFC-1212
  TRAP-TYPE
    FROM RFC-1215;

PositiveInteger    ::= INTEGER (0..2147483647)
NonNegativeInteger ::= INTEGER (0..2147483647)

toshiba      OBJECT IDENTIFIER ::= { enterprises 186 }
equ          OBJECT IDENTIFIER ::= { toshiba 1 }
equUPS       OBJECT IDENTIFIER ::= { equ 19 }
ticUPS       OBJECT IDENTIFIER ::= { equUPS 2 }
rmti4        OBJECT IDENTIFIER ::= { ticUPS 5 }
ups1600XP-i    OBJECT IDENTIFIER ::= { rmti4 2 }


upsIdent     OBJECT IDENTIFIER ::= { ups1600XP-i 1 }
upsInput     OBJECT IDENTIFIER ::= { ups1600XP-i 2 }
upsOutput    OBJECT IDENTIFIER ::= { ups1600XP-i 3 }
upsBypass    OBJECT IDENTIFIER ::= { ups1600XP-i 4 }
upsDCBus     OBJECT IDENTIFIER ::= { ups1600XP-i 5 }
upsBattery   OBJECT IDENTIFIER ::= { ups1600XP-i 6 }
upsStsCtlCfg OBJECT IDENTIFIER ::= { ups1600XP-i 7 }
upsHistory   OBJECT IDENTIFIER ::= { ups1600XP-i 8 }
upsDisplay   OBJECT IDENTIFIER ::= { ups1600XP-i 9 }
upsAlarm     OBJECT IDENTIFIER ::= { ups1600XP-i 10 }
upsPassword  OBJECT IDENTIFIER ::= { ups1600XP-i 11 }
upsTrap      OBJECT IDENTIFIER ::= { ups1600XP-i 12 }

-- ===========================================================================
-- upsIdent - ups1600XP-i Group 1
-- The UPS Identification Group
-- ===========================================================================

upsIdentManufacturer OBJECT-TYPE
    SYNTAX DisplayString (SIZE (0..31))
    ACCESS read-only
    STATUS mandatory
    DESCRIPTION
        "The name of the UPS manufacturer."
    ::= { upsIdent 1 }

upsIdentTypeform OBJECT-TYPE
    SYNTAX DisplayString (SIZE(0..16))
    ACCESS read-only
    STATUS mandatory
    DESCRIPTION
        "The UPS Typeform."
    ::= { upsIdent 2 }

upsIdentSerialNumber OBJECT-TYPE
    SYNTAX DisplayString (SIZE(0..16))
    ACCESS read-only
    STATUS mandatory
    DESCRIPTION
        "The UPS Serial Number."
    ::= { upsIdent 3 }

upsIdentMainFirmwareVersion OBJECT-TYPE
    SYNTAX DisplayString (SIZE(0..16))
    ACCESS read-only
    STATUS mandatory
    DESCRIPTION
        "The UPS firmware version of the main controller."
    ::= { upsIdent 4 }

upsIdentMainBootSectorVersion OBJECT-TYPE
    SYNTAX DisplayString (SIZE(0..16))
    ACCESS read-only
    STATUS mandatory
    DESCRIPTION
        "The UPS boot sector version of the main controller."
    ::= { upsIdent 5 }

upsIdentMainBootLoaderVersion OBJECT-TYPE
    SYNTAX DisplayString (SIZE(0..16))
    ACCESS read-only
    STATUS mandatory
    DESCRIPTION
        "The UPS Boot Loader version of the main controller."
    ::= { upsIdent 6 }

upsIdentJobNumber OBJECT-TYPE
    SYNTAX DisplayString (SIZE(0..16))
    ACCESS read-only
    STATUS mandatory
    DESCRIPTION
        "The UPS Job Number."
    ::= { upsIdent 7 }

upsIdentTestPerson OBJECT-TYPE
    SYNTAX DisplayString (SIZE(0..8))
    ACCESS read-only
    STATUS mandatory
    DESCRIPTION
        "The test person."
    ::= { upsIdent 8 }

upsIdentTestDate OBJECT-TYPE
    SYNTAX DisplayString (SIZE(0..8))
    ACCESS read-only
    STATUS mandatory
    DESCRIPTION
        "The test date displayed as YYYYMMDD format."
    ::= { upsIdent 9 }

upsIdentHardwareBuildDate OBJECT-TYPE
    SYNTAX DisplayString (SIZE(0..8))
    ACCESS read-only
    STATUS mandatory
    DESCRIPTION
        "The date that the UPS was built in YYYYMMDD format."
    ::= { upsIdent 10 }

upsIdentEEPROMVersion OBJECT-TYPE
    SYNTAX DisplayString (SIZE(0..16))
    ACCESS read-only
    STATUS mandatory
    DESCRIPTION
        "The UPS Main controller's EEPROM version."
    ::= { upsIdent 11 }

upsIdentSysName OBJECT-TYPE
    SYNTAX DisplayString (SIZE(0..16))
    ACCESS read-write
    STATUS mandatory
    DESCRIPTION
        "A string identifying the UPS. This object should be set by the administrator."
    ::= { upsIdent 12 }

upsIdentAttachedDevices OBJECT-TYPE
    SYNTAX DisplayString (SIZE(0..16))
    ACCESS read-write
    STATUS mandatory
    DESCRIPTION
        "A string identifying the devices attached to the output(s) of the UPS. This object should be set by the administrator."
    ::= { upsIdent 13 }

upsIdentInstallationDate OBJECT-TYPE
    SYNTAX DisplayString (SIZE(8))
    ACCESS read-write
    STATUS mandatory
    DESCRIPTION
        "The UPS installation date in YYYYMMDD format."
    ::= { upsIdent 14 }

-- ===========================================================================
-- upsInput - ups1600XP-i Group 2
-- The UPS Input Data Group 
-- ===========================================================================
upsInputPowerSupplyConfiguration OBJECT-TYPE
    SYNTAX INTEGER {
        undefined(1),
        volt200Hz60(2),
        volt200Hz50(3),
        volt208Hz60(4),
        volt208Hz50(5),
        volt230Hz60(6),
        volt230Hz50(7),
        volt240Hz60(8),
        volt240Hz50(9),
        volt220Hz60(10),
        volt220Hz50(11),
        reserved0(12),
        reserved2(13),
        reserved3(14),
        reserved4(15),
        reserved5(16)
    }
    ACCESS read-only
    STATUS mandatory
    DESCRIPTION
        "This parameter summarizes the measured and collected data describing the input power supply."
    ::= { upsInput 1 }

upsInputNumOfPhases OBJECT-TYPE
    SYNTAX INTEGER {
        one(1),
        two(2)
    }
    ACCESS read-only
    STATUS mandatory
    DESCRIPTION
        "The number of input lines utilized in this device. This variable indicates the number of rows in the input table."
    ::= { upsInput 2 }

upsInputTable OBJECT-TYPE
    SYNTAX SEQUENCE OF UpsInputEntry
    ACCESS not-accessible
    STATUS mandatory
    DESCRIPTION
        "A list of input table entries. The number of entries is given by the value of upsInputNumOfPhases."
    ::= { upsInput  3 }

upsInputEntry OBJECT-TYPE
    SYNTAX UpsInputEntry
    ACCESS not-accessible
    STATUS mandatory
    DESCRIPTION
        "An entry containing information applicable to a particular input line."
    INDEX { upsInputIndex }
    ::= { upsInputTable  1 }

UpsInputEntry ::=
    SEQUENCE {
        upsInputIndex      PositiveInteger,
        upsInputFrequency  INTEGER,
        upsInputVoltage    INTEGER,
        upsInputCurrent    INTEGER
    }

-- ===========================================================================
-- upsInputTable/upsInputEntry/upsInputIndex
-- ===========================================================================
upsInputIndex OBJECT-TYPE
    SYNTAX PositiveInteger 
    ACCESS not-accessible
    STATUS mandatory
    DESCRIPTION
        "The input line identifier"
    ::= { upsInputEntry 1 }

upsInputFrequency OBJECT-TYPE
    SYNTAX INTEGER
    UNITS  "0.1 Hertz"
    ACCESS read-only
    STATUS mandatory
    DESCRIPTION
        "The present input frequency to the UPS system in 1/10 of Hz."
    ::= { upsInputEntry 2 }

upsInputVoltage OBJECT-TYPE
    SYNTAX INTEGER
    UNITS  "RMS Volts"
    ACCESS read-only
    STATUS mandatory
    DESCRIPTION
        "The input utility line voltage in RMS volts."
    ::= { upsInputEntry 3 }

upsInputCurrent OBJECT-TYPE
    SYNTAX INTEGER
    UNITS  "0.1 RMS Amp"
    ACCESS read-only
    STATUS mandatory
    DESCRIPTION
        "The magnitude of the present input Current in 1/10 RMS Amp."
    ::= { upsInputEntry 4 }

upsInputActivePower OBJECT-TYPE
    SYNTAX INTEGER
    UNITS  "Watt"
    ACCESS read-only
    STATUS mandatory
    DESCRIPTION
        "The UPS active power in Watt. -1 if value is invalid."
    ::= { upsInput 4 }

upsInputApparentPower OBJECT-TYPE
    SYNTAX INTEGER
    UNITS  "Volt-Amp"
    ACCESS read-only
    STATUS mandatory
    DESCRIPTION
        "The input apparent power in Volt-Amp."
    ::= { upsInput 5 }

upsInputPowerFactor OBJECT-TYPE
    SYNTAX INTEGER
    UNITS  "0.01"
    ACCESS read-only
    STATUS mandatory
    DESCRIPTION
        "Ratio of actual power to apparent power. -1 if value is invalid."
    ::= { upsInput 6 }

upsInputRatedTable OBJECT-TYPE
    SYNTAX SEQUENCE OF UpsInputRatedEntry
    ACCESS not-accessible
    STATUS mandatory
    DESCRIPTION
        "A list of input table entries. The number of entries is given by the value of upsInputNumLine."
    ::= { upsInput  7 }

upsInputRatedEntry OBJECT-TYPE
    SYNTAX UpsInputRatedEntry
    ACCESS not-accessible
    STATUS mandatory
    DESCRIPTION
        "An entry containing information applicable to a particular input line."
    INDEX { upsInputSlotIndex }
    ::= { upsInputRatedTable  1 }

UpsInputRatedEntry ::=
    SEQUENCE {
        upsInputSlotIndex       PositiveInteger,
        upsInputRatedFrequency  INTEGER,
        upsInputRatedVoltage    INTEGER,
        upsInputRatedCurrent    INTEGER        
    }

-- ===========================================================================
-- upsInputTable/upsInputEntry/upsInputIndex
-- ===========================================================================
upsInputSlotIndex OBJECT-TYPE
    SYNTAX PositiveInteger 
    ACCESS not-accessible
    STATUS mandatory
    DESCRIPTION
        "The input line identifier"
    ::= { upsInputRatedEntry 1 }

upsInputRatedFrequency OBJECT-TYPE
    SYNTAX INTEGER
    UNITS  "0.1 Hertz"
    ACCESS read-only
    STATUS mandatory
    DESCRIPTION
        "The present rated input frequency of the UPS system in 1/10 of Hz."
    ::= { upsInputRatedEntry 2 }

upsInputRatedVoltage OBJECT-TYPE
    SYNTAX INTEGER
    UNITS  "RMS Volts"
    ACCESS read-write
    STATUS mandatory
    DESCRIPTION
        "The magnitude of the rated input voltage in RMS volts. This is set by the administrator."
    ::= { upsInputRatedEntry 3 }

upsInputRatedCurrent OBJECT-TYPE
    SYNTAX INTEGER
    UNITS  "0.1 RMS Amp"
    ACCESS read-only
    STATUS mandatory
    DESCRIPTION
        "The magnitude of the rated input current in 1/10 RMS Amp."
    ::= { upsInputRatedEntry 4 }

upsInputOverVoltageDetectLevel OBJECT-TYPE
    SYNTAX INTEGER
    UNITS  "RMS Volt"
    ACCESS read-only
    STATUS mandatory
    DESCRIPTION
        "This is the maximum limit of the input voltage before the UPS enters the over voltage state."
    ::= { upsInput 8 }

upsInputOverVoltageRecoveryLevel OBJECT-TYPE
    SYNTAX INTEGER
    UNITS  "RMS Volt"
    ACCESS read-only
    STATUS mandatory
    DESCRIPTION
        "The over voltage recovery level. It is the limit at which the UPS returns from over voltage state."
    ::= { upsInput 9 }

upsInputVoltagePercent OBJECT-TYPE
    SYNTAX INTEGER
    UNITS  "Percent"
    ACCESS read-only
    STATUS mandatory
    DESCRIPTION
        "The input voltage displayed as a percent."
    ::= { upsInput 10 }

upsInputCurrentPercent OBJECT-TYPE
    SYNTAX INTEGER
    UNITS  "Percent"
    ACCESS read-only
    STATUS mandatory
    DESCRIPTION
        "The input current displayed as a percent."
    ::= { upsInput 11 }

upsInputUnderVoltageDetectLevel OBJECT-TYPE
    SYNTAX INTEGER
    UNITS  "RMS Volt"
    ACCESS read-only
    STATUS mandatory
    DESCRIPTION
        "The input under voltage detection level in RMS volt."
    ::= { upsInput 12 }

upsInputUnderVoltageRecoveryLevel OBJECT-TYPE
    SYNTAX INTEGER
    UNITS  "RMS Volt"
    ACCESS read-only
    STATUS mandatory
    DESCRIPTION
        "The input under voltage recovery level in RMS volt."
    ::= { upsInput 13 }

upsInputRatedActivePower OBJECT-TYPE
    SYNTAX INTEGER
    UNITS  "Watts"
    ACCESS read-only
    STATUS mandatory
    DESCRIPTION
        "The rated input active power in Watt."
    ::= { upsInput 14 }

upsInputFreqWithErr OBJECT-TYPE
    SYNTAX INTEGER {
        hz50(1),
        hz60(2)
    }
    UNITS  "0.1 Hertz"
    ACCESS read-write
    STATUS mandatory
    DESCRIPTION
        "The input frequency configuration in 1/10 Hz when detection error occurred. This is set by the administrator."
    ::= { upsInput 15 }

-- ===========================================================================
-- upsOutput - ups1600XP-i Group 3
-- The UPS Output Data Group
-- ===========================================================================
upsOutputPowerSupplyConfiguration OBJECT-TYPE
    SYNTAX INTEGER {
        undefined(1),
        volt200Hz60(2),
        volt200Hz50(3),
        volt208Hz60(4),
        volt208Hz50(5),
        volt230Hz60(6),
        volt230Hz50(7),
        volt240Hz60(8),
        volt240Hz50(9),
        volt220Hz60(10),
        volt220Hz50(11),
        volt120Hz60(12),
        volt120Hz50(13),
        reserved0(14),
        reserved1(15),
        reserved2(16)
    }
    ACCESS read-only
    STATUS mandatory
    DESCRIPTION
        "This parameter summarizes the measured and collected data describing the output power supply."
    ::= { upsOutput 1 }

upsOutputNumOfPhases OBJECT-TYPE
    SYNTAX INTEGER {
        one(1),
        two(2)
    }
    ACCESS read-only
    STATUS mandatory
    DESCRIPTION
        "The number of output lines utilized in this device. This variable indicates the number of rows in the output table."
    ::= { upsOutput 2 }

upsOutputTable OBJECT-TYPE
    SYNTAX SEQUENCE OF UpsOutputEntry
    ACCESS not-accessible
    STATUS mandatory
    DESCRIPTION
        "A list of Output table entries. The number of entries is given by the value of upsOutputNumOfPhases."
    ::= { upsOutput  3 }

upsOutputEntry OBJECT-TYPE
    SYNTAX UpsOutputEntry
    ACCESS not-accessible
    STATUS mandatory
    DESCRIPTION
        "An entry containing information applicable to a particular Output line."
    INDEX { upsOutputIndex }
    ::= { upsOutputTable 1 }

UpsOutputEntry ::=
    SEQUENCE {
        upsOutputIndex         PositiveInteger,
        upsOutputFrequency     INTEGER,
        upsOutputVoltage       INTEGER,
        upsOutputCurrent       INTEGER,
        upsOutputActivePower   INTEGER,
        upsOutputApparentPower INTEGER
    }

-- ===========================================================================
-- upsOutputTable/upsOutputEntry/upsOutputIndex
-- ===========================================================================
upsOutputIndex OBJECT-TYPE
    SYNTAX PositiveInteger 
    ACCESS not-accessible
    STATUS mandatory
    DESCRIPTION
        "The Output line identifier."
    ::= { upsOutputEntry 1 }

upsOutputFrequency OBJECT-TYPE
    SYNTAX INTEGER
    UNITS  "0.1 Hertz"
    ACCESS read-only
    STATUS mandatory
    DESCRIPTION
        "The present output frequency of the UPS system in 1/10 of Hz."
    ::= { upsOutputEntry 2 }

upsOutputVoltage OBJECT-TYPE
    SYNTAX INTEGER
    UNITS  "RMS Volts"
    ACCESS read-only
    STATUS mandatory
    DESCRIPTION
        "The Output voltage in RMS volts."
    ::= { upsOutputEntry 3 }

upsOutputCurrent OBJECT-TYPE
    SYNTAX INTEGER
    UNITS  "0.1 RMS Amp"
    ACCESS read-only
    STATUS mandatory
    DESCRIPTION
        "The magnitude of the present output current in 1/10 RMS Amps."
    ::= { upsOutputEntry 4 }

upsOutputActivePower OBJECT-TYPE
    SYNTAX INTEGER
    UNITS  "Watts"
    ACCESS read-only
    STATUS mandatory
    DESCRIPTION
        "The present output active power in Watt."
    ::= { upsOutputEntry 5 }

upsOutputApparentPower OBJECT-TYPE
    SYNTAX INTEGER
    UNITS  "Volt-Amp"
    ACCESS read-only
    STATUS mandatory
    DESCRIPTION
        "The output apparent power in Volt-Amp."
    ::= { upsOutputEntry 6 }

upsOutputLoadPercentage OBJECT-TYPE
    SYNTAX INTEGER
    UNITS  "Percent"
    ACCESS read-only
    STATUS mandatory
    DESCRIPTION
        "The present UPS output load percentage which is current percent."
    ::= { upsOutput 4 }

upsOutputRatedTable OBJECT-TYPE
    SYNTAX SEQUENCE OF UpsOutputRatedEntry
    ACCESS not-accessible
    STATUS mandatory
    DESCRIPTION
        "A list of Output table entries. The number of entries is given by the value of upsOutputNumOfPhases."
    ::= { upsOutput  5 }

upsOutputRatedEntry OBJECT-TYPE
    SYNTAX UpsOutputRatedEntry
    ACCESS not-accessible
    STATUS mandatory
    DESCRIPTION
        "An entry containing information applicable to a particular Output line."
    INDEX {upsOutputIndex }
    ::= { upsOutputRatedTable 1 }

UpsOutputRatedEntry ::=
    SEQUENCE {
        upsOutputSlotIndex          PositiveInteger,
        upsOutputRatedFrequency     INTEGER,
        upsOutputRatedVoltage       INTEGER,
        upsOutputRatedCurrent       INTEGER,
        upsOutputRatedActivePower   INTEGER,
        upsOutputRatedApparentPower INTEGER
    }

-- ===========================================================================
-- upsOutputTable/upsOutputEntry/upsOutputIndex
-- ===========================================================================
upsOutputSlotIndex OBJECT-TYPE
    SYNTAX PositiveInteger 
    ACCESS not-accessible
    STATUS mandatory
    DESCRIPTION
        "The Output line identifier."
    ::= { upsOutputRatedEntry 1 }

upsOutputRatedFrequency OBJECT-TYPE
    SYNTAX INTEGER
    UNITS  "0.1 Hertz"
    ACCESS read-only
    STATUS mandatory
    DESCRIPTION
        "The present output rated frequency of the UPS system in 1/10 of Hz."
    ::= { upsOutputRatedEntry 2 }

upsOutputRatedVoltage OBJECT-TYPE
    SYNTAX INTEGER
    UNITS  "RMS Volts"
    ACCESS read-write
    STATUS mandatory
    DESCRIPTION
        "The rated output voltage in RMS volts. This is set by the administrator"
    ::= { upsOutputRatedEntry 3 }

upsOutputRatedCurrent OBJECT-TYPE
    SYNTAX INTEGER
    UNITS  "0.1 RMS Amp"
    ACCESS read-only
    STATUS mandatory
    DESCRIPTION
        "The output rated current in 1/10 RMS Amp."
    ::= { upsOutputRatedEntry 4 }

upsOutputRatedActivePower OBJECT-TYPE
    SYNTAX INTEGER
    UNITS  "Watts"
    ACCESS read-only
    STATUS mandatory
    DESCRIPTION
        "The output rated active power in Watt."
    ::= { upsOutputRatedEntry 5 }

upsOutputRatedApparentPower OBJECT-TYPE
    SYNTAX INTEGER
    UNITS  "Volt-Amp"
    ACCESS read-only
    STATUS mandatory
    DESCRIPTION
        "The output rated apparent power in Volt-Amp."
    ::= { upsOutputRatedEntry 6 }

upsOutputUnderVoltageDetectLevel OBJECT-TYPE
    SYNTAX INTEGER
    UNITS  "Percent"
    ACCESS read-only
    STATUS mandatory
    DESCRIPTION
        "This parameter displays the minimum allowable voltage before it falls into under voltage range."
    ::= { upsOutput 6 }

upsOutputOverVoltageDetectLevel OBJECT-TYPE
    SYNTAX INTEGER
    UNITS  "Percent"
    ACCESS read-only
    STATUS mandatory
    DESCRIPTION
        "This is the maximum limit of the output voltage before the UPS enters the over voltage state."
    ::= { upsOutput 7 }

upsOutputFrequencySynchRange OBJECT-TYPE
    SYNTAX NonNegativeInteger
    UNITS  "0.1 Hertz"
    ACCESS read-only
    STATUS mandatory
    DESCRIPTION
        "The allowable range for synchronizing output frequency in 1/10 of Hz."
    ::= { upsOutput 8 }

upsOutputVoltageAdjust OBJECT-TYPE
    SYNTAX DisplayString (SIZE(2))
    ACCESS read-write
    STATUS mandatory
    DESCRIPTION
        "This parameter allows UPS to be configured to have adjustable voltages. This is set by the administrator. Range: -5 to 5"
    ::= { upsOutput 9 }

upsOutputRatedPowerFactor OBJECT-TYPE
    SYNTAX INTEGER
    UNITS  "0.01"
    ACCESS read-only
    STATUS mandatory
    DESCRIPTION
        "The rated output power factor."
    ::= { upsOutput 10 }

-- ===========================================================================
-- upsBypass - ups1600XP-i Group 4
-- The UPS Output Data Group
-- ===========================================================================
upsBypassPowerSupplyConfiguration OBJECT-TYPE
    SYNTAX INTEGER {
        undefined(1),
        volt200Hz60(2),
        volt200Hz50(3),
        volt208Hz60(4),
        volt208Hz50(5),
        volt230Hz60(6),
        volt230Hz50(7),
        volt240Hz60(8),
        volt240Hz50(9),
        volt220Hz60(10),
        volt220Hz50(11),
        volt120Hz60(12),
        volt120Hz50(13),
        reserved0(14),
        reserved1(15),
        reserved2(16)
    }
    ACCESS read-only
    STATUS mandatory
    DESCRIPTION
        "This parameter summarizes the measured and collected data describing the power supply into the bypass circuit."
    ::= { upsBypass 1 }

upsBypassNumOfPhases OBJECT-TYPE
    SYNTAX INTEGER {
        one(1),
        two(2)
    }
    ACCESS read-only
    STATUS mandatory
    DESCRIPTION
        "The number of bypass lines utilized in this device. This variable indicates the number of rows in the bypass table."
    ::= { upsBypass 2 }

upsBypassTable OBJECT-TYPE
    SYNTAX SEQUENCE OF UpsBypassEntry
    ACCESS not-accessible
    STATUS mandatory
    DESCRIPTION
        "A list of Bypass table entries. The number of entries is given by the value of upsBypassNumofPhases."
    ::= { upsBypass  3 }

upsBypassEntry OBJECT-TYPE
    SYNTAX UpsBypassEntry
    ACCESS not-accessible
    STATUS mandatory
    DESCRIPTION
        "An entry containing information applicable to a particular line."
    INDEX {upsBypassIndex }
    ::= { upsBypassTable 1 }

UpsBypassEntry ::=
    SEQUENCE {
        upsBypassIndex      PositiveInteger,
        upsBypassFrequency  INTEGER,
        upsBypassVoltage    INTEGER,
        upsBypassCurrent    INTEGER        
    }

-- ===========================================================================
-- upsBypassTable/upsBypassEntry/upsBypassIndex
-- ===========================================================================
upsBypassIndex OBJECT-TYPE
    SYNTAX PositiveInteger 
    ACCESS not-accessible
    STATUS mandatory
    DESCRIPTION
        "The Bypass line identifier."
    ::= { upsBypassEntry 1 }

upsBypassFrequency OBJECT-TYPE
    SYNTAX INTEGER
    UNITS  "0.1 Hertz"
    ACCESS read-only
    STATUS mandatory
    DESCRIPTION
        "The present Bypass frequency of the UPS system in 1/10 of Hz of each phase."
    ::= { upsBypassEntry 2 }

upsBypassVoltage OBJECT-TYPE
    SYNTAX INTEGER
    UNITS  "RMS Volts"
    ACCESS read-only
    STATUS mandatory
    DESCRIPTION
        "The Bypass utility line voltage in RMS volts."
    ::= { upsBypassEntry 3 }

upsBypassCurrent OBJECT-TYPE
    SYNTAX INTEGER
    UNITS  "0.1 RMS Amp"
    ACCESS read-only
    STATUS mandatory
    DESCRIPTION
        "The magnitude of the present bypass Current in 1/10 RMS Amp."
    ::= { upsBypassEntry 4 }

upsBypassApparentPower OBJECT-TYPE
    SYNTAX INTEGER
    UNITS  "Volt-Amp"
    ACCESS read-only
    STATUS mandatory
    DESCRIPTION
        "The Bypass Apparent power in Volt-Amp."
    ::= { upsBypass 4 }

upsBypassUnderVoltageDetectLevel OBJECT-TYPE
    SYNTAX INTEGER
    UNITS  "Percent"
    ACCESS read-only
    STATUS mandatory
    DESCRIPTION
        "This parameter displays the minimum allowable voltage before it falls into bypass undervoltage range."
    ::= { upsBypass 5 }

upsBypassUnderVoltageRecoveryLevel OBJECT-TYPE
    SYNTAX INTEGER 
    UNITS  "Percent"
    ACCESS read-only
    STATUS mandatory
    DESCRIPTION
        "This parameter displays the allowable voltage that it can recover from."
    ::= { upsBypass 6 }

upsBypassOverVoltageDetectLevel OBJECT-TYPE
    SYNTAX INTEGER 
    UNITS  "RMS Volt"
    ACCESS read-only
    STATUS mandatory
    DESCRIPTION
        "This parameter displays the maximum allowable voltage before it falls into over voltage range."
    ::= { upsBypass 7 }

upsBypassOverVoltageRecoveryLevel OBJECT-TYPE
    SYNTAX INTEGER 
    UNITS  "RMS Volt"
    ACCESS read-only
    STATUS mandatory
    DESCRIPTION
        "This parameter displays the allowable voltage that it can recover from."
    ::= { upsBypass 8 }

-- ===========================================================================
-- upsDCBus - ups1600XP-i Group 5
-- The UPS DC Bus Data Group
-- ===========================================================================
upsDCBusTotalVoltage OBJECT-TYPE
    SYNTAX INTEGER
    UNITS  "DC Volts"
    ACCESS read-only
    STATUS mandatory
    DESCRIPTION
        "The DC Bus voltage in DC volts."
    ::= { upsDCBus 1 }

upsDCBusPositiveVoltage OBJECT-TYPE
    SYNTAX INTEGER
    UNITS  "DC Volts"
    ACCESS read-only
    STATUS mandatory
    DESCRIPTION
        "The DC Bus positive voltage in DC volts."
    ::= { upsDCBus 2 }

upsDCBusNegativeVoltage OBJECT-TYPE
    SYNTAX INTEGER
    UNITS  "DC Volts"
    ACCESS read-only
    STATUS mandatory
    DESCRIPTION
        "The DC Bus negative voltage in DC volts."
    ::= { upsDCBus 3 }

upsDCBusRatedVoltage OBJECT-TYPE
    SYNTAX INTEGER 
    UNITS  "DC Volts"
    ACCESS read-only
    STATUS mandatory
    DESCRIPTION
        "The DC Bus rated voltage in DC volts."
    ::= { upsDCBus 4 }

-- ===========================================================================
-- upsBattery ups1600XP-i Group 6
-- The UPS Battery Data Group
-- ===========================================================================

upsBatteryStatus OBJECT-TYPE
    SYNTAX INTEGER {
         unknown(1),
         batteryNormal(2),
         batteryLow(3),
         batteryDepleted(4),
         batteryDischarging(5),
         batteryTestFailure(6)
    }
    ACCESS read-only
    STATUS mandatory
    DESCRIPTION
        "The indication of the capacity remaining in the UPS system's batteries. A value of batteryNormal indicates that the remaining run-time sufficient to handle the load. A value of batteryLow indicates the battery level is low. Continued operation in battery mode will deplate batteries. A value of batteryDepleted indicates that the UPS will be unable to sustain the present load when and if the utility power is lost (including the possibility that the utility power is currently absent and the UPS is unable to sustain the output). A value of batteryDischarging indicates UPS system is in Battery power."
    ::= { upsBattery 1 }

upsElapsedTimeOnBatteryPower OBJECT-TYPE
    SYNTAX NonNegativeInteger
    UNITS   "Second"
    ACCESS read-only
    STATUS mandatory
    DESCRIPTION
        "If the unit is on battery power, the elapsed time since the UPS on battery power, or the time since the network management subsystem was last restarted, whichever is less. Zero shall be returned if the unit is not on battery power."
    ::= { upsBattery 2 }

upsEstimatedBatteryRuntime OBJECT-TYPE
     SYNTAX PositiveInteger
     UNITS "minutes"
     ACCESS read-only
     STATUS mandatory
     DESCRIPTION
         "An estimate of the time to battery charge depletion under the present load conditions if the utility power is off and remains off, or if it were to be lost and remain off."
     ::= { upsBattery 3 }

upsBatteryVoltage OBJECT-TYPE
    SYNTAX INTEGER
    UNITS  "DC Volt"
    ACCESS read-only
    STATUS mandatory
    DESCRIPTION
        "The magnitude of the present battery voltage in DC Volt."
    ::= { upsBattery 4 }

upsBatteryDischargeCurrent OBJECT-TYPE
    SYNTAX INTEGER
    UNITS  "0.1 DC Amp"
    ACCESS read-only
    STATUS mandatory
    DESCRIPTION
        "The present battery discharge current in 1/10 DC Amp."
    ::= { upsBattery 5 }

upsBatteryChargeStatus OBJECT-TYPE
    SYNTAX INTEGER {
        normal-charging(1),
        preventative-charging(2),
        stop-charging(3)
    }
    ACCESS read-only
    STATUS mandatory
    DESCRIPTION
        "The UPS charger status."
    ::= { upsBattery 6 }

upsBatteryNumberOfDischarge OBJECT-TYPE
    SYNTAX NonNegativeInteger
    ACCESS read-only
    STATUS mandatory
    DESCRIPTION
        "This will increment when ups goes into backup mode which is longer than 10 seconds."
    ::= { upsBattery 7 }

upsBatteryRatedShutdownVoltage OBJECT-TYPE
    SYNTAX INTEGER
    UNITS  "DC Volt"
    ACCESS read-only
    STATUS mandatory
    DESCRIPTION
        "The battery's shut down voltage in DC Volt."
    ::= { upsBattery 8 }

upsBatteryEstimatedLifeRemaining OBJECT-TYPE
    SYNTAX NonNegativeInteger
    UNITS  "Months"
    ACCESS read-only
    STATUS mandatory
    DESCRIPTION
        "The number of months of UPS operation in the present environment until the batteries must be replaced."
    ::= { upsBattery 9 }

upsBatteryRatedAmpereHour OBJECT-TYPE
    SYNTAX INTEGER
    UNITS  "Amp-Hour"
    ACCESS read-only
    STATUS mandatory
    DESCRIPTION
        "The battery capacity in Amp-Hour."
    ::= { upsBattery 10 }

upsBatteryInSeries OBJECT-TYPE
    SYNTAX INTEGER
    ACCESS read-only
    STATUS mandatory
    DESCRIPTION
        "The number of batteries in each string connected in series."
    ::= { upsBattery 11 }

upsBatteryInParallel OBJECT-TYPE
    SYNTAX INTEGER
    ACCESS read-only
    STATUS mandatory
    DESCRIPTION
        "The number of batteries connected in parallel."
    ::= { upsBattery 12 }

upsBatteryInstallationDate OBJECT-TYPE
    SYNTAX DisplayString (SIZE(10))
    ACCESS read-only
    STATUS mandatory
    DESCRIPTION
        "The battery installation date in YYYYMMDD format."
    ::= { upsBattery 13 }

upsBatteryVoltageShutdownLevel OBJECT-TYPE
    SYNTAX INTEGER
    UNITS  "Percent"
    ACCESS read-only
    STATUS mandatory
    DESCRIPTION
        "The UPS battery voltage shut down level."
    ::= { upsBattery 14 }

upsBatteryExtTable OBJECT-TYPE
    SYNTAX SEQUENCE OF UpsBatteryExtEntry
    ACCESS not-accessible
    STATUS mandatory
    DESCRIPTION
        "A list of Battery table entries."
    ::= { upsBattery 15 }

upsBatteryExtEntry OBJECT-TYPE
    SYNTAX UpsBatteryExtEntry
    ACCESS not-accessible
    STATUS mandatory
    DESCRIPTION
        "An entry containing information applicable to a particular Battery."
    INDEX {upsBatteryExtIndex }
    ::= { upsBatteryExtTable 1 }

UpsBatteryExtEntry ::=
    SEQUENCE {
        upsBatteryExtIndex						PositiveInteger,
        upsBatteryExtInstallationStatus			INTEGER,
        upsBatteryExtInSeries					INTEGER,
        upsBatteryExtInParallel					INTEGER,
        upsBatteryExtRatedAmpereHour			INTEGER,
        upsBatteryExtCRate						INTEGER,
        upsBatteryExtInstallationDate			DisplayString,
		upsBatteryExtCab1SerialNumber			DisplayString,
		upsBatteryExtCab1FirmwareVersion		DisplayString,
		upsBatteryExtCab1ChargerCurrent			INTEGER,
		upsBatteryExtCab1ChargerVoltage			INTEGER, 
		upsBatteryExtCab1AmbientTemperatureC	INTEGER, 
		upsBatteryExtCab1AmbientTemperatureF	INTEGER, 
		upsBatteryExtCab2SerialNumber			DisplayString, 
		upsBatteryExtCab2FirmwareVersion		DisplayString, 
		upsBatteryExtCab2ChargerCurrent			INTEGER, 
		upsBatteryExtCab2ChargerVoltage			INTEGER, 
		upsBatteryExtCab2AmbientTemperatureC	INTEGER, 
		upsBatteryExtCab2AmbientTemperatureF	INTEGER
    }

-- ===========================================================================
-- upsBatteryTable/upsBattery/upsBatteryIndex
-- ===========================================================================
upsBatteryExtIndex OBJECT-TYPE
    SYNTAX PositiveInteger 
    ACCESS not-accessible
    STATUS mandatory
    DESCRIPTION
        "The Battery line identifier"
    ::= { upsBatteryExtEntry 1 }

upsBatteryExtInstallationStatus OBJECT-TYPE
    SYNTAX INTEGER {
        uninstalled(1),
        installed(2)
    }
    ACCESS read-only
    STATUS mandatory
    DESCRIPTION
        "This reveals the installation status of the external battery cabinet."
    ::= { upsBatteryExtEntry 2 }

upsBatteryExtInSeries OBJECT-TYPE
    SYNTAX INTEGER
    ACCESS read-only
    STATUS mandatory
    DESCRIPTION
        "Specifies the number of batteries in the external cabinet that are connected in series."
    ::= { upsBatteryExtEntry 3 }

upsBatteryExtInParallel OBJECT-TYPE
    SYNTAX INTEGER
    ACCESS read-only
    STATUS mandatory
    DESCRIPTION
        "Specifies the number of batteries in the external cabinet that are connected in parallel."
    ::= { upsBatteryExtEntry 4 }

upsBatteryExtRatedAmpereHour OBJECT-TYPE
    SYNTAX INTEGER
    UNITS  "Amp-Hour"
    ACCESS read-only
    STATUS mandatory
    DESCRIPTION
        "The external battery's capacity in Amp-Hour."
    ::= { upsBatteryExtEntry 5 }

upsBatteryExtCRate OBJECT-TYPE
    SYNTAX INTEGER
    ACCESS read-only
    STATUS mandatory
    DESCRIPTION
        "The external battery's C rate."
    ::= { upsBatteryExtEntry 6 }

upsBatteryExtInstallationDate OBJECT-TYPE
    SYNTAX DisplayString (SIZE(10))
    UNITS "MM/DD/YYYY"
    ACCESS read-only
    STATUS mandatory
    DESCRIPTION
        "The battery installation date in YYYYMMDD format."
    ::= { upsBatteryExtEntry 7 }

upsBatteryExtCab1SerialNumber OBJECT-TYPE
    SYNTAX DisplayString (SIZE(0..16))
    UNITS "Serial #"
    ACCESS read-only
    STATUS mandatory
    DESCRIPTION
        "The matching battery cabinet 1 serial number."
    ::= { upsBatteryExtEntry 8 }

upsBatteryExtCab1FirmwareVersion OBJECT-TYPE
    SYNTAX DisplayString (SIZE(0..16))
    UNITS "FW VeR"
    ACCESS read-only
    STATUS mandatory
    DESCRIPTION
        "The matching battery cabinet 1 firmware version."
    ::= { upsBatteryExtEntry 9 }

upsBatteryExtCab1ChargerCurrent OBJECT-TYPE
    SYNTAX INTEGER
    UNITS  "Amps"
    ACCESS read-only
    STATUS mandatory
    DESCRIPTION
        "The matching battery cabinet 1 charger current."
    ::= { upsBatteryExtEntry 10 }

upsBatteryExtCab1ChargerVoltage OBJECT-TYPE
    SYNTAX INTEGER
    UNITS  "Volts"
    ACCESS read-only
    STATUS mandatory
    DESCRIPTION
        "The matching battery cabinet 1 charger voltage."
    ::= { upsBatteryExtEntry 11 }

upsBatteryExtCab1AmbientTemperatureC OBJECT-TYPE
    SYNTAX INTEGER
    UNITS  "Celsius"
    ACCESS read-only
    STATUS mandatory
    DESCRIPTION
        "The matching battery cabinet 1 ambient temperature in degrees Celsius."
    ::= { upsBatteryExtEntry 12 }

upsBatteryExtCab1AmbientTemperatureF  OBJECT-TYPE
    SYNTAX INTEGER
    UNITS  "Fahrenheit"
    ACCESS read-only
    STATUS mandatory
    DESCRIPTION
        "The matching battery cabinet 1 ambient temperature in degrees Fahrenheit."
    ::= { upsBatteryExtEntry 13 }

upsBatteryExtCab2SerialNumber OBJECT-TYPE
    SYNTAX DisplayString (SIZE(0..16))
    UNITS "Serial Number"
    ACCESS read-only
    STATUS mandatory
    DESCRIPTION
        "The matching battery cabinet 2 serial number."
    ::= { upsBatteryExtEntry 14 }

upsBatteryExtCab2FirmwareVersion OBJECT-TYPE
    SYNTAX DisplayString (SIZE(0..16))
    UNITS "FW Ver."
    ACCESS read-only
    STATUS mandatory
    DESCRIPTION
        "The matching battery cabinet 2 firmware version."
    ::= { upsBatteryExtEntry 15 }

upsBatteryExtCab2ChargerCurrent OBJECT-TYPE
    SYNTAX INTEGER
    UNITS  "Amps"
    ACCESS read-only
    STATUS mandatory
    DESCRIPTION
        "The matching battery cabinet 2 charger current."
    ::= { upsBatteryExtEntry 16 }

upsBatteryExtCab2ChargerVoltage OBJECT-TYPE
    SYNTAX INTEGER
    UNITS  "Volts"
    ACCESS read-only
    STATUS mandatory
    DESCRIPTION
        "The matching battery cabinet 2 charger voltage."
    ::= { upsBatteryExtEntry 17 }

upsBatteryExtCab2AmbientTemperatureC OBJECT-TYPE
    SYNTAX INTEGER
    UNITS  "Celsius"
    ACCESS read-only
    STATUS mandatory
    DESCRIPTION
        "The matching battery cabinet 1 ambient temperature in degrees Celsius."
    ::= { upsBatteryExtEntry 18 }

upsBatteryExtCab2AmbientTemperatureF OBJECT-TYPE
    SYNTAX INTEGER
    UNITS  "Fahrenheit"
    ACCESS read-only
    STATUS mandatory
    DESCRIPTION
        "The matching battery cabinet 1 ambient temperature in degrees Fahrenheit."
    ::= { upsBatteryExtEntry 19 }

upsBatteryRatedLowBattLevelPercent OBJECT-TYPE
    SYNTAX INTEGER
    UNITS  "Percent"
    ACCESS read-only
    STATUS mandatory
    DESCRIPTION
        "The low battery level of the UPS in percent."
    ::= { upsBattery 16 }

upsBatteryRatedLowBattLevel OBJECT-TYPE
    SYNTAX INTEGER
    UNITS  "Vdc"
    ACCESS read-only
    STATUS mandatory
    DESCRIPTION
        "The low battery level of the UPS."
    ::= { upsBattery 17 }

upsBatteryChargerOverVoltageDelay OBJECT-TYPE
    SYNTAX INTEGER
    UNITS  "Second"
    ACCESS read-only
    STATUS mandatory
    DESCRIPTION
        "The UPS's charger over voltage detection delay in seconds."
    ::= { upsBattery 18 }

upsBatteryCapacity OBJECT-TYPE
    SYNTAX INTEGER
    UNITS  "Percent"
    ACCESS read-only
    STATUS mandatory
    DESCRIPTION
        "The UPS battery capacity in percent."
    ::= { upsBattery 19 }

-- ===========================================================================
-- upsStsCtlCfg ups1600XP-i Group 7
-- The UPS status, control and configuration
-- ===========================================================================
upsStsCtlCfgSystemTemperature OBJECT-TYPE
    SYNTAX INTEGER 
    UNITS  "Celsius"
    ACCESS read-only
    STATUS mandatory
    DESCRIPTION
        "The UPS system temperature in Celsius."
    ::= { upsStsCtlCfg 1 }

upsStsCtlCfgBatteryTemperature OBJECT-TYPE
    SYNTAX INTEGER 
    UNITS  "Celsius"
    ACCESS read-only
    STATUS mandatory
    DESCRIPTION
        "The UPS Battery temperature in Celsius."
    ::= { upsStsCtlCfg 2 }

upsStsCtlCfgPresentMode OBJECT-TYPE
    SYNTAX INTEGER {
        shutdown0(1),
        shutdown1(2),
        shutdown2(3),
        online(4),
        backup(5),
        battery-test(6),
        bypass6(7),
        bypass7(8),
        bypass8(9),
        startup(10)
    }
    ACCESS read-only
    STATUS mandatory
    DESCRIPTION
        "The present mode of the UPS system."
    ::= { upsStsCtlCfg 3 }

upsStsCtlCfgModeRequest OBJECT-TYPE
    SYNTAX INTEGER {
        none(1),
		shutdown(2),
        bypass(3),
        online(4),
        battery-test(5)
    }
    ACCESS read-write
    STATUS mandatory
    DESCRIPTION
        "The mode of the UPS system requested by the user."
    ::= { upsStsCtlCfg 4 }

upsStsCtlCfgModeTransitionTimer OBJECT-TYPE
    SYNTAX NonNegativeInteger
    UNITS  "Second"
    ACCESS read-write
    STATUS mandatory
    DESCRIPTION
        "The timer upon whose expiration a mode transition will be attempted by the system."
    ::= { upsStsCtlCfg 5 }

upsStsCtlCfgEPOContactState OBJECT-TYPE
    SYNTAX INTEGER {
        open(1),
        closed(2)
    }
    ACCESS read-only
    STATUS mandatory
    DESCRIPTION
        "The EPO contact state of the UPS system."
    ::= { upsStsCtlCfg 6 }

upsStsCtlCfgRunStopSwitchState OBJECT-TYPE
    SYNTAX INTEGER {
        stop(1),
        run(2)
    }
    ACCESS read-only
    STATUS mandatory
    DESCRIPTION
        "The Run/Stop switch state of the UPS system."
    ::= { upsStsCtlCfg 7 }

upsStsCtlCfgServicePortCommStatus OBJECT-TYPE
    SYNTAX INTEGER {
        unknown(1),
        normal-OK(2),
        idle(3),
        error(4)
    }
    ACCESS read-only
    STATUS mandatory
    DESCRIPTION
        "The service port communication status."
    ::= { upsStsCtlCfg 8 }

upsStsCtlCfgInternalCommStatus OBJECT-TYPE
    SYNTAX INTEGER {
        unknown(1),
        normal-OK(2),
        off(3),
        error(4)
    }
    ACCESS read-only
    STATUS mandatory
    DESCRIPTION
        "The internal communication status of the UPS system such as display panel."
    ::= { upsStsCtlCfg 9 }

upsStsCtlCfgSecurityLevel OBJECT-TYPE
    SYNTAX DisplayString (SIZE(0..16))
    ACCESS read-only
    STATUS mandatory
    DESCRIPTION
        "The current security level of the UPS system"
    ::= { upsStsCtlCfg 10 }

upsStsCtlCfgPresentDate OBJECT-TYPE
    SYNTAX NonNegativeInteger
    ACCESS read-write
    STATUS mandatory
    DESCRIPTION 
        "The present date of the UPS. This is configurable by Administrator."
    ::= { upsStsCtlCfg 11 }

upsStsCtlCfgPresentTime OBJECT-TYPE
    SYNTAX NonNegativeInteger
    ACCESS read-write
    STATUS mandatory
    DESCRIPTION 
        "The present time of the UPS. This is configurable by Administrator."
    ::= { upsStsCtlCfg 12 }

upsStsCtlCfgPresentTimeStamp OBJECT-TYPE
    SYNTAX INTEGER
    ACCESS read-only
    STATUS mandatory
    DESCRIPTION 
        "Present system time stamp."
    ::= { upsStsCtlCfg 13 }

upsStsCtlCfgEnableRMTIToControlMode OBJECT-TYPE
    SYNTAX INTEGER {
        disable(1),
        enable(2)
    }
    ACCESS read-write
    STATUS mandatory
    DESCRIPTION
        "Allow to enable or disable SNMP to control the UPS Shut down and Online Mode."
    ::= { upsStsCtlCfg 14 }

upsStsCtlCfgEnableStartupDelay OBJECT-TYPE
    SYNTAX INTEGER {
        disable(1),
        enable(2)
    }
    ACCESS read-write
    STATUS mandatory
    DESCRIPTION
        "This delay timer, when enabled, will begin counting down at UPS start up immediately following a UPS shut down by any means other than battery exhaustion. UPS output of any kind will be prohibited."
    ::= { upsStsCtlCfg 15 }

upsStsCtlCfgStartUpDelayMode OBJECT-TYPE
    SYNTAX INTEGER {
        bypass(1),
        online(2)
    }
    ACCESS read-write
    STATUS mandatory
    DESCRIPTION
        "UPS mode into which the UPS will transition at the expiration of the Start-Up delay timer."
    ::= { upsStsCtlCfg 16 }

upsStsCtlCfgStartUpDelay OBJECT-TYPE
    SYNTAX NonNegativeInteger
    UNITS  "Second"
    ACCESS read-write
    STATUS mandatory
    DESCRIPTION
        "When the timer is counting down, its changing value is reflected,otherwise its starting value is reported."
    ::= { upsStsCtlCfg 17 }

upsStsCtlCfgRemoteShutDownContactState OBJECT-TYPE
    SYNTAX INTEGER {
        open(1),
        closed(2)
    }
    ACCESS read-only
    STATUS mandatory
    DESCRIPTION
        "The state of the Remote Contacts Shut down Control."
    ::= { upsStsCtlCfg 18 }

upsStsCtlCfgRemoteShutdownContactMode OBJECT-TYPE
    SYNTAX INTEGER {
        bypass(1),
        shutdown-while-contact-closed(2)
    }
    ACCESS read-write
    STATUS mandatory
    DESCRIPTION
        "The mode of the Remote Contacts Shut down control."
    ::= { upsStsCtlCfg 19 }

upsStsCtlCfgEnableDryContactLANShutdown OBJECT-TYPE
    SYNTAX INTEGER {
        disable(1),
        enable(2)
    }
    ACCESS read-write
    STATUS mandatory
    DESCRIPTION
        "When enable, UPS will accept LAN signal request for UPS shut down but only in accordance with restrictions of the following timer."
    ::= { upsStsCtlCfg 20 }

upsStsCtlCfgDryContactLANShutdownTimer OBJECT-TYPE
    SYNTAX NonNegativeInteger
    UNITS  "Second"
    ACCESS read-write
    STATUS mandatory
    DESCRIPTION
        "Timer begins upon input power recovery and during its lifetime, allows the LAN input signal to affect a UPS Shut down control."
    ::= { upsStsCtlCfg 21 }

upsStsCtlCfgDryContactOnBattDelay OBJECT-TYPE
    SYNTAX NonNegativeInteger
    UNITS  "Second"
    ACCESS read-write
    STATUS mandatory
    DESCRIPTION
        "Time delay between actual event occurrence and dry contact closure to signal external devices of the event."
    ::= { upsStsCtlCfg 22 }

upsStsCtlCfgDryContactLowBattDelay OBJECT-TYPE
    SYNTAX NonNegativeInteger
    UNITS  "Second"
    ACCESS read-write
    STATUS mandatory
    DESCRIPTION
        "Delay timer between actual event occurrence and dry contact closure to signal external devices of the event."
    ::= { upsStsCtlCfg 23 }

upsStsCtlCfgEnableStartupBattTest OBJECT-TYPE
    SYNTAX INTEGER {
        disable(1),
        enable(2)
    }
    ACCESS read-write
    STATUS mandatory
    DESCRIPTION
        "Forces a battery test when UPS starts."
    ::= { upsStsCtlCfg 24 }

upsStsCtlCfgEnableBatteryTest OBJECT-TYPE
    SYNTAX INTEGER {
        disable(1),
        enable(2)
    }
    ACCESS read-write
    STATUS mandatory
    DESCRIPTION
        "Allow to enable or disable battery test."
    ::= { upsStsCtlCfg 25 }

upsStsCtlCfgBatteryTestConditionStatus OBJECT-TYPE
    SYNTAX INTEGER {
        battery-test-prohibited(1),
        battery-test-ok(2)
    }
    ACCESS read-only
    STATUS mandatory
    DESCRIPTION
        "This notifies the user of the availability of the battery test feature."
    ::= { upsStsCtlCfg 26 }

upsStsCtlCfgMaxBatteryTestFreq OBJECT-TYPE
    SYNTAX INTEGER {
        daily(1),
        weekly(2),
        monthly(3)
    }
    ACCESS read-write
    STATUS mandatory
    DESCRIPTION
        "This specified how often the battery test should occur. This is set by the administrator"
    ::= { upsStsCtlCfg 27 }

upsStsCtlCfgEnableRestartAfterBattShutdown OBJECT-TYPE
    SYNTAX INTEGER {
        disable(1),
        enable(2)
    }
    ACCESS read-write
    STATUS mandatory
    DESCRIPTION
        "Mode set for UPS input power detection immediately after a shut down while on batteries. This is set by the administrator."
    ::= { upsStsCtlCfg 28 }

upsStsCtlCfgRestartDelay OBJECT-TYPE
    SYNTAX INTEGER
    UNITS  "Second"
    ACCESS read-write
    STATUS mandatory
    DESCRIPTION
        "Countdown begins only when UPS input power is restored immediately following a UPS Shut down while on batteries."
    ::= { upsStsCtlCfg 29 }

upsStsCtlCfgEnableAutoTransferMode OBJECT-TYPE
    SYNTAX INTEGER {
        disable(1),
        enable(2) 
    }
    ACCESS read-write
    STATUS mandatory
    DESCRIPTION
        "This feature allows the administrators to enable or to disable the auto transfer feature of the UPS."
    ::= { upsStsCtlCfg 30 }

upsStsCtlCfgAutoTransferDelay OBJECT-TYPE
    SYNTAX INTEGER
    UNITS  "Second"
    ACCESS read-write
    STATUS mandatory
    DESCRIPTION
        "Time period to wait after fault occurrence before attempting transfer back Online"
    ::= { upsStsCtlCfg 31 }

upsStsCtlCfgServicePortCommSetting OBJECT-TYPE
    SYNTAX INTEGER {
        bd9600(1),
        bd19200(2), 
        bd38400(3),
        bd57600(4)
    }
    ACCESS read-write
    STATUS mandatory
    DESCRIPTION
        "The UPS baud rate settings."
    ::= { upsStsCtlCfg 32 }

upsStsCtlCfgInvertRemoteShutdownLogic OBJECT-TYPE
    SYNTAX INTEGER {
        not-inverted(1),
        inverted(2) 
    }
    ACCESS read-write
    STATUS mandatory
    DESCRIPTION 
        "Remote Shut down logic."
    ::= { upsStsCtlCfg 33 }

upsStsCtlCfgRestartMode OBJECT-TYPE
    SYNTAX INTEGER {
        bypass(1),
        online(2) 
    }
    ACCESS read-write
    STATUS mandatory
    DESCRIPTION 
        "Restart Mode."
    ::= { upsStsCtlCfg 34 }
	
upsStsCtlCfgUserDefinedOverloadSetPoint OBJECT-TYPE
    SYNTAX INTEGER
	UNITS "%"
    ACCESS read-write
    STATUS mandatory
    DESCRIPTION 
        "The maximum output load % defined by the user."
    ::= { upsStsCtlCfg 35 }

-- ===========================================================================
-- upsHistory ups1600XP-i Group 8
-- The UPS History Data Group
-- ===========================================================================
upsHistorySysOperationTime OBJECT-TYPE
    SYNTAX NonNegativeInteger
    UNITS  "Hours"
    ACCESS read-only
    STATUS mandatory
    DESCRIPTION 
        "The amount of time the UPS has been on."
    ::= { upsHistory 1 }

upsHistoryInverterOperationTime OBJECT-TYPE
    SYNTAX NonNegativeInteger
    UNITS  "Hours"
    ACCESS read-only
    STATUS mandatory
    DESCRIPTION 
        "The amount of time the UPS has been in On-Line Mode."
    ::= { upsHistory 2 }

upsHistoryBackupOperationTime OBJECT-TYPE
    SYNTAX NonNegativeInteger
    UNITS  "Seconds"
    ACCESS read-only
    STATUS mandatory
    DESCRIPTION 
        "The amount of time the UPS has been in BackUp Mode."
    ::= { upsHistory 3 }

upsHistoryLifetimeRemaining OBJECT-TYPE
    SYNTAX NonNegativeInteger
    UNITS  "Months"
    ACCESS read-only
    STATUS mandatory
    DESCRIPTION 
        "The remaining lifetime of the UPS."
    ::= { upsHistory 4 }

upsHistoryHighestSystemTempC OBJECT-TYPE
    SYNTAX INTEGER 
    UNITS  "Celsius"
    ACCESS read-only
    STATUS mandatory
    DESCRIPTION 
        "The highest system temperature of the UPS."
    ::= { upsHistory 5 }

upsHistoryHighestSystemTempF OBJECT-TYPE
    SYNTAX INTEGER 
    UNITS  "Fahrenheit"
    ACCESS read-only
    STATUS mandatory
    DESCRIPTION 
        "The highest system temperature of the UPS."
    ::= { upsHistory 6 }

upsHistoryHighestBatteryTempC OBJECT-TYPE
    SYNTAX INTEGER 
    UNITS  "Celsius"
    ACCESS read-only
    STATUS mandatory
    DESCRIPTION 
        "The highest battery temperature."
    ::= { upsHistory 7 }

upsHistoryHighestBatteryTempF OBJECT-TYPE
    SYNTAX INTEGER 
    UNITS  "Fahrenheit"
    ACCESS read-only
    STATUS mandatory
    DESCRIPTION 
        "The highest battery temperature."
    ::= { upsHistory 8 }

upsHistoryTotalNumInputUnderVolt OBJECT-TYPE
    SYNTAX NonNegativeInteger
    ACCESS read-only
    STATUS mandatory
    DESCRIPTION 
        "Total number of times the UPS has entered under voltage state."
    ::= { upsHistory 9 }

upsHistoryTotalNumOverload OBJECT-TYPE
    SYNTAX NonNegativeInteger
    ACCESS read-only
    STATUS mandatory
    DESCRIPTION 
        "Total number of times the UPS has been overloaded."
    ::= { upsHistory 10}

upsHistoryTotalNumTest OBJECT-TYPE
    SYNTAX NonNegativeInteger
    ACCESS read-only
    STATUS mandatory
    DESCRIPTION 
        "Total number of tests that has been conducted on the UPS."
    ::= { upsHistory 11}

upsHistoryTotalNumBackup OBJECT-TYPE
    SYNTAX NonNegativeInteger
    ACCESS read-only
    STATUS mandatory
    DESCRIPTION 
        "Total number of times the UPS has been in Back-Up mode."
    ::= { upsHistory 12}

upsHistoryTotalNumFaults OBJECT-TYPE
    SYNTAX NonNegativeInteger
    ACCESS read-only
    STATUS mandatory
    DESCRIPTION 
        "Total number of faults that has occurred on the UPS."
    ::= { upsHistory 13}

upsHistoryTotalNumOperationModeChange OBJECT-TYPE
    SYNTAX NonNegativeInteger
    ACCESS read-only
    STATUS mandatory
    DESCRIPTION 
        "The number of mode changes that has occurred."
    ::= { upsHistory 14}

upsHistoryTotalNumWarnings OBJECT-TYPE
    SYNTAX NonNegativeInteger
    ACCESS read-only
    STATUS mandatory
    DESCRIPTION 
        "The number of warnings that has occurred on the UPS."
    ::= { upsHistory 15}

upsHistoryTotalNumSystemSettingsChange OBJECT-TYPE
    SYNTAX NonNegativeInteger
    ACCESS read-only
    STATUS mandatory
    DESCRIPTION 
        "The number of times the System settings have been changed."
    ::= { upsHistory 16}

upsHistoryTotalNumResets OBJECT-TYPE
    SYNTAX NonNegativeInteger
    ACCESS read-only
    STATUS mandatory
    DESCRIPTION 
        "The number of times the UPS has reset."
    ::= { upsHistory 17}

-- ===========================================================================
-- upsDisplay ups1600XP-i Group 9
-- The UPS Display Data Group
-- ===========================================================================
upsDisplayFirmwareVersion OBJECT-TYPE
    SYNTAX DisplayString (SIZE(0..15))
    ACCESS read-only
    STATUS mandatory
    DESCRIPTION
        "The firmware version of the display."
    ::= { upsDisplay 1 }

upsDisplayBootSectorVersion OBJECT-TYPE
    SYNTAX DisplayString (SIZE(0..15))
    ACCESS read-only
    STATUS mandatory
    DESCRIPTION
        "The boot sector version of the display."
    ::= { upsDisplay 2 }

upsDisplayBootLoaderVersion OBJECT-TYPE
    SYNTAX DisplayString (SIZE(0..15))
    ACCESS read-only
    STATUS mandatory
    DESCRIPTION
        "The boot loader version of the display."
    ::= { upsDisplay 3 }

upsDisplayFirmwareBuiltDate OBJECT-TYPE
    SYNTAX DisplayString (SIZE(0..15))
    ACCESS read-only
    STATUS mandatory
    DESCRIPTION
        "The firmware build date of the display."
    ::= { upsDisplay 4 } 

upsDisplayFirmwareBuiltTime OBJECT-TYPE
    SYNTAX DisplayString (SIZE(0..15))
    ACCESS read-only
    STATUS mandatory
    DESCRIPTION
        "The firmware build time of the display."
    ::= { upsDisplay 5 } 

upsDisplaySleepTimer OBJECT-TYPE
    SYNTAX NonNegativeInteger
    UNITS  "Minutes"
    ACCESS read-write
    STATUS mandatory
    DESCRIPTION 
        "The sleep timer for the display."
    ::= { upsDisplay 6 }

upsDisplayBuzzerMode OBJECT-TYPE
    SYNTAX INTEGER {
        disable(1),
        enable(2)
    }          
    ACCESS read-write
    STATUS mandatory
    DESCRIPTION
        "Configures buzzer mode."
    ::= { upsDisplay 7 }

upsDisplayBuzzerStatus OBJECT-TYPE
    SYNTAX INTEGER {
        off(1),
        idle(2),
        alarm(3),
        silenced(4)
    }          
    ACCESS read-only
    STATUS mandatory
    DESCRIPTION
        "Shows the current state of the buzzer."
    ::= { upsDisplay 8 }

upsDisplayRMTIInstallationDate OBJECT-TYPE
    SYNTAX DisplayString(SIZE(8))
    ACCESS read-only
    STATUS mandatory
    DESCRIPTION
        "The RemotEye installation date."
    ::= { upsDisplay 9 }

upsDisplayRMTIVersion OBJECT-TYPE
    SYNTAX DisplayString(SIZE(0..15))
    ACCESS read-only
    STATUS mandatory
    DESCRIPTION
        "The RemotEye Firmware Version."
    ::= { upsDisplay 10 } 

upsDisplayRMTIInstallationStatus OBJECT-TYPE
    SYNTAX INTEGER {
        uninstalled(1),
        installed(2)
    }          
    ACCESS read-only
    STATUS mandatory
    DESCRIPTION
        "Shows the installation status of the RemotEye."
    ::= { upsDisplay 11 }

upsDisplayRMTIBaudRate OBJECT-TYPE
    SYNTAX INTEGER {
        bd9600(1),
        bd19200(2),
        bd38400(3),
        bd57600(4)
    }          
    ACCESS read-only
    STATUS mandatory
    DESCRIPTION
        "Configures the baud rate."
    ::= { upsDisplay 12 }

upsDisplayRMTIDataLink OBJECT-TYPE
    SYNTAX INTEGER {
        unknown(1),
        link-down(2),
        link-up(3)
    }          
    ACCESS read-only
    STATUS mandatory
    DESCRIPTION
        "Shows the data status of the RemotEye."
    ::= { upsDisplay 13 }

upsDisplayRMTINetworkLink OBJECT-TYPE
    SYNTAX INTEGER {
        unknown(1),
        link-down(2),
        link-up(3)
    }          
    ACCESS read-only
    STATUS mandatory
    DESCRIPTION
        "Shows the network status of the RemotEye."
    ::= { upsDisplay 14 }

-- ===========================================================================
-- upsAlarm ups1600XP-i Group 10
-- The UPS Alarm List
-- ===========================================================================
upsAlarmsPresent OBJECT-TYPE
    SYNTAX Gauge32
    ACCESS read-only
    STATUS mandatory
    DESCRIPTION
        "One or more alarms reported."
    ::= { upsAlarm 1 }

upsAlarmTable OBJECT-TYPE
    SYNTAX SEQUENCE OF UpsAlarmEntry
    ACCESS not-accessible
    STATUS mandatory
    DESCRIPTION
        "A list of alarm table entries. The table contains
         zero, one, or many rows at any moment, depending upon
         the number of alarm conditions in effect. The table
         is initially empty at agent start up. The agent
         creates a row in the table each time a condition is
         detected and deletes that row when that condition no
         longer pertains. The agent creates the first row with
         upsAlarmId equal to 1, and increments the value of
         upsAlarmId each time a new row is created, wrapping to
         the first free value greater than or equal to 1 when
         the maximum value of upsAlarmId would otherwise be
         exceeded. Consequently, after multiple operations,
         the table may become sparse, e.g., containing entries
         for rows 95, 100, 101, and 203 and the entries should
         not be assumed to be in chronological order because
         upsAlarmId might have wrapped.

         Alarms are named by an OBJECT IDENTIFIER,
         upsAlarmDescr, to allow a single table to
         reflect well known alarms plus alarms defined by a
         particular implementation, i.e., as documented in the
         private enterprise MIB definition for the device. No
         two rows will have the same value of upsAlarmDescr,
         since alarms define conditions. In order to meet this
         requirement, care should be taken in the definition of
         alarm conditions to insure that a system cannot enter
         the same condition multiple times simultaneously.

         The number of rows in the table at any given time is
         reflected by the value of upsAlarmsPresent."
    ::= { upsAlarm  2 }

upsAlarmEntry OBJECT-TYPE
    SYNTAX UpsAlarmEntry
    ACCESS not-accessible
    STATUS mandatory
    DESCRIPTION
        "An entry containing information applicable to a
         particular alarm."
    INDEX { upsAlarmId }
    ::= { upsAlarmTable  1 }

UpsAlarmEntry ::=
    SEQUENCE {
        upsAlarmId              PositiveInteger,
        upsAlarmDescr           AutonomousType,
        upsAlarmTime            TimeStamp
    }

-- ===========================================================================
-- upsAlarmTable/upsAlarmEntry/upsAlarmId
-- ===========================================================================
upsAlarmId OBJECT-TYPE
    SYNTAX PositiveInteger
    ACCESS not-accessible
    STATUS mandatory
    DESCRIPTION
        "An unique identifier for an alarm condition. This
         value must remain constant."
    ::= { upsAlarmEntry 1 }

upsAlarmDescr OBJECT-TYPE
    SYNTAX AutonomousType
    ACCESS read-only
    STATUS mandatory
    DESCRIPTION
        "A reference to an alarm description object. The
         object referenced should not be accessible, but rather
         be used to provide a unique description of the alarm
         condition."
    ::= { upsAlarmEntry 2 }

-- ===========================================================================
-- .../upsAlarmTime
-- ===========================================================================
upsAlarmTime OBJECT-TYPE
    SYNTAX TimeStamp
    ACCESS read-only
    STATUS mandatory
    DESCRIPTION
        "The value of upsConfigSystemTime when the alarm condition was
          detected. If the alarm condition was detected at the
          time of agent start up and presumably existed before
          agent start up, the value of upsAlarmTime shall equal 0."
    ::= { upsAlarmEntry 3 }

upsWellKnownAlarms OBJECT IDENTIFIER ::= { upsAlarm  3 }

upsAlarmFault OBJECT-TYPE 
    SYNTAX INTEGER
    ACCESS read-only
    STATUS mandatory
    DESCRIPTION
        "Fault: One or more fault reported."
    ::= { upsWellKnownAlarms 1 }

upsAlarmOpenFuse OBJECT-TYPE 
    SYNTAX INTEGER
    ACCESS read-only
    STATUS mandatory
    DESCRIPTION
        "Fault: An open fuse reported."
    ::= { upsWellKnownAlarms 2 }

upsAlarmCurrentLimitFault OBJECT-TYPE 
    SYNTAX INTEGER
    ACCESS read-only
    STATUS mandatory
    DESCRIPTION
        "Fault: A current limit reported."
    ::= { upsWellKnownAlarms 3 }

upsAlarmDCBusOverCurrent OBJECT-TYPE 
    SYNTAX INTEGER
    ACCESS read-only
    STATUS mandatory
    DESCRIPTION
        "Fault: A DC bus over current reported."
    ::= { upsWellKnownAlarms 4 }

upsAlarmDCBusOverVoltage OBJECT-TYPE 
    SYNTAX INTEGER
    ACCESS read-only
    STATUS mandatory
    DESCRIPTION
        "Fault: A DC bus over voltage reported."
    ::= { upsWellKnownAlarms 5 }

upsAlarmDCBusImbalance OBJECT-TYPE 
    SYNTAX INTEGER
    ACCESS read-only
    STATUS mandatory
    DESCRIPTION
        "Fault: A DC bus imbalance reported."
    ::= { upsWellKnownAlarms 6 }

upsAlarmOutputUnderVoltage OBJECT-TYPE 
    SYNTAX INTEGER
    ACCESS read-only
    STATUS mandatory
    DESCRIPTION
        "Fault: An inverter output under voltage reported."
    ::= { upsWellKnownAlarms 7 }

upsAlarmOutputOverVoltage OBJECT-TYPE 
    SYNTAX INTEGER
    ACCESS read-only
    STATUS mandatory
    DESCRIPTION
        "Fault: An inverter output over voltage reported."
    ::= { upsWellKnownAlarms 8 }

upsAlarmUPSOverheat OBJECT-TYPE 
    SYNTAX INTEGER
    ACCESS read-only
    STATUS mandatory
    DESCRIPTION
        "Fault: Heat sink or device overheat reported."
    ::= { upsWellKnownAlarms 9 }

upsAlarmBypassOverload OBJECT-TYPE 
    SYNTAX INTEGER
    ACCESS read-only
    STATUS mandatory
    DESCRIPTION
        "Fault: A bypass overload reported."
    ::= { upsWellKnownAlarms 10 }

upsAlarmChargerOverVoltageFault OBJECT-TYPE 
    SYNTAX INTEGER
    ACCESS read-only
    STATUS mandatory
    DESCRIPTION
        "Fault: Charger over voltage reported."
    ::= { upsWellKnownAlarms 11 }

upsAlarmOutputOverCurrent OBJECT-TYPE 
    SYNTAX INTEGER
    ACCESS read-only
    STATUS mandatory
    DESCRIPTION
        "Fault: A output over current reported."
    ::= { upsWellKnownAlarms 12 }

upsAlarmDCBusUnderVoltAtBoostUp OBJECT-TYPE 
    SYNTAX INTEGER
    ACCESS read-only
    STATUS mandatory
    DESCRIPTION
        "Fault: A DC bus under voltage reported during DC bus boost-up."
    ::= { upsWellKnownAlarms 13 }

upsAlarmDCBusUnderVoltAtCharge OBJECT-TYPE 
    SYNTAX INTEGER
    ACCESS read-only
    STATUS mandatory
    DESCRIPTION
        "Fault: A DC bus under voltage during DC bus charging reported."
    ::= { upsWellKnownAlarms 14 }

upsAlarmBypassOverheat OBJECT-TYPE 
    SYNTAX INTEGER
    ACCESS read-only
    STATUS mandatory
    DESCRIPTION
        "Fault: A bypass Overheat reported."
    ::= { upsWellKnownAlarms 15 }

upsAlarmResettableInverterOverload OBJECT-TYPE 
    SYNTAX INTEGER
    ACCESS read-only
    STATUS mandatory
    DESCRIPTION
        "Fault: An inverter overload reported. It is resettable."
    ::= { upsWellKnownAlarms 16 }

upsAlarmUnresettableInverterOverload OBJECT-TYPE 
    SYNTAX INTEGER
    ACCESS read-only
    STATUS mandatory
    DESCRIPTION
        "Fault: An inverter overload reported. It is not resettable."
    ::= { upsWellKnownAlarms 17 }

upsAlarmInputOverVoltage OBJECT-TYPE 
    SYNTAX INTEGER
    ACCESS read-only
    STATUS mandatory
    DESCRIPTION
        "Warning: An input over voltage reported."
    ::= { upsWellKnownAlarms 18 }

upsAlarmInputUnderVoltage OBJECT-TYPE 
    SYNTAX INTEGER
    ACCESS read-only
    STATUS mandatory
    DESCRIPTION
        "Warning: An input under voltage reported."
    ::= { upsWellKnownAlarms 19 }

upsAlarmInputFrequencyError OBJECT-TYPE 
    SYNTAX INTEGER
    ACCESS read-only
    STATUS mandatory
    DESCRIPTION
        "Warning: An input frequency error reported."
    ::= { upsWellKnownAlarms 20 }

upsAlarmBypassOverVoltage OBJECT-TYPE 
    SYNTAX INTEGER
    ACCESS read-only
    STATUS mandatory
    DESCRIPTION
        "Warning: A bypass over voltage reported."
    ::= { upsWellKnownAlarms 21 }

upsAlarmBypassUnderVoltage OBJECT-TYPE 
    SYNTAX INTEGER
    ACCESS read-only
    STATUS mandatory
    DESCRIPTION
        "Warning: A bypass under voltage reported."
    ::= { upsWellKnownAlarms 22 }

upsAlarmBypassFrequencyError OBJECT-TYPE 
    SYNTAX INTEGER
    ACCESS read-only
    STATUS mandatory
    DESCRIPTION
        "Warning: An bypass frequency error reported."
    ::= { upsWellKnownAlarms 23 }

upsAlarmDCBusUnderVoltAtBattTest OBJECT-TYPE 
    SYNTAX INTEGER
    ACCESS read-only
    STATUS mandatory
    DESCRIPTION
        "Warning: A DC bus under voltage reported during battery test"
    ::= { upsWellKnownAlarms 24 }

upsAlarmBatteryLow OBJECT-TYPE
    SYNTAX INTEGER
    ACCESS read-only
    STATUS mandatory
    DESCRIPTION
        "Warning: A Low battery reported."
    ::= { upsWellKnownAlarms 25 }

upsAlarmBatteryAtShutdownLevel OBJECT-TYPE
    SYNTAX INTEGER
    ACCESS read-only
    STATUS mandatory
    DESCRIPTION
        "Warning: A Battery shut down voltage level reported."
    ::= { upsWellKnownAlarms 26 }

upsAlarmReplaceBattery OBJECT-TYPE 
    SYNTAX INTEGER
    ACCESS read-only
    STATUS mandatory
    DESCRIPTION
        "Warning: Batteries are in need of replacement."
    ::= { upsWellKnownAlarms 27 }

upsAlarmChargerOverVoltageWarning OBJECT-TYPE 
    SYNTAX INTEGER
    ACCESS read-only
    STATUS mandatory
    DESCRIPTION
        "Warning: Charger over voltage reported."
    ::= { upsWellKnownAlarms 28 }

upsAlarmBatteryTestFailed OBJECT-TYPE 
    SYNTAX INTEGER
    ACCESS read-only
    STATUS mandatory
    DESCRIPTION
        "Warning: A battery test failed event reported."
    ::= { upsWellKnownAlarms 29 }

upsAlarmBatteryDepleted OBJECT-TYPE
    SYNTAX INTEGER
    ACCESS read-only
    STATUS mandatory
    DESCRIPTION
        "Warning: A battery depleted event reported. It will not be able to support critical loads."
    ::= { upsWellKnownAlarms 30 }

upsAlarmBatteryOverheat OBJECT-TYPE 
    SYNTAX INTEGER
    ACCESS read-only
    STATUS mandatory
    DESCRIPTION
        "Warning: A Battery overheat reported."
    ::= { upsWellKnownAlarms 31 }

upsAlarmSystemOverheat OBJECT-TYPE 
    SYNTAX INTEGER
    ACCESS read-only
    STATUS mandatory
    DESCRIPTION
        "Warning: A system overheat reported."
    ::= { upsWellKnownAlarms 32 }

upsAlarmOutputOverloadWarning OBJECT-TYPE 
    SYNTAX INTEGER
    ACCESS read-only
    STATUS mandatory
    DESCRIPTION
        "Warning: An inverter output overload reported. UPS will switch to bypass operation or shut down if no action is taken. Shut down excess equipment to reduce Load."
    ::= { upsWellKnownAlarms 33 }

upsAlarmUserDefinedOverloadWarning OBJECT-TYPE 
    SYNTAX INTEGER
    ACCESS read-only
    STATUS mandatory
    DESCRIPTION
        "Warning: The inverter output load % is greater than the user defined overload set point (default: 110%)."
    ::= { upsWellKnownAlarms 34 }
	
upsAlarmCurrentLimitWarning OBJECT-TYPE 
    SYNTAX INTEGER
    ACCESS read-only
    STATUS mandatory
    DESCRIPTION
        "Warning: A current limit reported."
    ::= { upsWellKnownAlarms 35 }

upsAlarmAsyncOperation OBJECT-TYPE 
    SYNTAX INTEGER
    ACCESS read-only
    STATUS mandatory
    DESCRIPTION
        "Warning: An Asynchronous operation reported."
    ::= { upsWellKnownAlarms 36 }

upsAlarmServiceUPS OBJECT-TYPE 
    SYNTAX INTEGER
    ACCESS read-only
    STATUS mandatory
    DESCRIPTION
        "Warning: UPS is in need of service. Please contact authorized Toshiba service center for assistance."
    ::= { upsWellKnownAlarms 37 }

upsAlarmBatteryNearExpiration OBJECT-TYPE 
    SYNTAX INTEGER
    ACCESS read-only
    STATUS mandatory
    DESCRIPTION
        "Warning: Batteries are nearing the end of their expected lifetime."
    ::= { upsWellKnownAlarms 38 }

upsAlarmBatteryExpired OBJECT-TYPE 
    SYNTAX INTEGER
    ACCESS read-only
    STATUS mandatory
    DESCRIPTION
        "Warning: Batteries have reached their expected lifetime."
    ::= { upsWellKnownAlarms 39 }

upsAlarmDisplayCableError OBJECT-TYPE 
    SYNTAX INTEGER
    ACCESS read-only
    STATUS mandatory
    DESCRIPTION
        "Warning: A display cable error reported."
    ::= { upsWellKnownAlarms 40 }

upsAlarmRemotEyeCommError OBJECT-TYPE 
    SYNTAX INTEGER
    ACCESS read-only
    STATUS mandatory
    DESCRIPTION
        "Warning: A Communication error between the main control and the RemotEye reported."
    ::= { upsWellKnownAlarms 41 }

upsAlarmRemotEyeUplinkCommError OBJECT-TYPE 
    SYNTAX INTEGER
    ACCESS read-only
    STATUS mandatory
    DESCRIPTION
        "Warning: A communication error between the RemotEye 4 and the network reported."
    ::= { upsWellKnownAlarms 42 }

upsAlarmServicePortCommError OBJECT-TYPE 
    SYNTAX INTEGER
    ACCESS read-only
    STATUS mandatory
    DESCRIPTION
        "Warning: A communication error between the main controller and the service communication 
         port reported."
    ::= { upsWellKnownAlarms 43 }

upsAlarmDispCommError OBJECT-TYPE 
    SYNTAX INTEGER
    ACCESS read-only
    STATUS mandatory
    DESCRIPTION
        "Warning: A communication error between the main controller and display controller reported."
    ::= { upsWellKnownAlarms 44 }

upsAlarmSystemTestFailed OBJECT-TYPE 
    SYNTAX INTEGER
    ACCESS read-only
    STATUS mandatory
    DESCRIPTION
        "Warning: A system test failed event reported."
    ::= { upsWellKnownAlarms 45 }

upsAlarmOnBypass OBJECT-TYPE 
    SYNTAX INTEGER
    ACCESS read-only
    STATUS mandatory
    DESCRIPTION
        "Warning: The UPS is in Stop (Bypass) mode"
    ::= { upsWellKnownAlarms 46 }

upsAlarmPowerFailure OBJECT-TYPE 
    SYNTAX INTEGER
    ACCESS read-only
    STATUS mandatory
    DESCRIPTION
        "Info: A power failure reported."
    ::= { upsWellKnownAlarms 47 }

upsAlarmShutdownPending OBJECT-TYPE 
    SYNTAX INTEGER
    ACCESS read-only
    STATUS mandatory
    DESCRIPTION
        "Info: An output shut down in progress reported. Output will turn off after delay."
    ::= { upsWellKnownAlarms 48 }

upsAlarmOutputOffAsRequested OBJECT-TYPE 
    SYNTAX INTEGER
    ACCESS read-only
    STATUS mandatory
    DESCRIPTION
        "Info: An output shut down mode requested."
    ::= { upsWellKnownAlarms 49 }

upsAlarmOutputOff OBJECT-TYPE 
    SYNTAX INTEGER
    ACCESS read-only
    STATUS mandatory
    DESCRIPTION
        "Info: An output off reported."
    ::= { upsWellKnownAlarms 50 }

upsAlarmBatteryTestInProgress OBJECT-TYPE 
    SYNTAX INTEGER
    ACCESS read-only
    STATUS mandatory
    DESCRIPTION
        "Info: A battery test in progress reported."
    ::= { upsWellKnownAlarms 51 }

upsAlarmOnBattery OBJECT-TYPE
    SYNTAX INTEGER
    ACCESS read-only
    STATUS mandatory
    DESCRIPTION
        "Info: The UPS is on Battery mode; it is supplying output power from its batteries."
    ::= { upsWellKnownAlarms 52 }

upsAlarmExtBattCab1String1Disconnected OBJECT-TYPE
    SYNTAX INTEGER
    ACCESS read-only
    STATUS mandatory
    DESCRIPTION
        "Warning: Matching battery cabinet 1, battery string 1 is disconnected."
    ::= { upsWellKnownAlarms 53 }

upsAlarmExtBattCab1String2Disconnected OBJECT-TYPE
    SYNTAX INTEGER
    ACCESS read-only
    STATUS mandatory
    DESCRIPTION
        "Warning: Matching battery cabinet 1, battery string 2 is disconnected."
    ::= { upsWellKnownAlarms 54 }

upsAlarmExtBattCab1String3Disconnected OBJECT-TYPE
    SYNTAX INTEGER
    ACCESS read-only
    STATUS mandatory
    DESCRIPTION
        "Warning: Matching battery cabinet 1, battery string 3 is disconnected."
    ::= { upsWellKnownAlarms 55 }

upsAlarmExtBattCab1String1LooseHCTConnection OBJECT-TYPE
    SYNTAX INTEGER
    ACCESS read-only
    STATUS mandatory
    DESCRIPTION
        "Fault: Matching battery cabinet 1, battery string 1 loose HCT connection."
    ::= { upsWellKnownAlarms 56 }

upsAlarmExtBattCab1String2LooseHCTConnection OBJECT-TYPE
    SYNTAX INTEGER
    ACCESS read-only
    STATUS mandatory
    DESCRIPTION
        "Fault: Matching battery cabinet 1, battery string 2 loose HCT connection."
    ::= { upsWellKnownAlarms 57 }

upsAlarmExtBattCab1String3LooseHCTConnection OBJECT-TYPE
    SYNTAX INTEGER
    ACCESS read-only
    STATUS mandatory
    DESCRIPTION
        "Fault: Matching battery cabinet 1, battery string 3 loose HCT connection."
    ::= { upsWellKnownAlarms 58 }

upsAlarmExtBattCab1OverTemperatureWarning OBJECT-TYPE
    SYNTAX INTEGER
    ACCESS read-only
    STATUS mandatory
    DESCRIPTION
        "Warning: Matching battery cabinet 1 over temperature."
    ::= { upsWellKnownAlarms 59 }

upsAlarmExtBattCab1ChargerOverVoltageFault OBJECT-TYPE
    SYNTAX INTEGER
    ACCESS read-only
    STATUS mandatory
    DESCRIPTION
        "Fault: Matching battery cabinet 1 charger over voltage fault."
    ::= { upsWellKnownAlarms 60 }

upsAlarmExtBattCab1ChargerOverCurrentFault OBJECT-TYPE
    SYNTAX INTEGER
    ACCESS read-only
    STATUS mandatory
    DESCRIPTION
        "Fault: Matching battery cabinet 1 charger over current fault."
    ::= { upsWellKnownAlarms 61 }

upsAlarmExtBattCab1LostCommunication OBJECT-TYPE
    SYNTAX INTEGER
    ACCESS read-only
    STATUS mandatory
    DESCRIPTION
        "Warning: Matching battery cabinet 1 lost communication."
    ::= { upsWellKnownAlarms 62 }

upsAlarmExtBattCab2String1Disconnected OBJECT-TYPE
    SYNTAX INTEGER
    ACCESS read-only
    STATUS mandatory
    DESCRIPTION
        "Warning: Matching battery cabinet 2, battery string 1 is disconnected."
    ::= { upsWellKnownAlarms 63 }

upsAlarmExtBattCab2String2Disconnected OBJECT-TYPE
    SYNTAX INTEGER
    ACCESS read-only
    STATUS mandatory
    DESCRIPTION
        "Warning: Matching battery cabinet 2, battery string 2 is disconnected."
    ::= { upsWellKnownAlarms 64 }

upsAlarmExtBattCab2String3Disconnected OBJECT-TYPE
    SYNTAX INTEGER
    ACCESS read-only
    STATUS mandatory
    DESCRIPTION
        "Warning: Matching battery cabinet 2, battery string 3 is disconnected."
    ::= { upsWellKnownAlarms 65 }

upsAlarmExtBattCab2String1LooseHCTConnection OBJECT-TYPE
    SYNTAX INTEGER
    ACCESS read-only
    STATUS mandatory
    DESCRIPTION
        "Fault: Matching battery cabinet 2, battery string 1 loose HCT connection."
    ::= { upsWellKnownAlarms 66 }

upsAlarmExtBattCab2String2LooseHCTConnection OBJECT-TYPE
    SYNTAX INTEGER
    ACCESS read-only
    STATUS mandatory
    DESCRIPTION
        "Fault: Matching battery cabinet 2, battery string 2 loose HCT connection."
    ::= { upsWellKnownAlarms 67 }

upsAlarmExtBattCab2String3LooseHCTConnection OBJECT-TYPE
    SYNTAX INTEGER
    ACCESS read-only
    STATUS mandatory
    DESCRIPTION
        "Fault: Matching battery cabinet 2, battery string 3 loose HCT connection."
    ::= { upsWellKnownAlarms 68 }

upsAlarmExtBattCab2OverTemperatureWarning OBJECT-TYPE
    SYNTAX INTEGER
    ACCESS read-only
    STATUS mandatory
    DESCRIPTION
        "Warning: Matching battery cabinet 2 over temperature."
    ::= { upsWellKnownAlarms 69 }

upsAlarmExtBattCab2ChargerOverVoltageFault OBJECT-TYPE
    SYNTAX INTEGER
    ACCESS read-only
    STATUS mandatory
    DESCRIPTION
        "Fault: Matching battery cabinet 2 charger over voltage fault."
    ::= { upsWellKnownAlarms 70 }

upsAlarmExtBattCab2ChargerOverCurrentFault OBJECT-TYPE
    SYNTAX INTEGER
    ACCESS read-only
    STATUS mandatory
    DESCRIPTION
        "Fault: Matching battery cabinet 2 charger over current fault."
    ::= { upsWellKnownAlarms 71 }

upsAlarmExtBattCab2LostCommunication OBJECT-TYPE
    SYNTAX INTEGER
    ACCESS read-only
    STATUS mandatory
    DESCRIPTION
        "Warning: Matching battery cabinet 2 lost communication."
    ::= { upsWellKnownAlarms 72 }


upsAlarmLogInError OBJECT-TYPE
    SYNTAX INTEGER
    ACCESS read-only
    STATUS mandatory
    DESCRIPTION
        "Info: The UPS Admin Password is incorrect."
    ::= { upsWellKnownAlarms 73 }

-- ===========================================================================
-- upsPassword  ups1600XP-i Group 11
-- The UPS Password group
-- ===========================================================================
upsPwdAdminCurrentAccessLevel OBJECT-TYPE
    SYNTAX DisplayString (SIZE (0..15))
    ACCESS read-only
    STATUS mandatory
    DESCRIPTION
        "The UPS administrator access level."
    ::= { upsPassword 1 }

upsPwdAdminCurrentPwd OBJECT-TYPE
    SYNTAX DisplayString (SIZE (0..15))
    ACCESS read-write
    STATUS mandatory
    DESCRIPTION
        "The UPS current password."
    ::= { upsPassword 2 }

upsPwdAdminNewPwd OBJECT-TYPE
    SYNTAX DisplayString (SIZE (0..7))
    ACCESS read-write
    STATUS mandatory
    DESCRIPTION
        "The UPS current password."
    ::= { upsPassword 3 }


-- ===========================================================================
-- upsTraps - Group 12
-- Traps group
-- ===========================================================================
upsTrapFault TRAP-TYPE
    ENTERPRISE ups1600XP-i 
    DESCRIPTION
        "Fault: One or more fault reported."
   --#TYPE "Fault: One or more fault reported."
   --#SUMMARY "Fault: One or more fault reported."
   --#SEVERITY INFORMATIONAL
   --#TIMEINDEX 1
   --#HELP ""
   --#HELPTAG 0
   --#STATE OPERATIONAL
    ::= 1

upsTrapFaultClear TRAP-TYPE
    ENTERPRISE ups1600XP-i 
    DESCRIPTION
        "Fault Clear: One or more fault reported."
   --#TYPE "Fault Clear: One or more fault reported."
   --#SUMMARY "Fault Clear: One or more fault reported."
   --#SEVERITY INFORMATIONAL
   --#TIMEINDEX 1
   --#HELP ""
   --#HELPTAG 0
   --#STATE OPERATIONAL
    ::= 2

upsTrapOpenFuse TRAP-TYPE 
    ENTERPRISE ups1600XP-i
    DESCRIPTION
        "Fault: An open fuse reported."
   --#TYPE "Fault: An open fuse reported."
   --#SUMMARY "Fault: An open fuse reported."
   --#SEVERITY INFORMATIONAL
   --#TIMEINDEX 1
   --#HELP ""
   --#HELPTAG 0
   --#STATE OPERATIONAL
    ::= 3

upsTrapOpenFuseClear TRAP-TYPE 
    ENTERPRISE ups1600XP-i
    DESCRIPTION
        "Fault Clear: An open fuse reported."
   --#TYPE "Fault Clear: An open fuse reported."
   --#SUMMARY "Fault Clear: An open fuse reported."
   --#SEVERITY INFORMATIONAL
   --#TIMEINDEX 1
   --#HELP ""
   --#HELPTAG 0
   --#STATE OPERATIONAL
    ::= 4

upsTrapCurrentLimitFault TRAP-TYPE
    ENTERPRISE ups1600XP-i
    DESCRIPTION
        "Fault: A current limit fault reported. Contact your Toshiba authorized service center for examination."
   --#TYPE "Fault: A current limit fault reported. Contact your Toshiba authorized service center for examination."
   --#SUMMARY "Fault: A current limit fault reported. Contact your Toshiba authorized service center for examination."
   --#SEVERITY INFORMATIONAL
   --#TIMEINDEX 1
   --#HELP ""
   --#HELPTAG 0
   --#STATE OPERATIONAL
    ::= 5

upsTrapCurrentLimitFaultClear TRAP-TYPE
    ENTERPRISE ups1600XP-i
    DESCRIPTION
        "Fault Clear: A current limit fault reported. Contact your Toshiba authorized service center for examination."
   --#TYPE "Fault Clear: A current limit fault reported. Contact your Toshiba authorized service center for examination."
   --#SUMMARY "Fault Clear: A current limit fault reported. Contact your Toshiba authorized service center for examination."
   --#SEVERITY INFORMATIONAL
   --#TIMEINDEX 1
   --#HELP ""
   --#HELPTAG 0
   --#STATE OPERATIONAL
    ::= 6

upsTrapDCBusOverCurrent TRAP-TYPE 
    ENTERPRISE ups1600XP-i
    DESCRIPTION
        "Fault: A DC bus over current reported. Contact your Toshiba authorized service center for examination."
   --#TYPE "Fault: A DC bus over current reported. Contact your Toshiba authorized service center for examination."
   --#SUMMARY "Fault: A DC bus over current reported. Contact your Toshiba authorized service center for examination."
   --#SEVERITY INFORMATIONAL
   --#TIMEINDEX 1
   --#HELP ""
   --#HELPTAG 0
   --#STATE OPERATIONAL
    ::= 7

upsTrapDCBusOverCurrentClear TRAP-TYPE 
    ENTERPRISE ups1600XP-i
    DESCRIPTION
        "Fault Clear: A DC bus over current reported. Contact your Toshiba authorized service center for examination."
   --#TYPE "Fault Clear: A DC bus over current reported. Contact your Toshiba authorized service center for examination."
   --#SUMMARY "Fault Clear: A DC bus over current reported. Contact your Toshiba authorized service center for examination."
   --#SEVERITY INFORMATIONAL
   --#TIMEINDEX 1
   --#HELP ""
   --#HELPTAG 0
   --#STATE OPERATIONAL
    ::= 8

upsTrapDCBusOverVoltage TRAP-TYPE 
    ENTERPRISE ups1600XP-i
    DESCRIPTION
        "Fault: A DC bus over voltage reported. Contact your Toshiba authorized service center for examination."
   --#TYPE "Fault: A DC bus over voltage reported. Contact your Toshiba authorized service center for examination."
   --#SUMMARY "Fault: A DC bus over voltage reported. Contact your Toshiba authorized service center for examination."
   --#SEVERITY INFORMATIONAL
   --#TIMEINDEX 1
   --#HELP ""
   --#HELPTAG 0
   --#STATE OPERATIONAL
    ::= 9

upsTrapDCBusOverVoltageClear TRAP-TYPE 
    ENTERPRISE ups1600XP-i
    DESCRIPTION
        "Fault Clear: A DC bus over voltage reported. Contact your Toshiba authorized service center for examination."
   --#TYPE "Fault Clear: A DC bus over voltage reported. Contact your Toshiba authorized service center for examination."
   --#SUMMARY "Fault Clear: A DC bus over voltage reported. Contact your Toshiba authorized service center for examination."
   --#SEVERITY INFORMATIONAL
   --#TIMEINDEX 1
   --#HELP ""
   --#HELPTAG 0
   --#STATE OPERATIONAL
    ::= 10

upsTrapDCBusImbalance TRAP-TYPE 
    ENTERPRISE ups1600XP-i
    DESCRIPTION
        "Fault: A DC bus imbalance reported. Contact your Toshiba authorized service center for examination."
   --#TYPE "Fault: A DC bus imbalance reported. Contact your Toshiba authorized service center for examination."
   --#SUMMARY "Fault: A DC bus imbalance reported. Contact your Toshiba authorized service center for examination."
   --#SEVERITY INFORMATIONAL
   --#TIMEINDEX 1
   --#HELP ""
   --#HELPTAG 0
   --#STATE OPERATIONAL
    ::= 11

upsTrapDCBusImbalanceClear TRAP-TYPE 
    ENTERPRISE ups1600XP-i
    DESCRIPTION
        "Fault Clear: A DC bus imbalance reported. Contact your Toshiba authorized service center for examination."
   --#TYPE "Fault Clear: A DC bus imbalance reported. Contact your Toshiba authorized service center for examination."
   --#SUMMARY "Fault Clear: A DC bus imbalance reported. Contact your Toshiba authorized service center for examination."
   --#SEVERITY INFORMATIONAL
   --#TIMEINDEX 1
   --#HELP ""
   --#HELPTAG 0
   --#STATE OPERATIONAL
    ::= 12

upsTrapOutputUnderVoltage TRAP-TYPE 
    ENTERPRISE ups1600XP-i
    DESCRIPTION
        "Fault: An output under voltage reported. Contact your Toshiba authorized service center for examination."
   --#TYPE "Fault: An output under voltage reported. Contact your Toshiba authorized service center for examination."
   --#SUMMARY "Fault: An output under voltage reported. Contact your Toshiba authorized service center for examination."
   --#SEVERITY INFORMATIONAL
   --#TIMEINDEX 1
   --#HELP ""
   --#HELPTAG 0
   --#STATE OPERATIONAL
    ::= 13

upsTrapOutputUnderVoltageClear TRAP-TYPE 
    ENTERPRISE ups1600XP-i
    DESCRIPTION
        "Fault Clear: An output under voltage reported. Contact your Toshiba authorized service center for examination."
   --#TYPE "Fault Clear: An output under voltage reported. Contact your Toshiba authorized service center for examination."
   --#SUMMARY "Fault Clear: An output under voltage reported. Contact your Toshiba authorized service center for examination."
   --#SEVERITY INFORMATIONAL
   --#TIMEINDEX 1
   --#HELP ""
   --#HELPTAG 0
   --#STATE OPERATIONAL
    ::= 14

upsTrapOutputOverVoltage TRAP-TYPE 
    ENTERPRISE ups1600XP-i
    DESCRIPTION
        "Fault: An output over voltage reported. Contact your Toshiba authorized service center for examination."
   --#TYPE "Fault: An output over voltage reported. Contact your Toshiba authorized service center for examination."
   --#SUMMARY "Fault: An output over voltage reported. Contact your Toshiba authorized service center for examination."
   --#SEVERITY INFORMATIONAL
   --#TIMEINDEX 1
   --#HELP ""
   --#HELPTAG 0
   --#STATE OPERATIONAL
    ::= 15

upsTrapOutputOverVoltageClear TRAP-TYPE 
    ENTERPRISE ups1600XP-i
    DESCRIPTION
        "Fault Clear: An output over voltage reported. Contact your Toshiba authorized service center for examination."
   --#TYPE "Fault Clear: An output over voltage reported. Contact your Toshiba service center for examination."
   --#SUMMARY "Fault Clear: An output over voltage reported. Contact your Toshiba authorized service center for examination."
   --#SEVERITY INFORMATIONAL
   --#TIMEINDEX 1
   --#HELP ""
   --#HELPTAG 0
   --#STATE OPERATIONAL
    ::= 16

upsTrapUPSOverheat TRAP-TYPE 
    ENTERPRISE ups1600XP-i
    DESCRIPTION
        "Fault: A Heat sink or device overheat reported."
   --#TYPE "Fault: A Heat sink or device overheat reported."
   --#SUMMARY "Fault: A Heat sink or device overheat reported."
   --#SEVERITY INFORMATIONAL
   --#TIMEINDEX 1
   --#HELP ""
   --#HELPTAG 0
   --#STATE OPERATIONAL
    ::= 17

upsTrapUPSOverheatClear TRAP-TYPE 
    ENTERPRISE ups1600XP-i
    DESCRIPTION
        "Fault Clear: A Heat sink or device overheat reported."
   --#TYPE "Fault Clear: A Heat sink or device overheat reported."
   --#SUMMARY "Fault Clear: A Heat sink or device overheat reported."
   --#SEVERITY INFORMATIONAL
   --#TIMEINDEX 1
   --#HELP ""
   --#HELPTAG 0
   --#STATE OPERATIONAL
    ::= 18

upsTrapBypassOverload TRAP-TYPE 
    ENTERPRISE ups1600XP-i 
    DESCRIPTION
        "Fault: A bypass overload reported."
   --#TYPE "Fault: A bypass overload reported."
   --#SUMMARY "Fault: A bypass overload reported."
   --#SEVERITY INFORMATIONAL
   --#TIMEINDEX 1
   --#HELP ""
   --#HELPTAG 0
   --#STATE OPERATIONAL
    ::= 19

upsTrapBypassOverloadClear TRAP-TYPE 
    ENTERPRISE ups1600XP-i 
    DESCRIPTION
        "Fault Clear: A bypass overload reported."
   --#TYPE "Fault Clear: A bypass overload reported."
   --#SUMMARY "Fault Clear: A bypass overload reported."
   --#SEVERITY INFORMATIONAL
   --#TIMEINDEX 1
   --#HELP ""
   --#HELPTAG 0
   --#STATE OPERATIONAL
    ::= 20


upsTrapChargerOverVoltageFault TRAP-TYPE 
    ENTERPRISE ups1600XP-i
    DESCRIPTION
        "Warning: Charger over voltage reported."
   --#TYPE "Warning: Charger over voltage reported."
   --#SUMMARY "Warning: Charger over voltage reported."
   --#SEVERITY INFORMATIONAL
   --#TIMEINDEX 1
   --#HELP ""
   --#HELPTAG 0
   --#STATE OPERATIONAL
    ::= 21

upsTrapChargerOverVoltageFaultClear TRAP-TYPE 
    ENTERPRISE ups1600XP-i
    DESCRIPTION
        "Warning Clear: Charger over voltage reported."
   --#TYPE "Warning Clear: Charger over voltage reported."
   --#SUMMARY "Warning Clear: Charger over voltage reported."
   --#SEVERITY INFORMATIONAL
   --#TIMEINDEX 1
   --#HELP ""
   --#HELPTAG 0
   --#STATE OPERATIONAL
    ::= 22

upsTrapOutputOverCurrent TRAP-TYPE 
    ENTERPRISE ups1600XP-i
    DESCRIPTION
        "Warning: An output over current reported."
   --#TYPE "Warning: An output over current reported."
   --#SUMMARY "Warning: An output over current reported."
   --#SEVERITY INFORMATIONAL
   --#TIMEINDEX 1
   --#HELP ""
   --#HELPTAG 0
   --#STATE OPERATIONAL
    ::= 23

upsTrapOutputOverCurrentClear TRAP-TYPE 
    ENTERPRISE ups1600XP-i
    DESCRIPTION
        "Warning Clear: An output over current reported."
   --#TYPE "Warning Clear: An output over current reported."
   --#SUMMARY "Warning Clear: An output over current reported."
   --#SEVERITY INFORMATIONAL
   --#TIMEINDEX 1
   --#HELP ""
   --#HELPTAG 0
   --#STATE OPERATIONAL
    ::= 24

upsTrapDCBusUnderVoltAtBoostUp TRAP-TYPE 
    ENTERPRISE ups1600XP-i
    DESCRIPTION
        "Fault: A DC bus under voltage during boost-up reported."
   --#TYPE "Fault: A DC bus under voltage during boost-up reported."
   --#SUMMARY "Fault: A DC bus under voltage during boost-up reported."
   --#SEVERITY INFORMATIONAL
   --#TIMEINDEX 1
   --#HELP ""
   --#HELPTAG 0
   --#STATE OPERATIONAL
    ::= 25

upsTrapDCBusUnderVoltAtBoostUpClear TRAP-TYPE 
    ENTERPRISE ups1600XP-i
    DESCRIPTION
        "Fault Clear: A DC bus under voltage during boost-up reported."
   --#TYPE "Fault Clear: A DC bus under voltage during boost-up reported."
   --#SUMMARY "Fault Clear: A DC bus under voltage during boost-up reported."
   --#SEVERITY INFORMATIONAL
   --#TIMEINDEX 1
   --#HELP ""
   --#HELPTAG 0
   --#STATE OPERATIONAL
    ::= 26

upsTrapDCBusUnderVoltAtCharge TRAP-TYPE 
    ENTERPRISE ups1600XP-i
    DESCRIPTION
        "Fault: A DC bus under voltage during charging reported."
   --#TYPE "Fault: A DC bus under voltage during charging reported."
   --#SUMMARY "Fault: A DC bus under voltage during charging reported."
   --#SEVERITY INFORMATIONAL
   --#TIMEINDEX 1
   --#HELP ""
   --#HELPTAG 0
   --#STATE OPERATIONAL
    ::= 27

upsTrapDCBusUnderVoltAtChargeClear TRAP-TYPE 
    ENTERPRISE ups1600XP-i
    DESCRIPTION
        "Fault Clear: A DC bus under voltage during charging reported."
   --#TYPE "Fault Clear: A DC bus under voltage during charging reported."
   --#SUMMARY "Fault Clear: A DC bus under voltage during charging reported."
   --#SEVERITY INFORMATIONAL
   --#TIMEINDEX 1
   --#HELP ""
   --#HELPTAG 0
   --#STATE OPERATIONAL
    ::= 28

upsTrapBypassOverheat TRAP-TYPE
    ENTERPRISE ups1600XP-i
    DESCRIPTION
        "Fault: A Bypass overheat reported."
   --#TYPE "Fault: A Bypass overheat reported."
   --#SUMMARY "Fault: A Bypass overheat reported."
   --#SEVERITY INFORMATIONAL
   --#TIMEINDEX 1
   --#HELP ""
   --#HELPTAG 0
   --#STATE OPERATIONAL
    ::= 29

upsTrapBypassOverheatClear TRAP-TYPE
    ENTERPRISE ups1600XP-i
    DESCRIPTION
        "Fault Clear: A Bypass overheat reported."
   --#TYPE "Fault Clear: A Bypass overheat reported."
   --#SUMMARY "Fault Clear: A Bypass overheat reported."
   --#SEVERITY INFORMATIONAL
   --#TIMEINDEX 1
   --#HELP ""
   --#HELPTAG 0
   --#STATE OPERATIONAL
    ::= 30

upsTrapResettableInverterOverload TRAP-TYPE
    ENTERPRISE ups1600XP-i
    DESCRIPTION
        "Fault: An inverter overload reported. It is resettable."
   --#TYPE "Fault: An inverter overload reported. It is resettable."
   --#SUMMARY "Fault: An inverter overload reported. It is resettable."
   --#SEVERITY INFORMATIONAL
   --#TIMEINDEX 1
   --#HELP ""
   --#HELPTAG 0
   --#STATE OPERATIONAL
    ::= 31

upsTrapResettableInverterOverloadClear TRAP-TYPE
    ENTERPRISE ups1600XP-i
    DESCRIPTION
        "Fault Clear: An inverter overload reported. It is resettable."
   --#TYPE "Fault Clear: An inverter overload reported. It is resettable."
   --#SUMMARY "Fault Clear: An inverter overload reported. It is resettable."
   --#SEVERITY INFORMATIONAL
   --#TIMEINDEX 1
   --#HELP ""
   --#HELPTAG 0
   --#STATE OPERATIONAL
    ::= 32

upsTrapUnResettableInverterOverload TRAP-TYPE
    ENTERPRISE ups1600XP-i
    DESCRIPTION
        "Fault: An inverter overload reported. It is not resettable."
   --#TYPE "Fault: An inverter overload reported. It is not resettable."
   --#SUMMARY "Fault: An inverter overload reported. It is not resettable."
   --#SEVERITY INFORMATIONAL
   --#TIMEINDEX 1
   --#HELP ""
   --#HELPTAG 0
   --#STATE OPERATIONAL
    ::= 33

upsTrapUnResettableInverterOverloadClear TRAP-TYPE
    ENTERPRISE ups1600XP-i
    DESCRIPTION
        "Fault Clear: An inverter overload reported. It is not resettable."
   --#TYPE "Fault Clear: An inverter overload reported. It is not resettable."
   --#SUMMARY "Fault Clear: An inverter overload reported. It is not resettable."
   --#SEVERITY INFORMATIONAL
   --#TIMEINDEX 1
   --#HELP ""
   --#HELPTAG 0
   --#STATE OPERATIONAL
    ::= 34

upsTrapInputOverVoltage TRAP-TYPE 
    ENTERPRISE ups1600XP-i
    DESCRIPTION
        "Warning: An input over voltage reported."
   --#TYPE "Warning: An input over voltage reported."
   --#SUMMARY "Warning: An input over voltage reported."
   --#SEVERITY INFORMATIONAL
   --#TIMEINDEX 1
   --#HELP ""
   --#HELPTAG 0
   --#STATE OPERATIONAL
    ::= 35

upsTrapInputOverVoltageClear TRAP-TYPE 
    ENTERPRISE ups1600XP-i
    DESCRIPTION
        "Warning Clear: An input over voltage reported."
   --#TYPE "Warning Clear: An input over voltage reported."
   --#SUMMARY "Warning Clear: An input over voltage reported."
   --#SEVERITY INFORMATIONAL
   --#TIMEINDEX 1
   --#HELP ""
   --#HELPTAG 0
   --#STATE OPERATIONAL
    ::= 36

upsTrapInputUnderVoltage TRAP-TYPE 
    ENTERPRISE ups1600XP-i 
    DESCRIPTION
        "Warning: An input under voltage reported."
   --#TYPE "Warning: An input under voltage reported."
   --#SUMMARY "Warning: An input under voltage reported."
   --#SEVERITY INFORMATIONAL
   --#TIMEINDEX 1
   --#HELP ""
   --#HELPTAG 0
   --#STATE OPERATIONAL
    ::= 37

upsTrapInputUnderVoltageClear TRAP-TYPE 
    ENTERPRISE ups1600XP-i 
    DESCRIPTION
        "Warning Clear: An input under voltage reported."
   --#TYPE "Warning Clear: An input under voltage reported."
   --#SUMMARY "Warning Clear: An input under voltage reported."
   --#SEVERITY INFORMATIONAL
   --#TIMEINDEX 1
   --#HELP ""
   --#HELPTAG 0
   --#STATE OPERATIONAL
    ::= 38

upsTrapInputFrequencyError TRAP-TYPE 
    ENTERPRISE ups1600XP-i
    DESCRIPTION
        "Warning: An input frequency error reported."
   --#TYPE "Warning: An input frequency error reported."
   --#SUMMARY "Warning: An input frequency error reported."
   --#SEVERITY INFORMATIONAL
   --#TIMEINDEX 1
   --#HELP ""
   --#HELPTAG 0
   --#STATE OPERATIONAL
    ::= 39


upsTrapInputFrequencyErrorClear TRAP-TYPE 
    ENTERPRISE ups1600XP-i
    DESCRIPTION
        "Warning Clear: An input frequency error reported."
   --#TYPE "Warning Clear: An input frequency error reported."
   --#SUMMARY "Warning Clear: An input frequency error reported."
   --#SEVERITY INFORMATIONAL
   --#TIMEINDEX 1
   --#HELP ""
   --#HELPTAG 0
   --#STATE OPERATIONAL
    ::= 40
													 
upsTrapBypassOverVoltage TRAP-TYPE 
    ENTERPRISE ups1600XP-i 
    DESCRIPTION
        "Warning: A bypass over voltage reported."
   --#TYPE "Warning: A bypass over voltage reported."
   --#SUMMARY "Warning: A bypass over voltage reported."
   --#SEVERITY INFORMATIONAL
   --#TIMEINDEX 1
   --#HELP ""
   --#HELPTAG 0
   --#STATE OPERATIONAL
    ::= 41

upsTrapBypassOverVoltageClear TRAP-TYPE 
    ENTERPRISE ups1600XP-i 
    DESCRIPTION
        "Warning Clear: A bypass over voltage reported."
   --#TYPE "Warning Clear: A bypass over voltage reported."
   --#SUMMARY "Warning Clear: A bypass over voltage reported."
   --#SEVERITY INFORMATIONAL
   --#TIMEINDEX 1
   --#HELP ""
   --#HELPTAG 0
   --#STATE OPERATIONAL
    ::= 42

upsTrapBypassUnderVoltage TRAP-TYPE 
    ENTERPRISE ups1600XP-i 
    DESCRIPTION
        "Warning: A bypass under voltage reported."
   --#TYPE "Warning: A bypass under voltage reported."
   --#SUMMARY "Warning: A bypass under voltage reported."
   --#SEVERITY INFORMATIONAL
   --#TIMEINDEX 1
   --#HELP ""
   --#HELPTAG 0
   --#STATE OPERATIONAL
    ::= 43

upsTrapBypassUnderVoltageClear TRAP-TYPE 
    ENTERPRISE ups1600XP-i 
    DESCRIPTION
        "Warning Clear: A bypass under voltage reported."
   --#TYPE "Warning Clear: A bypass under voltage reported."
   --#SUMMARY "Warning Clear: A bypass under voltage reported."
   --#SEVERITY INFORMATIONAL
   --#TIMEINDEX 1
   --#HELP ""
   --#HELPTAG 0
   --#STATE OPERATIONAL
    ::= 44

upsTrapBypassFrequencyError TRAP-TYPE 
    ENTERPRISE ups1600XP-i
    DESCRIPTION
        "Warning: A bypass frequency error reported."
   --#TYPE "Warning: A bypass frequency error reported."
   --#SUMMARY "Warning: A bypass frequency error reported."
   --#SEVERITY INFORMATIONAL
   --#TIMEINDEX 1
   --#HELP ""
   --#HELPTAG 0
   --#STATE OPERATIONAL
    ::= 45

upsTrapBypassFrequencyErrorClear TRAP-TYPE 
    ENTERPRISE ups1600XP-i
    DESCRIPTION
        "Warning Clear: A bypass frequency error reported."
   --#TYPE "Warning Clear: A bypass frequency error reported."
   --#SUMMARY "Warning Clear: A bypass frequency error reported."
   --#SEVERITY INFORMATIONAL
   --#TIMEINDEX 1
   --#HELP ""
   --#HELPTAG 0
   --#STATE OPERATIONAL
    ::= 46

upsTrapDCBusUnderVoltAtBattTest TRAP-TYPE 
    ENTERPRISE ups1600XP-i
    DESCRIPTION
        "Warning: A DC bus under voltage during battery test reported."
   --#TYPE "Warning: A DC bus under voltage during battery test reported."
   --#SUMMARY "Warning: A DC bus under voltage during battery test reported."
   --#SEVERITY INFORMATIONAL
   --#TIMEINDEX 1
   --#HELP ""
   --#HELPTAG 0
   --#STATE OPERATIONAL
    ::= 47

upsTrapDCBusUnderVoltAtTestClear TRAP-TYPE 
    ENTERPRISE ups1600XP-i
    DESCRIPTION
        "Warning Clear: A DC bus under voltage during battery test reported."
   --#TYPE "Warning Clear: A DC bus under voltage during battery test reported."
   --#SUMMARY "Warning Clear: A DC bus under voltage during battery test reported."
   --#SEVERITY INFORMATIONAL
   --#TIMEINDEX 1
   --#HELP ""
   --#HELPTAG 0
   --#STATE OPERATIONAL
    ::= 48

upsTrapBatteryLow TRAP-TYPE
    ENTERPRISE ups1600XP-i
    DESCRIPTION
        "Warning: A low battery level reported."
   --#TYPE "Warning: A low battery level reported."
   --#SUMMARY "Warning: A low battery level reported."
   --#SEVERITY INFORMATIONAL
   --#TIMEINDEX 1
   --#HELP ""
   --#HELPTAG 0
   --#STATE OPERATIONAL
    ::= 49

upsTrapBatteryLowClear TRAP-TYPE
    ENTERPRISE ups1600XP-i
    DESCRIPTION
        "Warning Clear: A low battery level reported."
   --#TYPE "Warning Clear: A low battery level reported."
   --#SUMMARY "Warning Clear: A low battery level reported."
   --#SEVERITY INFORMATIONAL
   --#TIMEINDEX 1
   --#HELP ""
   --#HELPTAG 0
   --#STATE OPERATIONAL
    ::= 50

upsTrapBatteryAtShutdownLevel TRAP-TYPE
    ENTERPRISE ups1600XP-i
    DESCRIPTION
        "Warning: A shut down battery level reported."
   --#TYPE "Warning: A shut down battery level reported."
   --#SUMMARY "Warning: A shut down battery level reported."
   --#SEVERITY INFORMATIONAL
   --#TIMEINDEX 1
   --#HELP ""
   --#HELPTAG 0
   --#STATE OPERATIONAL
    ::= 51

upsTrapBatteryAtShutdownLevelClear TRAP-TYPE
    ENTERPRISE ups1600XP-i
    DESCRIPTION
        "Warning Clear: A shut down battery level reported."
   --#TYPE "Warning Clear: A shut down battery level reported."
   --#SUMMARY "Warning Clear: A shut down battery level reported."
   --#SEVERITY INFORMATIONAL
   --#TIMEINDEX 1
   --#HELP ""
   --#HELPTAG 0
   --#STATE OPERATIONAL
    ::= 52

upsTrapReplaceBattery TRAP-TYPE 
    ENTERPRISE ups1600XP-i
    DESCRIPTION
        "Warning: A replacement of batteries reported."
   --#TYPE "Warning: A replacement of batteries reported."
   --#SUMMARY "Warning: A replacement of batteries reported."
   --#SEVERITY INFORMATIONAL
   --#TIMEINDEX 1
   --#HELP ""
   --#HELPTAG 0
   --#STATE OPERATIONAL
    ::= 53

upsTrapReplaceBatteryClear TRAP-TYPE 
    ENTERPRISE ups1600XP-i
    DESCRIPTION
        "Warning Clear: A replacement of batteries reported."
   --#TYPE "Warning Clear: A replacement of batteries reported."
   --#SUMMARY "Warning Clear: A replacement of batteries reported."
   --#SEVERITY INFORMATIONAL
   --#TIMEINDEX 1
   --#HELP ""
   --#HELPTAG 0
   --#STATE OPERATIONAL
    ::= 54

upsTrapChargerOverVoltageWarning TRAP-TYPE 
    ENTERPRISE ups1600XP-i
    DESCRIPTION
        "Warning: A charger over voltage reported."
   --#TYPE "Warning: A charger over voltage reported."
   --#SUMMARY "Warning: A charger over voltage reported."
   --#SEVERITY INFORMATIONAL
   --#TIMEINDEX 1
   --#HELP ""
   --#HELPTAG 0
   --#STATE OPERATIONAL
    ::= 55

upsTrapChargerOverVoltageWarningClear TRAP-TYPE 
    ENTERPRISE ups1600XP-i
    DESCRIPTION
        "Warning Clear: A charger over voltage reported."
   --#TYPE "Warning Clear: A charger over voltage reported."
   --#SUMMARY "Warning Clear: A charger over voltage reported."
   --#SEVERITY INFORMATIONAL
   --#TIMEINDEX 1
   --#HELP ""
   --#HELPTAG 0
   --#STATE OPERATIONAL
    ::= 56

upsTrapBatteryTestFailed TRAP-TYPE 
    ENTERPRISE ups1600XP-i
    DESCRIPTION
        "Warning: A battery test failed event reported."
   --#TYPE "Warning: A battery test failed event reported."
   --#SUMMARY "Warning: A battery test failed event reported."
   --#SEVERITY INFORMATIONAL
   --#TIMEINDEX 1
   --#HELP ""
   --#HELPTAG 0
   --#STATE OPERATIONAL
    ::= 57

upsTrapBatteryTestFailedClear TRAP-TYPE 
    ENTERPRISE ups1600XP-i
    DESCRIPTION
        "Warning Clear: A battery test failed event reported."
   --#TYPE "Warning Clear: A battery test failed event reported."
   --#SUMMARY "Warning Clear: A battery test failed event reported."
   --#SEVERITY INFORMATIONAL
   --#TIMEINDEX 1
   --#HELP ""
   --#HELPTAG 0
   --#STATE OPERATIONAL
    ::= 58

upsTrapBatteryDepleted TRAP-TYPE
    ENTERPRISE ups1600XP-i
    DESCRIPTION
        "Warning: A battery depleted event reported."
   --#TYPE "Warning: A battery depleted event reported."
   --#SUMMARY "Warning: A battery depleted event reported."
   --#SEVERITY INFORMATIONAL
   --#TIMEINDEX 1
   --#HELP ""
   --#HELPTAG 0
   --#STATE OPERATIONAL
    ::= 59

upsTrapBatteryDepletedClear TRAP-TYPE
    ENTERPRISE ups1600XP-i
    DESCRIPTION
        "Warning Clear: A battery depleted event reported."
   --#TYPE "Warning Clear: A battery depleted event reported."
   --#SUMMARY "Warning Clear: A battery depleted event reported."
   --#SEVERITY INFORMATIONAL
   --#TIMEINDEX 1
   --#HELP ""
   --#HELPTAG 0
   --#STATE OPERATIONAL
    ::= 60

upsTrapBatteryOverheat TRAP-TYPE
    ENTERPRISE ups1600XP-i
    DESCRIPTION
        "Warning: A battery overheat reported."
   --#TYPE "Warning: A battery overheat reported."
   --#SUMMARY "Warning: A battery overheat reported."
   --#SEVERITY INFORMATIONAL
   --#TIMEINDEX 1
   --#HELP ""
   --#HELPTAG 0
   --#STATE OPERATIONAL
    ::= 61

upsTrapBatteryOverheatClear TRAP-TYPE
    ENTERPRISE ups1600XP-i
    DESCRIPTION
        "Warning Clear: A battery overheat reported."
   --#TYPE "Warning Clear: A battery overheat reported."
   --#SUMMARY "Warning Clear: A battery overheat reported."
   --#SEVERITY INFORMATIONAL
   --#TIMEINDEX 1
   --#HELP ""
   --#HELPTAG 0
   --#STATE OPERATIONAL
    ::= 62

upsTrapSystemOverheat TRAP-TYPE 
    ENTERPRISE ups1600XP-i
    DESCRIPTION
        "Warning: A system overheat reported."
   --#TYPE "Warning: A system overheat reported."
   --#SUMMARY "Warning: A system overheat reported."
   --#SEVERITY INFORMATIONAL
   --#TIMEINDEX 1
   --#HELP ""
   --#HELPTAG 0
   --#STATE OPERATIONAL
    ::= 63

upsTrapSystemOverheatClear TRAP-TYPE 
    ENTERPRISE ups1600XP-i
    DESCRIPTION
        "Warning Clear: A system overheat reported."
   --#TYPE "Warning Clear: A system overheat reported."
   --#SUMMARY "Warning Clear: A system overheat reported."
   --#SEVERITY INFORMATIONAL
   --#TIMEINDEX 1
   --#HELP ""
   --#HELPTAG 0
   --#STATE OPERATIONAL
    ::= 64

upsTrapOutputOverloadWarning TRAP-TYPE 
    ENTERPRISE ups1600XP-i
    DESCRIPTION
        "Warning: An output overload reported."
   --#TYPE "Warning: An output overload reported."
   --#SUMMARY "Warning: An output overload reported."
   --#SEVERITY INFORMATIONAL
   --#TIMEINDEX 1
   --#HELP ""
   --#HELPTAG 0
   --#STATE OPERATIONAL
    ::= 65

upsTrapOutputOverloadWarningClear TRAP-TYPE 
    ENTERPRISE ups1600XP-i
    DESCRIPTION
        "Warning Clear: An output overload reported."
   --#TYPE "Warning Clear: An output overload reported."
   --#SUMMARY "Warning Clear: An output overload reported."
   --#SEVERITY INFORMATIONAL
   --#TIMEINDEX 1
   --#HELP ""
   --#HELPTAG 0
   --#STATE OPERATIONAL
    ::= 66
	
upsTrapUserDefinedOverloadWarning TRAP-TYPE 
    ENTERPRISE ups1600XP-i
    DESCRIPTION
        "Warning: The inverter output load % is greater than the user defined overload set point (default: 110%)."
   --#TYPE "Warning: The inverter output load % is greater than the user defined overload set point (default: 110%)."
   --#SUMMARY "Warning: The inverter output load % is greater than the user defined overload set point (default: 110%)."
   --#SEVERITY INFORMATIONAL
   --#TIMEINDEX 1
   --#HELP ""
   --#HELPTAG 0
   --#STATE OPERATIONAL
    ::= 67
	
upsTrapUserDefinedOverloadWarningClear TRAP-TYPE 
    ENTERPRISE ups1600XP-i
    DESCRIPTION
        "Warning Clear: The inverter output load % is greater than the user defined overload set point (default: 110%)."
   --#TYPE "Warning Clear: The inverter output load % is greater than the user defined overload set point (default: 110%)."
   --#SUMMARY "Warning Clear: The inverter output load % is greater than the user defined overload set point (default: 110%)."
   --#SEVERITY INFORMATIONAL
   --#TIMEINDEX 1
   --#HELP ""
   --#HELPTAG 0
   --#STATE OPERATIONAL
    ::= 68

upsTrapCurrentLimitWarning TRAP-TYPE
    ENTERPRISE ups1600XP-i
    DESCRIPTION
        "Warning: A current limit reported."
   --#TYPE "Warning: A current limit reported."
   --#SUMMARY "Warning: A current limit reported."
   --#SEVERITY INFORMATIONAL
   --#TIMEINDEX 1
   --#HELP ""
   --#HELPTAG 0
   --#STATE OPERATIONAL
    ::= 69

upsTrapCurrentLimitWarningClear TRAP-TYPE
    ENTERPRISE ups1600XP-i
    DESCRIPTION
        "Warning Clear: A current limit reported."
   --#TYPE "Warning Clear: A current limit reported."
   --#SUMMARY "Warning Clear: A current limit reported."
   --#SEVERITY INFORMATIONAL
   --#TIMEINDEX 1
   --#HELP ""
   --#HELPTAG 0
   --#STATE OPERATIONAL
    ::= 70

upsTrapAsyncOperation TRAP-TYPE 
    ENTERPRISE ups1600XP-i
    DESCRIPTION
        "Warning: An Asynchronous operation reported."
   --#TYPE "Warning: An Asynchronous operation reported."
   --#SUMMARY "Warning: An Asynchronous operation reported."
   --#SEVERITY INFORMATIONAL
   --#TIMEINDEX 1
   --#HELP ""
   --#HELPTAG 0
   --#STATE OPERATIONAL
    ::= 71

upsTrapAsyncOperationClear TRAP-TYPE 
    ENTERPRISE ups1600XP-i
    DESCRIPTION
        "Warning Clear: An Asynchronous operation reported."
   --#TYPE "Warning Clear: An Asynchronous operation reported."
   --#SUMMARY "Warning Clear: An Asynchronous operation reported."
   --#SEVERITY INFORMATIONAL
   --#TIMEINDEX 1
   --#HELP ""
   --#HELPTAG 0
   --#STATE OPERATIONAL
    ::= 72

upsTrapServiceUPS TRAP-TYPE 
    ENTERPRISE ups1600XP-i
    DESCRIPTION
        "Warning: UPS is in need of service."
   --#TYPE "Warning: UPS is in need of service."
   --#SUMMARY "Warning: UPS is in need of service."
   --#SEVERITY INFORMATIONAL
   --#TIMEINDEX 1
   --#HELP ""
   --#HELPTAG 0
   --#STATE OPERATIONAL
    ::= 73

upsTrapServiceUPSClear TRAP-TYPE 
    ENTERPRISE ups1600XP-i
    DESCRIPTION
        "Warning Clear: UPS is in need of service."
   --#TYPE "Warning Clear: UPS is in need of service."
   --#SUMMARY "Warning Clear: UPS is in need of service."
   --#SEVERITY INFORMATIONAL
   --#TIMEINDEX 1
   --#HELP ""
   --#HELPTAG 0
   --#STATE OPERATIONAL
    ::= 74

upsTrapBatteryNearExpiration TRAP-TYPE 
    ENTERPRISE ups1600XP-i
    DESCRIPTION
        "Warning: A near expiration of batteries reported."
   --#TYPE "Warning: A near expiration of batteries reported."
   --#SUMMARY "Warning: A near expiration of batteries reported."
   --#SEVERITY INFORMATIONAL
   --#TIMEINDEX 1
   --#HELP ""
   --#HELPTAG 0
   --#STATE OPERATIONAL
    ::= 75

upsTrapBatteryNearExpirationClear TRAP-TYPE 
    ENTERPRISE ups1600XP-i
    DESCRIPTION
        "Warning Clear: A near expiration of batteries reported."
   --#TYPE "Warning Clear: A near expiration of batteries reported."
   --#SUMMARY "Warning Clear: A near expiration of batteries reported."
   --#SEVERITY INFORMATIONAL
   --#TIMEINDEX 1
   --#HELP ""
   --#HELPTAG 0
   --#STATE OPERATIONAL
    ::= 76

upsTrapBatteryExpired TRAP-TYPE 
    ENTERPRISE ups1600XP-i
    DESCRIPTION
        "Warning: A expiration of batteries reported."
   --#TYPE "Warning: A expiration of batteries reported."
   --#SUMMARY "Warning: A expiration of batteries reported."
   --#SEVERITY INFORMATIONAL
   --#TIMEINDEX 1
   --#HELP ""
   --#HELPTAG 0
   --#STATE OPERATIONAL
    ::= 77

upsTrapBatteryExpiredClear TRAP-TYPE 
    ENTERPRISE ups1600XP-i
    DESCRIPTION
        "Warning Clear: A expiration of batteries reported."
   --#TYPE "Warning Clear: A expiration of batteries reported."
   --#SUMMARY "Warning Clear: A expiration of batteries reported."
   --#SEVERITY INFORMATIONAL
   --#TIMEINDEX 1
   --#HELP ""
   --#HELPTAG 0
   --#STATE OPERATIONAL
    ::= 78

upsTrapDisplayCableError TRAP-TYPE 
    ENTERPRISE ups1600XP-i
    DESCRIPTION
        "Warning: A display cable error reported."
   --#TYPE "Warning: A display cable error reported."
   --#SUMMARY "Warning: A display cable error reported."
   --#SEVERITY INFORMATIONAL
   --#TIMEINDEX 1
   --#HELP ""
   --#HELPTAG 0
   --#STATE OPERATIONAL
    ::= 79

upsTrapDisplayCableErrorClear TRAP-TYPE 
    ENTERPRISE ups1600XP-i
    DESCRIPTION
        "Warning Clear: A display cable error reported."
   --#TYPE "Warning Clear: A display cable error reported."
   --#SUMMARY "Warning Clear: A display cable error reported."
   --#SEVERITY INFORMATIONAL
   --#TIMEINDEX 1
   --#HELP ""
   --#HELPTAG 0
   --#STATE OPERATIONAL
    ::= 80

upsTrapRemotEyeCommError TRAP-TYPE
    ENTERPRISE ups1600XP-i
    DESCRIPTION
        "Warning: A communication error between the main control and the RemotEye 4 reported."
   --#TYPE "Warning: A communication error between the main control and the RemotEye 4 reported."
   --#SUMMARY "Warning: A communication error between the main control and the RemotEye 4 reported."
   --#SEVERITY INFORMATIONAL
   --#TIMEINDEX 1
   --#HELP ""
   --#HELPTAG 0
   --#STATE OPERATIONAL
    ::= 81

upsTrapRemotEyeCommErrorClear TRAP-TYPE
    ENTERPRISE ups1600XP-i
    DESCRIPTION
        "Warning Clear: A communication error between the main control and the RemotEye 4 reported."
   --#TYPE "Warning Clear: A communication error between the main control and the RemotEye 4 reported."
   --#SUMMARY "Warning Clear: A communication error between the main control and the RemotEye 4 reported."
   --#SEVERITY INFORMATIONAL
   --#TIMEINDEX 1
   --#HELP ""
   --#HELPTAG 0
   --#STATE OPERATIONAL
    ::= 82

upsTrapRemotEyeUplinkCommError TRAP-TYPE 
    ENTERPRISE ups1600XP-i
    DESCRIPTION
        "Warning: A communication error between the RemotEye 4 and the network reported."
   --#TYPE "Warning: A communication error between the RemotEye 4 and the network reported."
   --#SUMMARY "Warning: A communication error between the RemotEye 4 and the network reported."
   --#SEVERITY INFORMATIONAL
   --#TIMEINDEX 1
   --#HELP ""
   --#HELPTAG 0
   --#STATE OPERATIONAL
    ::= 83

upsTrapRemotEyeUplinkCommErrorClear TRAP-TYPE 
    ENTERPRISE ups1600XP-i
    DESCRIPTION
        "Warning Clear: A communication error between the RemotEye 4 and the network reported."
   --#TYPE "Warning Clear: A communication error between the RemotEye 4 and the network reported."
   --#SUMMARY "Warning Clear: A communication error between the RemotEye 4 and the network reported."
   --#SEVERITY INFORMATIONAL
   --#TIMEINDEX 1
   --#HELP ""
   --#HELPTAG 0
   --#STATE OPERATIONAL
    ::= 84

upsTrapServicePortCommError TRAP-TYPE 
    ENTERPRISE ups1600XP-i
    DESCRIPTION
        "Warning: A communication error between the main controller and the service port reported."
   --#TYPE "Warning: A communication error between the main controller and the service port reported."
   --#SUMMARY "Warning: A communication error between the main controller and the service port reported."
   --#SEVERITY INFORMATIONAL
   --#TIMEINDEX 1
   --#HELP ""
   --#HELPTAG 0
   --#STATE OPERATIONAL
    ::= 85

upsTrapServicePortCommErrorClear TRAP-TYPE 
    ENTERPRISE ups1600XP-i
    DESCRIPTION
        "Warning Clear: A communication error between the main controller and the service port reported."
   --#TYPE "Warning Clear: A communication error between the main controller and the service port reported."
   --#SUMMARY "Warning Clear: A communication error between the main controller and the service port reported."
   --#SEVERITY INFORMATIONAL
   --#TIMEINDEX 1
   --#HELP ""
   --#HELPTAG 0
   --#STATE OPERATIONAL
    ::= 86

upsTrapDispCommError TRAP-TYPE 
    ENTERPRISE ups1600XP-i
    DESCRIPTION
        "Warning: A communication error between the main controller and the display controller reported."
   --#TYPE "Warning: A communication error between the main controller and the display controller reported."
   --#SUMMARY "Warning: A communication error between the main controller and the display controller reported."
   --#SEVERITY INFORMATIONAL
   --#TIMEINDEX 1
   --#HELP ""
   --#HELPTAG 0
   --#STATE OPERATIONAL
    ::= 87

upsTrapDispCommErrorClear TRAP-TYPE 
    ENTERPRISE ups1600XP-i
    DESCRIPTION
        "Warning Clear: A communication error between the main controller and the display controller reported."
   --#TYPE "Warning Clear: A communication error between the main controller and the display controller reported."
   --#SUMMARY "Warning Clear: A communication error between the main controller and the display controller reported."
   --#SEVERITY INFORMATIONAL
   --#TIMEINDEX 1
   --#HELP ""
   --#HELPTAG 0
   --#STATE OPERATIONAL	 
    ::= 88

upsTrapSystemTestFailed TRAP-TYPE
    ENTERPRISE ups1600XP-i
    DESCRIPTION
        "Warning: A system test failed event reported."
   --#TYPE "Warning: A system test failed event reported."
   --#SUMMARY "Warning: A system test failed event reported."
   --#SEVERITY INFORMATIONAL
   --#TIMEINDEX 1
   --#HELP ""
   --#HELPTAG 0
   --#STATE OPERATIONAL	
    ::= 89

upsTrapSystemTestFailedClear TRAP-TYPE
    ENTERPRISE ups1600XP-i
    DESCRIPTION
        "Warning Clear: A system test failed event reported."
   --#TYPE "Warning Clear: A system test failed event reported."
   --#SUMMARY "Warning Clear: A system test failed event reported."
   --#SEVERITY INFORMATIONAL
   --#TIMEINDEX 1
   --#HELP ""
   --#HELPTAG 0
   --#STATE OPERATIONAL	
    ::= 90

upsTrapOnBypass TRAP-TYPE
    ENTERPRISE ups1600XP-i
    DESCRIPTION
        "Warning: The UPS is in Stop (Bypass) mode."
   --#TYPE "Info: The UPS is in Stop (Bypass) mode."
   --#SUMMARY "Info: The UPS is in Stop (Bypass) mode."
   --#SEVERITY INFORMATIONAL
   --#TIMEINDEX 1
   --#HELP ""
   --#HELPTAG 0
   --#STATE OPERATIONAL	
    ::= 91

upsTrapOnBypassClear TRAP-TYPE
    ENTERPRISE ups1600XP-i
    DESCRIPTION
        "Warning Clear: The UPS is in Stop (Bypass) mode."
   --#TYPE "Info Clear: The UPS is in Stop (Bypass) mode."
   --#SUMMARY "Info Clear: The UPS is in Stop (Bypass) mode."
   --#SEVERITY INFORMATIONAL
   --#TIMEINDEX 1
   --#HELP ""
   --#HELPTAG 0
   --#STATE OPERATIONAL	
    ::= 92

upsTrapPowerFailure TRAP-TYPE 
    ENTERPRISE ups1600XP-i
    DESCRIPTION
        "Info: A power failure reported."
   --#TYPE "Info: A power failure reported."
   --#SUMMARY "Info: A power failure reported."
   --#SEVERITY INFORMATIONAL
   --#TIMEINDEX 1
   --#HELP ""
   --#HELPTAG 0
   --#STATE OPERATIONAL	
    ::= 93

upsTrapPowerFailureClear TRAP-TYPE 
    ENTERPRISE ups1600XP-i
    DESCRIPTION
        "Info Clear: A power failure reported."
   --#TYPE "Info Clear: A power failure reported."
   --#SUMMARY "Info Clear: A power failure reported."
   --#SEVERITY INFORMATIONAL
   --#TIMEINDEX 1
   --#HELP ""
   --#HELPTAG 0
   --#STATE OPERATIONAL	
    ::= 94

upsTrapShutdownPending TRAP-TYPE
    ENTERPRISE ups1600XP-i
    DESCRIPTION
        "Info: A output shut down in progress reported. Output will turn off after delay."
   --#TYPE "Info: A output shut down in progress reported. Output will turn off after delay."
   --#SUMMARY "Info: A output shut down in progress reported. Output will turn off after delay."
   --#SEVERITY INFORMATIONAL
   --#TIMEINDEX 1
   --#HELP ""
   --#HELPTAG 0
   --#STATE OPERATIONAL	
    ::= 95

upsTrapShutdownPendingClear TRAP-TYPE
    ENTERPRISE ups1600XP-i
    DESCRIPTION
        "Info Clear: A output show down in progress reported. Output will turn off after delay."
   --#TYPE "Info Clear: A output shut down in progress reported. Output will turn off after delay."
   --#SUMMARY "Info Clear: A output shut down in progress reported. Output will turn off after delay."
   --#SEVERITY INFORMATIONAL
   --#TIMEINDEX 1
   --#HELP ""
   --#HELPTAG 0
   --#STATE OPERATIONAL	
    ::= 96

upsTrapOutputOffAsRequested TRAP-TYPE
    ENTERPRISE ups1600XP-i
    DESCRIPTION
        "Info: An output shut down mode requested."
   --#TYPE "Info: An output shut down mode requested."
   --#SUMMARY "Info: An output shut down mode requested."
   --#SEVERITY INFORMATIONAL
   --#TIMEINDEX 1
   --#HELP ""
   --#HELPTAG 0
   --#STATE OPERATIONAL	
    ::= 97

upsTrapOutputOffAsRequestedClear TRAP-TYPE
    ENTERPRISE ups1600XP-i
    DESCRIPTION
        "Info Clear: An output shut down mode requested."
   --#TYPE "Info Clear: An output shut down mode requested."
   --#SUMMARY "Info Clear: An output shut down mode requested."
   --#SEVERITY INFORMATIONAL
   --#TIMEINDEX 1
   --#HELP ""
   --#HELPTAG 0
   --#STATE OPERATIONAL	
    ::= 98

upsTrapOutputOff TRAP-TYPE
    ENTERPRISE ups1600XP-i
    DESCRIPTION
        "Info: The UPS system output is off."
   --#TYPE "Info: The UPS system output is off."
   --#SUMMARY "Info: The UPS system output is off."
   --#SEVERITY INFORMATIONAL
   --#TIMEINDEX 1
   --#HELP ""
   --#HELPTAG 0
   --#STATE OPERATIONAL	
    ::= 99

upsTrapOutputOffClear TRAP-TYPE
    ENTERPRISE ups1600XP-i
    DESCRIPTION
        "Info Clear: The UPS system output is off."
   --#TYPE "Info Clear: The UPS system output is off."
   --#SUMMARY "Info Clear: The UPS system output is off."
   --#SEVERITY INFORMATIONAL
   --#TIMEINDEX 1
   --#HELP ""
   --#HELPTAG 0
   --#STATE OPERATIONAL	
    ::= 100

upsTrapBatteryTestInProgress TRAP-TYPE
    ENTERPRISE ups1600XP-i
    DESCRIPTION
        "Info: A battery test in progress reported."
   --#TYPE "Info: A battery test in progress reported."
   --#SUMMARY "Info: A battery test in progress reported."
   --#SEVERITY INFORMATIONAL
   --#TIMEINDEX 1
   --#HELP ""
   --#HELPTAG 0
   --#STATE OPERATIONAL	
    ::= 101

upsTrapBatteryTestInProgressClear TRAP-TYPE
    ENTERPRISE ups1600XP-i
    DESCRIPTION
        "Info Clear: A battery test in progress reported."
   --#TYPE "Info Clear: A battery test in progress reported."
   --#SUMMARY "Info Clear: A battery test in progress reported."
   --#SEVERITY INFORMATIONAL
   --#TIMEINDEX 1
   --#HELP ""
   --#HELPTAG 0
   --#STATE OPERATIONAL	
    ::= 102

upsTrapOnBattery TRAP-TYPE
    ENTERPRISE ups1600XP-i
    DESCRIPTION
        "Info: The UPS is on Battery mode; it is supplying output power from its batteries."
   --#TYPE "Info: The UPS is on Battery mode; it is supplying output power from  its batteries."
   --#SUMMARY "Info: The UPS is on Battery mode; it is supplying output power from its batteries."
   --#SEVERITY INFORMATIONAL
   --#TIMEINDEX 1
   --#HELP ""
   --#HELPTAG 0
   --#STATE OPERATIONAL	
    ::= 103

upsTrapOnBatteryClear TRAP-TYPE
    ENTERPRISE ups1600XP-i
    DESCRIPTION
        "Info Clear: The UPS is on Battery mode; it is supplying output power from its batteries."
   --#TYPE "Info Clear: The UPS is on Battery mode; it is supplying output power from its batteries."
   --#SUMMARY "Info Clear: The UPS is on Battery mode; it is supplying output power from its batteries."
   --#SEVERITY INFORMATIONAL
   --#TIMEINDEX 1
   --#HELP ""
   --#HELPTAG 0
   --#STATE OPERATIONAL	
    ::= 104

upsTrapExtBattCab1String1Disconnected TRAP-TYPE
    ENTERPRISE ups1600XP-i
    DESCRIPTION
        "Warning: Matching battery cabinet 1, battery string 1 is disconnected."
   --#TYPE "Warning: Matching battery cabinet 1, battery string 1 is disconnected."
   --#SUMMARY "Warning: Matching battery cabinet 1, battery string 1 is disconnected."
   --#SEVERITY INFORMATIONAL
   --#TIMEINDEX 1
   --#HELP ""
   --#HELPTAG 0
   --#STATE OPERATIONAL	
    ::= 105

upsTrapExtBattCab1String1DisconnectedClear TRAP-TYPE
    ENTERPRISE ups1600XP-i
    DESCRIPTION
        "Warning Clear: Matching battery cabinet 1, battery string 1 is disconnected."
   --#TYPE "Warning Clear: Matching battery cabinet 1, battery string 1 is disconnected."
   --#SUMMARY "Warning Clear: Matching battery cabinet 1, battery string 1 is disconnected."
   --#SEVERITY INFORMATIONAL
   --#TIMEINDEX 1
   --#HELP ""
   --#HELPTAG 0
   --#STATE OPERATIONAL	
    ::= 106

upsTrapExtBattCab1String2Disconnected TRAP-TYPE
    ENTERPRISE ups1600XP-i
    DESCRIPTION
        "Warning: Matching battery cabinet 1, battery string 2 is disconnected."
   --#TYPE "Warning: Matching battery cabinet 1, battery string 2 is disconnected."
   --#SUMMARY "Warning: Matching battery cabinet 1, battery string 2 is disconnected."
   --#SEVERITY INFORMATIONAL
   --#TIMEINDEX 1
   --#HELP ""
   --#HELPTAG 0
   --#STATE OPERATIONAL	
    ::= 107

upsTrapExtBattCab1String2DisconnectedClear TRAP-TYPE
    ENTERPRISE ups1600XP-i
    DESCRIPTION
        "Warning Clear: Matching battery cabinet 1, battery string 2 is disconnected."
   --#TYPE "Warning Clear: Matching battery cabinet 1, battery string 2 is disconnected."
   --#SUMMARY "Warning Clear: Matching battery cabinet 1, battery string 2 is disconnected."
   --#SEVERITY INFORMATIONAL
   --#TIMEINDEX 1
   --#HELP ""
   --#HELPTAG 0
   --#STATE OPERATIONAL	
    ::= 108

upsTrapExtBattCab1String3Disconnected TRAP-TYPE
    ENTERPRISE ups1600XP-i
    DESCRIPTION
        "Warning: Matching battery cabinet 1, battery string 3 is disconnected."
   --#TYPE "Warning: Matching battery cabinet 1, battery string 3 is disconnected."
   --#SUMMARY " Warning: Matching battery cabinet 1, battery string 3 is disconnected."
   --#SEVERITY INFORMATIONAL
   --#TIMEINDEX 1
   --#HELP ""
   --#HELPTAG 0
   --#STATE OPERATIONAL	
    ::= 109

upsTrapExtBattCab1String3DisconnectedClear TRAP-TYPE
    ENTERPRISE ups1600XP-i
    DESCRIPTION
        "Warning Clear: Matching battery cabinet 1, battery string 3 is disconnected."
   --#TYPE "Warning Clear: Matching battery cabinet 1, battery string 3 is disconnected."
   --#SUMMARY "Warning Clear: Matching battery cabinet 1, battery string 3 is disconnected."
   --#SEVERITY INFORMATIONAL
   --#TIMEINDEX 1
   --#HELP ""
   --#HELPTAG 0
   --#STATE OPERATIONAL	
    ::= 110

upsTrapExtBattCab1String1LooseHCTConnection TRAP-TYPE
    ENTERPRISE ups1600XP-i
    DESCRIPTION
        "Fault: Matching battery cabinet 1, battery string 1 loose HCT connection."
   --#TYPE "Fault: Matching battery cabinet 1, battery string 1 loose HCT connection."
   --#SUMMARY " Fault: Matching battery cabinet 1, battery string 1 loose HCT connection."
   --#SEVERITY INFORMATIONAL
   --#TIMEINDEX 1
   --#HELP ""
   --#HELPTAG 0
   --#STATE OPERATIONAL	
    ::= 111

upsTrapExtBattCab1String1LooseHCTConnectionClear TRAP-TYPE
    ENTERPRISE ups1600XP-i
    DESCRIPTION
        "Fault Clear: Matching battery cabinet 1, battery string 1 loose HCT connection."
   --#TYPE "Fault Clear: Matching battery cabinet 1, battery string 1 loose HCT connection."
   --#SUMMARY "Fault Clear: Matching battery cabinet 1, battery string 1 loose HCT connection."
   --#SEVERITY INFORMATIONAL
   --#TIMEINDEX 1
   --#HELP ""
   --#HELPTAG 0
   --#STATE OPERATIONAL	
    ::= 112

upsTrapExtBattCab1String2LooseHCTConnection TRAP-TYPE
    ENTERPRISE ups1600XP-i
    DESCRIPTION
        "Fault: Matching battery cabinet 1, battery string 2 loose HCT connection."
   --#TYPE "Fault: Matching battery cabinet 1, battery string 2 loose HCT connection."
   --#SUMMARY "Fault: Matching battery cabinet 1, battery string 2 loose HCT connection."
   --#SEVERITY INFORMATIONAL
   --#TIMEINDEX 1
   --#HELP ""
   --#HELPTAG 0
   --#STATE OPERATIONAL	
    ::= 113

upsTrapExtBattCab1String2LooseHCTConnectionClear TRAP-TYPE
    ENTERPRISE ups1600XP-i
    DESCRIPTION
        "Fault Clear: Matching battery cabinet 1, battery string 2 loose HCT connection."
   --#TYPE "Fault Clear: Matching battery cabinet 1, battery string 2 loose HCT connection."
   --#SUMMARY "Fault Clear: Matching battery cabinet 1, battery string 2 loose HCT connection."
   --#SEVERITY INFORMATIONAL
   --#TIMEINDEX 1
   --#HELP ""
   --#HELPTAG 0
   --#STATE OPERATIONAL	
    ::= 114

upsTrapExtBattCab1String3LooseHCTConnection TRAP-TYPE
    ENTERPRISE ups1600XP-i
    DESCRIPTION
        "Fault: Matching battery cabinet 1, battery string 3 loose HCT connection."
   --#TYPE "Fault: Matching battery cabinet 1, battery string 3 loose HCT connection."
   --#SUMMARY "Fault: Matching battery cabinet 1, battery string 3 loose HCT connection."
   --#SEVERITY INFORMATIONAL
   --#TIMEINDEX 1
   --#HELP ""
   --#HELPTAG 0
   --#STATE OPERATIONAL	
    ::= 115

upsTrapExtBattCab1String3LooseHCTConnectionClear TRAP-TYPE
    ENTERPRISE ups1600XP-i
    DESCRIPTION
        "Fault Clear: Matching battery cabinet 1, battery string 3 loose HCT connection."
   --#TYPE "Fault Clear: Matching battery cabinet 1, battery string 3 loose HCT connection."
   --#SUMMARY "Fault Clear: Matching battery cabinet 1, battery string 3 loose HCT connection."
   --#SEVERITY INFORMATIONAL
   --#TIMEINDEX 1
   --#HELP ""
   --#HELPTAG 0
   --#STATE OPERATIONAL	
    ::= 116

upsTrapExtBattCab1OverTemperatureWarning TRAP-TYPE
    ENTERPRISE ups1600XP-i
    DESCRIPTION
        "Warning: Matching battery cabinet 1 over temperature."
   --#TYPE "Warning: Matching battery cabinet 1 over temperature."
   --#SUMMARY "Warning: Matching battery cabinet 1 over temperature."
   --#SEVERITY INFORMATIONAL
   --#TIMEINDEX 1
   --#HELP ""
   --#HELPTAG 0
   --#STATE OPERATIONAL	
    ::= 117

upsTrapExtBattCab1OverTemperatureWarningClear TRAP-TYPE
    ENTERPRISE ups1600XP-i
    DESCRIPTION
        "Warning Clear: Matching battery cabinet 1 over temperature."
   --#TYPE "Warning Clear: Matching battery cabinet 1 over temperature."
   --#SUMMARY "Warning Clear: Matching battery cabinet 1 over temperature."
   --#SEVERITY INFORMATIONAL
   --#TIMEINDEX 1
   --#HELP ""
   --#HELPTAG 0
   --#STATE OPERATIONAL	
    ::= 118

upsTrapExtBattCab1ChargerOverVoltageFault TRAP-TYPE
    ENTERPRISE ups1600XP-i
    DESCRIPTION
        "Fault: Matching battery cabinet 1 charger over voltage fault."
   --#TYPE "Fault: Matching battery cabinet 1 charger over voltage fault."
   --#SUMMARY "Fault: Matching battery cabinet 1 charger over voltage fault."
   --#SEVERITY INFORMATIONAL
   --#TIMEINDEX 1
   --#HELP ""
   --#HELPTAG 0
   --#STATE OPERATIONAL	
    ::= 119

upsTrapExtBattCab1ChargerOverVoltageFaultClear TRAP-TYPE
    ENTERPRISE ups1600XP-i
    DESCRIPTION
        "Fault Clear: Matching battery cabinet 1 charger over voltage fault."
   --#TYPE "Fault Clear: Matching battery cabinet 1 charger over voltage fault."
   --#SUMMARY "Fault Clear: Matching battery cabinet 1 charger over voltage fault."
   --#SEVERITY INFORMATIONAL
   --#TIMEINDEX 1
   --#HELP ""
   --#HELPTAG 0
   --#STATE OPERATIONAL	
    ::= 120

upsTrapExtBattCab1ChargerOverCurrentFault TRAP-TYPE
    ENTERPRISE ups1600XP-i
    DESCRIPTION
        "Fault: Matching battery cabinet 1 charger over current fault."
   --#TYPE "Fault: Matching battery cabinet 1 charger over current fault."
   --#SUMMARY "Fault: Matching battery cabinet 1 charger over current fault."
   --#SEVERITY INFORMATIONAL
   --#TIMEINDEX 1
   --#HELP ""
   --#HELPTAG 0
   --#STATE OPERATIONAL	
    ::= 121

upsTrapExtBattCab1ChargerOverCurrentFaultClear TRAP-TYPE
    ENTERPRISE ups1600XP-i
    DESCRIPTION
        "Fault Clear: Matching battery cabinet 1 charger over current fault."
   --#TYPE "Fault Clear: Matching battery cabinet 1 charger over current fault."
   --#SUMMARY "Fault Clear: Matching battery cabinet 1 charger over current fault."
   --#SEVERITY INFORMATIONAL
   --#TIMEINDEX 1
   --#HELP ""
   --#HELPTAG 0
   --#STATE OPERATIONAL	
    ::= 122

upsTrapExtBattCab1LostCommunication TRAP-TYPE
    ENTERPRISE ups1600XP-i
    DESCRIPTION
        "Warning: Matching battery cabinet 1 lost communication."
   --#TYPE "Warning: Matching battery cabinet 1 lost communication."
   --#SUMMARY "Warning: Matching battery cabinet 1 lost communication."
   --#SEVERITY INFORMATIONAL
   --#TIMEINDEX 1
   --#HELP ""
   --#HELPTAG 0
   --#STATE OPERATIONAL	
    ::= 123

upsTrapExtBattCab1LostCommunicationClear TRAP-TYPE
    ENTERPRISE ups1600XP-i
    DESCRIPTION
        "Warning Clear: Matching battery cabinet 1 lost communication."
   --#TYPE "Warning Clear: Matching battery cabinet 1 lost communication.”
   --#SUMMARY "Warning Clear: Matching battery cabinet 1 lost communication."
   --#SEVERITY INFORMATIONAL
   --#TIMEINDEX 1
   --#HELP ""
   --#HELPTAG 0
   --#STATE OPERATIONAL	
    ::= 124

upsTrapExtBattCab2String1Disconnected TRAP-TYPE
    ENTERPRISE ups1600XP-i
    DESCRIPTION
        "Warning: Matching battery cabinet 2, battery string 1 is disconnected."
   --#TYPE "Warning: Matching battery cabinet 2, battery string 1 is disconnected.”
   --#SUMMARY "Warning: Matching battery cabinet 2, battery string 1 is disconnected."
   --#SEVERITY INFORMATIONAL
   --#TIMEINDEX 1
   --#HELP ""
   --#HELPTAG 0
   --#STATE OPERATIONAL	
    ::= 125

upsTrapExtBattCab2String1DisconnectedClear TRAP-TYPE
    ENTERPRISE ups1600XP-i
    DESCRIPTION
        "Warning Clear: Matching battery cabinet 2, battery string 1 is disconnected."
   --#TYPE "Warning Clear: Matching battery cabinet 2, battery string 1 is disconnected.”
   --#SUMMARY "Warning Clear: Matching battery cabinet 2, battery string 1 is disconnected."
   --#SEVERITY INFORMATIONAL
   --#TIMEINDEX 1
   --#HELP ""
   --#HELPTAG 0
   --#STATE OPERATIONAL	
    ::= 126

upsTrapExtBattCab2String2Disconnected TRAP-TYPE
    ENTERPRISE ups1600XP-i
    DESCRIPTION
        "Warning: Matching battery cabinet 2, battery string 2 is disconnected."
   --#TYPE "Warning: Matching battery cabinet 2, battery string 2 is disconnected.”
   --#SUMMARY "Warning: Matching battery cabinet 2, battery string 2 is disconnected."
   --#SEVERITY INFORMATIONAL
   --#TIMEINDEX 1
   --#HELP ""
   --#HELPTAG 0
   --#STATE OPERATIONAL	
    ::= 127

upsTrapExtBattCab2String2DisconnectedClear TRAP-TYPE
    ENTERPRISE ups1600XP-i
    DESCRIPTION
        "Warning Clear: Matching battery cabinet 2, battery string 2 is disconnected."
   --#TYPE "Warning Clear: Matching battery cabinet 2, battery string 2 is disconnected.”
   --#SUMMARY "Warning Clear: Matching battery cabinet 2, battery string 2 is disconnected."
   --#SEVERITY INFORMATIONAL
   --#TIMEINDEX 1
   --#HELP ""
   --#HELPTAG 0
   --#STATE OPERATIONAL	
    ::= 128

upsTrapExtBattCab2String3Disconnected TRAP-TYPE
    ENTERPRISE ups1600XP-i
    DESCRIPTION
        "Warning: Matching battery cabinet 2, battery string 3 is disconnected."
   --#TYPE "Warning: Matching battery cabinet 2, battery string 3 is disconnected.”
   --#SUMMARY "Warning: Matching battery cabinet 2, battery string 3 is disconnected."
   --#SEVERITY INFORMATIONAL
   --#TIMEINDEX 1
   --#HELP ""
   --#HELPTAG 0
   --#STATE OPERATIONAL	
    ::= 129

upsTrapExtBattCab2String3DisconnectedClear TRAP-TYPE
    ENTERPRISE ups1600XP-i
    DESCRIPTION
        "Warning Clear: Matching battery cabinet 2, battery string 3 is disconnected."
   --#TYPE "Warning Clear: Matching battery cabinet 2, battery string 3 is disconnected.”
   --#SUMMARY "Warning Clear: Matching battery cabinet 2, battery string 3 is disconnected."
   --#SEVERITY INFORMATIONAL
   --#TIMEINDEX 1
   --#HELP ""
   --#HELPTAG 0
   --#STATE OPERATIONAL	
    ::= 130

upsTrapExtBattCab2String1LooseHCTConnection TRAP-TYPE
    ENTERPRISE ups1600XP-i
    DESCRIPTION
        "Fault: Matching battery cabinet 2, battery string 1 loose HCT connection."
   --#TYPE "Fault: Matching battery cabinet 2, battery string 1 loose HCT connection.”
   --#SUMMARY "Fault: Matching battery cabinet 2, battery string 1 loose HCT connection."
   --#SEVERITY INFORMATIONAL
   --#TIMEINDEX 1
   --#HELP ""
   --#HELPTAG 0
   --#STATE OPERATIONAL	
    ::= 131

upsTrapExtBattCab2String1LooseHCTConnectionClear TRAP-TYPE
    ENTERPRISE ups1600XP-i
    DESCRIPTION
        "Fault Clear: Matching battery cabinet 2, battery string 1 loose HCT connection."
   --#TYPE "Fault Clear: Matching battery cabinet 2, battery string 1 loose HCT connection.”
   --#SUMMARY "Fault Clear: Matching battery cabinet 2, battery string 1 loose HCT connection."
   --#SEVERITY INFORMATIONAL
   --#TIMEINDEX 1
   --#HELP ""
   --#HELPTAG 0
   --#STATE OPERATIONAL	
    ::= 132

upsTrapExtBattCab2String2LooseHCTConnection TRAP-TYPE
    ENTERPRISE ups1600XP-i
    DESCRIPTION
        "Fault: Matching battery cabinet 2, battery string 2 loose HCT connection."
   --#TYPE "Fault: Matching battery cabinet 2, battery string 2 loose HCT connection.”
   --#SUMMARY "Fault: Matching battery cabinet 2, battery string 2 loose HCT connection."
   --#SEVERITY INFORMATIONAL
   --#TIMEINDEX 1
   --#HELP ""
   --#HELPTAG 0
   --#STATE OPERATIONAL	
    ::= 133

upsTrapExtBattCab2String2LooseHCTConnectionClear TRAP-TYPE
    ENTERPRISE ups1600XP-i
    DESCRIPTION
        "Fault Clear: Matching battery cabinet 2, battery string 2 loose HCT connection."
   --#TYPE "Fault Clear: Matching battery cabinet 2, battery string 2 loose HCT connection.”
   --#SUMMARY "Fault Clear: Matching battery cabinet 2, battery string 2 loose HCT connection."
   --#SEVERITY INFORMATIONAL
   --#TIMEINDEX 1
   --#HELP ""
   --#HELPTAG 0
   --#STATE OPERATIONAL	
    ::= 134

upsTrapExtBattCab2String3LooseHCTConnection TRAP-TYPE
    ENTERPRISE ups1600XP-i
    DESCRIPTION
        "Fault: Matching battery cabinet 2, battery string 3 loose HCT connection."
   --#TYPE "Fault: Matching battery cabinet 2, battery string 3 loose HCT connection.”
   --#SUMMARY "Fault: Matching battery cabinet 2, battery string 3 loose HCT connection."
   --#SEVERITY INFORMATIONAL
   --#TIMEINDEX 1
   --#HELP ""
   --#HELPTAG 0
   --#STATE OPERATIONAL	
    ::= 135

upsTrapExtBattCab2String3LooseHCTConnectionClear TRAP-TYPE
    ENTERPRISE ups1600XP-i
    DESCRIPTION
        "Fault Clear: Matching battery cabinet 2, battery string 3 loose HCT connection."
   --#TYPE "Fault Clear: Matching battery cabinet 2, battery string 3 loose HCT connection.”
   --#SUMMARY "Fault Clear: Matching battery cabinet 2, battery string 3 loose HCT connection."
   --#SEVERITY INFORMATIONAL
   --#TIMEINDEX 1
   --#HELP ""
   --#HELPTAG 0
   --#STATE OPERATIONAL	
    ::= 136

upsTrapExtBattCab2OverTemperatureWarning TRAP-TYPE
    ENTERPRISE ups1600XP-i
    DESCRIPTION
        "Warning: Matching battery cabinet 2 over temperature."
   --#TYPE "Warning: Matching battery cabinet 2 over temperature.”
   --#SUMMARY "Warning: Matching battery cabinet 2 over temperature."
   --#SEVERITY INFORMATIONAL
   --#TIMEINDEX 1
   --#HELP ""
   --#HELPTAG 0
   --#STATE OPERATIONAL	
    ::= 137

upsTrapExtBattCab2OverTemperatureWarningClear TRAP-TYPE
    ENTERPRISE ups1600XP-i
    DESCRIPTION
        "Warning Clear: Matching battery cabinet 2 over temperature."
   --#TYPE "Warning Clear: Matching battery cabinet 2 over temperature.”
   --#SUMMARY "Warning Clear: Matching battery cabinet 2 over temperature."
   --#SEVERITY INFORMATIONAL
   --#TIMEINDEX 1
   --#HELP ""
   --#HELPTAG 0
   --#STATE OPERATIONAL	
    ::= 138

upsTrapExtBattCab2ChargerOverVoltageFault TRAP-TYPE
    ENTERPRISE ups1600XP-i
    DESCRIPTION
        "Fault: Matching battery cabinet 2 charger over voltage fault."
   --#TYPE "Fault: Matching battery cabinet 2 charger over voltage fault.”
   --#SUMMARY "Fault: Matching battery cabinet 2 charger over voltage fault."
   --#SEVERITY INFORMATIONAL
   --#TIMEINDEX 1
   --#HELP ""
   --#HELPTAG 0
   --#STATE OPERATIONAL	
    ::= 139

upsTrapExtBattCab2ChargerOverVoltageFaultClear TRAP-TYPE
    ENTERPRISE ups1600XP-i
    DESCRIPTION
        "Fault Clear: Matching battery cabinet 2 charger over voltage fault."
   --#TYPE "Fault Clear: Matching battery cabinet 2 charger over voltage fault.”
   --#SUMMARY "Fault Clear: Matching battery cabinet 2 charger over voltage fault."
   --#SEVERITY INFORMATIONAL
   --#TIMEINDEX 1
   --#HELP ""
   --#HELPTAG 0
   --#STATE OPERATIONAL	
    ::= 140

upsTrapExtBattCab2ChargerOverCurrentFault TRAP-TYPE
    ENTERPRISE ups1600XP-i
    DESCRIPTION
        "Fault: Matching battery cabinet 2 charger over current fault."
   --#TYPE "Fault: Matching battery cabinet 2 charger over current fault.”
   --#SUMMARY "Fault: Matching battery cabinet 2 charger over current fault."
   --#SEVERITY INFORMATIONAL
   --#TIMEINDEX 1
   --#HELP ""
   --#HELPTAG 0
   --#STATE OPERATIONAL	
    ::= 141

upsTrapExtBattCab2ChargerOverCurrentFaultClear TRAP-TYPE
    ENTERPRISE ups1600XP-i
    DESCRIPTION
        "Fault Clear: Matching battery cabinet 2 charger over current fault."
   --#TYPE "Fault Clear: Matching battery cabinet 2 charger over current fault.”
   --#SUMMARY "Fault Clear: Matching battery cabinet 2 charger over current fault."
   --#SEVERITY INFORMATIONAL
   --#TIMEINDEX 1
   --#HELP ""
   --#HELPTAG 0
   --#STATE OPERATIONAL	
    ::= 142

upsTrapExtBattCab2LostCommunication TRAP-TYPE
    ENTERPRISE ups1600XP-i
    DESCRIPTION
        "Warning: Matching battery cabinet 2 lost communication."
   --#TYPE "Warning: Matching battery cabinet 2 lost communication.”
   --#SUMMARY "Warning: Matching battery cabinet 2 lost communication."
   --#SEVERITY INFORMATIONAL
   --#TIMEINDEX 1
   --#HELP ""
   --#HELPTAG 0
   --#STATE OPERATIONAL	
    ::= 143

upsTrapExtBattCab2LostCommunicationClear TRAP-TYPE
    ENTERPRISE ups1600XP-i
    DESCRIPTION
        "Warning Clear: Matching battery cabinet 2 lost communication."
   --#TYPE "Warning Clear: Matching battery cabinet 2 lost communication.”
   --#SUMMARY " Warning Clear: Matching battery cabinet 2 lost communication."
   --#SEVERITY INFORMATIONAL
   --#TIMEINDEX 1
   --#HELP ""
   --#HELPTAG 0
   --#STATE OPERATIONAL	
    ::= 144

upsTrapLogInError TRAP-TYPE 
    ENTERPRISE ups1600XP-i
    DESCRIPTION
        "Info: UPS Password is incorrect."
   --#TYPE "Info: UPS Password is incorrect."
   --#SUMMARY "Info: UPS Password is incorrect."
   --#SEVERITY INFORMATIONAL
   --#TIMEINDEX 1
   --#HELP ""
   --#HELPTAG 0
   --#STATE OPERATIONAL		
    ::= 145

upsTrapLogInErrorClear TRAP-TYPE 
    ENTERPRISE ups1600XP-i
    DESCRIPTION
        "Info Clear: UPS Password is incorrect."
   --#TYPE "Info Clear: UPS Password is incorrect."
   --#SUMMARY "Info Clear: UPS Password is incorrect."
   --#SEVERITY INFORMATIONAL
   --#TIMEINDEX 1
   --#HELP ""
   --#HELPTAG 0
   --#STATE OPERATIONAL		
    ::= 146


END
