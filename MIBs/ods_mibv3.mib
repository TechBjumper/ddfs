ODS-MIB DEFINITIONS ::= BEGIN

IMPORTS


DisplayString                                                   FROM SNMPv2-TC
MODULE-IDENTITY, OBJECT-TYPE, enterprises, Gauge32,
NOTIFICATION-TYPE FROM                                          SNMPv2-SMI;

opengate MODULE-IDENTITY
	LAST-UPDATED "201003220000Z"
	ORGANIZATION "Opengate Data Systems"
	CONTACT-INFO "support@opengatedata.com"
	DESCRIPTION "The MIB for Opengate Data Systems Products"
	::= { enterprises 29414 }

-- opengate OBJECT IDENTIFIER
-- 	::= { enterprises 29414 }

ods OBJECT IDENTIFIER
	::= { opengate 1 }

deviceInfo OBJECT IDENTIFIER
	::= { ods 1 }

productTitle OBJECT-TYPE
	SYNTAX DisplayString
	MAX-ACCESS read-only
	STATUS current
	DESCRIPTION "Product name"
	::= { deviceInfo 1 }

productVersion OBJECT-TYPE
	SYNTAX DisplayString
	MAX-ACCESS read-only
	STATUS current
	DESCRIPTION "Product version"
	::= { deviceInfo 2 }

productFriendlyName OBJECT-TYPE
	SYNTAX DisplayString
	MAX-ACCESS read-only
	STATUS current
	DESCRIPTION "User-assigned name"
	::= { deviceInfo 3 }

productMacAddress OBJECT-TYPE
	SYNTAX DisplayString
	MAX-ACCESS read-only
	STATUS current
	DESCRIPTION "Product's unique MAC address"
	::= { deviceInfo 4 }

productUrl OBJECT-TYPE
	SYNTAX DisplayString
	MAX-ACCESS read-only
	STATUS current
	DESCRIPTION "Product's main URL access point"
	::= { deviceInfo 5 }

alarmTripType OBJECT-TYPE
        SYNTAX INTEGER(0..9)
        MAX-ACCESS read-only
        STATUS current
        DESCRIPTION "Type of alarm trip. 0 = None, 1 = Low, 2 = High, 3 = Unplugged"
        ::= { deviceInfo 6 }


productHardware OBJECT-TYPE
        SYNTAX DisplayString
        MAX-ACCESS read-only
        STATUS current
        DESCRIPTION "Product's hardware type"
        ::= { deviceInfo 7 }

sensorCountsBase OBJECT IDENTIFIER
	::= { deviceInfo 8 }

sensorCounts OBJECT IDENTIFIER
	::= { sensorCountsBase 1 }

climateCount OBJECT-TYPE
        SYNTAX INTEGER(0..16)
        MAX-ACCESS read-only
        STATUS current
        DESCRIPTION "Number of climate monitors currently plugged in"
        ::= { sensorCounts 2 }

dewPointSensorCount OBJECT-TYPE
        SYNTAX INTEGER(0..16)
        MAX-ACCESS read-only
        STATUS current
        DESCRIPTION "Number of dewpoint sensors currently plugged in"
        ::= { sensorCounts 3 }

fancontrolCount OBJECT-TYPE
        SYNTAX INTEGER(0..16)
        MAX-ACCESS read-only
        STATUS current
        DESCRIPTION "Number of fan controllers currently plugged in"
        ::= { sensorCounts 4 }

tempSensorCount OBJECT-TYPE
        SYNTAX INTEGER(0..16)
        MAX-ACCESS read-only
        STATUS current
        DESCRIPTION "Number of temperature sensors currently plugged in"
        ::= { sensorCounts 5 }

flowcontrolCount OBJECT-TYPE
        SYNTAX INTEGER(0..16)
        MAX-ACCESS read-only
        STATUS current
        DESCRIPTION "Number of fan controllers currently plugged in"
        ::= { sensorCounts 6 }

powerDMCount OBJECT-TYPE
        SYNTAX INTEGER(0..16)
        MAX-ACCESS read-only
        STATUS current
        DESCRIPTION "Number of DM48 current sensors currently plugged in"
        ::= { sensorCounts 7 }

climateTable OBJECT-TYPE
	SYNTAX SEQUENCE OF ClimateEntry
	MAX-ACCESS  not-accessible
	STATUS current
	DESCRIPTION "Climate sensors (internal sensors for climate units)"
	::= { ods 2 }

dewPointSensorTable OBJECT-TYPE
	SYNTAX SEQUENCE OF DewPointSensorEntry
	MAX-ACCESS  not-accessible
	STATUS current
	DESCRIPTION "A table of dew point sensors"
	::= { ods 3 }

fancontrolTable OBJECT-TYPE
	SYNTAX SEQUENCE OF FancontrolEntry
	MAX-ACCESS  not-accessible
	STATUS current
	DESCRIPTION "ODS EC Fan Controller status"
	::= { ods 4 }

tempSensorTable OBJECT-TYPE
	SYNTAX SEQUENCE OF TempSensorEntry
	MAX-ACCESS  not-accessible
	STATUS current
	DESCRIPTION "A table of temperature sensors"
	::= { ods 5 }

flowcontrolTable OBJECT-TYPE
	SYNTAX SEQUENCE OF FlowcontrolEntry
	MAX-ACCESS  not-accessible
	STATUS current
	DESCRIPTION "ODS FC Flow Controller status"
	::= { ods 6 }

powerDMTable OBJECT-TYPE
	SYNTAX SEQUENCE OF PowerDMEntry
	MAX-ACCESS  not-accessible
	STATUS current
	DESCRIPTION "A table of DM48 current monitors"
	::= { ods 7 }

climateEntry OBJECT-TYPE
	SYNTAX  ClimateEntry
	MAX-ACCESS  not-accessible
	STATUS current
	DESCRIPTION
		"Entry in the climate table: each entry contains
an index (climateIndex) and other details"
	INDEX { climateIndex }
	::= { climateTable 1 }

ClimateEntry ::= SEQUENCE {
	climateIndex		INTEGER,
	climateSerial		DisplayString,
	climateName		DisplayString,
	climateAvail		Gauge32,
	climateTempC		INTEGER,
	climateTempF		INTEGER,
	climateHumidity		INTEGER,
	climateLight		INTEGER,
	climateAirflow		INTEGER,
	climateSound		INTEGER,
	climateIO1		INTEGER,
	climateIO2		INTEGER,
	climateIO3		INTEGER
}

climateIndex OBJECT-TYPE
	SYNTAX  INTEGER(1..1)
	MAX-ACCESS  not-accessible
	STATUS current
	DESCRIPTION "Table entry index value"
	::= { climateEntry  1 }

climateSerial OBJECT-TYPE
	SYNTAX  DisplayString
	MAX-ACCESS  read-only
	STATUS current
	DESCRIPTION "Serial Number"
	::= { climateEntry  2 }

climateName OBJECT-TYPE
	SYNTAX  DisplayString
	MAX-ACCESS  read-only
	STATUS current
	DESCRIPTION "Friendly Name"
	::= { climateEntry  3 }

climateAvail OBJECT-TYPE
	SYNTAX  Gauge32
	MAX-ACCESS  read-only
	STATUS current
	DESCRIPTION "Is device currently plugged in?"
	::= { climateEntry  4 }

climateTempC OBJECT-TYPE
	SYNTAX  INTEGER(-50..100)
	UNITS "Degrees Celsius"
	MAX-ACCESS  read-only
	STATUS current
	DESCRIPTION "Current reading for Temperature (C)"
	::= { climateEntry  5 }

climateTempF OBJECT-TYPE
	SYNTAX  INTEGER(-58..212)
	UNITS "Degress Fahrenheit"
	MAX-ACCESS  read-only
	STATUS current
	DESCRIPTION "Current reading for Temperature (F)"
	::= { climateEntry  6 }

climateHumidity OBJECT-TYPE
	SYNTAX  INTEGER(0..100)
	UNITS "%"
	MAX-ACCESS  read-only
	STATUS current
	DESCRIPTION "Current reading for Humidity"
	::= { climateEntry  7 }

climateLight OBJECT-TYPE
	SYNTAX  INTEGER(0..100)
	MAX-ACCESS  read-only
	STATUS current
	DESCRIPTION "Current reading for Ambient Light"
	::= { climateEntry  8 }

climateAirflow OBJECT-TYPE
	SYNTAX  INTEGER(0..100)
	MAX-ACCESS  read-only
	STATUS current
	DESCRIPTION "Current reading for Airflow"
	::= { climateEntry  9 }

climateSound OBJECT-TYPE
	SYNTAX  INTEGER(0..100)
	MAX-ACCESS  read-only
	STATUS current
	DESCRIPTION "Current reading for Sound"
	::= { climateEntry  10 }

climateIO1 OBJECT-TYPE
	SYNTAX  INTEGER(0..100)
	MAX-ACCESS  read-only
	STATUS current
	DESCRIPTION "Current reading for Analog Input 1"
	::= { climateEntry  11 }

climateIO2 OBJECT-TYPE
	SYNTAX  INTEGER(0..100)
	MAX-ACCESS  read-only
	STATUS current
	DESCRIPTION "Current reading for Analog Input 2"
	::= { climateEntry  12 }

climateIO3 OBJECT-TYPE
	SYNTAX  INTEGER(0..100)
	MAX-ACCESS  read-only
	STATUS current
	DESCRIPTION "Current reading for Analog Input 3"
	::= { climateEntry  13 }

dewPointSensorEntry OBJECT-TYPE
	SYNTAX  DewPointSensorEntry
	MAX-ACCESS  not-accessible
	STATUS current
	DESCRIPTION
		"Entry in the dew point sensor table: each entry contains
an index (dewpointsensorIndex) and other sensor details"
	INDEX { dewPointSensorIndex }
	::= { dewPointSensorTable 1 }

DewPointSensorEntry ::= SEQUENCE {
	dewPointSensorIndex		INTEGER,
	dewPointSensorSerial		DisplayString,
	dewPointSensorName		DisplayString,
	dewPointSensorAvail		Gauge32,
	dewPointSensorTempC		INTEGER,
	dewPointSensorTempF		INTEGER,
	dewPointSensorHumidity		INTEGER,
	dewPointSensorDewpointC		INTEGER,
	dewPointSensorDewpointF		INTEGER
}

dewPointSensorIndex OBJECT-TYPE
	SYNTAX  INTEGER(1..100)
	MAX-ACCESS  not-accessible
	STATUS current
	DESCRIPTION "Table entry index value"
	::= { dewPointSensorEntry  1 }

dewPointSensorSerial OBJECT-TYPE
	SYNTAX  DisplayString
	MAX-ACCESS  read-only
	STATUS current
	DESCRIPTION "Serial Number"
	::= { dewPointSensorEntry  2 }

dewPointSensorName OBJECT-TYPE
	SYNTAX  DisplayString
	MAX-ACCESS  read-only
	STATUS current
	DESCRIPTION "Friendly Name"
	::= { dewPointSensorEntry  3 }

dewPointSensorAvail OBJECT-TYPE
	SYNTAX  Gauge32
	MAX-ACCESS  read-only
	STATUS current
	DESCRIPTION "Is device currently plugged in?"
	::= { dewPointSensorEntry  4 }

dewPointSensorTempC OBJECT-TYPE
	SYNTAX  INTEGER(-50..100)
	UNITS "Temperature reading in C"
	MAX-ACCESS  read-only
	STATUS current
	DESCRIPTION "Remote Dew point Sensor - Temperature Trap"
	::= { dewPointSensorEntry  5 }

dewPointSensorTempF OBJECT-TYPE
	SYNTAX  INTEGER(-58..212)
	UNITS "Temperature reading in F"
	MAX-ACCESS  read-only
	STATUS current
	DESCRIPTION "Remote Dew point Sensor - Temperature Trap"
	::= { dewPointSensorEntry  6 }

dewPointSensorHumidity OBJECT-TYPE
	SYNTAX  INTEGER(0..100)
	UNITS "Humidity reading"
	MAX-ACCESS  read-only
	STATUS current
	DESCRIPTION "Remote Dew point - Humidity"
	::= { dewPointSensorEntry  7 }

dewPointSensorDewpointC OBJECT-TYPE
	SYNTAX  INTEGER(0..100)
	UNITS "Dew point reading"
	MAX-ACCESS  read-only
	STATUS current
	DESCRIPTION "Remote Dew point - Dew point Trap"
	::= { dewPointSensorEntry  8 }

dewPointSensorDewpointF OBJECT-TYPE
	SYNTAX  INTEGER(0..100)
	UNITS "Dew point reading"
	MAX-ACCESS  read-only
	STATUS current
	DESCRIPTION "Remote Dew point - Dew point Trap"
	::= { dewPointSensorEntry  9 }

fancontrolEntry OBJECT-TYPE
	SYNTAX  FancontrolEntry
	MAX-ACCESS  not-accessible
	STATUS current
	DESCRIPTION
		"Entry in the ODS EC table: each entry contains
an index (fancontroller) and other details"
	INDEX { fancontrolIndex }
	::= { fancontrolTable 1 }

FancontrolEntry ::= SEQUENCE {
	fancontrolIndex		INTEGER,
	fancontrolSerial		DisplayString,
	fancontrolName		DisplayString,
	fancontrolAvail		Gauge32,
	fancontrolTempCreturnA		INTEGER,
	fancontrolTempFreturnA		INTEGER,
	fancontrolTempCreturnB		INTEGER,
	fancontrolTempFreturnB		INTEGER,
	fancontrolRpmFanA		Gauge32,
	fancontrolRpmFanB		Gauge32,
	fancontrolCapacityA		INTEGER,
	fancontrolCapacityB		INTEGER,
	fancontrolPressErr		INTEGER,
	fancontrolPressDiff		INTEGER,
	fancontrolSetPoint		INTEGER,
	fancontrolCFM		Gauge32,
	fancontrolMCH		Gauge32,
	fancontrolTempCreturn		INTEGER,
	fancontrolTempFreturn		INTEGER,
	fancontrolCapacity		INTEGER,
	fancontrolFanMissing		Gauge32,
	fancontrolFanMismatch		Gauge32,
	fancontrolFanErrorA		Gauge32,
	fancontrolFanErrorB		Gauge32,
	fancontrolTempBus1		Gauge32,
	fancontrolPowerFeed		Gauge32,
	fancontrolFanEndofLife		Gauge32
}

fancontrolIndex OBJECT-TYPE
	SYNTAX  INTEGER(1..1)
	UNITS "Table entry index value"
	MAX-ACCESS  not-accessible
	STATUS current
	DESCRIPTION "Reading for Index"
	::= { fancontrolEntry  1 }

fancontrolSerial OBJECT-TYPE
	SYNTAX  DisplayString
	UNITS "Serial Number"
	MAX-ACCESS  read-only
	STATUS current
	DESCRIPTION "Reading for Serial"
	::= { fancontrolEntry  2 }

fancontrolName OBJECT-TYPE
	SYNTAX  DisplayString
	UNITS "Friendly Name"
	MAX-ACCESS  read-only
	STATUS current
	DESCRIPTION "Reading for Name"
	::= { fancontrolEntry  3 }

fancontrolAvail OBJECT-TYPE
	SYNTAX  Gauge32
	UNITS "Is device currently plugged in?"
	MAX-ACCESS  read-only
	STATUS current
	DESCRIPTION "Reading for Avail"
	::= { fancontrolEntry  4 }

fancontrolTempCreturnA OBJECT-TYPE
	SYNTAX  INTEGER(-40..100)
	UNITS "Celsius temperature of return air on fan A"
	MAX-ACCESS  read-only
	STATUS current
	DESCRIPTION "TempCreturnA Active Set Point Sensor Trap"
	::= { fancontrolEntry  5 }

fancontrolTempFreturnA OBJECT-TYPE
	SYNTAX  INTEGER(-40..212)
	UNITS "Fahrenheit temperature of return air on fan A"
	MAX-ACCESS  read-only
	STATUS current
	DESCRIPTION "TempFreturnA Active Set Point Sensor Trap"
	::= { fancontrolEntry  6 }

fancontrolTempCreturnB OBJECT-TYPE
	SYNTAX  INTEGER(-40..100)
	UNITS "Celsius temperature of return air on fan B"
	MAX-ACCESS  read-only
	STATUS current
	DESCRIPTION "TempCreturnB Active Set Point Sensor Trap"
	::= { fancontrolEntry  7 }

fancontrolTempFreturnB OBJECT-TYPE
	SYNTAX  INTEGER(-40..212)
	UNITS "Fahrenheit temperature of return air on fan B"
	MAX-ACCESS  read-only
	STATUS current
	DESCRIPTION "TempFreturnB Active Set Point Sensor Trap"
	::= { fancontrolEntry  8 }

fancontrolRpmFanA OBJECT-TYPE
	SYNTAX  Gauge32
	UNITS "RPM of fan A"
	MAX-ACCESS  read-only
	STATUS current
	DESCRIPTION "RpmFanA Active Set Point Sensor Trap"
	::= { fancontrolEntry  9 }

fancontrolRpmFanB OBJECT-TYPE
	SYNTAX  Gauge32
	UNITS "RPM of fan B"
	MAX-ACCESS  read-only
	STATUS current
	DESCRIPTION "RpmFanB Active Set Point Sensor Trap"
	::= { fancontrolEntry  10 }

fancontrolCapacityA OBJECT-TYPE
	SYNTAX  INTEGER(0..100)
	UNITS "Capacity of fan A"
	MAX-ACCESS  read-only
	STATUS current
	DESCRIPTION "CapacityA Active Set Point Sensor Trap"
	::= { fancontrolEntry  11 }

fancontrolCapacityB OBJECT-TYPE
	SYNTAX  INTEGER(0..100)
	UNITS "Capacity of fan B"
	MAX-ACCESS  read-only
	STATUS current
	DESCRIPTION "CapacityB Active Set Point Sensor Trap"
	::= { fancontrolEntry  12 }

fancontrolPressErr OBJECT-TYPE
	SYNTAX  INTEGER(-1..1)
	UNITS "Pressure error"
	MAX-ACCESS  read-only
	STATUS current
	DESCRIPTION "PressErr Active Set Point Sensor Trap"
	::= { fancontrolEntry  13 }

fancontrolPressDiff OBJECT-TYPE
	SYNTAX  INTEGER(-1..1)
	UNITS "Pressure Difference"
	MAX-ACCESS  read-only
	STATUS current
	DESCRIPTION "PressDiff Active Set Point Sensor Trap"
	::= { fancontrolEntry  14 }

fancontrolSetPoint OBJECT-TYPE
	SYNTAX  INTEGER(-1..1)
	UNITS "Pressure Set Point"
	MAX-ACCESS  read-only
	STATUS current
	DESCRIPTION "SetPoint Active Set Point Sensor Trap"
	::= { fancontrolEntry  15 }

fancontrolCFM OBJECT-TYPE
	SYNTAX  Gauge32
	UNITS "Cubic Feet per minute of system air"
	MAX-ACCESS  read-only
	STATUS current
	DESCRIPTION "CFM Active Set Point Sensor Trap"
	::= { fancontrolEntry  16 }

fancontrolMCH OBJECT-TYPE
	SYNTAX  Gauge32
	UNITS "Meters cubed per hour of system air"
	MAX-ACCESS  read-only
	STATUS current
	DESCRIPTION "MCH Active Set Point Sensor Trap"
	::= { fancontrolEntry  17 }

fancontrolTempCreturn OBJECT-TYPE
	SYNTAX  INTEGER(-40..100)
	UNITS "Higher temp of fan A or B"
	MAX-ACCESS  read-only
	STATUS current
	DESCRIPTION "TempCreturn Active Set Point Sensor Trap"
	::= { fancontrolEntry  18 }

fancontrolTempFreturn OBJECT-TYPE
	SYNTAX  INTEGER(-40..212)
	UNITS "Higher temp of fan A or B"
	MAX-ACCESS  read-only
	STATUS current
	DESCRIPTION "TempCreturn Active Set Point Sensor Trap"
	::= { fancontrolEntry  19 }

fancontrolCapacity OBJECT-TYPE
	SYNTAX  INTEGER(0..100)
	UNITS "Total Capacity"
	MAX-ACCESS  read-only
	STATUS current
	DESCRIPTION "Capacity Active Set Point Sensor Trap"
	::= { fancontrolEntry  20 }

fancontrolFanMissing OBJECT-TYPE
	SYNTAX  Gauge32
	UNITS "Fan Missing Error"
	MAX-ACCESS  read-only
	STATUS current
	DESCRIPTION "FanMissing Active Set Point Sensor Trap"
	::= { fancontrolEntry  21 }

fancontrolFanMismatch OBJECT-TYPE
	SYNTAX  Gauge32
	UNITS "Fan Mismatch Error"
	MAX-ACCESS  read-only
	STATUS current
	DESCRIPTION "FanMismatch Active Set Point Sensor Trap"
	::= { fancontrolEntry  22 }

fancontrolFanErrorA OBJECT-TYPE
	SYNTAX  Gauge32
	UNITS "Fan Cartridge A Error"
	MAX-ACCESS  read-only
	STATUS current
	DESCRIPTION "FanErrorA Active Set Point Sensor Trap"
	::= { fancontrolEntry  23 }

fancontrolFanErrorB OBJECT-TYPE
	SYNTAX  Gauge32
	UNITS "Fan Cartridge B Error"
	MAX-ACCESS  read-only
	STATUS current
	DESCRIPTION "FanErrorB Active Set Point Sensor Trap"
	::= { fancontrolEntry  24 }

fancontrolTempBus1 OBJECT-TYPE
	SYNTAX  Gauge32
	UNITS "Disconnected External Sensor"
	MAX-ACCESS  read-only
	STATUS current
	DESCRIPTION "TempBus1 Active Set Point Sensor Trap"
	::= { fancontrolEntry  25 }

fancontrolPowerFeed OBJECT-TYPE
	SYNTAX  Gauge32
	UNITS "A/B Feed Error"
	MAX-ACCESS  read-only
	STATUS current
	DESCRIPTION "PowerFeed Active Set Point Sensor Trap"
	::= { fancontrolEntry  26 }

fancontrolFanEndofLife OBJECT-TYPE
	SYNTAX  Gauge32
	UNITS "Fan End of Life"
	MAX-ACCESS  read-only
	STATUS current
	DESCRIPTION "FanEndofLife Active Set Point Sensor Trap"
	::= { fancontrolEntry  27 }

tempSensorEntry OBJECT-TYPE
	SYNTAX  TempSensorEntry
	MAX-ACCESS  not-accessible
	STATUS current
	DESCRIPTION
		"Entry in the temperature sensor table: each entry contains
an index (tempIndex) and other sensor details"
	INDEX { tempSensorIndex }
	::= { tempSensorTable 1 }

TempSensorEntry ::= SEQUENCE {
	tempSensorIndex		INTEGER,
	tempSensorSerial		DisplayString,
	tempSensorName		DisplayString,
	tempSensorAvail		Gauge32,
	tempSensorTempC		INTEGER,
	tempSensorTempF		INTEGER
}

tempSensorIndex OBJECT-TYPE
	SYNTAX  INTEGER(1..100)
	MAX-ACCESS  not-accessible
	STATUS current
	DESCRIPTION "Table entry index value"
	::= { tempSensorEntry  1 }

tempSensorSerial OBJECT-TYPE
	SYNTAX  DisplayString
	MAX-ACCESS  read-only
	STATUS current
	DESCRIPTION "Serial Number"
	::= { tempSensorEntry  2 }

tempSensorName OBJECT-TYPE
	SYNTAX  DisplayString
	MAX-ACCESS  read-only
	STATUS current
	DESCRIPTION "Friendly Name"
	::= { tempSensorEntry  3 }

tempSensorAvail OBJECT-TYPE
	SYNTAX  Gauge32
	MAX-ACCESS  read-only
	STATUS current
	DESCRIPTION "Is device currently plugged in?"
	::= { tempSensorEntry  4 }

tempSensorTempC OBJECT-TYPE
	SYNTAX  INTEGER(-50..100)
	UNITS "Temperature in Celsius"
	MAX-ACCESS  read-only
	STATUS current
	DESCRIPTION "Remote Temp Sensor - Temperature Trap"
	::= { tempSensorEntry  5 }

tempSensorTempF OBJECT-TYPE
	SYNTAX  INTEGER(-58..212)
	UNITS "Temperature in Fahrenheit"
	MAX-ACCESS  read-only
	STATUS current
	DESCRIPTION "Remote Temp Sensor - Temperature Trap"
	::= { tempSensorEntry  6 }

flowcontrolEntry OBJECT-TYPE
	SYNTAX  FlowcontrolEntry
	MAX-ACCESS  not-accessible
	STATUS current
	DESCRIPTION
		"Entry in the ODS FC table: each entry contains
an index (fancontroller) and other details"
	INDEX { flowcontrolIndex }
	::= { flowcontrolTable 1 }

FlowcontrolEntry ::= SEQUENCE {
	flowcontrolIndex		INTEGER,
	flowcontrolSerial		DisplayString,
	flowcontrolName		DisplayString,
	flowcontrolAvail		Gauge32,
	flowcontrolRpmFan		Gauge32,
	flowcontrolCapacity		INTEGER,
	flowcontrolPressErr		INTEGER,
	flowcontrolPressDiff		INTEGER,
	flowcontrolSetPoint		INTEGER,
	flowcontrolCFM		Gauge32,
	flowcontrolMCH		Gauge32,
	flowcontrolTempBus1		Gauge32,
	flowcontrolPowerFeed		Gauge32
}

flowcontrolIndex OBJECT-TYPE
	SYNTAX  INTEGER(1..1)
	UNITS "Table entry index value"
	MAX-ACCESS  not-accessible
	STATUS current
	DESCRIPTION "Reading for Index"
	::= { flowcontrolEntry  1 }

flowcontrolSerial OBJECT-TYPE
	SYNTAX  DisplayString
	UNITS "Serial Number"
	MAX-ACCESS  read-only
	STATUS current
	DESCRIPTION "Reading for Serial"
	::= { flowcontrolEntry  2 }

flowcontrolName OBJECT-TYPE
	SYNTAX  DisplayString
	UNITS "Friendly Name"
	MAX-ACCESS  read-only
	STATUS current
	DESCRIPTION "Reading for Name"
	::= { flowcontrolEntry  3 }

flowcontrolAvail OBJECT-TYPE
	SYNTAX  Gauge32
	UNITS "Is device currently plugged in?"
	MAX-ACCESS  read-only
	STATUS current
	DESCRIPTION "Reading for Avail"
	::= { flowcontrolEntry  4 }

flowcontrolRpmFan OBJECT-TYPE
	SYNTAX  Gauge32
	UNITS "RPM of fan"
	MAX-ACCESS  read-only
	STATUS current
	DESCRIPTION "RpmFan Active Set Point Sensor Trap"
	::= { flowcontrolEntry  5 }

flowcontrolCapacity OBJECT-TYPE
	SYNTAX  INTEGER(0..100)
	UNITS "Total Capacity"
	MAX-ACCESS  read-only
	STATUS current
	DESCRIPTION "Capacity Active Set Point Sensor Trap"
	::= { flowcontrolEntry  6 }

flowcontrolPressErr OBJECT-TYPE
	SYNTAX  INTEGER(-1..1)
	UNITS "Pressure error"
	MAX-ACCESS  read-only
	STATUS current
	DESCRIPTION "PressErr Active Set Point Sensor Trap"
	::= { flowcontrolEntry  7 }

flowcontrolPressDiff OBJECT-TYPE
	SYNTAX  INTEGER(-1..1)
	UNITS "Pressure Difference"
	MAX-ACCESS  read-only
	STATUS current
	DESCRIPTION "PressDiff Active Set Point Sensor Trap"
	::= { flowcontrolEntry  8 }

flowcontrolSetPoint OBJECT-TYPE
	SYNTAX  INTEGER(-1..1)
	UNITS "Pressure Set Point"
	MAX-ACCESS  read-only
	STATUS current
	DESCRIPTION "SetPoint Active Set Point Sensor Trap"
	::= { flowcontrolEntry  9 }

flowcontrolCFM OBJECT-TYPE
	SYNTAX  Gauge32
	UNITS "Cubic Feet per minute of system air"
	MAX-ACCESS  read-only
	STATUS current
	DESCRIPTION "CFM Active Set Point Sensor Trap"
	::= { flowcontrolEntry  10 }

flowcontrolMCH OBJECT-TYPE
	SYNTAX  Gauge32
	UNITS "Meters cubed per hour of system air"
	MAX-ACCESS  read-only
	STATUS current
	DESCRIPTION "MCH Active Set Point Sensor Trap"
	::= { flowcontrolEntry  11 }

flowcontrolTempBus1 OBJECT-TYPE
	SYNTAX  Gauge32
	UNITS "Disconnected External Sensor"
	MAX-ACCESS  read-only
	STATUS current
	DESCRIPTION "TempBus1 Active Set Point Sensor Trap"
	::= { flowcontrolEntry  12 }

flowcontrolPowerFeed OBJECT-TYPE
	SYNTAX  Gauge32
	UNITS "A/B Feed Error"
	MAX-ACCESS  read-only
	STATUS current
	DESCRIPTION "PowerFeed Active Set Point Sensor Trap"
	::= { flowcontrolEntry  13 }

powerDMEntry OBJECT-TYPE
	SYNTAX  PowerDMEntry
	MAX-ACCESS  not-accessible
	STATUS current
	DESCRIPTION
		"Entry in the DM48 current monitor table: each entry contains
an index (powerDMIndex) and other sensor details"
	INDEX { powerDMIndex }
	::= { powerDMTable 1 }

PowerDMEntry ::= SEQUENCE {
	powerDMIndex		INTEGER,
	powerDMSerial		DisplayString,
	powerDMName		DisplayString,
	powerDMAvail		Gauge32,
	powerDMUnitInfoTitle		DisplayString,
	powerDMUnitInfoVersion		DisplayString,
	powerDMUnitInfoMainCount		INTEGER,
	powerDMUnitInfoAuxCount		INTEGER,
	powerDMChannelName1		DisplayString,
	powerDMChannelName2		DisplayString,
	powerDMChannelName3		DisplayString,
	powerDMChannelName4		DisplayString,
	powerDMChannelName5		DisplayString,
	powerDMChannelName6		DisplayString,
	powerDMChannelName7		DisplayString,
	powerDMChannelName8		DisplayString,
	powerDMChannelName9		DisplayString,
	powerDMChannelName10		DisplayString,
	powerDMChannelName11		DisplayString,
	powerDMChannelName12		DisplayString,
	powerDMChannelName13		DisplayString,
	powerDMChannelName14		DisplayString,
	powerDMChannelName15		DisplayString,
	powerDMChannelName16		DisplayString,
	powerDMChannelName17		DisplayString,
	powerDMChannelName18		DisplayString,
	powerDMChannelName19		DisplayString,
	powerDMChannelName20		DisplayString,
	powerDMChannelName21		DisplayString,
	powerDMChannelName22		DisplayString,
	powerDMChannelName23		DisplayString,
	powerDMChannelName24		DisplayString,
	powerDMChannelName25		DisplayString,
	powerDMChannelName26		DisplayString,
	powerDMChannelName27		DisplayString,
	powerDMChannelName28		DisplayString,
	powerDMChannelName29		DisplayString,
	powerDMChannelName30		DisplayString,
	powerDMChannelName31		DisplayString,
	powerDMChannelName32		DisplayString,
	powerDMChannelName33		DisplayString,
	powerDMChannelName34		DisplayString,
	powerDMChannelName35		DisplayString,
	powerDMChannelName36		DisplayString,
	powerDMChannelName37		DisplayString,
	powerDMChannelName38		DisplayString,
	powerDMChannelName39		DisplayString,
	powerDMChannelName40		DisplayString,
	powerDMChannelName41		DisplayString,
	powerDMChannelName42		DisplayString,
	powerDMChannelName43		DisplayString,
	powerDMChannelName44		DisplayString,
	powerDMChannelName45		DisplayString,
	powerDMChannelName46		DisplayString,
	powerDMChannelName47		DisplayString,
	powerDMChannelName48		DisplayString,
	powerDMChannelFriendly1		DisplayString,
	powerDMChannelFriendly2		DisplayString,
	powerDMChannelFriendly3		DisplayString,
	powerDMChannelFriendly4		DisplayString,
	powerDMChannelFriendly5		DisplayString,
	powerDMChannelFriendly6		DisplayString,
	powerDMChannelFriendly7		DisplayString,
	powerDMChannelFriendly8		DisplayString,
	powerDMChannelFriendly9		DisplayString,
	powerDMChannelFriendly10		DisplayString,
	powerDMChannelFriendly11		DisplayString,
	powerDMChannelFriendly12		DisplayString,
	powerDMChannelFriendly13		DisplayString,
	powerDMChannelFriendly14		DisplayString,
	powerDMChannelFriendly15		DisplayString,
	powerDMChannelFriendly16		DisplayString,
	powerDMChannelFriendly17		DisplayString,
	powerDMChannelFriendly18		DisplayString,
	powerDMChannelFriendly19		DisplayString,
	powerDMChannelFriendly20		DisplayString,
	powerDMChannelFriendly21		DisplayString,
	powerDMChannelFriendly22		DisplayString,
	powerDMChannelFriendly23		DisplayString,
	powerDMChannelFriendly24		DisplayString,
	powerDMChannelFriendly25		DisplayString,
	powerDMChannelFriendly26		DisplayString,
	powerDMChannelFriendly27		DisplayString,
	powerDMChannelFriendly28		DisplayString,
	powerDMChannelFriendly29		DisplayString,
	powerDMChannelFriendly30		DisplayString,
	powerDMChannelFriendly31		DisplayString,
	powerDMChannelFriendly32		DisplayString,
	powerDMChannelFriendly33		DisplayString,
	powerDMChannelFriendly34		DisplayString,
	powerDMChannelFriendly35		DisplayString,
	powerDMChannelFriendly36		DisplayString,
	powerDMChannelFriendly37		DisplayString,
	powerDMChannelFriendly38		DisplayString,
	powerDMChannelFriendly39		DisplayString,
	powerDMChannelFriendly40		DisplayString,
	powerDMChannelFriendly41		DisplayString,
	powerDMChannelFriendly42		DisplayString,
	powerDMChannelFriendly43		DisplayString,
	powerDMChannelFriendly44		DisplayString,
	powerDMChannelFriendly45		DisplayString,
	powerDMChannelFriendly46		DisplayString,
	powerDMChannelFriendly47		DisplayString,
	powerDMChannelFriendly48		DisplayString,
	powerDMChannelGroup1		DisplayString,
	powerDMChannelGroup2		DisplayString,
	powerDMChannelGroup3		DisplayString,
	powerDMChannelGroup4		DisplayString,
	powerDMChannelGroup5		DisplayString,
	powerDMChannelGroup6		DisplayString,
	powerDMChannelGroup7		DisplayString,
	powerDMChannelGroup8		DisplayString,
	powerDMChannelGroup9		DisplayString,
	powerDMChannelGroup10		DisplayString,
	powerDMChannelGroup11		DisplayString,
	powerDMChannelGroup12		DisplayString,
	powerDMChannelGroup13		DisplayString,
	powerDMChannelGroup14		DisplayString,
	powerDMChannelGroup15		DisplayString,
	powerDMChannelGroup16		DisplayString,
	powerDMChannelGroup17		DisplayString,
	powerDMChannelGroup18		DisplayString,
	powerDMChannelGroup19		DisplayString,
	powerDMChannelGroup20		DisplayString,
	powerDMChannelGroup21		DisplayString,
	powerDMChannelGroup22		DisplayString,
	powerDMChannelGroup23		DisplayString,
	powerDMChannelGroup24		DisplayString,
	powerDMChannelGroup25		DisplayString,
	powerDMChannelGroup26		DisplayString,
	powerDMChannelGroup27		DisplayString,
	powerDMChannelGroup28		DisplayString,
	powerDMChannelGroup29		DisplayString,
	powerDMChannelGroup30		DisplayString,
	powerDMChannelGroup31		DisplayString,
	powerDMChannelGroup32		DisplayString,
	powerDMChannelGroup33		DisplayString,
	powerDMChannelGroup34		DisplayString,
	powerDMChannelGroup35		DisplayString,
	powerDMChannelGroup36		DisplayString,
	powerDMChannelGroup37		DisplayString,
	powerDMChannelGroup38		DisplayString,
	powerDMChannelGroup39		DisplayString,
	powerDMChannelGroup40		DisplayString,
	powerDMChannelGroup41		DisplayString,
	powerDMChannelGroup42		DisplayString,
	powerDMChannelGroup43		DisplayString,
	powerDMChannelGroup44		DisplayString,
	powerDMChannelGroup45		DisplayString,
	powerDMChannelGroup46		DisplayString,
	powerDMChannelGroup47		DisplayString,
	powerDMChannelGroup48		DisplayString,
	powerDMDeciAmps1		INTEGER,
	powerDMDeciAmps2		INTEGER,
	powerDMDeciAmps3		INTEGER,
	powerDMDeciAmps4		INTEGER,
	powerDMDeciAmps5		INTEGER,
	powerDMDeciAmps6		INTEGER,
	powerDMDeciAmps7		INTEGER,
	powerDMDeciAmps8		INTEGER,
	powerDMDeciAmps9		INTEGER,
	powerDMDeciAmps10		INTEGER,
	powerDMDeciAmps11		INTEGER,
	powerDMDeciAmps12		INTEGER,
	powerDMDeciAmps13		INTEGER,
	powerDMDeciAmps14		INTEGER,
	powerDMDeciAmps15		INTEGER,
	powerDMDeciAmps16		INTEGER,
	powerDMDeciAmps17		INTEGER,
	powerDMDeciAmps18		INTEGER,
	powerDMDeciAmps19		INTEGER,
	powerDMDeciAmps20		INTEGER,
	powerDMDeciAmps21		INTEGER,
	powerDMDeciAmps22		INTEGER,
	powerDMDeciAmps23		INTEGER,
	powerDMDeciAmps24		INTEGER,
	powerDMDeciAmps25		INTEGER,
	powerDMDeciAmps26		INTEGER,
	powerDMDeciAmps27		INTEGER,
	powerDMDeciAmps28		INTEGER,
	powerDMDeciAmps29		INTEGER,
	powerDMDeciAmps30		INTEGER,
	powerDMDeciAmps31		INTEGER,
	powerDMDeciAmps32		INTEGER,
	powerDMDeciAmps33		INTEGER,
	powerDMDeciAmps34		INTEGER,
	powerDMDeciAmps35		INTEGER,
	powerDMDeciAmps36		INTEGER,
	powerDMDeciAmps37		INTEGER,
	powerDMDeciAmps38		INTEGER,
	powerDMDeciAmps39		INTEGER,
	powerDMDeciAmps40		INTEGER,
	powerDMDeciAmps41		INTEGER,
	powerDMDeciAmps42		INTEGER,
	powerDMDeciAmps43		INTEGER,
	powerDMDeciAmps44		INTEGER,
	powerDMDeciAmps45		INTEGER,
	powerDMDeciAmps46		INTEGER,
	powerDMDeciAmps47		INTEGER,
	powerDMDeciAmps48		INTEGER
}

powerDMIndex OBJECT-TYPE
	SYNTAX  INTEGER(1..100)
	MAX-ACCESS  not-accessible
	STATUS current
	DESCRIPTION "Table entry index value"
	::= { powerDMEntry  1 }

powerDMSerial OBJECT-TYPE
	SYNTAX  DisplayString
	MAX-ACCESS  read-only
	STATUS current
	DESCRIPTION "Serial Number"
	::= { powerDMEntry  2 }

powerDMName OBJECT-TYPE
	SYNTAX  DisplayString
	MAX-ACCESS  read-only
	STATUS current
	DESCRIPTION "Friendly Name"
	::= { powerDMEntry  3 }

powerDMAvail OBJECT-TYPE
	SYNTAX  Gauge32
	MAX-ACCESS  read-only
	STATUS current
	DESCRIPTION "Is device currently plugged in?"
	::= { powerDMEntry  4 }

powerDMUnitInfoTitle OBJECT-TYPE
	SYNTAX  DisplayString
	MAX-ACCESS  read-only
	STATUS current
	DESCRIPTION "Type of Unit"
	::= { powerDMEntry  5 }

powerDMUnitInfoVersion OBJECT-TYPE
	SYNTAX  DisplayString
	MAX-ACCESS  read-only
	STATUS current
	DESCRIPTION "Unit Version Number"
	::= { powerDMEntry  6 }

powerDMUnitInfoMainCount OBJECT-TYPE
	SYNTAX  INTEGER(0..16)
	MAX-ACCESS  read-only
	STATUS current
	DESCRIPTION "Number of Main (Total Amps) Channels on the Unit"
	::= { powerDMEntry  7 }

powerDMUnitInfoAuxCount OBJECT-TYPE
	SYNTAX  INTEGER(0..48)
	MAX-ACCESS  read-only
	STATUS current
	DESCRIPTION "Number of Auxiliary (Outlet) Channels on the Unit"
	::= { powerDMEntry  8 }

powerDMChannelName1 OBJECT-TYPE
	SYNTAX  DisplayString
	MAX-ACCESS  read-only
	STATUS current
	DESCRIPTION "Channel 1 Factory Name"
	::= { powerDMEntry  9 }

powerDMChannelName2 OBJECT-TYPE
	SYNTAX  DisplayString
	MAX-ACCESS  read-only
	STATUS current
	DESCRIPTION "Channel 2 Factory Name"
	::= { powerDMEntry  10 }

powerDMChannelName3 OBJECT-TYPE
	SYNTAX  DisplayString
	MAX-ACCESS  read-only
	STATUS current
	DESCRIPTION "Channel 3 Factory Name"
	::= { powerDMEntry  11 }

powerDMChannelName4 OBJECT-TYPE
	SYNTAX  DisplayString
	MAX-ACCESS  read-only
	STATUS current
	DESCRIPTION "Channel 4 Factory Name"
	::= { powerDMEntry  12 }

powerDMChannelName5 OBJECT-TYPE
	SYNTAX  DisplayString
	MAX-ACCESS  read-only
	STATUS current
	DESCRIPTION "Channel 5 Factory Name"
	::= { powerDMEntry  13 }

powerDMChannelName6 OBJECT-TYPE
	SYNTAX  DisplayString
	MAX-ACCESS  read-only
	STATUS current
	DESCRIPTION "Channel 6 Factory Name"
	::= { powerDMEntry  14 }

powerDMChannelName7 OBJECT-TYPE
	SYNTAX  DisplayString
	MAX-ACCESS  read-only
	STATUS current
	DESCRIPTION "Channel 7 Factory Name"
	::= { powerDMEntry  15 }

powerDMChannelName8 OBJECT-TYPE
	SYNTAX  DisplayString
	MAX-ACCESS  read-only
	STATUS current
	DESCRIPTION "Channel 8 Factory Name"
	::= { powerDMEntry  16 }

powerDMChannelName9 OBJECT-TYPE
	SYNTAX  DisplayString
	MAX-ACCESS  read-only
	STATUS current
	DESCRIPTION "Channel 9 Factory Name"
	::= { powerDMEntry  17 }

powerDMChannelName10 OBJECT-TYPE
	SYNTAX  DisplayString
	MAX-ACCESS  read-only
	STATUS current
	DESCRIPTION "Channel 10 Factory Name"
	::= { powerDMEntry  18 }

powerDMChannelName11 OBJECT-TYPE
	SYNTAX  DisplayString
	MAX-ACCESS  read-only
	STATUS current
	DESCRIPTION "Channel 11 Factory Name"
	::= { powerDMEntry  19 }

powerDMChannelName12 OBJECT-TYPE
	SYNTAX  DisplayString
	MAX-ACCESS  read-only
	STATUS current
	DESCRIPTION "Channel 12 Factory Name"
	::= { powerDMEntry  20 }

powerDMChannelName13 OBJECT-TYPE
	SYNTAX  DisplayString
	MAX-ACCESS  read-only
	STATUS current
	DESCRIPTION "Channel 13 Factory Name"
	::= { powerDMEntry  21 }

powerDMChannelName14 OBJECT-TYPE
	SYNTAX  DisplayString
	MAX-ACCESS  read-only
	STATUS current
	DESCRIPTION "Channel 14 Factory Name"
	::= { powerDMEntry  22 }

powerDMChannelName15 OBJECT-TYPE
	SYNTAX  DisplayString
	MAX-ACCESS  read-only
	STATUS current
	DESCRIPTION "Channel 15 Factory Name"
	::= { powerDMEntry  23 }

powerDMChannelName16 OBJECT-TYPE
	SYNTAX  DisplayString
	MAX-ACCESS  read-only
	STATUS current
	DESCRIPTION "Channel 16 Factory Name"
	::= { powerDMEntry  24 }

powerDMChannelName17 OBJECT-TYPE
	SYNTAX  DisplayString
	MAX-ACCESS  read-only
	STATUS current
	DESCRIPTION "Channel 17 Factory Name"
	::= { powerDMEntry  25 }

powerDMChannelName18 OBJECT-TYPE
	SYNTAX  DisplayString
	MAX-ACCESS  read-only
	STATUS current
	DESCRIPTION "Channel 18 Factory Name"
	::= { powerDMEntry  26 }

powerDMChannelName19 OBJECT-TYPE
	SYNTAX  DisplayString
	MAX-ACCESS  read-only
	STATUS current
	DESCRIPTION "Channel 19 Factory Name"
	::= { powerDMEntry  27 }

powerDMChannelName20 OBJECT-TYPE
	SYNTAX  DisplayString
	MAX-ACCESS  read-only
	STATUS current
	DESCRIPTION "Channel 20 Factory Name"
	::= { powerDMEntry  28 }

powerDMChannelName21 OBJECT-TYPE
	SYNTAX  DisplayString
	MAX-ACCESS  read-only
	STATUS current
	DESCRIPTION "Channel 21 Factory Name"
	::= { powerDMEntry  29 }

powerDMChannelName22 OBJECT-TYPE
	SYNTAX  DisplayString
	MAX-ACCESS  read-only
	STATUS current
	DESCRIPTION "Channel 22 Factory Name"
	::= { powerDMEntry  30 }

powerDMChannelName23 OBJECT-TYPE
	SYNTAX  DisplayString
	MAX-ACCESS  read-only
	STATUS current
	DESCRIPTION "Channel 23 Factory Name"
	::= { powerDMEntry  31 }

powerDMChannelName24 OBJECT-TYPE
	SYNTAX  DisplayString
	MAX-ACCESS  read-only
	STATUS current
	DESCRIPTION "Channel 24 Factory Name"
	::= { powerDMEntry  32 }

powerDMChannelName25 OBJECT-TYPE
	SYNTAX  DisplayString
	MAX-ACCESS  read-only
	STATUS current
	DESCRIPTION "Channel 25 Factory Name"
	::= { powerDMEntry  33 }

powerDMChannelName26 OBJECT-TYPE
	SYNTAX  DisplayString
	MAX-ACCESS  read-only
	STATUS current
	DESCRIPTION "Channel 26 Factory Name"
	::= { powerDMEntry  34 }

powerDMChannelName27 OBJECT-TYPE
	SYNTAX  DisplayString
	MAX-ACCESS  read-only
	STATUS current
	DESCRIPTION "Channel 27 Factory Name"
	::= { powerDMEntry  35 }

powerDMChannelName28 OBJECT-TYPE
	SYNTAX  DisplayString
	MAX-ACCESS  read-only
	STATUS current
	DESCRIPTION "Channel 28 Factory Name"
	::= { powerDMEntry  36 }

powerDMChannelName29 OBJECT-TYPE
	SYNTAX  DisplayString
	MAX-ACCESS  read-only
	STATUS current
	DESCRIPTION "Channel 29 Factory Name"
	::= { powerDMEntry  37 }

powerDMChannelName30 OBJECT-TYPE
	SYNTAX  DisplayString
	MAX-ACCESS  read-only
	STATUS current
	DESCRIPTION "Channel 30 Factory Name"
	::= { powerDMEntry  38 }

powerDMChannelName31 OBJECT-TYPE
	SYNTAX  DisplayString
	MAX-ACCESS  read-only
	STATUS current
	DESCRIPTION "Channel 31 Factory Name"
	::= { powerDMEntry  39 }

powerDMChannelName32 OBJECT-TYPE
	SYNTAX  DisplayString
	MAX-ACCESS  read-only
	STATUS current
	DESCRIPTION "Channel 32 Factory Name"
	::= { powerDMEntry  40 }

powerDMChannelName33 OBJECT-TYPE
	SYNTAX  DisplayString
	MAX-ACCESS  read-only
	STATUS current
	DESCRIPTION "Channel 33 Factory Name"
	::= { powerDMEntry  41 }

powerDMChannelName34 OBJECT-TYPE
	SYNTAX  DisplayString
	MAX-ACCESS  read-only
	STATUS current
	DESCRIPTION "Channel 34 Factory Name"
	::= { powerDMEntry  42 }

powerDMChannelName35 OBJECT-TYPE
	SYNTAX  DisplayString
	MAX-ACCESS  read-only
	STATUS current
	DESCRIPTION "Channel 35 Factory Name"
	::= { powerDMEntry  43 }

powerDMChannelName36 OBJECT-TYPE
	SYNTAX  DisplayString
	MAX-ACCESS  read-only
	STATUS current
	DESCRIPTION "Channel 36 Factory Name"
	::= { powerDMEntry  44 }

powerDMChannelName37 OBJECT-TYPE
	SYNTAX  DisplayString
	MAX-ACCESS  read-only
	STATUS current
	DESCRIPTION "Channel 37 Factory Name"
	::= { powerDMEntry  45 }

powerDMChannelName38 OBJECT-TYPE
	SYNTAX  DisplayString
	MAX-ACCESS  read-only
	STATUS current
	DESCRIPTION "Channel 38 Factory Name"
	::= { powerDMEntry  46 }

powerDMChannelName39 OBJECT-TYPE
	SYNTAX  DisplayString
	MAX-ACCESS  read-only
	STATUS current
	DESCRIPTION "Channel 39 Factory Name"
	::= { powerDMEntry  47 }

powerDMChannelName40 OBJECT-TYPE
	SYNTAX  DisplayString
	MAX-ACCESS  read-only
	STATUS current
	DESCRIPTION "Channel 40 Factory Name"
	::= { powerDMEntry  48 }

powerDMChannelName41 OBJECT-TYPE
	SYNTAX  DisplayString
	MAX-ACCESS  read-only
	STATUS current
	DESCRIPTION "Channel 41 Factory Name"
	::= { powerDMEntry  49 }

powerDMChannelName42 OBJECT-TYPE
	SYNTAX  DisplayString
	MAX-ACCESS  read-only
	STATUS current
	DESCRIPTION "Channel 42 Factory Name"
	::= { powerDMEntry  50 }

powerDMChannelName43 OBJECT-TYPE
	SYNTAX  DisplayString
	MAX-ACCESS  read-only
	STATUS current
	DESCRIPTION "Channel 43 Factory Name"
	::= { powerDMEntry  51 }

powerDMChannelName44 OBJECT-TYPE
	SYNTAX  DisplayString
	MAX-ACCESS  read-only
	STATUS current
	DESCRIPTION "Channel 44 Factory Name"
	::= { powerDMEntry  52 }

powerDMChannelName45 OBJECT-TYPE
	SYNTAX  DisplayString
	MAX-ACCESS  read-only
	STATUS current
	DESCRIPTION "Channel 45 Factory Name"
	::= { powerDMEntry  53 }

powerDMChannelName46 OBJECT-TYPE
	SYNTAX  DisplayString
	MAX-ACCESS  read-only
	STATUS current
	DESCRIPTION "Channel 46 Factory Name"
	::= { powerDMEntry  54 }

powerDMChannelName47 OBJECT-TYPE
	SYNTAX  DisplayString
	MAX-ACCESS  read-only
	STATUS current
	DESCRIPTION "Channel 47 Factory Name"
	::= { powerDMEntry  55 }

powerDMChannelName48 OBJECT-TYPE
	SYNTAX  DisplayString
	MAX-ACCESS  read-only
	STATUS current
	DESCRIPTION "Channel 48 Factory Name"
	::= { powerDMEntry  56 }

powerDMChannelFriendly1 OBJECT-TYPE
	SYNTAX  DisplayString
	MAX-ACCESS  read-only
	STATUS current
	DESCRIPTION "Channel 1 Friendly Name"
	::= { powerDMEntry  57 }

powerDMChannelFriendly2 OBJECT-TYPE
	SYNTAX  DisplayString
	MAX-ACCESS  read-only
	STATUS current
	DESCRIPTION "Channel 2 Friendly Name"
	::= { powerDMEntry  58 }

powerDMChannelFriendly3 OBJECT-TYPE
	SYNTAX  DisplayString
	MAX-ACCESS  read-only
	STATUS current
	DESCRIPTION "Channel 3 Friendly Name"
	::= { powerDMEntry  59 }

powerDMChannelFriendly4 OBJECT-TYPE
	SYNTAX  DisplayString
	MAX-ACCESS  read-only
	STATUS current
	DESCRIPTION "Channel 4 Friendly Name"
	::= { powerDMEntry  60 }

powerDMChannelFriendly5 OBJECT-TYPE
	SYNTAX  DisplayString
	MAX-ACCESS  read-only
	STATUS current
	DESCRIPTION "Channel 5 Friendly Name"
	::= { powerDMEntry  61 }

powerDMChannelFriendly6 OBJECT-TYPE
	SYNTAX  DisplayString
	MAX-ACCESS  read-only
	STATUS current
	DESCRIPTION "Channel 6 Friendly Name"
	::= { powerDMEntry  62 }

powerDMChannelFriendly7 OBJECT-TYPE
	SYNTAX  DisplayString
	MAX-ACCESS  read-only
	STATUS current
	DESCRIPTION "Channel 7 Friendly Name"
	::= { powerDMEntry  63 }

powerDMChannelFriendly8 OBJECT-TYPE
	SYNTAX  DisplayString
	MAX-ACCESS  read-only
	STATUS current
	DESCRIPTION "Channel 8 Friendly Name"
	::= { powerDMEntry  64 }

powerDMChannelFriendly9 OBJECT-TYPE
	SYNTAX  DisplayString
	MAX-ACCESS  read-only
	STATUS current
	DESCRIPTION "Channel 9 Friendly Name"
	::= { powerDMEntry  65 }

powerDMChannelFriendly10 OBJECT-TYPE
	SYNTAX  DisplayString
	MAX-ACCESS  read-only
	STATUS current
	DESCRIPTION "Channel 10 Friendly Name"
	::= { powerDMEntry  66 }

powerDMChannelFriendly11 OBJECT-TYPE
	SYNTAX  DisplayString
	MAX-ACCESS  read-only
	STATUS current
	DESCRIPTION "Channel 11 Friendly Name"
	::= { powerDMEntry  67 }

powerDMChannelFriendly12 OBJECT-TYPE
	SYNTAX  DisplayString
	MAX-ACCESS  read-only
	STATUS current
	DESCRIPTION "Channel 12 Friendly Name"
	::= { powerDMEntry  68 }

powerDMChannelFriendly13 OBJECT-TYPE
	SYNTAX  DisplayString
	MAX-ACCESS  read-only
	STATUS current
	DESCRIPTION "Channel 13 Friendly Name"
	::= { powerDMEntry  69 }

powerDMChannelFriendly14 OBJECT-TYPE
	SYNTAX  DisplayString
	MAX-ACCESS  read-only
	STATUS current
	DESCRIPTION "Channel 14 Friendly Name"
	::= { powerDMEntry  70 }

powerDMChannelFriendly15 OBJECT-TYPE
	SYNTAX  DisplayString
	MAX-ACCESS  read-only
	STATUS current
	DESCRIPTION "Channel 15 Friendly Name"
	::= { powerDMEntry  71 }

powerDMChannelFriendly16 OBJECT-TYPE
	SYNTAX  DisplayString
	MAX-ACCESS  read-only
	STATUS current
	DESCRIPTION "Channel 16 Friendly Name"
	::= { powerDMEntry  72 }

powerDMChannelFriendly17 OBJECT-TYPE
	SYNTAX  DisplayString
	MAX-ACCESS  read-only
	STATUS current
	DESCRIPTION "Channel 17 Friendly Name"
	::= { powerDMEntry  73 }

powerDMChannelFriendly18 OBJECT-TYPE
	SYNTAX  DisplayString
	MAX-ACCESS  read-only
	STATUS current
	DESCRIPTION "Channel 18 Friendly Name"
	::= { powerDMEntry  74 }

powerDMChannelFriendly19 OBJECT-TYPE
	SYNTAX  DisplayString
	MAX-ACCESS  read-only
	STATUS current
	DESCRIPTION "Channel 19 Friendly Name"
	::= { powerDMEntry  75 }

powerDMChannelFriendly20 OBJECT-TYPE
	SYNTAX  DisplayString
	MAX-ACCESS  read-only
	STATUS current
	DESCRIPTION "Channel 20 Friendly Name"
	::= { powerDMEntry  76 }

powerDMChannelFriendly21 OBJECT-TYPE
	SYNTAX  DisplayString
	MAX-ACCESS  read-only
	STATUS current
	DESCRIPTION "Channel 21 Friendly Name"
	::= { powerDMEntry  77 }

powerDMChannelFriendly22 OBJECT-TYPE
	SYNTAX  DisplayString
	MAX-ACCESS  read-only
	STATUS current
	DESCRIPTION "Channel 22 Friendly Name"
	::= { powerDMEntry  78 }

powerDMChannelFriendly23 OBJECT-TYPE
	SYNTAX  DisplayString
	MAX-ACCESS  read-only
	STATUS current
	DESCRIPTION "Channel 23 Friendly Name"
	::= { powerDMEntry  79 }

powerDMChannelFriendly24 OBJECT-TYPE
	SYNTAX  DisplayString
	MAX-ACCESS  read-only
	STATUS current
	DESCRIPTION "Channel 24 Friendly Name"
	::= { powerDMEntry  80 }

powerDMChannelFriendly25 OBJECT-TYPE
	SYNTAX  DisplayString
	MAX-ACCESS  read-only
	STATUS current
	DESCRIPTION "Channel 25 Friendly Name"
	::= { powerDMEntry  81 }

powerDMChannelFriendly26 OBJECT-TYPE
	SYNTAX  DisplayString
	MAX-ACCESS  read-only
	STATUS current
	DESCRIPTION "Channel 26 Friendly Name"
	::= { powerDMEntry  82 }

powerDMChannelFriendly27 OBJECT-TYPE
	SYNTAX  DisplayString
	MAX-ACCESS  read-only
	STATUS current
	DESCRIPTION "Channel 27 Friendly Name"
	::= { powerDMEntry  83 }

powerDMChannelFriendly28 OBJECT-TYPE
	SYNTAX  DisplayString
	MAX-ACCESS  read-only
	STATUS current
	DESCRIPTION "Channel 28 Friendly Name"
	::= { powerDMEntry  84 }

powerDMChannelFriendly29 OBJECT-TYPE
	SYNTAX  DisplayString
	MAX-ACCESS  read-only
	STATUS current
	DESCRIPTION "Channel 29 Friendly Name"
	::= { powerDMEntry  85 }

powerDMChannelFriendly30 OBJECT-TYPE
	SYNTAX  DisplayString
	MAX-ACCESS  read-only
	STATUS current
	DESCRIPTION "Channel 30 Friendly Name"
	::= { powerDMEntry  86 }

powerDMChannelFriendly31 OBJECT-TYPE
	SYNTAX  DisplayString
	MAX-ACCESS  read-only
	STATUS current
	DESCRIPTION "Channel 31 Friendly Name"
	::= { powerDMEntry  87 }

powerDMChannelFriendly32 OBJECT-TYPE
	SYNTAX  DisplayString
	MAX-ACCESS  read-only
	STATUS current
	DESCRIPTION "Channel 32 Friendly Name"
	::= { powerDMEntry  88 }

powerDMChannelFriendly33 OBJECT-TYPE
	SYNTAX  DisplayString
	MAX-ACCESS  read-only
	STATUS current
	DESCRIPTION "Channel 33 Friendly Name"
	::= { powerDMEntry  89 }

powerDMChannelFriendly34 OBJECT-TYPE
	SYNTAX  DisplayString
	MAX-ACCESS  read-only
	STATUS current
	DESCRIPTION "Channel 34 Friendly Name"
	::= { powerDMEntry  90 }

powerDMChannelFriendly35 OBJECT-TYPE
	SYNTAX  DisplayString
	MAX-ACCESS  read-only
	STATUS current
	DESCRIPTION "Channel 35 Friendly Name"
	::= { powerDMEntry  91 }

powerDMChannelFriendly36 OBJECT-TYPE
	SYNTAX  DisplayString
	MAX-ACCESS  read-only
	STATUS current
	DESCRIPTION "Channel 36 Friendly Name"
	::= { powerDMEntry  92 }

powerDMChannelFriendly37 OBJECT-TYPE
	SYNTAX  DisplayString
	MAX-ACCESS  read-only
	STATUS current
	DESCRIPTION "Channel 37 Friendly Name"
	::= { powerDMEntry  93 }

powerDMChannelFriendly38 OBJECT-TYPE
	SYNTAX  DisplayString
	MAX-ACCESS  read-only
	STATUS current
	DESCRIPTION "Channel 38 Friendly Name"
	::= { powerDMEntry  94 }

powerDMChannelFriendly39 OBJECT-TYPE
	SYNTAX  DisplayString
	MAX-ACCESS  read-only
	STATUS current
	DESCRIPTION "Channel 39 Friendly Name"
	::= { powerDMEntry  95 }

powerDMChannelFriendly40 OBJECT-TYPE
	SYNTAX  DisplayString
	MAX-ACCESS  read-only
	STATUS current
	DESCRIPTION "Channel 40 Friendly Name"
	::= { powerDMEntry  96 }

powerDMChannelFriendly41 OBJECT-TYPE
	SYNTAX  DisplayString
	MAX-ACCESS  read-only
	STATUS current
	DESCRIPTION "Channel 41 Friendly Name"
	::= { powerDMEntry  97 }

powerDMChannelFriendly42 OBJECT-TYPE
	SYNTAX  DisplayString
	MAX-ACCESS  read-only
	STATUS current
	DESCRIPTION "Channel 42 Friendly Name"
	::= { powerDMEntry  98 }

powerDMChannelFriendly43 OBJECT-TYPE
	SYNTAX  DisplayString
	MAX-ACCESS  read-only
	STATUS current
	DESCRIPTION "Channel 43 Friendly Name"
	::= { powerDMEntry  99 }

powerDMChannelFriendly44 OBJECT-TYPE
	SYNTAX  DisplayString
	MAX-ACCESS  read-only
	STATUS current
	DESCRIPTION "Channel 44 Friendly Name"
	::= { powerDMEntry  100 }

powerDMChannelFriendly45 OBJECT-TYPE
	SYNTAX  DisplayString
	MAX-ACCESS  read-only
	STATUS current
	DESCRIPTION "Channel 45 Friendly Name"
	::= { powerDMEntry  101 }

powerDMChannelFriendly46 OBJECT-TYPE
	SYNTAX  DisplayString
	MAX-ACCESS  read-only
	STATUS current
	DESCRIPTION "Channel 46 Friendly Name"
	::= { powerDMEntry  102 }

powerDMChannelFriendly47 OBJECT-TYPE
	SYNTAX  DisplayString
	MAX-ACCESS  read-only
	STATUS current
	DESCRIPTION "Channel 47 Friendly Name"
	::= { powerDMEntry  103 }

powerDMChannelFriendly48 OBJECT-TYPE
	SYNTAX  DisplayString
	MAX-ACCESS  read-only
	STATUS current
	DESCRIPTION "Channel 48 Friendly Name"
	::= { powerDMEntry  104 }

powerDMChannelGroup1 OBJECT-TYPE
	SYNTAX  DisplayString
	MAX-ACCESS  read-only
	STATUS current
	DESCRIPTION "Channel 1 Group"
	::= { powerDMEntry  105 }

powerDMChannelGroup2 OBJECT-TYPE
	SYNTAX  DisplayString
	MAX-ACCESS  read-only
	STATUS current
	DESCRIPTION "Channel 2 Group"
	::= { powerDMEntry  106 }

powerDMChannelGroup3 OBJECT-TYPE
	SYNTAX  DisplayString
	MAX-ACCESS  read-only
	STATUS current
	DESCRIPTION "Channel 3 Group"
	::= { powerDMEntry  107 }

powerDMChannelGroup4 OBJECT-TYPE
	SYNTAX  DisplayString
	MAX-ACCESS  read-only
	STATUS current
	DESCRIPTION "Channel 4 Group"
	::= { powerDMEntry  108 }

powerDMChannelGroup5 OBJECT-TYPE
	SYNTAX  DisplayString
	MAX-ACCESS  read-only
	STATUS current
	DESCRIPTION "Channel 5 Group"
	::= { powerDMEntry  109 }

powerDMChannelGroup6 OBJECT-TYPE
	SYNTAX  DisplayString
	MAX-ACCESS  read-only
	STATUS current
	DESCRIPTION "Channel 6 Group"
	::= { powerDMEntry  110 }

powerDMChannelGroup7 OBJECT-TYPE
	SYNTAX  DisplayString
	MAX-ACCESS  read-only
	STATUS current
	DESCRIPTION "Channel 7 Group"
	::= { powerDMEntry  111 }

powerDMChannelGroup8 OBJECT-TYPE
	SYNTAX  DisplayString
	MAX-ACCESS  read-only
	STATUS current
	DESCRIPTION "Channel 8 Group"
	::= { powerDMEntry  112 }

powerDMChannelGroup9 OBJECT-TYPE
	SYNTAX  DisplayString
	MAX-ACCESS  read-only
	STATUS current
	DESCRIPTION "Channel 9 Group"
	::= { powerDMEntry  113 }

powerDMChannelGroup10 OBJECT-TYPE
	SYNTAX  DisplayString
	MAX-ACCESS  read-only
	STATUS current
	DESCRIPTION "Channel 10 Group"
	::= { powerDMEntry  114 }

powerDMChannelGroup11 OBJECT-TYPE
	SYNTAX  DisplayString
	MAX-ACCESS  read-only
	STATUS current
	DESCRIPTION "Channel 11 Group"
	::= { powerDMEntry  115 }

powerDMChannelGroup12 OBJECT-TYPE
	SYNTAX  DisplayString
	MAX-ACCESS  read-only
	STATUS current
	DESCRIPTION "Channel 12 Group"
	::= { powerDMEntry  116 }

powerDMChannelGroup13 OBJECT-TYPE
	SYNTAX  DisplayString
	MAX-ACCESS  read-only
	STATUS current
	DESCRIPTION "Channel 13 Group"
	::= { powerDMEntry  117 }

powerDMChannelGroup14 OBJECT-TYPE
	SYNTAX  DisplayString
	MAX-ACCESS  read-only
	STATUS current
	DESCRIPTION "Channel 14 Group"
	::= { powerDMEntry  118 }

powerDMChannelGroup15 OBJECT-TYPE
	SYNTAX  DisplayString
	MAX-ACCESS  read-only
	STATUS current
	DESCRIPTION "Channel 15 Group"
	::= { powerDMEntry  119 }

powerDMChannelGroup16 OBJECT-TYPE
	SYNTAX  DisplayString
	MAX-ACCESS  read-only
	STATUS current
	DESCRIPTION "Channel 16 Group"
	::= { powerDMEntry  120 }

powerDMChannelGroup17 OBJECT-TYPE
	SYNTAX  DisplayString
	MAX-ACCESS  read-only
	STATUS current
	DESCRIPTION "Channel 17 Group"
	::= { powerDMEntry  121 }

powerDMChannelGroup18 OBJECT-TYPE
	SYNTAX  DisplayString
	MAX-ACCESS  read-only
	STATUS current
	DESCRIPTION "Channel 18 Group"
	::= { powerDMEntry  122 }

powerDMChannelGroup19 OBJECT-TYPE
	SYNTAX  DisplayString
	MAX-ACCESS  read-only
	STATUS current
	DESCRIPTION "Channel 19 Group"
	::= { powerDMEntry  123 }

powerDMChannelGroup20 OBJECT-TYPE
	SYNTAX  DisplayString
	MAX-ACCESS  read-only
	STATUS current
	DESCRIPTION "Channel 20 Group"
	::= { powerDMEntry  124 }

powerDMChannelGroup21 OBJECT-TYPE
	SYNTAX  DisplayString
	MAX-ACCESS  read-only
	STATUS current
	DESCRIPTION "Channel 21 Group"
	::= { powerDMEntry  125 }

powerDMChannelGroup22 OBJECT-TYPE
	SYNTAX  DisplayString
	MAX-ACCESS  read-only
	STATUS current
	DESCRIPTION "Channel 22 Group"
	::= { powerDMEntry  126 }

powerDMChannelGroup23 OBJECT-TYPE
	SYNTAX  DisplayString
	MAX-ACCESS  read-only
	STATUS current
	DESCRIPTION "Channel 23 Group"
	::= { powerDMEntry  127 }

powerDMChannelGroup24 OBJECT-TYPE
	SYNTAX  DisplayString
	MAX-ACCESS  read-only
	STATUS current
	DESCRIPTION "Channel 24 Group"
	::= { powerDMEntry  128 }

powerDMChannelGroup25 OBJECT-TYPE
	SYNTAX  DisplayString
	MAX-ACCESS  read-only
	STATUS current
	DESCRIPTION "Channel 25 Group"
	::= { powerDMEntry  129 }

powerDMChannelGroup26 OBJECT-TYPE
	SYNTAX  DisplayString
	MAX-ACCESS  read-only
	STATUS current
	DESCRIPTION "Channel 26 Group"
	::= { powerDMEntry  130 }

powerDMChannelGroup27 OBJECT-TYPE
	SYNTAX  DisplayString
	MAX-ACCESS  read-only
	STATUS current
	DESCRIPTION "Channel 27 Group"
	::= { powerDMEntry  131 }

powerDMChannelGroup28 OBJECT-TYPE
	SYNTAX  DisplayString
	MAX-ACCESS  read-only
	STATUS current
	DESCRIPTION "Channel 28 Group"
	::= { powerDMEntry  132 }

powerDMChannelGroup29 OBJECT-TYPE
	SYNTAX  DisplayString
	MAX-ACCESS  read-only
	STATUS current
	DESCRIPTION "Channel 29 Group"
	::= { powerDMEntry  133 }

powerDMChannelGroup30 OBJECT-TYPE
	SYNTAX  DisplayString
	MAX-ACCESS  read-only
	STATUS current
	DESCRIPTION "Channel 30 Group"
	::= { powerDMEntry  134 }

powerDMChannelGroup31 OBJECT-TYPE
	SYNTAX  DisplayString
	MAX-ACCESS  read-only
	STATUS current
	DESCRIPTION "Channel 31 Group"
	::= { powerDMEntry  135 }

powerDMChannelGroup32 OBJECT-TYPE
	SYNTAX  DisplayString
	MAX-ACCESS  read-only
	STATUS current
	DESCRIPTION "Channel 32 Group"
	::= { powerDMEntry  136 }

powerDMChannelGroup33 OBJECT-TYPE
	SYNTAX  DisplayString
	MAX-ACCESS  read-only
	STATUS current
	DESCRIPTION "Channel 33 Group"
	::= { powerDMEntry  137 }

powerDMChannelGroup34 OBJECT-TYPE
	SYNTAX  DisplayString
	MAX-ACCESS  read-only
	STATUS current
	DESCRIPTION "Channel 34 Group"
	::= { powerDMEntry  138 }

powerDMChannelGroup35 OBJECT-TYPE
	SYNTAX  DisplayString
	MAX-ACCESS  read-only
	STATUS current
	DESCRIPTION "Channel 35 Group"
	::= { powerDMEntry  139 }

powerDMChannelGroup36 OBJECT-TYPE
	SYNTAX  DisplayString
	MAX-ACCESS  read-only
	STATUS current
	DESCRIPTION "Channel 36 Group"
	::= { powerDMEntry  140 }

powerDMChannelGroup37 OBJECT-TYPE
	SYNTAX  DisplayString
	MAX-ACCESS  read-only
	STATUS current
	DESCRIPTION "Channel 37 Group"
	::= { powerDMEntry  141 }

powerDMChannelGroup38 OBJECT-TYPE
	SYNTAX  DisplayString
	MAX-ACCESS  read-only
	STATUS current
	DESCRIPTION "Channel 38 Group"
	::= { powerDMEntry  142 }

powerDMChannelGroup39 OBJECT-TYPE
	SYNTAX  DisplayString
	MAX-ACCESS  read-only
	STATUS current
	DESCRIPTION "Channel 39 Group"
	::= { powerDMEntry  143 }

powerDMChannelGroup40 OBJECT-TYPE
	SYNTAX  DisplayString
	MAX-ACCESS  read-only
	STATUS current
	DESCRIPTION "Channel 40 Group"
	::= { powerDMEntry  144 }

powerDMChannelGroup41 OBJECT-TYPE
	SYNTAX  DisplayString
	MAX-ACCESS  read-only
	STATUS current
	DESCRIPTION "Channel 41 Group"
	::= { powerDMEntry  145 }

powerDMChannelGroup42 OBJECT-TYPE
	SYNTAX  DisplayString
	MAX-ACCESS  read-only
	STATUS current
	DESCRIPTION "Channel 42 Group"
	::= { powerDMEntry  146 }

powerDMChannelGroup43 OBJECT-TYPE
	SYNTAX  DisplayString
	MAX-ACCESS  read-only
	STATUS current
	DESCRIPTION "Channel 43 Group"
	::= { powerDMEntry  147 }

powerDMChannelGroup44 OBJECT-TYPE
	SYNTAX  DisplayString
	MAX-ACCESS  read-only
	STATUS current
	DESCRIPTION "Channel 44 Group"
	::= { powerDMEntry  148 }

powerDMChannelGroup45 OBJECT-TYPE
	SYNTAX  DisplayString
	MAX-ACCESS  read-only
	STATUS current
	DESCRIPTION "Channel 45 Group"
	::= { powerDMEntry  149 }

powerDMChannelGroup46 OBJECT-TYPE
	SYNTAX  DisplayString
	MAX-ACCESS  read-only
	STATUS current
	DESCRIPTION "Channel 46 Group"
	::= { powerDMEntry  150 }

powerDMChannelGroup47 OBJECT-TYPE
	SYNTAX  DisplayString
	MAX-ACCESS  read-only
	STATUS current
	DESCRIPTION "Channel 47 Group"
	::= { powerDMEntry  151 }

powerDMChannelGroup48 OBJECT-TYPE
	SYNTAX  DisplayString
	MAX-ACCESS  read-only
	STATUS current
	DESCRIPTION "Channel 48 Group"
	::= { powerDMEntry  152 }

powerDMDeciAmps1 OBJECT-TYPE
	SYNTAX  INTEGER(0..1209)
	UNITS "0.1 Amps"
	MAX-ACCESS  read-only
	STATUS current
	DESCRIPTION "Current in deciamps"
	::= { powerDMEntry  153 }

powerDMDeciAmps2 OBJECT-TYPE
	SYNTAX  INTEGER(0..1209)
	UNITS "0.1 Amps"
	MAX-ACCESS  read-only
	STATUS current
	DESCRIPTION "Current in deciamps"
	::= { powerDMEntry  154 }

powerDMDeciAmps3 OBJECT-TYPE
	SYNTAX  INTEGER(0..1209)
	UNITS "0.1 Amps"
	MAX-ACCESS  read-only
	STATUS current
	DESCRIPTION "Current in deciamps"
	::= { powerDMEntry  155 }

powerDMDeciAmps4 OBJECT-TYPE
	SYNTAX  INTEGER(0..1209)
	UNITS "0.1 Amps"
	MAX-ACCESS  read-only
	STATUS current
	DESCRIPTION "Current in deciamps"
	::= { powerDMEntry  156 }

powerDMDeciAmps5 OBJECT-TYPE
	SYNTAX  INTEGER(0..1209)
	UNITS "0.1 Amps"
	MAX-ACCESS  read-only
	STATUS current
	DESCRIPTION "Current in deciamps"
	::= { powerDMEntry  157 }

powerDMDeciAmps6 OBJECT-TYPE
	SYNTAX  INTEGER(0..1209)
	UNITS "0.1 Amps"
	MAX-ACCESS  read-only
	STATUS current
	DESCRIPTION "Current in deciamps"
	::= { powerDMEntry  158 }

powerDMDeciAmps7 OBJECT-TYPE
	SYNTAX  INTEGER(0..1209)
	UNITS "0.1 Amps"
	MAX-ACCESS  read-only
	STATUS current
	DESCRIPTION "Current in deciamps"
	::= { powerDMEntry  159 }

powerDMDeciAmps8 OBJECT-TYPE
	SYNTAX  INTEGER(0..1209)
	UNITS "0.1 Amps"
	MAX-ACCESS  read-only
	STATUS current
	DESCRIPTION "Current in deciamps"
	::= { powerDMEntry  160 }

powerDMDeciAmps9 OBJECT-TYPE
	SYNTAX  INTEGER(0..1209)
	UNITS "0.1 Amps"
	MAX-ACCESS  read-only
	STATUS current
	DESCRIPTION "Current in deciamps"
	::= { powerDMEntry  161 }

powerDMDeciAmps10 OBJECT-TYPE
	SYNTAX  INTEGER(0..1209)
	UNITS "0.1 Amps"
	MAX-ACCESS  read-only
	STATUS current
	DESCRIPTION "Current in deciamps"
	::= { powerDMEntry  162 }

powerDMDeciAmps11 OBJECT-TYPE
	SYNTAX  INTEGER(0..1209)
	UNITS "0.1 Amps"
	MAX-ACCESS  read-only
	STATUS current
	DESCRIPTION "Current in deciamps"
	::= { powerDMEntry  163 }

powerDMDeciAmps12 OBJECT-TYPE
	SYNTAX  INTEGER(0..1209)
	UNITS "0.1 Amps"
	MAX-ACCESS  read-only
	STATUS current
	DESCRIPTION "Current in deciamps"
	::= { powerDMEntry  164 }

powerDMDeciAmps13 OBJECT-TYPE
	SYNTAX  INTEGER(0..1209)
	UNITS "0.1 Amps"
	MAX-ACCESS  read-only
	STATUS current
	DESCRIPTION "Current in deciamps"
	::= { powerDMEntry  165 }

powerDMDeciAmps14 OBJECT-TYPE
	SYNTAX  INTEGER(0..1209)
	UNITS "0.1 Amps"
	MAX-ACCESS  read-only
	STATUS current
	DESCRIPTION "Current in deciamps"
	::= { powerDMEntry  166 }

powerDMDeciAmps15 OBJECT-TYPE
	SYNTAX  INTEGER(0..1209)
	UNITS "0.1 Amps"
	MAX-ACCESS  read-only
	STATUS current
	DESCRIPTION "Current in deciamps"
	::= { powerDMEntry  167 }

powerDMDeciAmps16 OBJECT-TYPE
	SYNTAX  INTEGER(0..1209)
	UNITS "0.1 Amps"
	MAX-ACCESS  read-only
	STATUS current
	DESCRIPTION "Current in deciamps"
	::= { powerDMEntry  168 }

powerDMDeciAmps17 OBJECT-TYPE
	SYNTAX  INTEGER(0..1209)
	UNITS "0.1 Amps"
	MAX-ACCESS  read-only
	STATUS current
	DESCRIPTION "Current in deciamps"
	::= { powerDMEntry  169 }

powerDMDeciAmps18 OBJECT-TYPE
	SYNTAX  INTEGER(0..1209)
	UNITS "0.1 Amps"
	MAX-ACCESS  read-only
	STATUS current
	DESCRIPTION "Current in deciamps"
	::= { powerDMEntry  170 }

powerDMDeciAmps19 OBJECT-TYPE
	SYNTAX  INTEGER(0..1209)
	UNITS "0.1 Amps"
	MAX-ACCESS  read-only
	STATUS current
	DESCRIPTION "Current in deciamps"
	::= { powerDMEntry  171 }

powerDMDeciAmps20 OBJECT-TYPE
	SYNTAX  INTEGER(0..1209)
	UNITS "0.1 Amps"
	MAX-ACCESS  read-only
	STATUS current
	DESCRIPTION "Current in deciamps"
	::= { powerDMEntry  172 }

powerDMDeciAmps21 OBJECT-TYPE
	SYNTAX  INTEGER(0..1209)
	UNITS "0.1 Amps"
	MAX-ACCESS  read-only
	STATUS current
	DESCRIPTION "Current in deciamps"
	::= { powerDMEntry  173 }

powerDMDeciAmps22 OBJECT-TYPE
	SYNTAX  INTEGER(0..1209)
	UNITS "0.1 Amps"
	MAX-ACCESS  read-only
	STATUS current
	DESCRIPTION "Current in deciamps"
	::= { powerDMEntry  174 }

powerDMDeciAmps23 OBJECT-TYPE
	SYNTAX  INTEGER(0..1209)
	UNITS "0.1 Amps"
	MAX-ACCESS  read-only
	STATUS current
	DESCRIPTION "Current in deciamps"
	::= { powerDMEntry  175 }

powerDMDeciAmps24 OBJECT-TYPE
	SYNTAX  INTEGER(0..1209)
	UNITS "0.1 Amps"
	MAX-ACCESS  read-only
	STATUS current
	DESCRIPTION "Current in deciamps"
	::= { powerDMEntry  176 }

powerDMDeciAmps25 OBJECT-TYPE
	SYNTAX  INTEGER(0..1209)
	UNITS "0.1 Amps"
	MAX-ACCESS  read-only
	STATUS current
	DESCRIPTION "Current in deciamps"
	::= { powerDMEntry  177 }

powerDMDeciAmps26 OBJECT-TYPE
	SYNTAX  INTEGER(0..1209)
	UNITS "0.1 Amps"
	MAX-ACCESS  read-only
	STATUS current
	DESCRIPTION "Current in deciamps"
	::= { powerDMEntry  178 }

powerDMDeciAmps27 OBJECT-TYPE
	SYNTAX  INTEGER(0..1209)
	UNITS "0.1 Amps"
	MAX-ACCESS  read-only
	STATUS current
	DESCRIPTION "Current in deciamps"
	::= { powerDMEntry  179 }

powerDMDeciAmps28 OBJECT-TYPE
	SYNTAX  INTEGER(0..1209)
	UNITS "0.1 Amps"
	MAX-ACCESS  read-only
	STATUS current
	DESCRIPTION "Current in deciamps"
	::= { powerDMEntry  180 }

powerDMDeciAmps29 OBJECT-TYPE
	SYNTAX  INTEGER(0..1209)
	UNITS "0.1 Amps"
	MAX-ACCESS  read-only
	STATUS current
	DESCRIPTION "Current in deciamps"
	::= { powerDMEntry  181 }

powerDMDeciAmps30 OBJECT-TYPE
	SYNTAX  INTEGER(0..1209)
	UNITS "0.1 Amps"
	MAX-ACCESS  read-only
	STATUS current
	DESCRIPTION "Current in deciamps"
	::= { powerDMEntry  182 }

powerDMDeciAmps31 OBJECT-TYPE
	SYNTAX  INTEGER(0..1209)
	UNITS "0.1 Amps"
	MAX-ACCESS  read-only
	STATUS current
	DESCRIPTION "Current in deciamps"
	::= { powerDMEntry  183 }

powerDMDeciAmps32 OBJECT-TYPE
	SYNTAX  INTEGER(0..1209)
	UNITS "0.1 Amps"
	MAX-ACCESS  read-only
	STATUS current
	DESCRIPTION "Current in deciamps"
	::= { powerDMEntry  184 }

powerDMDeciAmps33 OBJECT-TYPE
	SYNTAX  INTEGER(0..1209)
	UNITS "0.1 Amps"
	MAX-ACCESS  read-only
	STATUS current
	DESCRIPTION "Current in deciamps"
	::= { powerDMEntry  185 }

powerDMDeciAmps34 OBJECT-TYPE
	SYNTAX  INTEGER(0..1209)
	UNITS "0.1 Amps"
	MAX-ACCESS  read-only
	STATUS current
	DESCRIPTION "Current in deciamps"
	::= { powerDMEntry  186 }

powerDMDeciAmps35 OBJECT-TYPE
	SYNTAX  INTEGER(0..1209)
	UNITS "0.1 Amps"
	MAX-ACCESS  read-only
	STATUS current
	DESCRIPTION "Current in deciamps"
	::= { powerDMEntry  187 }

powerDMDeciAmps36 OBJECT-TYPE
	SYNTAX  INTEGER(0..1209)
	UNITS "0.1 Amps"
	MAX-ACCESS  read-only
	STATUS current
	DESCRIPTION "Current in deciamps"
	::= { powerDMEntry  188 }

powerDMDeciAmps37 OBJECT-TYPE
	SYNTAX  INTEGER(0..1209)
	UNITS "0.1 Amps"
	MAX-ACCESS  read-only
	STATUS current
	DESCRIPTION "Current in deciamps"
	::= { powerDMEntry  189 }

powerDMDeciAmps38 OBJECT-TYPE
	SYNTAX  INTEGER(0..1209)
	UNITS "0.1 Amps"
	MAX-ACCESS  read-only
	STATUS current
	DESCRIPTION "Current in deciamps"
	::= { powerDMEntry  190 }

powerDMDeciAmps39 OBJECT-TYPE
	SYNTAX  INTEGER(0..1209)
	UNITS "0.1 Amps"
	MAX-ACCESS  read-only
	STATUS current
	DESCRIPTION "Current in deciamps"
	::= { powerDMEntry  191 }

powerDMDeciAmps40 OBJECT-TYPE
	SYNTAX  INTEGER(0..1209)
	UNITS "0.1 Amps"
	MAX-ACCESS  read-only
	STATUS current
	DESCRIPTION "Current in deciamps"
	::= { powerDMEntry  192 }

powerDMDeciAmps41 OBJECT-TYPE
	SYNTAX  INTEGER(0..1209)
	UNITS "0.1 Amps"
	MAX-ACCESS  read-only
	STATUS current
	DESCRIPTION "Current in deciamps"
	::= { powerDMEntry  193 }

powerDMDeciAmps42 OBJECT-TYPE
	SYNTAX  INTEGER(0..1209)
	UNITS "0.1 Amps"
	MAX-ACCESS  read-only
	STATUS current
	DESCRIPTION "Current in deciamps"
	::= { powerDMEntry  194 }

powerDMDeciAmps43 OBJECT-TYPE
	SYNTAX  INTEGER(0..1209)
	UNITS "0.1 Amps"
	MAX-ACCESS  read-only
	STATUS current
	DESCRIPTION "Current in deciamps"
	::= { powerDMEntry  195 }

powerDMDeciAmps44 OBJECT-TYPE
	SYNTAX  INTEGER(0..1209)
	UNITS "0.1 Amps"
	MAX-ACCESS  read-only
	STATUS current
	DESCRIPTION "Current in deciamps"
	::= { powerDMEntry  196 }

powerDMDeciAmps45 OBJECT-TYPE
	SYNTAX  INTEGER(0..1209)
	UNITS "0.1 Amps"
	MAX-ACCESS  read-only
	STATUS current
	DESCRIPTION "Current in deciamps"
	::= { powerDMEntry  197 }

powerDMDeciAmps46 OBJECT-TYPE
	SYNTAX  INTEGER(0..1209)
	UNITS "0.1 Amps"
	MAX-ACCESS  read-only
	STATUS current
	DESCRIPTION "Current in deciamps"
	::= { powerDMEntry  198 }

powerDMDeciAmps47 OBJECT-TYPE
	SYNTAX  INTEGER(0..1209)
	UNITS "0.1 Amps"
	MAX-ACCESS  read-only
	STATUS current
	DESCRIPTION "Current in deciamps"
	::= { powerDMEntry  199 }

powerDMDeciAmps48 OBJECT-TYPE
	SYNTAX  INTEGER(0..1209)
	UNITS "0.1 Amps"
	MAX-ACCESS  read-only
	STATUS current
	DESCRIPTION "Current in deciamps"
	::= { powerDMEntry  200 }

odsTrap OBJECT IDENTIFIER ::= { ods 32767 }
odsTrapPrefix OBJECT IDENTIFIER ::= { odsTrap 0 }

odsTestNOTIFY NOTIFICATION-TYPE
	STATUS current
	DESCRIPTION "Test SNMP Trap"
	::= { odsTrapPrefix 10101 }

odsClimateTempCNOTIFY NOTIFICATION-TYPE
OBJECTS { climateTempC, climateName, productFriendlyName, alarmTripType }
STATUS current
DESCRIPTION "Climate Temperature Sensor Trap"
::= { odsTrapPrefix 10205 }

odsClimateTempFNOTIFY NOTIFICATION-TYPE
OBJECTS { climateTempF, climateName, productFriendlyName, alarmTripType }
STATUS current
DESCRIPTION "Climate Temperature Sensor Trap"
::= { odsTrapPrefix 10206 }

odsClimateHumidityNOTIFY NOTIFICATION-TYPE
OBJECTS { climateHumidity, climateName, productFriendlyName, alarmTripType }
STATUS current
DESCRIPTION "Climate Humidity Sensor Trap"
::= { odsTrapPrefix 10207 }

odsClimateLightNOTIFY NOTIFICATION-TYPE
OBJECTS { climateLight, climateName, productFriendlyName, alarmTripType }
STATUS current
DESCRIPTION "Climate Light Sensor Trap"
::= { odsTrapPrefix 10208 }

odsClimateAirflowNOTIFY NOTIFICATION-TYPE
OBJECTS { climateAirflow, climateName, productFriendlyName, alarmTripType }
STATUS current
DESCRIPTION "Climate Air Flow Sensor Trap"
::= { odsTrapPrefix 10209 }

odsClimateSoundNOTIFY NOTIFICATION-TYPE
OBJECTS { climateSound, climateName, productFriendlyName, alarmTripType }
STATUS current
DESCRIPTION "Climate Sound Sensor Trap"
::= { odsTrapPrefix 10210 }

odsClimateIO1NOTIFY NOTIFICATION-TYPE
OBJECTS { climateIO1, climateName, productFriendlyName, alarmTripType }
STATUS current
DESCRIPTION "Climate IO1 Sensor Trap"
::= { odsTrapPrefix 10211 }

odsClimateIO2NOTIFY NOTIFICATION-TYPE
OBJECTS { climateIO2, climateName, productFriendlyName, alarmTripType }
STATUS current
DESCRIPTION "Climate IO2 Sensor Trap"
::= { odsTrapPrefix 10212 }

odsClimateIO3NOTIFY NOTIFICATION-TYPE
OBJECTS { climateIO3, climateName, productFriendlyName, alarmTripType }
STATUS current
DESCRIPTION "Climate IO3 Sensor Trap"
::= { odsTrapPrefix 10213 }

odsDewPointSensorTempCNOTIFY NOTIFICATION-TYPE
OBJECTS { dewPointSensorTempC, dewPointSensorName, productFriendlyName, alarmTripType }
STATUS current
DESCRIPTION "Remote Dew point Sensor - Temperature Clear Trap"
::= { odsTrapPrefix 10305 }

odsDewPointSensorTempFNOTIFY NOTIFICATION-TYPE
OBJECTS { dewPointSensorTempF, dewPointSensorName, productFriendlyName, alarmTripType }
STATUS current
DESCRIPTION "Remote Dew point Sensor - Temperature Clear Trap"
::= { odsTrapPrefix 10306 }

odsDewPointSensorHumidityNOTIFY NOTIFICATION-TYPE
OBJECTS { dewPointSensorHumidity, dewPointSensorName, productFriendlyName, alarmTripType }
STATUS current
DESCRIPTION "Remote Dew point Sensor - Humidity Clear Trap"
::= { odsTrapPrefix 10307 }

odsDewPointSensorDewpointCNOTIFY NOTIFICATION-TYPE
OBJECTS { dewPointSensorDewpointC, dewPointSensorName, productFriendlyName, alarmTripType }
STATUS current
DESCRIPTION "Remote Dew point Sensor - Dew point Clear Trap"
::= { odsTrapPrefix 10308 }

odsDewPointSensorDewpointFNOTIFY NOTIFICATION-TYPE
OBJECTS { dewPointSensorDewpointF, dewPointSensorName, productFriendlyName, alarmTripType }
STATUS current
DESCRIPTION "Remote Dew point Sensor - Dew point Clear Trap"
::= { odsTrapPrefix 10309 }

odsFancontrolTempCreturnANOTIFY NOTIFICATION-TYPE
OBJECTS { fancontrolTempCreturnA, fancontrolName, productFriendlyName, alarmTripType }
STATUS current
DESCRIPTION "TempCreturnA Active Set Point Sensor Clear"
::= { odsTrapPrefix 10405 }

odsFancontrolTempFreturnANOTIFY NOTIFICATION-TYPE
OBJECTS { fancontrolTempFreturnA, fancontrolName, productFriendlyName, alarmTripType }
STATUS current
DESCRIPTION "TempFreturnA Active Set Point Sensor Clear"
::= { odsTrapPrefix 10406 }

odsFancontrolTempCreturnBNOTIFY NOTIFICATION-TYPE
OBJECTS { fancontrolTempCreturnB, fancontrolName, productFriendlyName, alarmTripType }
STATUS current
DESCRIPTION "TempCreturnB Active Set Point Sensor Clear"
::= { odsTrapPrefix 10407 }

odsFancontrolTempFreturnBNOTIFY NOTIFICATION-TYPE
OBJECTS { fancontrolTempFreturnB, fancontrolName, productFriendlyName, alarmTripType }
STATUS current
DESCRIPTION "TempFreturnB Active Set Point Sensor Clear"
::= { odsTrapPrefix 10408 }

odsFancontrolRpmFanANOTIFY NOTIFICATION-TYPE
OBJECTS { fancontrolRpmFanA, fancontrolName, productFriendlyName, alarmTripType }
STATUS current
DESCRIPTION "RpmFanA Active Set Point Sensor Clear"
::= { odsTrapPrefix 10409 }

odsFancontrolRpmFanBNOTIFY NOTIFICATION-TYPE
OBJECTS { fancontrolRpmFanB, fancontrolName, productFriendlyName, alarmTripType }
STATUS current
DESCRIPTION "RpmFanB Active Set Point Sensor Clear"
::= { odsTrapPrefix 10410 }

odsFancontrolCapacityANOTIFY NOTIFICATION-TYPE
OBJECTS { fancontrolCapacityA, fancontrolName, productFriendlyName, alarmTripType }
STATUS current
DESCRIPTION "CapacityA Active Set Point Sensor Clear"
::= { odsTrapPrefix 10411 }

odsFancontrolCapacityBNOTIFY NOTIFICATION-TYPE
OBJECTS { fancontrolCapacityB, fancontrolName, productFriendlyName, alarmTripType }
STATUS current
DESCRIPTION "CapacityB Active Set Point Sensor Clear"
::= { odsTrapPrefix 10412 }

odsFancontrolPressErrNOTIFY NOTIFICATION-TYPE
OBJECTS { fancontrolPressErr, fancontrolName, productFriendlyName, alarmTripType }
STATUS current
DESCRIPTION "PressErr Active Set Point Sensor Clear"
::= { odsTrapPrefix 10413 }

odsFancontrolPressDiffNOTIFY NOTIFICATION-TYPE
OBJECTS { fancontrolPressDiff, fancontrolName, productFriendlyName, alarmTripType }
STATUS current
DESCRIPTION "PressDiff Active Set Point Sensor Clear"
::= { odsTrapPrefix 10414 }

odsFancontrolSetPointNOTIFY NOTIFICATION-TYPE
OBJECTS { fancontrolSetPoint, fancontrolName, productFriendlyName, alarmTripType }
STATUS current
DESCRIPTION "SetPoint Active Set Point Sensor Clear"
::= { odsTrapPrefix 10415 }

odsFancontrolCFMNOTIFY NOTIFICATION-TYPE
OBJECTS { fancontrolCFM, fancontrolName, productFriendlyName, alarmTripType }
STATUS current
DESCRIPTION "CFM Active Set Point Sensor Clear"
::= { odsTrapPrefix 10416 }

odsFancontrolMCHNOTIFY NOTIFICATION-TYPE
OBJECTS { fancontrolMCH, fancontrolName, productFriendlyName, alarmTripType }
STATUS current
DESCRIPTION "MCH Active Set Point Sensor Clear"
::= { odsTrapPrefix 10417 }

odsFancontrolTempCreturnNOTIFY NOTIFICATION-TYPE
OBJECTS { fancontrolTempCreturn, fancontrolName, productFriendlyName, alarmTripType }
STATUS current
DESCRIPTION "TempCreturn Active Set Point Sensor Clear"
::= { odsTrapPrefix 10418 }

odsFancontrolTempFreturnNOTIFY NOTIFICATION-TYPE
OBJECTS { fancontrolTempFreturn, fancontrolName, productFriendlyName, alarmTripType }
STATUS current
DESCRIPTION "TempCreturn Active Set Point Sensor Clear"
::= { odsTrapPrefix 10419 }

odsFancontrolCapacityNOTIFY NOTIFICATION-TYPE
OBJECTS { fancontrolCapacity, fancontrolName, productFriendlyName, alarmTripType }
STATUS current
DESCRIPTION "Capacity Active Set Point Sensor Clear"
::= { odsTrapPrefix 10420 }

odsFancontrolFanMissingNOTIFY NOTIFICATION-TYPE
OBJECTS { fancontrolFanMissing, fancontrolName, productFriendlyName, alarmTripType }
STATUS current
DESCRIPTION "FanMissing Active Set Point Sensor Clear"
::= { odsTrapPrefix 10421 }

odsFancontrolFanMismatchNOTIFY NOTIFICATION-TYPE
OBJECTS { fancontrolFanMismatch, fancontrolName, productFriendlyName, alarmTripType }
STATUS current
DESCRIPTION "FanMismatch Active Set Point Sensor Clear"
::= { odsTrapPrefix 10422 }

odsFancontrolFanErrorANOTIFY NOTIFICATION-TYPE
OBJECTS { fancontrolFanErrorA, fancontrolName, productFriendlyName, alarmTripType }
STATUS current
DESCRIPTION "FanErrorA Active Set Point Sensor Clear"
::= { odsTrapPrefix 10423 }

odsFancontrolFanErrorBNOTIFY NOTIFICATION-TYPE
OBJECTS { fancontrolFanErrorB, fancontrolName, productFriendlyName, alarmTripType }
STATUS current
DESCRIPTION "FanErrorB Active Set Point Sensor Clear"
::= { odsTrapPrefix 10424 }

odsFancontrolTempBus1NOTIFY NOTIFICATION-TYPE
OBJECTS { fancontrolTempBus1, fancontrolName, productFriendlyName, alarmTripType }
STATUS current
DESCRIPTION "TempBus1 Active Set Point Sensor Clear"
::= { odsTrapPrefix 10425 }

odsFancontrolPowerFeedNOTIFY NOTIFICATION-TYPE
OBJECTS { fancontrolPowerFeed, fancontrolName, productFriendlyName, alarmTripType }
STATUS current
DESCRIPTION "PowerFeed Active Set Point Sensor Clear"
::= { odsTrapPrefix 10426 }

odsFancontrolFanEndofLifeNOTIFY NOTIFICATION-TYPE
OBJECTS { fancontrolFanEndofLife, fancontrolName, productFriendlyName, alarmTripType }
STATUS current
DESCRIPTION "FanEndofLife Active Set Point Sensor Clear"
::= { odsTrapPrefix 10427 }

odsTempSensorTempCNOTIFY NOTIFICATION-TYPE
OBJECTS { tempSensorTempC, tempSensorName, productFriendlyName, alarmTripType }
STATUS current
DESCRIPTION "Remote Temp Sensor - Temperature Clear Trap"
::= { odsTrapPrefix 10505 }

odsTempSensorTempFNOTIFY NOTIFICATION-TYPE
OBJECTS { tempSensorTempF, tempSensorName, productFriendlyName, alarmTripType }
STATUS current
DESCRIPTION "Remote Temp Sensor - Temperature Clear Trap"
::= { odsTrapPrefix 10506 }

odsFlowcontrolRpmFanNOTIFY NOTIFICATION-TYPE
OBJECTS { flowcontrolRpmFan, flowcontrolName, productFriendlyName, alarmTripType }
STATUS current
DESCRIPTION "RpmFan Active Set Point Sensor Clear"
::= { odsTrapPrefix 10605 }

odsFlowcontrolCapacityNOTIFY NOTIFICATION-TYPE
OBJECTS { flowcontrolCapacity, flowcontrolName, productFriendlyName, alarmTripType }
STATUS current
DESCRIPTION "Capacity Active Set Point Sensor Clear"
::= { odsTrapPrefix 10606 }

odsFlowcontrolPressErrNOTIFY NOTIFICATION-TYPE
OBJECTS { flowcontrolPressErr, flowcontrolName, productFriendlyName, alarmTripType }
STATUS current
DESCRIPTION "PressErr Active Set Point Sensor Clear"
::= { odsTrapPrefix 10607 }

odsFlowcontrolPressDiffNOTIFY NOTIFICATION-TYPE
OBJECTS { flowcontrolPressDiff, flowcontrolName, productFriendlyName, alarmTripType }
STATUS current
DESCRIPTION "PressDiff Active Set Point Sensor Clear"
::= { odsTrapPrefix 10608 }

odsFlowcontrolSetPointNOTIFY NOTIFICATION-TYPE
OBJECTS { flowcontrolSetPoint, flowcontrolName, productFriendlyName, alarmTripType }
STATUS current
DESCRIPTION "SetPoint Active Set Point Sensor Clear"
::= { odsTrapPrefix 10609 }

odsFlowcontrolCFMNOTIFY NOTIFICATION-TYPE
OBJECTS { flowcontrolCFM, flowcontrolName, productFriendlyName, alarmTripType }
STATUS current
DESCRIPTION "CFM Active Set Point Sensor Clear"
::= { odsTrapPrefix 10610 }

odsFlowcontrolMCHNOTIFY NOTIFICATION-TYPE
OBJECTS { flowcontrolMCH, flowcontrolName, productFriendlyName, alarmTripType }
STATUS current
DESCRIPTION "MCH Active Set Point Sensor Clear"
::= { odsTrapPrefix 10611 }

odsFlowcontrolTempBus1NOTIFY NOTIFICATION-TYPE
OBJECTS { flowcontrolTempBus1, flowcontrolName, productFriendlyName, alarmTripType }
STATUS current
DESCRIPTION "TempBus1 Active Set Point Sensor Clear"
::= { odsTrapPrefix 10612 }

odsFlowcontrolPowerFeedNOTIFY NOTIFICATION-TYPE
OBJECTS { flowcontrolPowerFeed, flowcontrolName, productFriendlyName, alarmTripType }
STATUS current
DESCRIPTION "PowerFeed Active Set Point Sensor Clear"
::= { odsTrapPrefix 10613 }

odsPowerDMDeciAmps1NOTIFY NOTIFICATION-TYPE
OBJECTS { powerDMDeciAmps1, powerDMName, productFriendlyName, alarmTripType }
STATUS current
DESCRIPTION "DM48 Current Monitor Amps Trap"
::= { odsTrapPrefix 107153 }

odsPowerDMDeciAmps2NOTIFY NOTIFICATION-TYPE
OBJECTS { powerDMDeciAmps2, powerDMName, productFriendlyName, alarmTripType }
STATUS current
DESCRIPTION "DM48 Current Monitor Amps Trap"
::= { odsTrapPrefix 107154 }

odsPowerDMDeciAmps3NOTIFY NOTIFICATION-TYPE
OBJECTS { powerDMDeciAmps3, powerDMName, productFriendlyName, alarmTripType }
STATUS current
DESCRIPTION "DM48 Current Monitor Amps Trap"
::= { odsTrapPrefix 107155 }

odsPowerDMDeciAmps4NOTIFY NOTIFICATION-TYPE
OBJECTS { powerDMDeciAmps4, powerDMName, productFriendlyName, alarmTripType }
STATUS current
DESCRIPTION "DM48 Current Monitor Amps Trap"
::= { odsTrapPrefix 107156 }

odsPowerDMDeciAmps5NOTIFY NOTIFICATION-TYPE
OBJECTS { powerDMDeciAmps5, powerDMName, productFriendlyName, alarmTripType }
STATUS current
DESCRIPTION "DM48 Current Monitor Amps Trap"
::= { odsTrapPrefix 107157 }

odsPowerDMDeciAmps6NOTIFY NOTIFICATION-TYPE
OBJECTS { powerDMDeciAmps6, powerDMName, productFriendlyName, alarmTripType }
STATUS current
DESCRIPTION "DM48 Current Monitor Amps Trap"
::= { odsTrapPrefix 107158 }

odsPowerDMDeciAmps7NOTIFY NOTIFICATION-TYPE
OBJECTS { powerDMDeciAmps7, powerDMName, productFriendlyName, alarmTripType }
STATUS current
DESCRIPTION "DM48 Current Monitor Amps Trap"
::= { odsTrapPrefix 107159 }

odsPowerDMDeciAmps8NOTIFY NOTIFICATION-TYPE
OBJECTS { powerDMDeciAmps8, powerDMName, productFriendlyName, alarmTripType }
STATUS current
DESCRIPTION "DM48 Current Monitor Amps Trap"
::= { odsTrapPrefix 107160 }

odsPowerDMDeciAmps9NOTIFY NOTIFICATION-TYPE
OBJECTS { powerDMDeciAmps9, powerDMName, productFriendlyName, alarmTripType }
STATUS current
DESCRIPTION "DM48 Current Monitor Amps Trap"
::= { odsTrapPrefix 107161 }

odsPowerDMDeciAmps10NOTIFY NOTIFICATION-TYPE
OBJECTS { powerDMDeciAmps10, powerDMName, productFriendlyName, alarmTripType }
STATUS current
DESCRIPTION "DM48 Current Monitor Amps Trap"
::= { odsTrapPrefix 107162 }

odsPowerDMDeciAmps11NOTIFY NOTIFICATION-TYPE
OBJECTS { powerDMDeciAmps11, powerDMName, productFriendlyName, alarmTripType }
STATUS current
DESCRIPTION "DM48 Current Monitor Amps Trap"
::= { odsTrapPrefix 107163 }

odsPowerDMDeciAmps12NOTIFY NOTIFICATION-TYPE
OBJECTS { powerDMDeciAmps12, powerDMName, productFriendlyName, alarmTripType }
STATUS current
DESCRIPTION "DM48 Current Monitor Amps Trap"
::= { odsTrapPrefix 107164 }

odsPowerDMDeciAmps13NOTIFY NOTIFICATION-TYPE
OBJECTS { powerDMDeciAmps13, powerDMName, productFriendlyName, alarmTripType }
STATUS current
DESCRIPTION "DM48 Current Monitor Amps Trap"
::= { odsTrapPrefix 107165 }

odsPowerDMDeciAmps14NOTIFY NOTIFICATION-TYPE
OBJECTS { powerDMDeciAmps14, powerDMName, productFriendlyName, alarmTripType }
STATUS current
DESCRIPTION "DM48 Current Monitor Amps Trap"
::= { odsTrapPrefix 107166 }

odsPowerDMDeciAmps15NOTIFY NOTIFICATION-TYPE
OBJECTS { powerDMDeciAmps15, powerDMName, productFriendlyName, alarmTripType }
STATUS current
DESCRIPTION "DM48 Current Monitor Amps Trap"
::= { odsTrapPrefix 107167 }

odsPowerDMDeciAmps16NOTIFY NOTIFICATION-TYPE
OBJECTS { powerDMDeciAmps16, powerDMName, productFriendlyName, alarmTripType }
STATUS current
DESCRIPTION "DM48 Current Monitor Amps Trap"
::= { odsTrapPrefix 107168 }

odsPowerDMDeciAmps17NOTIFY NOTIFICATION-TYPE
OBJECTS { powerDMDeciAmps17, powerDMName, productFriendlyName, alarmTripType }
STATUS current
DESCRIPTION "DM48 Current Monitor Amps Trap"
::= { odsTrapPrefix 107169 }

odsPowerDMDeciAmps18NOTIFY NOTIFICATION-TYPE
OBJECTS { powerDMDeciAmps18, powerDMName, productFriendlyName, alarmTripType }
STATUS current
DESCRIPTION "DM48 Current Monitor Amps Trap"
::= { odsTrapPrefix 107170 }

odsPowerDMDeciAmps19NOTIFY NOTIFICATION-TYPE
OBJECTS { powerDMDeciAmps19, powerDMName, productFriendlyName, alarmTripType }
STATUS current
DESCRIPTION "DM48 Current Monitor Amps Trap"
::= { odsTrapPrefix 107171 }

odsPowerDMDeciAmps20NOTIFY NOTIFICATION-TYPE
OBJECTS { powerDMDeciAmps20, powerDMName, productFriendlyName, alarmTripType }
STATUS current
DESCRIPTION "DM48 Current Monitor Amps Trap"
::= { odsTrapPrefix 107172 }

odsPowerDMDeciAmps21NOTIFY NOTIFICATION-TYPE
OBJECTS { powerDMDeciAmps21, powerDMName, productFriendlyName, alarmTripType }
STATUS current
DESCRIPTION "DM48 Current Monitor Amps Trap"
::= { odsTrapPrefix 107173 }

odsPowerDMDeciAmps22NOTIFY NOTIFICATION-TYPE
OBJECTS { powerDMDeciAmps22, powerDMName, productFriendlyName, alarmTripType }
STATUS current
DESCRIPTION "DM48 Current Monitor Amps Trap"
::= { odsTrapPrefix 107174 }

odsPowerDMDeciAmps23NOTIFY NOTIFICATION-TYPE
OBJECTS { powerDMDeciAmps23, powerDMName, productFriendlyName, alarmTripType }
STATUS current
DESCRIPTION "DM48 Current Monitor Amps Trap"
::= { odsTrapPrefix 107175 }

odsPowerDMDeciAmps24NOTIFY NOTIFICATION-TYPE
OBJECTS { powerDMDeciAmps24, powerDMName, productFriendlyName, alarmTripType }
STATUS current
DESCRIPTION "DM48 Current Monitor Amps Trap"
::= { odsTrapPrefix 107176 }

odsPowerDMDeciAmps25NOTIFY NOTIFICATION-TYPE
OBJECTS { powerDMDeciAmps25, powerDMName, productFriendlyName, alarmTripType }
STATUS current
DESCRIPTION "DM48 Current Monitor Amps Trap"
::= { odsTrapPrefix 107177 }

odsPowerDMDeciAmps26NOTIFY NOTIFICATION-TYPE
OBJECTS { powerDMDeciAmps26, powerDMName, productFriendlyName, alarmTripType }
STATUS current
DESCRIPTION "DM48 Current Monitor Amps Trap"
::= { odsTrapPrefix 107178 }

odsPowerDMDeciAmps27NOTIFY NOTIFICATION-TYPE
OBJECTS { powerDMDeciAmps27, powerDMName, productFriendlyName, alarmTripType }
STATUS current
DESCRIPTION "DM48 Current Monitor Amps Trap"
::= { odsTrapPrefix 107179 }

odsPowerDMDeciAmps28NOTIFY NOTIFICATION-TYPE
OBJECTS { powerDMDeciAmps28, powerDMName, productFriendlyName, alarmTripType }
STATUS current
DESCRIPTION "DM48 Current Monitor Amps Trap"
::= { odsTrapPrefix 107180 }

odsPowerDMDeciAmps29NOTIFY NOTIFICATION-TYPE
OBJECTS { powerDMDeciAmps29, powerDMName, productFriendlyName, alarmTripType }
STATUS current
DESCRIPTION "DM48 Current Monitor Amps Trap"
::= { odsTrapPrefix 107181 }

odsPowerDMDeciAmps30NOTIFY NOTIFICATION-TYPE
OBJECTS { powerDMDeciAmps30, powerDMName, productFriendlyName, alarmTripType }
STATUS current
DESCRIPTION "DM48 Current Monitor Amps Trap"
::= { odsTrapPrefix 107182 }

odsPowerDMDeciAmps31NOTIFY NOTIFICATION-TYPE
OBJECTS { powerDMDeciAmps31, powerDMName, productFriendlyName, alarmTripType }
STATUS current
DESCRIPTION "DM48 Current Monitor Amps Trap"
::= { odsTrapPrefix 107183 }

odsPowerDMDeciAmps32NOTIFY NOTIFICATION-TYPE
OBJECTS { powerDMDeciAmps32, powerDMName, productFriendlyName, alarmTripType }
STATUS current
DESCRIPTION "DM48 Current Monitor Amps Trap"
::= { odsTrapPrefix 107184 }

odsPowerDMDeciAmps33NOTIFY NOTIFICATION-TYPE
OBJECTS { powerDMDeciAmps33, powerDMName, productFriendlyName, alarmTripType }
STATUS current
DESCRIPTION "DM48 Current Monitor Amps Trap"
::= { odsTrapPrefix 107185 }

odsPowerDMDeciAmps34NOTIFY NOTIFICATION-TYPE
OBJECTS { powerDMDeciAmps34, powerDMName, productFriendlyName, alarmTripType }
STATUS current
DESCRIPTION "DM48 Current Monitor Amps Trap"
::= { odsTrapPrefix 107186 }

odsPowerDMDeciAmps35NOTIFY NOTIFICATION-TYPE
OBJECTS { powerDMDeciAmps35, powerDMName, productFriendlyName, alarmTripType }
STATUS current
DESCRIPTION "DM48 Current Monitor Amps Trap"
::= { odsTrapPrefix 107187 }

odsPowerDMDeciAmps36NOTIFY NOTIFICATION-TYPE
OBJECTS { powerDMDeciAmps36, powerDMName, productFriendlyName, alarmTripType }
STATUS current
DESCRIPTION "DM48 Current Monitor Amps Trap"
::= { odsTrapPrefix 107188 }

odsPowerDMDeciAmps37NOTIFY NOTIFICATION-TYPE
OBJECTS { powerDMDeciAmps37, powerDMName, productFriendlyName, alarmTripType }
STATUS current
DESCRIPTION "DM48 Current Monitor Amps Trap"
::= { odsTrapPrefix 107189 }

odsPowerDMDeciAmps38NOTIFY NOTIFICATION-TYPE
OBJECTS { powerDMDeciAmps38, powerDMName, productFriendlyName, alarmTripType }
STATUS current
DESCRIPTION "DM48 Current Monitor Amps Trap"
::= { odsTrapPrefix 107190 }

odsPowerDMDeciAmps39NOTIFY NOTIFICATION-TYPE
OBJECTS { powerDMDeciAmps39, powerDMName, productFriendlyName, alarmTripType }
STATUS current
DESCRIPTION "DM48 Current Monitor Amps Trap"
::= { odsTrapPrefix 107191 }

odsPowerDMDeciAmps40NOTIFY NOTIFICATION-TYPE
OBJECTS { powerDMDeciAmps40, powerDMName, productFriendlyName, alarmTripType }
STATUS current
DESCRIPTION "DM48 Current Monitor Amps Trap"
::= { odsTrapPrefix 107192 }

odsPowerDMDeciAmps41NOTIFY NOTIFICATION-TYPE
OBJECTS { powerDMDeciAmps41, powerDMName, productFriendlyName, alarmTripType }
STATUS current
DESCRIPTION "DM48 Current Monitor Amps Trap"
::= { odsTrapPrefix 107193 }

odsPowerDMDeciAmps42NOTIFY NOTIFICATION-TYPE
OBJECTS { powerDMDeciAmps42, powerDMName, productFriendlyName, alarmTripType }
STATUS current
DESCRIPTION "DM48 Current Monitor Amps Trap"
::= { odsTrapPrefix 107194 }

odsPowerDMDeciAmps43NOTIFY NOTIFICATION-TYPE
OBJECTS { powerDMDeciAmps43, powerDMName, productFriendlyName, alarmTripType }
STATUS current
DESCRIPTION "DM48 Current Monitor Amps Trap"
::= { odsTrapPrefix 107195 }

odsPowerDMDeciAmps44NOTIFY NOTIFICATION-TYPE
OBJECTS { powerDMDeciAmps44, powerDMName, productFriendlyName, alarmTripType }
STATUS current
DESCRIPTION "DM48 Current Monitor Amps Trap"
::= { odsTrapPrefix 107196 }

odsPowerDMDeciAmps45NOTIFY NOTIFICATION-TYPE
OBJECTS { powerDMDeciAmps45, powerDMName, productFriendlyName, alarmTripType }
STATUS current
DESCRIPTION "DM48 Current Monitor Amps Trap"
::= { odsTrapPrefix 107197 }

odsPowerDMDeciAmps46NOTIFY NOTIFICATION-TYPE
OBJECTS { powerDMDeciAmps46, powerDMName, productFriendlyName, alarmTripType }
STATUS current
DESCRIPTION "DM48 Current Monitor Amps Trap"
::= { odsTrapPrefix 107198 }

odsPowerDMDeciAmps47NOTIFY NOTIFICATION-TYPE
OBJECTS { powerDMDeciAmps47, powerDMName, productFriendlyName, alarmTripType }
STATUS current
DESCRIPTION "DM48 Current Monitor Amps Trap"
::= { odsTrapPrefix 107199 }

odsPowerDMDeciAmps48NOTIFY NOTIFICATION-TYPE
OBJECTS { powerDMDeciAmps48, powerDMName, productFriendlyName, alarmTripType }
STATUS current
DESCRIPTION "DM48 Current Monitor Amps Trap"
::= { odsTrapPrefix 107200 }

odsClimateTempCCLEAR NOTIFICATION-TYPE
OBJECTS { climateTempC, climateName, productFriendlyName, alarmTripType }
STATUS current
DESCRIPTION "Climate Temperature Sensor Clear Trap"
::= { odsTrapPrefix 20205 }

odsClimateTempFCLEAR NOTIFICATION-TYPE
OBJECTS { climateTempF, climateName, productFriendlyName, alarmTripType }
STATUS current
DESCRIPTION "Climate Temperature Sensor Clear Trap"
::= { odsTrapPrefix 20206 }

odsClimateHumidityCLEAR NOTIFICATION-TYPE
OBJECTS { climateHumidity, climateName, productFriendlyName, alarmTripType }
STATUS current
DESCRIPTION "Climate Humidity Sensor Clear Trap"
::= { odsTrapPrefix 20207 }

odsClimateLightCLEAR NOTIFICATION-TYPE
OBJECTS { climateLight, climateName, productFriendlyName, alarmTripType }
STATUS current
DESCRIPTION "Climate Light Sensor Clear Trap"
::= { odsTrapPrefix 20208 }

odsClimateAirflowCLEAR NOTIFICATION-TYPE
OBJECTS { climateAirflow, climateName, productFriendlyName, alarmTripType }
STATUS current
DESCRIPTION "Climate Air Flow Sensor Clear Trap"
::= { odsTrapPrefix 20209 }

odsClimateSoundCLEAR NOTIFICATION-TYPE
OBJECTS { climateSound, climateName, productFriendlyName, alarmTripType }
STATUS current
DESCRIPTION "Climate Sound Sensor Clear Trap"
::= { odsTrapPrefix 20210 }

odsClimateIO1CLEAR NOTIFICATION-TYPE
OBJECTS { climateIO1, climateName, productFriendlyName, alarmTripType }
STATUS current
DESCRIPTION "Climate IO1 Sensor Clear Trap"
::= { odsTrapPrefix 20211 }

odsClimateIO2CLEAR NOTIFICATION-TYPE
OBJECTS { climateIO2, climateName, productFriendlyName, alarmTripType }
STATUS current
DESCRIPTION "Climate IO2 Sensor Clear Trap"
::= { odsTrapPrefix 20212 }

odsClimateIO3CLEAR NOTIFICATION-TYPE
OBJECTS { climateIO3, climateName, productFriendlyName, alarmTripType }
STATUS current
DESCRIPTION "Climate IO3 Sensor Clear Trap"
::= { odsTrapPrefix 20213 }

odsDewPointSensorTempCCLEAR NOTIFICATION-TYPE
OBJECTS { dewPointSensorTempC, dewPointSensorName, productFriendlyName, alarmTripType }
STATUS current
DESCRIPTION "TempC Clear Trap"
::= { odsTrapPrefix 20305 }

odsDewPointSensorTempFCLEAR NOTIFICATION-TYPE
OBJECTS { dewPointSensorTempF, dewPointSensorName, productFriendlyName, alarmTripType }
STATUS current
DESCRIPTION "TempF Clear Trap"
::= { odsTrapPrefix 20306 }

odsDewPointSensorHumidityCLEAR NOTIFICATION-TYPE
OBJECTS { dewPointSensorHumidity, dewPointSensorName, productFriendlyName, alarmTripType }
STATUS current
DESCRIPTION "Humidity Clear Trap"
::= { odsTrapPrefix 20307 }

odsDewPointSensorDewpointCCLEAR NOTIFICATION-TYPE
OBJECTS { dewPointSensorDewpointC, dewPointSensorName, productFriendlyName, alarmTripType }
STATUS current
DESCRIPTION "DewpointC Clear Trap"
::= { odsTrapPrefix 20308 }

odsDewPointSensorDewpointFCLEAR NOTIFICATION-TYPE
OBJECTS { dewPointSensorDewpointF, dewPointSensorName, productFriendlyName, alarmTripType }
STATUS current
DESCRIPTION "DewpointF Clear Trap"
::= { odsTrapPrefix 20309 }

odsFancontrolTempCreturnACLEAR NOTIFICATION-TYPE
OBJECTS { fancontrolTempCreturnA, fancontrolName, productFriendlyName, alarmTripType }
STATUS current
DESCRIPTION "TempCreturnA Clear Trap"
::= { odsTrapPrefix 20405 }

odsFancontrolTempFreturnACLEAR NOTIFICATION-TYPE
OBJECTS { fancontrolTempFreturnA, fancontrolName, productFriendlyName, alarmTripType }
STATUS current
DESCRIPTION "TempFreturnA Clear Trap"
::= { odsTrapPrefix 20406 }

odsFancontrolTempCreturnBCLEAR NOTIFICATION-TYPE
OBJECTS { fancontrolTempCreturnB, fancontrolName, productFriendlyName, alarmTripType }
STATUS current
DESCRIPTION "TempCreturnB Clear Trap"
::= { odsTrapPrefix 20407 }

odsFancontrolTempFreturnBCLEAR NOTIFICATION-TYPE
OBJECTS { fancontrolTempFreturnB, fancontrolName, productFriendlyName, alarmTripType }
STATUS current
DESCRIPTION "TempFreturnB Clear Trap"
::= { odsTrapPrefix 20408 }

odsFancontrolRpmFanACLEAR NOTIFICATION-TYPE
OBJECTS { fancontrolRpmFanA, fancontrolName, productFriendlyName, alarmTripType }
STATUS current
DESCRIPTION "RpmFanA Clear Trap"
::= { odsTrapPrefix 20409 }

odsFancontrolRpmFanBCLEAR NOTIFICATION-TYPE
OBJECTS { fancontrolRpmFanB, fancontrolName, productFriendlyName, alarmTripType }
STATUS current
DESCRIPTION "RpmFanB Clear Trap"
::= { odsTrapPrefix 20410 }

odsFancontrolCapacityACLEAR NOTIFICATION-TYPE
OBJECTS { fancontrolCapacityA, fancontrolName, productFriendlyName, alarmTripType }
STATUS current
DESCRIPTION "CapacityA Clear Trap"
::= { odsTrapPrefix 20411 }

odsFancontrolCapacityBCLEAR NOTIFICATION-TYPE
OBJECTS { fancontrolCapacityB, fancontrolName, productFriendlyName, alarmTripType }
STATUS current
DESCRIPTION "CapacityB Clear Trap"
::= { odsTrapPrefix 20412 }

odsFancontrolPressErrCLEAR NOTIFICATION-TYPE
OBJECTS { fancontrolPressErr, fancontrolName, productFriendlyName, alarmTripType }
STATUS current
DESCRIPTION "PressErr Clear Trap"
::= { odsTrapPrefix 20413 }

odsFancontrolPressDiffCLEAR NOTIFICATION-TYPE
OBJECTS { fancontrolPressDiff, fancontrolName, productFriendlyName, alarmTripType }
STATUS current
DESCRIPTION "PressDiff Clear Trap"
::= { odsTrapPrefix 20414 }

odsFancontrolSetPointCLEAR NOTIFICATION-TYPE
OBJECTS { fancontrolSetPoint, fancontrolName, productFriendlyName, alarmTripType }
STATUS current
DESCRIPTION "SetPoint Clear Trap"
::= { odsTrapPrefix 20415 }

odsFancontrolCFMCLEAR NOTIFICATION-TYPE
OBJECTS { fancontrolCFM, fancontrolName, productFriendlyName, alarmTripType }
STATUS current
DESCRIPTION "CFM Clear Trap"
::= { odsTrapPrefix 20416 }

odsFancontrolMCHCLEAR NOTIFICATION-TYPE
OBJECTS { fancontrolMCH, fancontrolName, productFriendlyName, alarmTripType }
STATUS current
DESCRIPTION "MCH Clear Trap"
::= { odsTrapPrefix 20417 }

odsFancontrolTempCreturnCLEAR NOTIFICATION-TYPE
OBJECTS { fancontrolTempCreturn, fancontrolName, productFriendlyName, alarmTripType }
STATUS current
DESCRIPTION "TempCreturn Clear Trap"
::= { odsTrapPrefix 20418 }

odsFancontrolTempFreturnCLEAR NOTIFICATION-TYPE
OBJECTS { fancontrolTempFreturn, fancontrolName, productFriendlyName, alarmTripType }
STATUS current
DESCRIPTION "TempFreturn Clear Trap"
::= { odsTrapPrefix 20419 }

odsFancontrolCapacityCLEAR NOTIFICATION-TYPE
OBJECTS { fancontrolCapacity, fancontrolName, productFriendlyName, alarmTripType }
STATUS current
DESCRIPTION "Capacity Clear Trap"
::= { odsTrapPrefix 20420 }

odsFancontrolFanMissingCLEAR NOTIFICATION-TYPE
OBJECTS { fancontrolFanMissing, fancontrolName, productFriendlyName, alarmTripType }
STATUS current
DESCRIPTION "FanMissing Clear Trap"
::= { odsTrapPrefix 20421 }

odsFancontrolFanMismatchCLEAR NOTIFICATION-TYPE
OBJECTS { fancontrolFanMismatch, fancontrolName, productFriendlyName, alarmTripType }
STATUS current
DESCRIPTION "FanMismatch Clear Trap"
::= { odsTrapPrefix 20422 }

odsFancontrolFanErrorACLEAR NOTIFICATION-TYPE
OBJECTS { fancontrolFanErrorA, fancontrolName, productFriendlyName, alarmTripType }
STATUS current
DESCRIPTION "FanErrorA Clear Trap"
::= { odsTrapPrefix 20423 }

odsFancontrolFanErrorBCLEAR NOTIFICATION-TYPE
OBJECTS { fancontrolFanErrorB, fancontrolName, productFriendlyName, alarmTripType }
STATUS current
DESCRIPTION "FanErrorB Clear Trap"
::= { odsTrapPrefix 20424 }

odsFancontrolTempBus1CLEAR NOTIFICATION-TYPE
OBJECTS { fancontrolTempBus1, fancontrolName, productFriendlyName, alarmTripType }
STATUS current
DESCRIPTION "TempBus1 Clear Trap"
::= { odsTrapPrefix 20425 }

odsFancontrolPowerFeedCLEAR NOTIFICATION-TYPE
OBJECTS { fancontrolPowerFeed, fancontrolName, productFriendlyName, alarmTripType }
STATUS current
DESCRIPTION "PowerFeed Clear Trap"
::= { odsTrapPrefix 20426 }

odsFancontrolFanEndofLifeCLEAR NOTIFICATION-TYPE
OBJECTS { fancontrolFanEndofLife, fancontrolName, productFriendlyName, alarmTripType }
STATUS current
DESCRIPTION "FanEndofLife Clear Trap"
::= { odsTrapPrefix 20427 }

odsTempSensorTempCCLEAR NOTIFICATION-TYPE
OBJECTS { tempSensorTempC, tempSensorName, productFriendlyName, alarmTripType }
STATUS current
DESCRIPTION "TempC Clear Trap"
::= { odsTrapPrefix 20505 }

odsTempSensorTempFCLEAR NOTIFICATION-TYPE
OBJECTS { tempSensorTempF, tempSensorName, productFriendlyName, alarmTripType }
STATUS current
DESCRIPTION "TempF Clear Trap"
::= { odsTrapPrefix 20506 }

odsFlowcontrolRpmFanCLEAR NOTIFICATION-TYPE
OBJECTS { flowcontrolRpmFan, flowcontrolName, productFriendlyName, alarmTripType }
STATUS current
DESCRIPTION "RpmFan Clear Trap"
::= { odsTrapPrefix 20605 }

odsFlowcontrolCapacityCLEAR NOTIFICATION-TYPE
OBJECTS { flowcontrolCapacity, flowcontrolName, productFriendlyName, alarmTripType }
STATUS current
DESCRIPTION "Capacity Clear Trap"
::= { odsTrapPrefix 20606 }

odsFlowcontrolPressErrCLEAR NOTIFICATION-TYPE
OBJECTS { flowcontrolPressErr, flowcontrolName, productFriendlyName, alarmTripType }
STATUS current
DESCRIPTION "PressErr Clear Trap"
::= { odsTrapPrefix 20607 }

odsFlowcontrolPressDiffCLEAR NOTIFICATION-TYPE
OBJECTS { flowcontrolPressDiff, flowcontrolName, productFriendlyName, alarmTripType }
STATUS current
DESCRIPTION "PressDiff Clear Trap"
::= { odsTrapPrefix 20608 }

odsFlowcontrolSetPointCLEAR NOTIFICATION-TYPE
OBJECTS { flowcontrolSetPoint, flowcontrolName, productFriendlyName, alarmTripType }
STATUS current
DESCRIPTION "SetPoint Clear Trap"
::= { odsTrapPrefix 20609 }

odsFlowcontrolCFMCLEAR NOTIFICATION-TYPE
OBJECTS { flowcontrolCFM, flowcontrolName, productFriendlyName, alarmTripType }
STATUS current
DESCRIPTION "CFM Clear Trap"
::= { odsTrapPrefix 20610 }

odsFlowcontrolMCHCLEAR NOTIFICATION-TYPE
OBJECTS { flowcontrolMCH, flowcontrolName, productFriendlyName, alarmTripType }
STATUS current
DESCRIPTION "MCH Clear Trap"
::= { odsTrapPrefix 20611 }

odsFlowcontrolTempBus1CLEAR NOTIFICATION-TYPE
OBJECTS { flowcontrolTempBus1, flowcontrolName, productFriendlyName, alarmTripType }
STATUS current
DESCRIPTION "TempBus1 Clear Trap"
::= { odsTrapPrefix 20612 }

odsFlowcontrolPowerFeedCLEAR NOTIFICATION-TYPE
OBJECTS { flowcontrolPowerFeed, flowcontrolName, productFriendlyName, alarmTripType }
STATUS current
DESCRIPTION "PowerFeed Clear Trap"
::= { odsTrapPrefix 20613 }

odsPowerDMDeciAmps1CLEAR NOTIFICATION-TYPE
OBJECTS { powerDMDeciAmps1, powerDMName, productFriendlyName, alarmTripType }
STATUS current
DESCRIPTION "DM48 Current Monitor Amps Clear Trap"
::= { odsTrapPrefix 207153 }

odsPowerDMDeciAmps2CLEAR NOTIFICATION-TYPE
OBJECTS { powerDMDeciAmps2, powerDMName, productFriendlyName, alarmTripType }
STATUS current
DESCRIPTION "DM48 Current Monitor Amps Clear Trap"
::= { odsTrapPrefix 207154 }

odsPowerDMDeciAmps3CLEAR NOTIFICATION-TYPE
OBJECTS { powerDMDeciAmps3, powerDMName, productFriendlyName, alarmTripType }
STATUS current
DESCRIPTION "DM48 Current Monitor Amps Clear Trap"
::= { odsTrapPrefix 207155 }

odsPowerDMDeciAmps4CLEAR NOTIFICATION-TYPE
OBJECTS { powerDMDeciAmps4, powerDMName, productFriendlyName, alarmTripType }
STATUS current
DESCRIPTION "DM48 Current Monitor Amps Clear Trap"
::= { odsTrapPrefix 207156 }

odsPowerDMDeciAmps5CLEAR NOTIFICATION-TYPE
OBJECTS { powerDMDeciAmps5, powerDMName, productFriendlyName, alarmTripType }
STATUS current
DESCRIPTION "DM48 Current Monitor Amps Clear Trap"
::= { odsTrapPrefix 207157 }

odsPowerDMDeciAmps6CLEAR NOTIFICATION-TYPE
OBJECTS { powerDMDeciAmps6, powerDMName, productFriendlyName, alarmTripType }
STATUS current
DESCRIPTION "DM48 Current Monitor Amps Clear Trap"
::= { odsTrapPrefix 207158 }

odsPowerDMDeciAmps7CLEAR NOTIFICATION-TYPE
OBJECTS { powerDMDeciAmps7, powerDMName, productFriendlyName, alarmTripType }
STATUS current
DESCRIPTION "DM48 Current Monitor Amps Clear Trap"
::= { odsTrapPrefix 207159 }

odsPowerDMDeciAmps8CLEAR NOTIFICATION-TYPE
OBJECTS { powerDMDeciAmps8, powerDMName, productFriendlyName, alarmTripType }
STATUS current
DESCRIPTION "DM48 Current Monitor Amps Clear Trap"
::= { odsTrapPrefix 207160 }

odsPowerDMDeciAmps9CLEAR NOTIFICATION-TYPE
OBJECTS { powerDMDeciAmps9, powerDMName, productFriendlyName, alarmTripType }
STATUS current
DESCRIPTION "DM48 Current Monitor Amps Clear Trap"
::= { odsTrapPrefix 207161 }

odsPowerDMDeciAmps10CLEAR NOTIFICATION-TYPE
OBJECTS { powerDMDeciAmps10, powerDMName, productFriendlyName, alarmTripType }
STATUS current
DESCRIPTION "DM48 Current Monitor Amps Clear Trap"
::= { odsTrapPrefix 207162 }

odsPowerDMDeciAmps11CLEAR NOTIFICATION-TYPE
OBJECTS { powerDMDeciAmps11, powerDMName, productFriendlyName, alarmTripType }
STATUS current
DESCRIPTION "DM48 Current Monitor Amps Clear Trap"
::= { odsTrapPrefix 207163 }

odsPowerDMDeciAmps12CLEAR NOTIFICATION-TYPE
OBJECTS { powerDMDeciAmps12, powerDMName, productFriendlyName, alarmTripType }
STATUS current
DESCRIPTION "DM48 Current Monitor Amps Clear Trap"
::= { odsTrapPrefix 207164 }

odsPowerDMDeciAmps13CLEAR NOTIFICATION-TYPE
OBJECTS { powerDMDeciAmps13, powerDMName, productFriendlyName, alarmTripType }
STATUS current
DESCRIPTION "DM48 Current Monitor Amps Clear Trap"
::= { odsTrapPrefix 207165 }

odsPowerDMDeciAmps14CLEAR NOTIFICATION-TYPE
OBJECTS { powerDMDeciAmps14, powerDMName, productFriendlyName, alarmTripType }
STATUS current
DESCRIPTION "DM48 Current Monitor Amps Clear Trap"
::= { odsTrapPrefix 207166 }

odsPowerDMDeciAmps15CLEAR NOTIFICATION-TYPE
OBJECTS { powerDMDeciAmps15, powerDMName, productFriendlyName, alarmTripType }
STATUS current
DESCRIPTION "DM48 Current Monitor Amps Clear Trap"
::= { odsTrapPrefix 207167 }

odsPowerDMDeciAmps16CLEAR NOTIFICATION-TYPE
OBJECTS { powerDMDeciAmps16, powerDMName, productFriendlyName, alarmTripType }
STATUS current
DESCRIPTION "DM48 Current Monitor Amps Clear Trap"
::= { odsTrapPrefix 207168 }

odsPowerDMDeciAmps17CLEAR NOTIFICATION-TYPE
OBJECTS { powerDMDeciAmps17, powerDMName, productFriendlyName, alarmTripType }
STATUS current
DESCRIPTION "DM48 Current Monitor Amps Clear Trap"
::= { odsTrapPrefix 207169 }

odsPowerDMDeciAmps18CLEAR NOTIFICATION-TYPE
OBJECTS { powerDMDeciAmps18, powerDMName, productFriendlyName, alarmTripType }
STATUS current
DESCRIPTION "DM48 Current Monitor Amps Clear Trap"
::= { odsTrapPrefix 207170 }

odsPowerDMDeciAmps19CLEAR NOTIFICATION-TYPE
OBJECTS { powerDMDeciAmps19, powerDMName, productFriendlyName, alarmTripType }
STATUS current
DESCRIPTION "DM48 Current Monitor Amps Clear Trap"
::= { odsTrapPrefix 207171 }

odsPowerDMDeciAmps20CLEAR NOTIFICATION-TYPE
OBJECTS { powerDMDeciAmps20, powerDMName, productFriendlyName, alarmTripType }
STATUS current
DESCRIPTION "DM48 Current Monitor Amps Clear Trap"
::= { odsTrapPrefix 207172 }

odsPowerDMDeciAmps21CLEAR NOTIFICATION-TYPE
OBJECTS { powerDMDeciAmps21, powerDMName, productFriendlyName, alarmTripType }
STATUS current
DESCRIPTION "DM48 Current Monitor Amps Clear Trap"
::= { odsTrapPrefix 207173 }

odsPowerDMDeciAmps22CLEAR NOTIFICATION-TYPE
OBJECTS { powerDMDeciAmps22, powerDMName, productFriendlyName, alarmTripType }
STATUS current
DESCRIPTION "DM48 Current Monitor Amps Clear Trap"
::= { odsTrapPrefix 207174 }

odsPowerDMDeciAmps23CLEAR NOTIFICATION-TYPE
OBJECTS { powerDMDeciAmps23, powerDMName, productFriendlyName, alarmTripType }
STATUS current
DESCRIPTION "DM48 Current Monitor Amps Clear Trap"
::= { odsTrapPrefix 207175 }

odsPowerDMDeciAmps24CLEAR NOTIFICATION-TYPE
OBJECTS { powerDMDeciAmps24, powerDMName, productFriendlyName, alarmTripType }
STATUS current
DESCRIPTION "DM48 Current Monitor Amps Clear Trap"
::= { odsTrapPrefix 207176 }

odsPowerDMDeciAmps25CLEAR NOTIFICATION-TYPE
OBJECTS { powerDMDeciAmps25, powerDMName, productFriendlyName, alarmTripType }
STATUS current
DESCRIPTION "DM48 Current Monitor Amps Clear Trap"
::= { odsTrapPrefix 207177 }

odsPowerDMDeciAmps26CLEAR NOTIFICATION-TYPE
OBJECTS { powerDMDeciAmps26, powerDMName, productFriendlyName, alarmTripType }
STATUS current
DESCRIPTION "DM48 Current Monitor Amps Clear Trap"
::= { odsTrapPrefix 207178 }

odsPowerDMDeciAmps27CLEAR NOTIFICATION-TYPE
OBJECTS { powerDMDeciAmps27, powerDMName, productFriendlyName, alarmTripType }
STATUS current
DESCRIPTION "DM48 Current Monitor Amps Clear Trap"
::= { odsTrapPrefix 207179 }

odsPowerDMDeciAmps28CLEAR NOTIFICATION-TYPE
OBJECTS { powerDMDeciAmps28, powerDMName, productFriendlyName, alarmTripType }
STATUS current
DESCRIPTION "DM48 Current Monitor Amps Clear Trap"
::= { odsTrapPrefix 207180 }

odsPowerDMDeciAmps29CLEAR NOTIFICATION-TYPE
OBJECTS { powerDMDeciAmps29, powerDMName, productFriendlyName, alarmTripType }
STATUS current
DESCRIPTION "DM48 Current Monitor Amps Clear Trap"
::= { odsTrapPrefix 207181 }

odsPowerDMDeciAmps30CLEAR NOTIFICATION-TYPE
OBJECTS { powerDMDeciAmps30, powerDMName, productFriendlyName, alarmTripType }
STATUS current
DESCRIPTION "DM48 Current Monitor Amps Clear Trap"
::= { odsTrapPrefix 207182 }

odsPowerDMDeciAmps31CLEAR NOTIFICATION-TYPE
OBJECTS { powerDMDeciAmps31, powerDMName, productFriendlyName, alarmTripType }
STATUS current
DESCRIPTION "DM48 Current Monitor Amps Clear Trap"
::= { odsTrapPrefix 207183 }

odsPowerDMDeciAmps32CLEAR NOTIFICATION-TYPE
OBJECTS { powerDMDeciAmps32, powerDMName, productFriendlyName, alarmTripType }
STATUS current
DESCRIPTION "DM48 Current Monitor Amps Clear Trap"
::= { odsTrapPrefix 207184 }

odsPowerDMDeciAmps33CLEAR NOTIFICATION-TYPE
OBJECTS { powerDMDeciAmps33, powerDMName, productFriendlyName, alarmTripType }
STATUS current
DESCRIPTION "DM48 Current Monitor Amps Clear Trap"
::= { odsTrapPrefix 207185 }

odsPowerDMDeciAmps34CLEAR NOTIFICATION-TYPE
OBJECTS { powerDMDeciAmps34, powerDMName, productFriendlyName, alarmTripType }
STATUS current
DESCRIPTION "DM48 Current Monitor Amps Clear Trap"
::= { odsTrapPrefix 207186 }

odsPowerDMDeciAmps35CLEAR NOTIFICATION-TYPE
OBJECTS { powerDMDeciAmps35, powerDMName, productFriendlyName, alarmTripType }
STATUS current
DESCRIPTION "DM48 Current Monitor Amps Clear Trap"
::= { odsTrapPrefix 207187 }

odsPowerDMDeciAmps36CLEAR NOTIFICATION-TYPE
OBJECTS { powerDMDeciAmps36, powerDMName, productFriendlyName, alarmTripType }
STATUS current
DESCRIPTION "DM48 Current Monitor Amps Clear Trap"
::= { odsTrapPrefix 207188 }

odsPowerDMDeciAmps37CLEAR NOTIFICATION-TYPE
OBJECTS { powerDMDeciAmps37, powerDMName, productFriendlyName, alarmTripType }
STATUS current
DESCRIPTION "DM48 Current Monitor Amps Clear Trap"
::= { odsTrapPrefix 207189 }

odsPowerDMDeciAmps38CLEAR NOTIFICATION-TYPE
OBJECTS { powerDMDeciAmps38, powerDMName, productFriendlyName, alarmTripType }
STATUS current
DESCRIPTION "DM48 Current Monitor Amps Clear Trap"
::= { odsTrapPrefix 207190 }

odsPowerDMDeciAmps39CLEAR NOTIFICATION-TYPE
OBJECTS { powerDMDeciAmps39, powerDMName, productFriendlyName, alarmTripType }
STATUS current
DESCRIPTION "DM48 Current Monitor Amps Clear Trap"
::= { odsTrapPrefix 207191 }

odsPowerDMDeciAmps40CLEAR NOTIFICATION-TYPE
OBJECTS { powerDMDeciAmps40, powerDMName, productFriendlyName, alarmTripType }
STATUS current
DESCRIPTION "DM48 Current Monitor Amps Clear Trap"
::= { odsTrapPrefix 207192 }

odsPowerDMDeciAmps41CLEAR NOTIFICATION-TYPE
OBJECTS { powerDMDeciAmps41, powerDMName, productFriendlyName, alarmTripType }
STATUS current
DESCRIPTION "DM48 Current Monitor Amps Clear Trap"
::= { odsTrapPrefix 207193 }

odsPowerDMDeciAmps42CLEAR NOTIFICATION-TYPE
OBJECTS { powerDMDeciAmps42, powerDMName, productFriendlyName, alarmTripType }
STATUS current
DESCRIPTION "DM48 Current Monitor Amps Clear Trap"
::= { odsTrapPrefix 207194 }

odsPowerDMDeciAmps43CLEAR NOTIFICATION-TYPE
OBJECTS { powerDMDeciAmps43, powerDMName, productFriendlyName, alarmTripType }
STATUS current
DESCRIPTION "DM48 Current Monitor Amps Clear Trap"
::= { odsTrapPrefix 207195 }

odsPowerDMDeciAmps44CLEAR NOTIFICATION-TYPE
OBJECTS { powerDMDeciAmps44, powerDMName, productFriendlyName, alarmTripType }
STATUS current
DESCRIPTION "DM48 Current Monitor Amps Clear Trap"
::= { odsTrapPrefix 207196 }

odsPowerDMDeciAmps45CLEAR NOTIFICATION-TYPE
OBJECTS { powerDMDeciAmps45, powerDMName, productFriendlyName, alarmTripType }
STATUS current
DESCRIPTION "DM48 Current Monitor Amps Clear Trap"
::= { odsTrapPrefix 207197 }

odsPowerDMDeciAmps46CLEAR NOTIFICATION-TYPE
OBJECTS { powerDMDeciAmps46, powerDMName, productFriendlyName, alarmTripType }
STATUS current
DESCRIPTION "DM48 Current Monitor Amps Clear Trap"
::= { odsTrapPrefix 207198 }

odsPowerDMDeciAmps47CLEAR NOTIFICATION-TYPE
OBJECTS { powerDMDeciAmps47, powerDMName, productFriendlyName, alarmTripType }
STATUS current
DESCRIPTION "DM48 Current Monitor Amps Clear Trap"
::= { odsTrapPrefix 207199 }

odsPowerDMDeciAmps48CLEAR NOTIFICATION-TYPE
OBJECTS { powerDMDeciAmps48, powerDMName, productFriendlyName, alarmTripType }
STATUS current
DESCRIPTION "DM48 Current Monitor Amps Clear Trap"
::= { odsTrapPrefix 207200 }

END
