Brcm-adapterInfo-MIB DEFINITIONS ::= BEGIN

          -- Broadcom(R) NetXtreme Network Adapter Extended Information MIB
          -- 
          -- This MIB defines the Broadcom NetXtreme Adapter Extended Information Set.
          -- These objects are part of the enterprise MIB for Broadcom server and 
          -- work station network adapters.
          --

          IMPORTS
                  enterprises, OBJECT-TYPE, Counter
                          FROM RFC1155-SMI
                  DisplayString, PhysAddress
                          FROM RFC1213-MIB;


    broadcom         	OBJECT IDENTIFIER ::= { enterprises 4413 }
    enet             	OBJECT IDENTIFIER ::= { broadcom 1 }
    basp             	OBJECT IDENTIFIER ::= { enet 2 }
    ifControllers       OBJECT IDENTIFIER ::= { enet 3 }
    baspConfig       	OBJECT IDENTIFIER ::= { basp 1 }
    baspStat         	OBJECT IDENTIFIER ::= { basp 2 }
    baspTrap         	OBJECT IDENTIFIER ::= { basp 3 }
    
---------------------
-- adaptergroup Group
---------------------
          ifNumber OBJECT-TYPE
              SYNTAX  INTEGER
              ACCESS  read-only
              STATUS  mandatory
              DESCRIPTION
                      "The number of Broadcom network interfaces (regardless
                      of their current state) present on this system."
              ::= { ifControllers 1 }
              
          ifTable OBJECT-TYPE
              SYNTAX  SEQUENCE OF AdapterEntry
              ACCESS  not-accessible
              STATUS  mandatory
              DESCRIPTION
                      "A list of Broadcom network interface entries.  
                      The number of entries is given by the ifNumber."
              ::= { ifControllers 2 }

          ifEntry OBJECT-TYPE
              SYNTAX  AdapterEntry
              ACCESS  not-accessible
              STATUS  mandatory
              DESCRIPTION
                      "An entry containing statistics objects of a Broadcom
                       network interface in this system."
              INDEX   { ifIndex }
              ::= { ifTable 1 }
              
		 AdapterEntry ::=
              SEQUENCE {
			      ifIndex
					  INTEGER,
                  ifName
                      DisplayString,
				  ifDescr
				      DisplayString,
                  ifNetworkAddress
                      IpAddress,
				  ifSubnetMask
				      IpAddress,
				  ifPhysAddress
                      PhysAddress,
				  ifPermPhysAddress
                      PhysAddress,
				  ifLinkStatus
					  INTEGER,
                  ifState
                      INTEGER,
                  ifLineSpeed
                      INTEGER,
                  ifDuplexMode
                      INTEGER,
				  ifMemBaseLow
					  DisplayString,
				  ifMemBaseHigh
				  	  DisplayString,	
				  ifInterrupt
                      INTEGER,
				  ifBusNumber
					  INTEGER,
				  ifDeviceNumber
				      INTEGER,
				  ifFunctionNumber
				      INTEGER    		
			  }
              
          ifIndex  OBJECT-TYPE
              SYNTAX  INTEGER
              ACCESS  read-only
              STATUS  mandatory
              DESCRIPTION
                     "An unique value for each Broadcom interface.
                      The value for each interface must remain constant at
                      least from one re-initialization of the entity's
                      network management system to the next re-
                      initialization."
              ::= { ifEntry 1 }

          ifName  OBJECT-TYPE
              SYNTAX  DisplayString
              ACCESS  read-only
              STATUS  mandatory
              DESCRIPTION
                      " A textual string containing name of the adapter or team"
              ::= { ifEntry 2 }
              
          ifDescr  OBJECT-TYPE
              SYNTAX  DisplayString
              ACCESS  read-only
              STATUS  mandatory
              DESCRIPTION
                      " A textual string containing the adapter or team description"
              ::= { ifEntry 3 }
              
          ifNetworkAddress  OBJECT-TYPE
              SYNTAX  IpAddress
              ACCESS  read-only
              STATUS  mandatory
              DESCRIPTION
                     "IP address of the adapter."
              ::= { ifEntry 4 }

          ifSubnetMask  OBJECT-TYPE
              SYNTAX  IpAddress
              ACCESS  read-only
              STATUS  mandatory
              DESCRIPTION
                     "IP subnet Mask of the adapter."
              ::= { ifEntry 5 }

          ifPhysAddress  OBJECT-TYPE
              SYNTAX  PhysAddress
              ACCESS  read-only
              STATUS  mandatory
              DESCRIPTION
                      "MAC address of the adapter."
              ::= { ifEntry 6 }

          ifPermPhysAddress  OBJECT-TYPE
              SYNTAX  PhysAddress
              ACCESS  read-only
              STATUS  mandatory
              DESCRIPTION
                      "Permanent MAC address of the adapter."
              ::= { ifEntry 7 }

          ifLinkStatus OBJECT-TYPE
              SYNTAX  INTEGER
              {
                   link-up(1),
                   link-fail(2)
              }
              ACCESS  read-only
              STATUS  mandatory
              DESCRIPTION
                      "	Adapter link status, this information only
                      applicable to the Broadcom adapter"
          	  ::= { ifEntry 8 }

          ifState  OBJECT-TYPE
              SYNTAX INTEGER 
              {
                   normal-mode(1),
                   diagnotic-mode(2),
                   adapter-removed(3),
                   lowpower-mode(4)
              }
              ACCESS  read-only
              STATUS  mandatory
              DESCRIPTION
                      "The operating mode of the driver, this information only
                      applicable to the Broadcom adapter"
              ::= { ifEntry  9 }

    	   ifLineSpeed  OBJECT-TYPE
              SYNTAX  INTEGER
			  {
					unknown(1),
					speed-10-Mbps (2),
					speed-100-Mbps (3),
					speed-1000-Mbps (4)
			  } 
              ACCESS  read-only
              STATUS  mandatory
              DESCRIPTION
                      "	The operating speed of the adapter, this information only
                      applicable to the Broadcom adapter"
              ::= { ifEntry  10 }

           ifDuplexMode OBJECT-TYPE
              SYNTAX  INTEGER
              {
                   unknown(1),
                   half-duplex(2),
                   full-duplex(3)
              }
              ACCESS  read-only
              STATUS  mandatory
              DESCRIPTION
                      "	Adapter duplex mode, this information only
                      applicable to the Broadcom adapter"
           	  ::= { ifEntry 11 }

           ifMemBaseLow OBJECT-TYPE
              SYNTAX  DisplayString
              ACCESS  read-only
              STATUS  mandatory
              DESCRIPTION
                      "	memory low range of the adapter, this information only
                      applicable to the Broadcom adapter"
              ::= { ifEntry 12 }

           ifMemBaseHigh OBJECT-TYPE
              SYNTAX  DisplayString
              ACCESS  read-only
              STATUS  mandatory
              DESCRIPTION
                      "	memory high range of the adapter, this information only
                      applicable to the Broadcom adapter"
              ::= { ifEntry 13 }

    	   ifInterrupt  OBJECT-TYPE
              SYNTAX  INTEGER
              ACCESS  read-only
              STATUS  mandatory
              DESCRIPTION
                      "	IRQ value for the adapter, this information only
                      applicable to the Broadcom adapter"
              ::= { ifEntry 14 }

           ifBusNumber OBJECT-TYPE
              SYNTAX  INTEGER
              ACCESS  read-only
              STATUS  mandatory
              DESCRIPTION
                      "	PCI Bus Number where the Adapter is situated, this information only
                      applicable to the Broadcom adapter"
              ::= { ifEntry 15 }

           ifDeviceNumber OBJECT-TYPE
              SYNTAX  INTEGER
              ACCESS  read-only
              STATUS  mandatory
              DESCRIPTION
                      "	PCI Device Number of the adapter, this information only
                      applicable to the Broadcom adapter"
              ::= { ifEntry 16 }

           ifFunctionNumber OBJECT-TYPE
              SYNTAX  INTEGER
              ACCESS  read-only
              STATUS  mandatory
              DESCRIPTION
                      "	PCI Function Number of the adapter, this information only
                      applicable to the Broadcom adapter"
              ::= { ifEntry 17 }

END
