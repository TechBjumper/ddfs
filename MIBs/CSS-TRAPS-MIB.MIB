-
--Defines CSS-TRAPS-MIB.MIB for SNMP agent extension
--Contents:	Global Registration Module

--CSS  OIDs - Enterprise 14748
--Version:		0.10 	

-- Reviewed & developed by NK
--         software engineer
--         Computer Support Systems Pty Ltd

-- Updates
-- Added SafetyNet Series 5 Lite and Micro
-- Added SafetyNet Series 5 D40 and D20
-- Added Sentinel 20
-- Added Sentinel 10
-- Completed Tree for SafetyNet Series 5 D20
-- Added SafetyNet Series 5 Combo Version

-- Copyright (c) 2011 CSSPL.

CSS-TRAPS-MIB DEFINITIONS ::= BEGIN

IMPORTS
--	
	Counter, TimeTicks,
	enterprises,IpAddress, Gauge, Counter
	FROM RFC1155-SMI

	DisplayString,sysDescr,sysObjectID,sysUpTime,sysContact,sysName,sysLocation,sysServices,ifNumber,ifIndex, ifDescr,ifType
	FROM RFC1213-MIB

	OBJECT-TYPE
	FROM RFC-1212
	
	TRAP-TYPE				
	FROM RFC-1215   
;
		


computerSupportSystems  OBJECT IDENTIFIER ::= { enterprises 14748 } -- assigned by IANA
--MODULE-IDENTITY
--
--     LAST-UPDATED    "201111092300Z"  November, 2011
--     ORGANIZATION "Computer Support Systems Pty Ltd"
--     CONTACT-INFO 
--	  
--	  	"Nilkamal Kandamudali
--		Email: support@csspl.com.au
--		nilkamal@y7mail.com"
--																		
--    DESCRIPTION
--      "This MIB module defines MIB objects for products of Computer Support Systems."
--       
--		REVISION    "201111092300Z" November , 2011
--      DESCRIPTION "Initial version."		
    
  

		 

trapControl    		OBJECT IDENTIFIER ::= { computerSupportSystems 4 }
trapSource  		OBJECT IDENTIFIER ::= { trapControl 1}

products    		OBJECT IDENTIFIER ::= { computerSupportSystems 1 }
-- products 1-6 are covered in CSS.MIB file
safetynetseries5	OBJECT IDENTIFIER ::= { products 7 }
safetynetseries5lite	OBJECT IDENTIFIER ::= { products 8 }
safetynetseries5micro	OBJECT IDENTIFIER ::= { products 9 }
safetynetseries5D40	OBJECT IDENTIFIER ::= { products 10 }
safetynetseries5D20	OBJECT IDENTIFIER ::= { products 11 }
safetynetseries5Combo OBJECT IDENTIFIER ::= { products 12 }

-- Series 5 objects
ss5Readings			OBJECT IDENTIFIER ::= { safetynetseries5 1 }
ss5Relays			OBJECT IDENTIFIER ::= { safetynetseries5 2 }

ss5SensorOne	OBJECT IDENTIFIER ::= { ss5Readings 1 }
ss5SensorTwo	OBJECT IDENTIFIER ::= { ss5Readings 2 }
ss5SensorThree	OBJECT IDENTIFIER ::= { ss5Readings 3 }
ss5SensorFour	OBJECT IDENTIFIER ::= { ss5Readings 4 }
ss5SensorFive	OBJECT IDENTIFIER ::= { ss5Readings 5 }
ss5SensorSix	OBJECT IDENTIFIER ::= { ss5Readings 6 }
ss5SensorSeven	OBJECT IDENTIFIER ::= { ss5Readings 7 }
ss5SensorEight	OBJECT IDENTIFIER ::= { ss5Readings 8 }
ss5SensorNine	OBJECT IDENTIFIER ::= { ss5Readings 9 }
ss5SensorTen	OBJECT IDENTIFIER ::= { ss5Readings 10 }

-- Series 5 Lite objects
ss5LiteReadings			OBJECT IDENTIFIER ::= { safetynetseries5lite 1 }
ss5LiteRelay			OBJECT IDENTIFIER ::= { safetynetseries5lite 2 }

ss5LiteSensorOne	OBJECT IDENTIFIER ::= { ss5LiteReadings 1 }
ss5LiteSensorTwo	OBJECT IDENTIFIER ::= { ss5LiteReadings 2 }
ss5LiteSensorThree	OBJECT IDENTIFIER ::= { ss5LiteReadings 3 }
ss5LiteSensorFour	OBJECT IDENTIFIER ::= { ss5LiteReadings 4 }
ss5LiteSensorFive	OBJECT IDENTIFIER ::= { ss5LiteReadings 5 }
ss5LiteSensorSix	OBJECT IDENTIFIER ::= { ss5LiteReadings 6 }

-- Series 5 Micro objects
ss5MicroReadings			OBJECT IDENTIFIER ::= { safetynetseries5micro 1 }

ss5MicroSensorOne	OBJECT IDENTIFIER ::= { ss5MicroReadings 1 }
ss5MicroSensorTwo	OBJECT IDENTIFIER ::= { ss5MicroReadings 2 }
ss5MicroSensorThree	OBJECT IDENTIFIER ::= { ss5MicroReadings 3 }
ss5MicroSensorFour	OBJECT IDENTIFIER ::= { ss5MicroReadings 4 }


-- Series 5D40 objects
ss5D40Readings			OBJECT IDENTIFIER ::= { safetynetseries5D40 1 }
ss5D40Relays			OBJECT IDENTIFIER ::= { safetynetseries5D40 2 }

ss5D40Sensor01	OBJECT IDENTIFIER ::= { ss5D40Readings 1 }
ss5D40Sensor02	OBJECT IDENTIFIER ::= { ss5D40Readings 2 }
ss5D40Sensor03	OBJECT IDENTIFIER ::= { ss5D40Readings 3 }
ss5D40Sensor04	OBJECT IDENTIFIER ::= { ss5D40Readings 4 }
ss5D40Sensor05	OBJECT IDENTIFIER ::= { ss5D40Readings 5 }
ss5D40Sensor06	OBJECT IDENTIFIER ::= { ss5D40Readings 6 }
ss5D40Sensor07	OBJECT IDENTIFIER ::= { ss5D40Readings 7 }
ss5D40Sensor08	OBJECT IDENTIFIER ::= { ss5D40Readings 8 }
ss5D40Sensor09	OBJECT IDENTIFIER ::= { ss5D40Readings 9 }
ss5D40Sensor10	OBJECT IDENTIFIER ::= { ss5D40Readings 10 }
ss5D40Sensor11	OBJECT IDENTIFIER ::= { ss5D40Readings 11 }
ss5D40Sensor12	OBJECT IDENTIFIER ::= { ss5D40Readings 12 }
ss5D40Sensor13	OBJECT IDENTIFIER ::= { ss5D40Readings 13 }
ss5D40Sensor14	OBJECT IDENTIFIER ::= { ss5D40Readings 14 }
ss5D40Sensor15	OBJECT IDENTIFIER ::= { ss5D40Readings 15 }
ss5D40Sensor16	OBJECT IDENTIFIER ::= { ss5D40Readings 16 }
ss5D40Sensor17	OBJECT IDENTIFIER ::= { ss5D40Readings 17 }
ss5D40Sensor18	OBJECT IDENTIFIER ::= { ss5D40Readings 18 }
ss5D40Sensor19	OBJECT IDENTIFIER ::= { ss5D40Readings 19 }
ss5D40Sensor20	OBJECT IDENTIFIER ::= { ss5D40Readings 20 }
ss5D40Sensor21	OBJECT IDENTIFIER ::= { ss5D40Readings 21 }
ss5D40Sensor22	OBJECT IDENTIFIER ::= { ss5D40Readings 22 }
ss5D40Sensor23	OBJECT IDENTIFIER ::= { ss5D40Readings 23 }
ss5D40Sensor24	OBJECT IDENTIFIER ::= { ss5D40Readings 24 }
ss5D40Sensor25	OBJECT IDENTIFIER ::= { ss5D40Readings 25 }
ss5D40Sensor26	OBJECT IDENTIFIER ::= { ss5D40Readings 26 }
ss5D40Sensor27	OBJECT IDENTIFIER ::= { ss5D40Readings 27 }
ss5D40Sensor28	OBJECT IDENTIFIER ::= { ss5D40Readings 28 }
ss5D40Sensor29	OBJECT IDENTIFIER ::= { ss5D40Readings 29 }
ss5D40Sensor30	OBJECT IDENTIFIER ::= { ss5D40Readings 30 }
ss5D40Sensor31	OBJECT IDENTIFIER ::= { ss5D40Readings 31 }
ss5D40Sensor32	OBJECT IDENTIFIER ::= { ss5D40Readings 32 }
ss5D40Sensor33	OBJECT IDENTIFIER ::= { ss5D40Readings 33 }
ss5D40Sensor34	OBJECT IDENTIFIER ::= { ss5D40Readings 34 }
ss5D40Sensor35	OBJECT IDENTIFIER ::= { ss5D40Readings 35 }
ss5D40Sensor36	OBJECT IDENTIFIER ::= { ss5D40Readings 36 }
ss5D40Sensor37	OBJECT IDENTIFIER ::= { ss5D40Readings 37 }
ss5D40Sensor38	OBJECT IDENTIFIER ::= { ss5D40Readings 38 }
ss5D40Sensor39	OBJECT IDENTIFIER ::= { ss5D40Readings 39 }
ss5D40Sensor40	OBJECT IDENTIFIER ::= { ss5D40Readings 40 }

-- Series 5D20 objects
ss5D20Readings			OBJECT IDENTIFIER ::= { safetynetseries5D20 1 }
ss5D20Relays			OBJECT IDENTIFIER ::= { safetynetseries5D20 2 }

ss5D20Sensor01	OBJECT IDENTIFIER ::= { ss5D20Readings 1 }
ss5D20Sensor02	OBJECT IDENTIFIER ::= { ss5D20Readings 2 }
ss5D20Sensor03	OBJECT IDENTIFIER ::= { ss5D20Readings 3 }
ss5D20Sensor04	OBJECT IDENTIFIER ::= { ss5D20Readings 4 }
ss5D20Sensor05	OBJECT IDENTIFIER ::= { ss5D20Readings 5 }
ss5D20Sensor06	OBJECT IDENTIFIER ::= { ss5D20Readings 6 }
ss5D20Sensor07	OBJECT IDENTIFIER ::= { ss5D20Readings 7 }
ss5D20Sensor08	OBJECT IDENTIFIER ::= { ss5D20Readings 8 }
ss5D20Sensor09	OBJECT IDENTIFIER ::= { ss5D20Readings 9 }
ss5D20Sensor10	OBJECT IDENTIFIER ::= { ss5D20Readings 10 }
ss5D20Sensor11	OBJECT IDENTIFIER ::= { ss5D20Readings 11 }
ss5D20Sensor12	OBJECT IDENTIFIER ::= { ss5D20Readings 12 }
ss5D20Sensor13	OBJECT IDENTIFIER ::= { ss5D20Readings 13 }
ss5D20Sensor14	OBJECT IDENTIFIER ::= { ss5D20Readings 14 }
ss5D20Sensor15	OBJECT IDENTIFIER ::= { ss5D20Readings 15 }
ss5D20Sensor16	OBJECT IDENTIFIER ::= { ss5D20Readings 16 }
ss5D20Sensor17	OBJECT IDENTIFIER ::= { ss5D20Readings 17 }
ss5D20Sensor18	OBJECT IDENTIFIER ::= { ss5D20Readings 18 }
ss5D20Sensor19	OBJECT IDENTIFIER ::= { ss5D20Readings 19 }
ss5D20Sensor20	OBJECT IDENTIFIER ::= { ss5D20Readings 20 }


-- Series 5 Combo objects
ss5ComboReadings			OBJECT IDENTIFIER ::= { safetynetseries5Combo 1 }
ss5ComboRelays			OBJECT IDENTIFIER ::= { safetynetseries5Combo 2 }

ss5ComboUniversal01	OBJECT IDENTIFIER ::= { ss5ComboReadings 1 }
ss5ComboUniversal02	OBJECT IDENTIFIER ::= { ss5ComboReadings 2 }
ss5ComboUniversal03	OBJECT IDENTIFIER ::= { ss5ComboReadings 3 }
ss5ComboUniversal04	OBJECT IDENTIFIER ::= { ss5ComboReadings 4 }
ss5ComboUniversal05	OBJECT IDENTIFIER ::= { ss5ComboReadings 5 }
ss5ComboUniversal06	OBJECT IDENTIFIER ::= { ss5ComboReadings 6 }
ss5ComboDigital01		OBJECT IDENTIFIER ::= { ss5ComboReadings 7 }
ss5ComboDigital02		OBJECT IDENTIFIER ::= { ss5ComboReadings 8 }
ss5ComboDigital03		OBJECT IDENTIFIER ::= { ss5ComboReadings 9 }
ss5ComboDigital04		OBJECT IDENTIFIER ::= { ss5ComboReadings 10 }
ss5ComboDigital05		OBJECT IDENTIFIER ::= { ss5ComboReadings 11 }
ss5ComboDigital06		OBJECT IDENTIFIER ::= { ss5ComboReadings 12 }
ss5ComboDigital07		OBJECT IDENTIFIER ::= { ss5ComboReadings 13 }
ss5ComboDigital08		OBJECT IDENTIFIER ::= { ss5ComboReadings 14 }
ss5ComboDigital09		OBJECT IDENTIFIER ::= { ss5ComboReadings 15 }
ss5ComboDigital10		OBJECT IDENTIFIER ::= { ss5ComboReadings 16 }
ss5ComboDigital11		OBJECT IDENTIFIER ::= { ss5ComboReadings 17 }
ss5ComboDigital12		OBJECT IDENTIFIER ::= { ss5ComboReadings 18 }
ss5ComboDigital13		OBJECT IDENTIFIER ::= { ss5ComboReadings 19 }
ss5ComboDigital14		OBJECT IDENTIFIER ::= { ss5ComboReadings 20 }
ss5ComboDigital15		OBJECT IDENTIFIER ::= { ss5ComboReadings 21 }
ss5ComboDigital16		OBJECT IDENTIFIER ::= { ss5ComboReadings 22 }
ss5ComboDigital17		OBJECT IDENTIFIER ::= { ss5ComboReadings 23 }
ss5ComboDigital18		OBJECT IDENTIFIER ::= { ss5ComboReadings 24 }
ss5ComboDigital19		OBJECT IDENTIFIER ::= { ss5ComboReadings 25 }
ss5ComboDigital20		OBJECT IDENTIFIER ::= { ss5ComboReadings 26 }



oemProducts		OBJECT IDENTIFIER ::= { computerSupportSystems 2 }
-- oemProducts 1-6 are covered in CSS.MIB file
sentinel20Way		OBJECT IDENTIFIER ::= { oemProducts 7 }    
sentinel10Way		OBJECT IDENTIFIER ::= { oemProducts 8 } 


-- Sentinel 20 objects
sentinel20_outletReading		OBJECT IDENTIFIER ::= { sentinel20Way 1 }
sentinel20_sensorReading		OBJECT IDENTIFIER ::= { sentinel20Way 2 }

sentinel10_outletReading		OBJECT IDENTIFIER ::= { sentinel10Way 1 }
sentinel10_sensorReading		OBJECT IDENTIFIER ::= { sentinel10Way 2 }



ss5SensorOneType OBJECT-TYPE
	SYNTAX  	INTEGER(0..9)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid
				7 = Digital
				8 = Zoned Security
				9 = Security"
::= { ss5SensorOne 1 }


ss5SensorOneName OBJECT-TYPE
	SYNTAX		DisplayString (SIZE (0..42))
	ACCESS		read-only
	STATUS		mandatory
	DESCRIPTION	"Sensor Name of SafetyNet Series 5"
::= { ss5SensorOne 2 }

ss5SensorOneReading OBJECT-TYPE
	SYNTAX  	INTEGER(-200..1200)
	ACCESS		read-only
	STATUS		mandatory
	DESCRIPTION	"SafetyNet Series 5 sensor one reading.
	
				 If sensor is Digital
				 1 = sensor in alarm condition
				 0 = sensor not in alarm condition
				 
				 if sensor is Analogue use multiplier 0.1 for actual reading"
::= { ss5SensorOne 3 }


ss5SensorTwoType OBJECT-TYPE
	SYNTAX  	INTEGER(0..9)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid
				7 = Digital
				8 = Zoned Security
				9 = Security"
::= { ss5SensorTwo 1 }

ss5SensorTwoName OBJECT-TYPE
	SYNTAX		DisplayString (SIZE (0..42))
	ACCESS		read-only
	STATUS		mandatory
	DESCRIPTION	"Sensor Name of SafetyNet Series 5"
::= { ss5SensorTwo 2 }
	
ss5SensorTwoReading OBJECT-TYPE
	SYNTAX  	INTEGER(-200..1200)
	ACCESS		read-only
	STATUS		mandatory
	DESCRIPTION	"SafetyNet Series 5 sensor two reading.
	
				 If sensor is Digital
				 1 = sensor in alarm condition
				 0 = sensor not in alarm condition
				 
				 if sensor is Analogue use multiplier 0.1 for actual reading"
::= { ss5SensorTwo 3 }

ss5SensorThreeType OBJECT-TYPE
	SYNTAX  	INTEGER(0..9)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid
				7 = Digital
				8 = Zoned Security
				9 = Security"
::= { ss5SensorThree 1 }

ss5SensorThreeName OBJECT-TYPE
	SYNTAX		DisplayString (SIZE (0..42))
	ACCESS		read-only
	STATUS		mandatory
	DESCRIPTION	"Sensor Name of SafetyNet Series 5"
::= { ss5SensorThree 2 }

ss5SensorThreeReading OBJECT-TYPE
	SYNTAX  	INTEGER(-200..1200)
	ACCESS		read-only
	STATUS		mandatory
	DESCRIPTION	"SafetyNet Series 5 sensor three reading.
	
				 If sensor is Digital
				 1 = sensor in alarm condition
				 0 = sensor not in alarm condition
				 
				 if sensor is Analogue use multiplier 0.1 for actual reading"
::= { ss5SensorThree 3 }


ss5SensorFourType OBJECT-TYPE
	SYNTAX  	INTEGER(0..9)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid
				7 = Digital
				8 = Zoned Security
				9 = Security"
::= { ss5SensorFour 1 }

ss5SensorFourName OBJECT-TYPE
	SYNTAX		DisplayString (SIZE (0..42))
	ACCESS		read-only
	STATUS		mandatory
	DESCRIPTION	"Sensor Name of SafetyNet Series 5"
::= { ss5SensorFour 2 }

ss5SensorFourReading OBJECT-TYPE
	SYNTAX  	INTEGER(-200..1200)
	ACCESS		read-only
	STATUS		mandatory
	DESCRIPTION	"SafetyNet Series 5 sensor four reading.
	
				 If sensor is Digital
				 1 = sensor in alarm condition
				 0 = sensor not in alarm condition
				 
				 if sensor is Analogue use multiplier 0.1 for actual reading"
::= { ss5SensorFour 3 }
	
	
ss5SensorFiveType OBJECT-TYPE
	SYNTAX  	INTEGER(0..9)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid
				7 = Digital
				8 = Zoned Security
				9 = Security"
::= { ss5SensorFive 1 }

ss5SensorFiveName OBJECT-TYPE
	SYNTAX		DisplayString (SIZE (0..42))
	ACCESS		read-only
	STATUS		mandatory
	DESCRIPTION	"Sensor Name of SafetyNet Series 5"
::= { ss5SensorFive 2 }
	
ss5SensorFiveReading OBJECT-TYPE
	SYNTAX  	INTEGER(-200..1200)
	ACCESS		read-only
	STATUS		mandatory
	DESCRIPTION	"SafetyNet Series 5 sensor five reading.
	
				 If sensor is Digital
				 1 = sensor in alarm condition
				 0 = sensor not in alarm condition
				 
				 if sensor is Analogue use multiplier 0.1 for actual reading"
::= { ss5SensorFive 3 }

ss5SensorSixType OBJECT-TYPE
	SYNTAX  	INTEGER(0..9)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid
				7 = Digital
				8 = Zoned Security
				9 = Security"
::= { ss5SensorSix 1 }


ss5SensorSixName OBJECT-TYPE
	SYNTAX		DisplayString (SIZE (0..42))
	ACCESS		read-only
	STATUS		mandatory
	DESCRIPTION	"Sensor Name of SafetyNet Series 5"
::= { ss5SensorSix 2 }

ss5SensorSixReading OBJECT-TYPE
	SYNTAX  	INTEGER(-200..1200)
	ACCESS		read-only
	STATUS		mandatory
	DESCRIPTION	"SafetyNet Series 5 sensor six reading.
	
				 If sensor is Digital
				 1 = sensor in alarm condition
				 0 = sensor not in alarm condition
				 
				 if sensor is Analogue use multiplier 0.1 for actual reading"
::= { ss5SensorSix 3 }

ss5SensorSevenType OBJECT-TYPE
	SYNTAX  	INTEGER(0..9)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid
				7 = Digital
				8 = Zoned Security
				9 = Security"
::= { ss5SensorSeven 1 }

ss5SensorSevenName OBJECT-TYPE
	SYNTAX		DisplayString (SIZE (0..42))
	ACCESS		read-only
	STATUS		mandatory
	DESCRIPTION	"Sensor Name of SafetyNet Series 5"
::= { ss5SensorSeven 2 }

ss5SensorSevenReading OBJECT-TYPE
	SYNTAX  	INTEGER(-200..1200)
	ACCESS		read-only
	STATUS		mandatory
	DESCRIPTION	"SafetyNet Series 5 sensor seven reading.
	
				 If sensor is Digital
				 1 = sensor in alarm condition
				 0 = sensor not in alarm condition
				 
				 if sensor is Analogue use multiplier 0.1 for actual reading"
::= { ss5SensorSeven 3 }


ss5SensorEightType OBJECT-TYPE
	SYNTAX  	INTEGER(0..9)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid
				7 = Digital
				8 = Zoned Security
				9 = Security"
::= { ss5SensorEight 1 }

ss5SensorEightName OBJECT-TYPE
	SYNTAX		DisplayString (SIZE (0..42))
	ACCESS		read-only
	STATUS		mandatory
	DESCRIPTION	"Sensor Name of SafetyNet Series 5"
::= { ss5SensorEight 2 }

ss5SensorEightReading OBJECT-TYPE
	SYNTAX  	INTEGER(-200..1200)
	ACCESS		read-only
	STATUS		mandatory
	DESCRIPTION	"SafetyNet Series 5 sensor eight reading.
	
				 If sensor is Digital
				 1 = sensor in alarm condition
				 0 = sensor not in alarm condition
				 
				 if sensor is Analogue use multiplier 0.1 for actual reading"
::= { ss5SensorEight 3 }


ss5SensorNineType OBJECT-TYPE
	SYNTAX  	INTEGER(0..9)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid
				7 = Digital
				8 = Zoned Security
				9 = Security"
::= { ss5SensorNine 1 }


ss5SensorNineName OBJECT-TYPE
	SYNTAX		DisplayString (SIZE (0..42))
	ACCESS		read-only
	STATUS		mandatory
	DESCRIPTION	"Sensor Name of SafetyNet Series 5"
::= { ss5SensorNine 2 }

ss5SensorNineReading OBJECT-TYPE
	SYNTAX  	INTEGER(-200..1200)
	ACCESS		read-only
	STATUS		mandatory
	DESCRIPTION	"SafetyNet Series 5 sensor nine reading.
	
				 If sensor is Digital
				 1 = sensor in alarm condition
				 0 = sensor not in alarm condition
				 
				 if sensor is Analogue use multiplier 0.1 for actual reading"
::= { ss5SensorNine 3 }

ss5SensorTenType OBJECT-TYPE
	SYNTAX  	INTEGER(0..9)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid
				7 = Digital
				8 = Zoned Security
				9 = Security"
::= { ss5SensorTen 1 }

ss5SensorTenName OBJECT-TYPE
	SYNTAX		DisplayString (SIZE (0..42))
	ACCESS		read-only
	STATUS		mandatory
	DESCRIPTION	"Sensor Name of SafetyNet Series 5"
::= { ss5SensorTen 2 }

ss5SensorTenReading OBJECT-TYPE
	SYNTAX  	INTEGER(-200..1200)
	ACCESS		read-only
	STATUS		mandatory
	DESCRIPTION	"SafetyNet Series 5 sensor ten reading.
	
				 If sensor is Digital
				 1 = sensor in alarm condition
				 0 = sensor not in alarm condition
				 
				 if sensor is Analogue use multiplier 0.1 for actual reading"
::= { ss5SensorTen 3 }

ss5IpMonitoringReading OBJECT-TYPE
	SYNTAX  	INTEGER(0..1)
	ACCESS		read-only
	STATUS		mandatory
	DESCRIPTION	"SafetyNet Series 5 IP Monitoring Alarm.
				 1 = alarm condition
				 0 = not in alarm condition"
::= { ss5Readings 11 }

ss5LowBatteryReading OBJECT-TYPE
	SYNTAX  	INTEGER(0..1)
	ACCESS		read-only
	STATUS		mandatory
	DESCRIPTION	"SafetyNet Series 5 Low Battery.
				 1 = alarm condition
				 0 = not in alarm condition"
::= { ss5Readings 12 }

ss5MainsFailureReading OBJECT-TYPE
	SYNTAX  	INTEGER(0..1)
	ACCESS		read-only
	STATUS		mandatory
	DESCRIPTION	"SafetyNet Series 5 Mains Failure Alarm.
				 1 = alarm condition
				 0 = not in alarm condition"
::= { ss5Readings 13 }

ss5FaultySensorReading OBJECT-TYPE
	SYNTAX  	INTEGER(0..1)
	ACCESS		read-only
	STATUS		mandatory
	DESCRIPTION	"SafetyNet Series 5 Faulty Sensor(s) Alarm.
				 1 = alarm condition
				 0 = not in alarm condition"
::= { ss5Readings 14 }

ss5DialToneOrSIMErrorReading OBJECT-TYPE
	SYNTAX  	INTEGER(0..1)
	ACCESS		read-only
	STATUS		mandatory
	DESCRIPTION	"SafetyNet Series 5 Dial Tone Alarm for PSTN Modem Version. SafetyNet Series 5 GSM SIM Card Error Alarm for GSM Modem Version.
				 1 = alarm condition
				 0 = not in alarm condition"
::= { ss5Readings 15 }

ss5RelayOne OBJECT-TYPE
	SYNTAX  	INTEGER(0..1)
	ACCESS		read-only
	STATUS		mandatory
	DESCRIPTION	"SafetyNet Series 5 Relay One Status.
				 0 = Relay active
				 1 = Relay inactive"
::= { ss5Relays 1 }
	
ss5RelayTwo OBJECT-TYPE
	SYNTAX  	INTEGER(0..1)
	ACCESS		read-only
	STATUS		mandatory
	DESCRIPTION	"SafetyNet Series 5 Relay Two Status.
				 0 = Relay active
				 1 = Relay inactive"
::= { ss5Relays 2 }

-- Series 5 Lite begins here


ss5LiteSensorOneType OBJECT-TYPE
	SYNTAX  	INTEGER(0..9)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid
				7 = Digital
				8 = Zoned Security
				9 = Security"
::= { ss5LiteSensorOne 1 }


ss5LiteSensorOneName OBJECT-TYPE
	SYNTAX		DisplayString (SIZE (0..42))
	ACCESS		read-only
	STATUS		mandatory
	DESCRIPTION	"Sensor Name of SafetyNet Series 5 Lite"
::= { ss5LiteSensorOne 2 }

ss5LiteSensorOneReading OBJECT-TYPE
	SYNTAX  	INTEGER(-200..1200)
	ACCESS		read-only
	STATUS		mandatory
	DESCRIPTION	"SafetyNet Series 5 Lite sensor one reading.
	
				 If sensor is Digital
				 1 = sensor in alarm condition
				 0 = sensor not in alarm condition
				 
				 if sensor is Analogue use multiplier 0.1 for actual reading"
::= { ss5LiteSensorOne 3 }


ss5LiteSensorTwoType OBJECT-TYPE
	SYNTAX  	INTEGER(0..9)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid
				7 = Digital
				8 = Zoned Security
				9 = Security"
::= { ss5LiteSensorTwo 1 }

ss5LiteSensorTwoName OBJECT-TYPE
	SYNTAX		DisplayString (SIZE (0..42))
	ACCESS		read-only
	STATUS		mandatory
	DESCRIPTION	"Sensor Name of SafetyNet Series 5 Lite"
::= { ss5LiteSensorTwo 2 }
	
ss5LiteSensorTwoReading OBJECT-TYPE
	SYNTAX  	INTEGER(-200..1200)
	ACCESS		read-only
	STATUS		mandatory
	DESCRIPTION	"SafetyNet Series 5 Lite sensor two reading.
	
				 If sensor is Digital
				 1 = sensor in alarm condition
				 0 = sensor not in alarm condition
				 
				 if sensor is Analogue use multiplier 0.1 for actual reading"
::= { ss5LiteSensorTwo 3 }

ss5LiteSensorThreeType OBJECT-TYPE
	SYNTAX  	INTEGER(0..9)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid
				7 = Digital
				8 = Zoned Security
				9 = Security"
::= { ss5LiteSensorThree 1 }

ss5LiteSensorThreeName OBJECT-TYPE
	SYNTAX		DisplayString (SIZE (0..42))
	ACCESS		read-only
	STATUS		mandatory
	DESCRIPTION	"Sensor Name of SafetyNet Series 5 Lite"
::= { ss5LiteSensorThree 2 }

ss5LiteSensorThreeReading OBJECT-TYPE
	SYNTAX  	INTEGER(-200..1200)
	ACCESS		read-only
	STATUS		mandatory
	DESCRIPTION	"SafetyNet Series 5 Lite sensor three reading.
	
				 If sensor is Digital
				 1 = sensor in alarm condition
				 0 = sensor not in alarm condition
				 
				 if sensor is Analogue use multiplier 0.1 for actual reading"
::= { ss5LiteSensorThree 3 }


ss5LiteSensorFourType OBJECT-TYPE
	SYNTAX  	INTEGER(0..9)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid
				7 = Digital
				8 = Zoned Security
				9 = Security"
::= { ss5LiteSensorFour 1 }

ss5LiteSensorFourName OBJECT-TYPE
	SYNTAX		DisplayString (SIZE (0..42))
	ACCESS		read-only
	STATUS		mandatory
	DESCRIPTION	"Sensor Name of SafetyNet Series 5 Lite"
::= { ss5LiteSensorFour 2 }

ss5LiteSensorFourReading OBJECT-TYPE
	SYNTAX  	INTEGER(-200..1200)
	ACCESS		read-only
	STATUS		mandatory
	DESCRIPTION	"SafetyNet Series 5 Lite sensor four reading.
	
				 If sensor is Digital
				 1 = sensor in alarm condition
				 0 = sensor not in alarm condition
				 
				 if sensor is Analogue use multiplier 0.1 for actual reading"
::= { ss5LiteSensorFour 3 }
	
	
ss5LiteSensorFiveType OBJECT-TYPE
	SYNTAX  	INTEGER(0..9)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid
				7 = Digital
				8 = Zoned Security
				9 = Security"
::= { ss5LiteSensorFive 1 }

ss5LiteSensorFiveName OBJECT-TYPE
	SYNTAX		DisplayString (SIZE (0..42))
	ACCESS		read-only
	STATUS		mandatory
	DESCRIPTION	"Sensor Name of SafetyNet Series 5 Lite"
::= { ss5LiteSensorFive 2 }
	
ss5LiteSensorFiveReading OBJECT-TYPE
	SYNTAX  	INTEGER(-200..1200)
	ACCESS		read-only
	STATUS		mandatory
	DESCRIPTION	"SafetyNet Series 5 Lite sensor five reading.
	
				 If sensor is Digital
				 1 = sensor in alarm condition
				 0 = sensor not in alarm condition
				 
				 if sensor is Analogue use multiplier 0.1 for actual reading"
::= { ss5LiteSensorFive 3 }

ss5LiteSensorSixType OBJECT-TYPE
	SYNTAX  	INTEGER(0..9)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid
				7 = Digital
				8 = Zoned Security
				9 = Security"
::= { ss5LiteSensorSix 1 }


ss5LiteSensorSixName OBJECT-TYPE
	SYNTAX		DisplayString (SIZE (0..42))
	ACCESS		read-only
	STATUS		mandatory
	DESCRIPTION	"Sensor Name of SafetyNet Series 5 Lite"
::= { ss5LiteSensorSix 2 }

ss5LiteSensorSixReading OBJECT-TYPE
	SYNTAX  	INTEGER(-200..1200)
	ACCESS		read-only
	STATUS		mandatory
	DESCRIPTION	"SafetyNet Series 5 Lite sensor six reading.
	
				 If sensor is Digital
				 1 = sensor in alarm condition
				 0 = sensor not in alarm condition
				 
				 if sensor is Analogue use multiplier 0.1 for actual reading"
::= { ss5LiteSensorSix 3 }


ss5LiteIpMonitoringReading OBJECT-TYPE
	SYNTAX  	INTEGER(0..1)
	ACCESS		read-only
	STATUS		mandatory
	DESCRIPTION	"SafetyNet Series 5 Lite IP Monitoring Alarm.
				 1 = alarm condition
				 0 = not in alarm condition"
::= { ss5LiteReadings 7 }

ss5LiteLowBatteryReading OBJECT-TYPE
	SYNTAX  	INTEGER(0..1)
	ACCESS		read-only
	STATUS		mandatory
	DESCRIPTION	"SafetyNet Series 5 Lite Low Battery.
				 1 = alarm condition
				 0 = not in alarm condition"
::= { ss5LiteReadings 8 }

ss5LiteMainsFailureReading OBJECT-TYPE
	SYNTAX  	INTEGER(0..1)
	ACCESS		read-only
	STATUS		mandatory
	DESCRIPTION	"SafetyNet Series 5 Lite Mains Failure Alarm.
				 1 = alarm condition
				 0 = not in alarm condition"
::= { ss5LiteReadings 9 }

ss5LiteFaultySensorReading OBJECT-TYPE
	SYNTAX  	INTEGER(0..1)
	ACCESS		read-only
	STATUS		mandatory
	DESCRIPTION	"SafetyNet Series 5 Lite Faulty Sensor(s) Alarm.
				 1 = alarm condition
				 0 = not in alarm condition"
::= { ss5LiteReadings 10 }

ss5LiteDialToneOrSIMErrorReading OBJECT-TYPE
	SYNTAX  	INTEGER(0..1)
	ACCESS		read-only
	STATUS		mandatory
	DESCRIPTION	"SafetyNet Series 5 Lite Dial Tone Alarm for PSTN Modem Version. SafetyNet Series 5 Lite GSM SIM Card Error Alarm for GSM Modem Version.
				 1 = alarm condition
				 0 = not in alarm condition"
::= { ss5LiteReadings 11 }

ss5LiteRelay01 OBJECT-TYPE
	SYNTAX  	INTEGER(0..1)
	ACCESS		read-only
	STATUS		mandatory
	DESCRIPTION	"SafetyNet Series 5 Lite Relay Status.
				 0 = Relay active
				 1 = Relay inactive"
::= { ss5LiteRelay 1 }



-- Series 5 Micro begins here


ss5MicroSensorOneType OBJECT-TYPE
	SYNTAX  	INTEGER(0..9)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid
				7 = Digital
				8 = Zoned Security
				9 = Security"
::= { ss5MicroSensorOne 1 }


ss5MicroSensorOneName OBJECT-TYPE
	SYNTAX		DisplayString (SIZE (0..42))
	ACCESS		read-only
	STATUS		mandatory
	DESCRIPTION	"Sensor Name of SafetyNet Series 5 Micro"
::= { ss5MicroSensorOne 2 }

ss5MicroSensorOneReading OBJECT-TYPE
	SYNTAX  	INTEGER(-200..1200)
	ACCESS		read-only
	STATUS		mandatory
	DESCRIPTION	"SafetyNet Series 5 Micro sensor one reading.
	
				 If sensor is Digital
				 1 = sensor in alarm condition
				 0 = sensor not in alarm condition
				 
				 if sensor is Analogue use multiplier 0.1 for actual reading"
::= { ss5MicroSensorOne 3 }


ss5MicroSensorTwoType OBJECT-TYPE
	SYNTAX  	INTEGER(0..9)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid
				7 = Digital
				8 = Zoned Security
				9 = Security"
::= { ss5MicroSensorTwo 1 }

ss5MicroSensorTwoName OBJECT-TYPE
	SYNTAX		DisplayString (SIZE (0..42))
	ACCESS		read-only
	STATUS		mandatory
	DESCRIPTION	"Sensor Name of SafetyNet Series 5 Micro"
::= { ss5MicroSensorTwo 2 }
	
ss5MicroSensorTwoReading OBJECT-TYPE
	SYNTAX  	INTEGER(-200..1200)
	ACCESS		read-only
	STATUS		mandatory
	DESCRIPTION	"SafetyNet Series 5 Micro sensor two reading.
	
				 If sensor is Digital
				 1 = sensor in alarm condition
				 0 = sensor not in alarm condition
				 
				 if sensor is Analogue use multiplier 0.1 for actual reading"
::= { ss5MicroSensorTwo 3 }

ss5MicroSensorThreeType OBJECT-TYPE
	SYNTAX  	INTEGER(0..9)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid
				7 = Digital
				8 = Zoned Security
				9 = Security"
::= { ss5MicroSensorThree 1 }

ss5MicroSensorThreeName OBJECT-TYPE
	SYNTAX		DisplayString (SIZE (0..42))
	ACCESS		read-only
	STATUS		mandatory
	DESCRIPTION	"Sensor Name of SafetyNet Series 5 Micro"
::= { ss5MicroSensorThree 2 }

ss5MicroSensorThreeReading OBJECT-TYPE
	SYNTAX  	INTEGER(-200..1200)
	ACCESS		read-only
	STATUS		mandatory
	DESCRIPTION	"SafetyNet Series 5 Micro sensor three reading.
	
				 If sensor is Digital
				 1 = sensor in alarm condition
				 0 = sensor not in alarm condition
				 
				 if sensor is Analogue use multiplier 0.1 for actual reading"
::= { ss5MicroSensorThree 3 }


ss5MicroSensorFourType OBJECT-TYPE
	SYNTAX  	INTEGER(0..9)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid
				7 = Digital
				8 = Zoned Security
				9 = Security"
::= { ss5MicroSensorFour 1 }

ss5MicroSensorFourName OBJECT-TYPE
	SYNTAX		DisplayString (SIZE (0..42))
	ACCESS		read-only
	STATUS		mandatory
	DESCRIPTION	"Sensor Name of SafetyNet Series 5 Micro"
::= { ss5MicroSensorFour 2 }

ss5MicroSensorFourReading OBJECT-TYPE
	SYNTAX  	INTEGER(-200..1200)
	ACCESS		read-only
	STATUS		mandatory
	DESCRIPTION	"SafetyNet Series 5 Micro sensor four reading.
	
				 If sensor is Digital
				 1 = sensor in alarm condition
				 0 = sensor not in alarm condition
				 
				 if sensor is Analogue use multiplier 0.1 for actual reading"
::= { ss5MicroSensorFour 3 }
	
	

ss5MicroIpMonitoringReading OBJECT-TYPE
	SYNTAX  	INTEGER(0..1)
	ACCESS		read-only
	STATUS		mandatory
	DESCRIPTION	"SafetyNet Series 5 Micro IP Monitoring Alarm.
				 1 = alarm condition
				 0 = not in alarm condition"
::= { ss5MicroReadings 5 }

ss5MicroLowBatteryReading OBJECT-TYPE
	SYNTAX  	INTEGER(0..1)
	ACCESS		read-only
	STATUS		mandatory
	DESCRIPTION	"SafetyNet Series 5 Micro Low Battery.
				 1 = alarm condition
				 0 = not in alarm condition"
::= { ss5MicroReadings 6 }

ss5MicroMainsFailureReading OBJECT-TYPE
	SYNTAX  	INTEGER(0..1)
	ACCESS		read-only
	STATUS		mandatory
	DESCRIPTION	"SafetyNet Series 5 Micro Mains Failure Alarm.
				 1 = alarm condition
				 0 = not in alarm condition"
::= { ss5MicroReadings 7 }

ss5MicroFaultySensorReading OBJECT-TYPE
	SYNTAX  	INTEGER(0..1)
	ACCESS		read-only
	STATUS		mandatory
	DESCRIPTION	"SafetyNet Series 5 Micro Faulty Sensor(s) Alarm.
				 1 = alarm condition
				 0 = not in alarm condition"
::= { ss5MicroReadings 8 }

ss5MicroDialToneOrSIMErrorReading OBJECT-TYPE
	SYNTAX  	INTEGER(0..1)
	ACCESS		read-only
	STATUS		mandatory
	DESCRIPTION	"SafetyNet Series 5 Micro Dial Tone Alarm for PSTN Modem Version. SafetyNet Series 5 Micro GSM SIM Card Error Alarm for GSM Modem Version.
				 1 = alarm condition
				 0 = not in alarm condition"
::= { ss5MicroReadings 9}



--SafetyNet Series 5 D40 expansion.

ss5D40Sensor01Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor01 1 }

ss5D40Sensor01Name OBJECT-TYPE
	SYNTAX		DisplayString (SIZE (0..42))
	ACCESS		read-only
	STATUS		mandatory
	DESCRIPTION	"Sensor Name of SafetyNet Series 5"
::= { ss5D40Sensor01 2 }

ss5D40Sensor01Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor01 3 }

ss5D40Sensor02Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor02 1 }

ss5D40Sensor02Name OBJECT-TYPE
	SYNTAX		DisplayString (SIZE (0..42))
	ACCESS		read-only
	STATUS		mandatory
	DESCRIPTION	"Sensor Name of SafetyNet Series 5"
::= { ss5D40Sensor02 2 }

ss5D40Sensor02Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor02 3 }

ss5D40Sensor03Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor03 1 }

ss5D40Sensor03Name OBJECT-TYPE
	SYNTAX		DisplayString (SIZE (0..42))
	ACCESS		read-only
	STATUS		mandatory
	DESCRIPTION	"Sensor Name of SafetyNet Series 5"
::= { ss5D40Sensor03 2 }

ss5D40Sensor03Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor03 3 }

ss5D40Sensor04Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor04 1 }

ss5D40Sensor04Name OBJECT-TYPE
	SYNTAX		DisplayString (SIZE (0..42))
	ACCESS		read-only
	STATUS		mandatory
	DESCRIPTION	"Sensor Name of SafetyNet Series 5"
::= { ss5D40Sensor04 2 }

ss5D40Sensor04Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor04 3 }

ss5D40Sensor05Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor05 1 }

ss5D40Sensor05Name OBJECT-TYPE
	SYNTAX		DisplayString (SIZE (0..42))
	ACCESS		read-only
	STATUS		mandatory
	DESCRIPTION	"Sensor Name of SafetyNet Series 5"
::= { ss5D40Sensor05 2 }

ss5D40Sensor05Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor05 3 }

ss5D40Sensor06Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor06 1 }

ss5D40Sensor06Name OBJECT-TYPE
	SYNTAX		DisplayString (SIZE (0..42))
	ACCESS		read-only
	STATUS		mandatory
	DESCRIPTION	"Sensor Name of SafetyNet Series 5"
::= { ss5D40Sensor06 2 }

ss5D40Sensor06Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor06 3 }

ss5D40Sensor07Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor07 1 }

ss5D40Sensor07Name OBJECT-TYPE
	SYNTAX		DisplayString (SIZE (0..42))
	ACCESS		read-only
	STATUS		mandatory
	DESCRIPTION	"Sensor Name of SafetyNet Series 5"
::= { ss5D40Sensor07 2 }

ss5D40Sensor07Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor07 3 }

ss5D40Sensor08Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor08 1 }

ss5D40Sensor08Name OBJECT-TYPE
	SYNTAX		DisplayString (SIZE (0..42))
	ACCESS		read-only
	STATUS		mandatory
	DESCRIPTION	"Sensor Name of SafetyNet Series 5"
::= { ss5D40Sensor08 2 }

ss5D40Sensor08Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor08 3 }

ss5D40Sensor09Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor09 1 }

ss5D40Sensor09Name OBJECT-TYPE
	SYNTAX		DisplayString (SIZE (0..42))
	ACCESS		read-only
	STATUS		mandatory
	DESCRIPTION	"Sensor Name of SafetyNet Series 5"
::= { ss5D40Sensor09 2 }

ss5D40Sensor09Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor09 3 }

ss5D40Sensor10Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor10 1 }

ss5D40Sensor10Name OBJECT-TYPE
	SYNTAX		DisplayString (SIZE (0..42))
	ACCESS		read-only
	STATUS		mandatory
	DESCRIPTION	"Sensor Name of SafetyNet Series 5"
::= { ss5D40Sensor10 2 }

ss5D40Sensor10Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor10 3 }

ss5D40Sensor11Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor11 1 }

ss5D40Sensor11Name OBJECT-TYPE
	SYNTAX		DisplayString (SIZE (0..42))
	ACCESS		read-only
	STATUS		mandatory
	DESCRIPTION	"Sensor Name of SafetyNet Series 5"
::= { ss5D40Sensor11 2 }

ss5D40Sensor11Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor11 3 }

ss5D40Sensor12Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor12 1 }

ss5D40Sensor12Name OBJECT-TYPE
	SYNTAX		DisplayString (SIZE (0..42))
	ACCESS		read-only
	STATUS		mandatory
	DESCRIPTION	"Sensor Name of SafetyNet Series 5"
::= { ss5D40Sensor12 2 }

ss5D40Sensor12Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor12 3 }

ss5D40Sensor13Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor13 1 }

ss5D40Sensor13Name OBJECT-TYPE
	SYNTAX		DisplayString (SIZE (0..42))
	ACCESS		read-only
	STATUS		mandatory
	DESCRIPTION	"Sensor Name of SafetyNet Series 5"
::= { ss5D40Sensor13 2 }

ss5D40Sensor13Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor13 3 }

ss5D40Sensor14Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor14 1 }

ss5D40Sensor14Name OBJECT-TYPE
	SYNTAX		DisplayString (SIZE (0..42))
	ACCESS		read-only
	STATUS		mandatory
	DESCRIPTION	"Sensor Name of SafetyNet Series 5"
::= { ss5D40Sensor14 2 }

ss5D40Sensor14Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor14 3 }

ss5D40Sensor15Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor15 1 }

ss5D40Sensor15Name OBJECT-TYPE
	SYNTAX		DisplayString (SIZE (0..42))
	ACCESS		read-only
	STATUS		mandatory
	DESCRIPTION	"Sensor Name of SafetyNet Series 5"
::= { ss5D40Sensor15 2 }

ss5D40Sensor15Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor15 3 }

ss5D40Sensor16Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor16 1 }

ss5D40Sensor16Name OBJECT-TYPE
	SYNTAX		DisplayString (SIZE (0..42))
	ACCESS		read-only
	STATUS		mandatory
	DESCRIPTION	"Sensor Name of SafetyNet Series 5"
::= { ss5D40Sensor16 2 }

ss5D40Sensor16Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor16 3 }

ss5D40Sensor17Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor17 1 }

ss5D40Sensor17Name OBJECT-TYPE
	SYNTAX		DisplayString (SIZE (0..42))
	ACCESS		read-only
	STATUS		mandatory
	DESCRIPTION	"Sensor Name of SafetyNet Series 5"
::= { ss5D40Sensor17 2 }

ss5D40Sensor17Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor17 3 }

ss5D40Sensor18Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor18 1 }

ss5D40Sensor18Name OBJECT-TYPE
	SYNTAX		DisplayString (SIZE (0..42))
	ACCESS		read-only
	STATUS		mandatory
	DESCRIPTION	"Sensor Name of SafetyNet Series 5"
::= { ss5D40Sensor18 2 }

ss5D40Sensor18Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor18 3 }


ss5D40Sensor19Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor19 1 }

ss5D40Sensor19Name OBJECT-TYPE
	SYNTAX		DisplayString (SIZE (0..42))
	ACCESS		read-only
	STATUS		mandatory
	DESCRIPTION	"Sensor Name of SafetyNet Series 5"
::= { ss5D40Sensor19 2 }

ss5D40Sensor19Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor19 3 }

ss5D40Sensor20Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor20 1 }

ss5D40Sensor20Name OBJECT-TYPE
	SYNTAX		DisplayString (SIZE (0..42))
	ACCESS		read-only
	STATUS		mandatory
	DESCRIPTION	"Sensor Name of SafetyNet Series 5"
::= { ss5D40Sensor20 2 }

ss5D40Sensor20Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor20 3 }


ss5D40Sensor21Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor21 1 }

ss5D40Sensor21Name OBJECT-TYPE
	SYNTAX		DisplayString (SIZE (0..42))
	ACCESS		read-only
	STATUS		mandatory
	DESCRIPTION	"Sensor Name of SafetyNet Series 5"
::= { ss5D40Sensor21 2 }

ss5D40Sensor21Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor21 3 }

ss5D40Sensor22Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor22 1 }

ss5D40Sensor22Name OBJECT-TYPE
	SYNTAX		DisplayString (SIZE (0..42))
	ACCESS		read-only
	STATUS		mandatory
	DESCRIPTION	"Sensor Name of SafetyNet Series 5"
::= { ss5D40Sensor22 2 }

ss5D40Sensor22Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor22 3 }

ss5D40Sensor23Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor23 1 }

ss5D40Sensor23Name OBJECT-TYPE
	SYNTAX		DisplayString (SIZE (0..42))
	ACCESS		read-only
	STATUS		mandatory
	DESCRIPTION	"Sensor Name of SafetyNet Series 5"
::= { ss5D40Sensor23 2 }

ss5D40Sensor23Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor23 3 }

ss5D40Sensor24Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor24 1 }

ss5D40Sensor24Name OBJECT-TYPE
	SYNTAX		DisplayString (SIZE (0..42))
	ACCESS		read-only
	STATUS		mandatory
	DESCRIPTION	"Sensor Name of SafetyNet Series 5"
::= { ss5D40Sensor24 2 }

ss5D40Sensor24Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor24 3 }


ss5D40Sensor25Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor25 1 }

ss5D40Sensor25Name OBJECT-TYPE
	SYNTAX		DisplayString (SIZE (0..42))
	ACCESS		read-only
	STATUS		mandatory
	DESCRIPTION	"Sensor Name of SafetyNet Series 5"
::= { ss5D40Sensor25 2 }

ss5D40Sensor25Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor25 3 }

ss5D40Sensor26Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor26 1 }

ss5D40Sensor26Name OBJECT-TYPE
	SYNTAX		DisplayString (SIZE (0..42))
	ACCESS		read-only
	STATUS		mandatory
	DESCRIPTION	"Sensor Name of SafetyNet Series 5"
::= { ss5D40Sensor26 2 }

ss5D40Sensor26Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor26 3 }


ss5D40Sensor27Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor27 1 }

ss5D40Sensor27Name OBJECT-TYPE
	SYNTAX		DisplayString (SIZE (0..42))
	ACCESS		read-only
	STATUS		mandatory
	DESCRIPTION	"Sensor Name of SafetyNet Series 5"
::= { ss5D40Sensor27 2 }

ss5D40Sensor27Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor27 3 }

ss5D40Sensor28Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor28 1 }

ss5D40Sensor28Name OBJECT-TYPE
	SYNTAX		DisplayString (SIZE (0..42))
	ACCESS		read-only
	STATUS		mandatory
	DESCRIPTION	"Sensor Name of SafetyNet Series 5"
::= { ss5D40Sensor28 2 }

ss5D40Sensor28Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor28 3 }

ss5D40Sensor29Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor29 1 }

ss5D40Sensor29Name OBJECT-TYPE
	SYNTAX		DisplayString (SIZE (0..42))
	ACCESS		read-only
	STATUS		mandatory
	DESCRIPTION	"Sensor Name of SafetyNet Series 5"
::= { ss5D40Sensor29 2 }

ss5D40Sensor29Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor29 3 }


ss5D40Sensor30Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor30 1 }

ss5D40Sensor30Name OBJECT-TYPE
	SYNTAX		DisplayString (SIZE (0..42))
	ACCESS		read-only
	STATUS		mandatory
	DESCRIPTION	"Sensor Name of SafetyNet Series 5"
::= { ss5D40Sensor30 2 }

ss5D40Sensor30Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor30 3 }


ss5D40Sensor31Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor31 1 }

ss5D40Sensor31Name OBJECT-TYPE
	SYNTAX		DisplayString (SIZE (0..42))
	ACCESS		read-only
	STATUS		mandatory
	DESCRIPTION	"Sensor Name of SafetyNet Series 5"
::= { ss5D40Sensor31 2 }

ss5D40Sensor31Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor31 3 }


ss5D40Sensor32Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor32 1 }

ss5D40Sensor32Name OBJECT-TYPE
	SYNTAX		DisplayString (SIZE (0..42))
	ACCESS		read-only
	STATUS		mandatory
	DESCRIPTION	"Sensor Name of SafetyNet Series 5"
::= { ss5D40Sensor32 2 }

ss5D40Sensor32Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor32 3 }

ss5D40Sensor33Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor33 1 }

ss5D40Sensor33Name OBJECT-TYPE
	SYNTAX		DisplayString (SIZE (0..42))
	ACCESS		read-only
	STATUS		mandatory
	DESCRIPTION	"Sensor Name of SafetyNet Series 5"
::= { ss5D40Sensor33 2 }

ss5D40Sensor33Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor33 3 }


ss5D40Sensor34Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor34 1 }

ss5D40Sensor34Name OBJECT-TYPE
	SYNTAX		DisplayString (SIZE (0..42))
	ACCESS		read-only
	STATUS		mandatory
	DESCRIPTION	"Sensor Name of SafetyNet Series 5"
::= { ss5D40Sensor34 2 }

ss5D40Sensor34Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor34 3 }

ss5D40Sensor35Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor35 1 }

ss5D40Sensor35Name OBJECT-TYPE
	SYNTAX		DisplayString (SIZE (0..42))
	ACCESS		read-only
	STATUS		mandatory
	DESCRIPTION	"Sensor Name of SafetyNet Series 5"
::= { ss5D40Sensor35 2 }

ss5D40Sensor35Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor35 3 }

ss5D40Sensor36Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor36 1 }

ss5D40Sensor36Name OBJECT-TYPE
	SYNTAX		DisplayString (SIZE (0..42))
	ACCESS		read-only
	STATUS		mandatory
	DESCRIPTION	"Sensor Name of SafetyNet Series 5"
::= { ss5D40Sensor36 2 }

ss5D40Sensor36Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor36 3 }

ss5D40Sensor37Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor37 1 }

ss5D40Sensor37Name OBJECT-TYPE
	SYNTAX		DisplayString (SIZE (0..42))
	ACCESS		read-only
	STATUS		mandatory
	DESCRIPTION	"Sensor Name of SafetyNet Series 5"
::= { ss5D40Sensor37 2 }

ss5D40Sensor37Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor37 3 }

ss5D40Sensor38Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor38 1 }

ss5D40Sensor38Name OBJECT-TYPE
	SYNTAX		DisplayString (SIZE (0..42))
	ACCESS		read-only
	STATUS		mandatory
	DESCRIPTION	"Sensor Name of SafetyNet Series 5"
::= { ss5D40Sensor38 2 }

ss5D40Sensor38Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor38 3 }


ss5D40Sensor39Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor39 1 }

ss5D40Sensor39Name OBJECT-TYPE
	SYNTAX		DisplayString (SIZE (0..42))
	ACCESS		read-only
	STATUS		mandatory
	DESCRIPTION	"Sensor Name of SafetyNet Series 5"
::= { ss5D40Sensor39 2 }

ss5D40Sensor39Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor39 3 }

ss5D40Sensor40Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D40Sensor40 1 }

ss5D40Sensor40Name OBJECT-TYPE
	SYNTAX		DisplayString (SIZE (0..42))
	ACCESS		read-only
	STATUS		mandatory
	DESCRIPTION	"Sensor Name of SafetyNet Series 5"
::= { ss5D40Sensor40 2 }

ss5D40Sensor40Reading OBJECT-TYPE
	SYNTAX  	INTEGER(0..1)
	ACCESS		read-only
	STATUS		mandatory
	DESCRIPTION	"SafetyNet Series 5 sensor reading.
				 1 = sensor in alarm condition
				 0 = sensor not in alarm condition"
::= { ss5D40Sensor40 3 }


ss5D40IpMonitoringReading OBJECT-TYPE
	SYNTAX  	INTEGER(0..1)
	ACCESS		read-only
	STATUS		mandatory
	DESCRIPTION	"SafetyNet Series 5 IP Monitoring Alarm.
				 1 = alarm condition
				 0 = not in alarm condition"
::= { ss5D40Readings 41 }

ss5D40LowBatteryReading OBJECT-TYPE
	SYNTAX  	INTEGER(0..1)
	ACCESS		read-only
	STATUS		mandatory
	DESCRIPTION	"SafetyNet Series 5 Low Battery.
				 1 = alarm condition
				 0 = not in alarm condition"
::= { ss5D40Readings 42 }

ss5D40MainsFailureReading OBJECT-TYPE
	SYNTAX  	INTEGER(0..1)
	ACCESS		read-only
	STATUS		mandatory
	DESCRIPTION	"SafetyNet Series 5 Mains Failure Alarm.
				 1 = alarm condition
				 0 = not in alarm condition"
::= { ss5D40Readings 43 }

ss5D40DialToneOrSIMErrorReading OBJECT-TYPE
	SYNTAX  	INTEGER(0..1)
	ACCESS		read-only
	STATUS		mandatory
	DESCRIPTION	"SafetyNet Series 5 Dial Tone Alarm for PSTN Modem Version. SafetyNet Series 5 GSM SIM Card Error Alarm for GSM Modem Version.
				 1 = alarm condition
				 0 = not in alarm condition"
::= { ss5D40Readings 45 }


ss5D40RelayOne OBJECT-TYPE
	SYNTAX  	INTEGER(0..1)
	ACCESS		read-only
	STATUS		mandatory
	DESCRIPTION	"SafetyNet Series 5 D40 Relay One Status.
				 0 = Relay active
				 1 = Relay inactive"
::= { ss5D40Relays 1 }
	
ss5D40RelayTwo OBJECT-TYPE
	SYNTAX  	INTEGER(0..1)
	ACCESS		read-only
	STATUS		mandatory
	DESCRIPTION	"SafetyNet Series 5 D40 Relay Two Status.
				 0 = Relay active
				 1 = Relay inactive"
::= { ss5D40Relays 2 }


--SafetyNet Series 5 D20 expansion.

ss5D20Sensor01Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D20Sensor01 1 }

ss5D20Sensor01Name OBJECT-TYPE
	SYNTAX		DisplayString (SIZE (0..42))
	ACCESS		read-only
	STATUS		mandatory
	DESCRIPTION	"Sensor Name of SafetyNet Series 5"
::= { ss5D20Sensor01 2 }

ss5D20Sensor01Reading OBJECT-TYPE
	SYNTAX  	INTEGER(0..1)
	ACCESS		read-only
	STATUS		mandatory
	DESCRIPTION	"SafetyNet Series 5 sensor reading.
				 1 = sensor in alarm condition
				 0 = sensor not in alarm condition"
::= { ss5D20Sensor01 3 }

ss5D20Sensor02Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D20Sensor02 1 }

ss5D20Sensor02Name OBJECT-TYPE
	SYNTAX		DisplayString (SIZE (0..42))
	ACCESS		read-only
	STATUS		mandatory
	DESCRIPTION	"Sensor Name of SafetyNet Series 5"
::= { ss5D20Sensor02 2 }

ss5D20Sensor02Reading OBJECT-TYPE
	SYNTAX  	INTEGER(0..1)
	ACCESS		read-only
	STATUS		mandatory
	DESCRIPTION	"SafetyNet Series 5 sensor reading.
				 1 = sensor in alarm condition
				 0 = sensor not in alarm condition"
::= { ss5D20Sensor02 3 }

ss5D20Sensor03Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D20Sensor03 1 }

ss5D20Sensor03Name OBJECT-TYPE
	SYNTAX		DisplayString (SIZE (0..42))
	ACCESS		read-only
	STATUS		mandatory
	DESCRIPTION	"Sensor Name of SafetyNet Series 5"
::= { ss5D20Sensor03 2 }

ss5D20Sensor03Reading OBJECT-TYPE
	SYNTAX  	INTEGER(0..1)
	ACCESS		read-only
	STATUS		mandatory
	DESCRIPTION	"SafetyNet Series 5 sensor reading.
				 1 = sensor in alarm condition
				 0 = sensor not in alarm condition"
::= { ss5D20Sensor03 3 }

ss5D20Sensor04Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D20Sensor04 1 }

ss5D20Sensor04Name OBJECT-TYPE
	SYNTAX		DisplayString (SIZE (0..42))
	ACCESS		read-only
	STATUS		mandatory
	DESCRIPTION	"Sensor Name of SafetyNet Series 5"
::= { ss5D20Sensor04 2 }

ss5D20Sensor04Reading OBJECT-TYPE
	SYNTAX  	INTEGER(0..1)
	ACCESS		read-only
	STATUS		mandatory
	DESCRIPTION	"SafetyNet Series 5 sensor reading.
				 1 = sensor in alarm condition
				 0 = sensor not in alarm condition"
::= { ss5D20Sensor04 3 }

ss5D20Sensor05Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D20Sensor05 1 }

ss5D20Sensor05Name OBJECT-TYPE
	SYNTAX		DisplayString (SIZE (0..42))
	ACCESS		read-only
	STATUS		mandatory
	DESCRIPTION	"Sensor Name of SafetyNet Series 5"
::= { ss5D20Sensor05 2 }

ss5D20Sensor05Reading OBJECT-TYPE
	SYNTAX  	INTEGER(0..1)
	ACCESS		read-only
	STATUS		mandatory
	DESCRIPTION	"SafetyNet Series 5 sensor reading.
				 1 = sensor in alarm condition
				 0 = sensor not in alarm condition"
::= { ss5D20Sensor05 3 }

ss5D20Sensor06Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D20Sensor06 1 }

ss5D20Sensor06Name OBJECT-TYPE
	SYNTAX		DisplayString (SIZE (0..42))
	ACCESS		read-only
	STATUS		mandatory
	DESCRIPTION	"Sensor Name of SafetyNet Series 5"
::= { ss5D20Sensor06 2 }

ss5D20Sensor06Reading OBJECT-TYPE
	SYNTAX  	INTEGER(0..1)
	ACCESS		read-only
	STATUS		mandatory
	DESCRIPTION	"SafetyNet Series 5 sensor reading.
				 1 = sensor in alarm condition
				 0 = sensor not in alarm condition"
::= { ss5D20Sensor06 3 }

ss5D20Sensor07Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D20Sensor07 1 }

ss5D20Sensor07Name OBJECT-TYPE
	SYNTAX		DisplayString (SIZE (0..42))
	ACCESS		read-only
	STATUS		mandatory
	DESCRIPTION	"Sensor Name of SafetyNet Series 5"
::= { ss5D20Sensor07 2 }

ss5D20Sensor07Reading OBJECT-TYPE
	SYNTAX  	INTEGER(0..1)
	ACCESS		read-only
	STATUS		mandatory
	DESCRIPTION	"SafetyNet Series 5 sensor reading.
				 1 = sensor in alarm condition
				 0 = sensor not in alarm condition"
::= { ss5D20Sensor07 3 }

ss5D20Sensor08Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D20Sensor08 1 }

ss5D20Sensor08Name OBJECT-TYPE
	SYNTAX		DisplayString (SIZE (0..42))
	ACCESS		read-only
	STATUS		mandatory
	DESCRIPTION	"Sensor Name of SafetyNet Series 5"
::= { ss5D20Sensor08 2 }

ss5D20Sensor08Reading OBJECT-TYPE
	SYNTAX  	INTEGER(0..1)
	ACCESS		read-only
	STATUS		mandatory
	DESCRIPTION	"SafetyNet Series 5 sensor reading.
				 1 = sensor in alarm condition
				 0 = sensor not in alarm condition"
::= { ss5D20Sensor08 3 }

ss5D20Sensor09Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D20Sensor09 1 }

ss5D20Sensor09Name OBJECT-TYPE
	SYNTAX		DisplayString (SIZE (0..42))
	ACCESS		read-only
	STATUS		mandatory
	DESCRIPTION	"Sensor Name of SafetyNet Series 5"
::= { ss5D20Sensor09 2 }

ss5D20Sensor09Reading OBJECT-TYPE
	SYNTAX  	INTEGER(0..1)
	ACCESS		read-only
	STATUS		mandatory
	DESCRIPTION	"SafetyNet Series 5 sensor reading.
				 1 = sensor in alarm condition
				 0 = sensor not in alarm condition"
::= { ss5D20Sensor09 3 }

ss5D20Sensor10Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D20Sensor10 1 }

ss5D20Sensor10Name OBJECT-TYPE
	SYNTAX		DisplayString (SIZE (0..42))
	ACCESS		read-only
	STATUS		mandatory
	DESCRIPTION	"Sensor Name of SafetyNet Series 5"
::= { ss5D20Sensor10 2 }

ss5D20Sensor10Reading OBJECT-TYPE
	SYNTAX  	INTEGER(0..1)
	ACCESS		read-only
	STATUS		mandatory
	DESCRIPTION	"SafetyNet Series 5 sensor reading.
				 1 = sensor in alarm condition
				 0 = sensor not in alarm condition"
::= { ss5D20Sensor10 3 }

ss5D20Sensor11Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D20Sensor11 1 }

ss5D20Sensor11Name OBJECT-TYPE
	SYNTAX		DisplayString (SIZE (0..42))
	ACCESS		read-only
	STATUS		mandatory
	DESCRIPTION	"Sensor Name of SafetyNet Series 5"
::= { ss5D20Sensor11 2 }

ss5D20Sensor11Reading OBJECT-TYPE
	SYNTAX  	INTEGER(0..1)
	ACCESS		read-only
	STATUS		mandatory
	DESCRIPTION	"SafetyNet Series 5 sensor reading.
				 1 = sensor in alarm condition
				 0 = sensor not in alarm condition"
::= { ss5D20Sensor11 3 }

ss5D20Sensor12Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D20Sensor12 1 }

ss5D20Sensor12Name OBJECT-TYPE
	SYNTAX		DisplayString (SIZE (0..42))
	ACCESS		read-only
	STATUS		mandatory
	DESCRIPTION	"Sensor Name of SafetyNet Series 5"
::= { ss5D20Sensor12 2 }

ss5D20Sensor12Reading OBJECT-TYPE
	SYNTAX  	INTEGER(0..1)
	ACCESS		read-only
	STATUS		mandatory
	DESCRIPTION	"SafetyNet Series 5 sensor reading.
				 1 = sensor in alarm condition
				 0 = sensor not in alarm condition"
::= { ss5D20Sensor12 3 }

ss5D20Sensor13Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D20Sensor13 1 }

ss5D20Sensor13Name OBJECT-TYPE
	SYNTAX		DisplayString (SIZE (0..42))
	ACCESS		read-only
	STATUS		mandatory
	DESCRIPTION	"Sensor Name of SafetyNet Series 5"
::= { ss5D20Sensor13 2 }

ss5D20Sensor13Reading OBJECT-TYPE
	SYNTAX  	INTEGER(0..1)
	ACCESS		read-only
	STATUS		mandatory
	DESCRIPTION	"SafetyNet Series 5 sensor reading.
				 1 = sensor in alarm condition
				 0 = sensor not in alarm condition"
::= { ss5D20Sensor13 3 }

ss5D20Sensor14Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D20Sensor14 1 }

ss5D20Sensor14Name OBJECT-TYPE
	SYNTAX		DisplayString (SIZE (0..42))
	ACCESS		read-only
	STATUS		mandatory
	DESCRIPTION	"Sensor Name of SafetyNet Series 5"
::= { ss5D20Sensor14 2 }

ss5D20Sensor14Reading OBJECT-TYPE
	SYNTAX  	INTEGER(0..1)
	ACCESS		read-only
	STATUS		mandatory
	DESCRIPTION	"SafetyNet Series 5 sensor reading.
				 1 = sensor in alarm condition
				 0 = sensor not in alarm condition"
::= { ss5D20Sensor14 3 }

ss5D20Sensor15Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D20Sensor15 1 }

ss5D20Sensor15Name OBJECT-TYPE
	SYNTAX		DisplayString (SIZE (0..42))
	ACCESS		read-only
	STATUS		mandatory
	DESCRIPTION	"Sensor Name of SafetyNet Series 5"
::= { ss5D20Sensor15 2 }

ss5D20Sensor15Reading OBJECT-TYPE
	SYNTAX  	INTEGER(0..1)
	ACCESS		read-only
	STATUS		mandatory
	DESCRIPTION	"SafetyNet Series 5 sensor reading.
				 1 = sensor in alarm condition
				 0 = sensor not in alarm condition"
::= { ss5D20Sensor15 3 }

ss5D20Sensor16Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D20Sensor16 1 }

ss5D20Sensor16Name OBJECT-TYPE
	SYNTAX		DisplayString (SIZE (0..42))
	ACCESS		read-only
	STATUS		mandatory
	DESCRIPTION	"Sensor Name of SafetyNet Series 5"
::= { ss5D20Sensor16 2 }

ss5D20Sensor16Reading OBJECT-TYPE
	SYNTAX  	INTEGER(0..1)
	ACCESS		read-only
	STATUS		mandatory
	DESCRIPTION	"SafetyNet Series 5 sensor reading.
				 1 = sensor in alarm condition
				 0 = sensor not in alarm condition"
::= { ss5D20Sensor16 3 }

ss5D20Sensor17Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D20Sensor17 1 }

ss5D20Sensor17Name OBJECT-TYPE
	SYNTAX		DisplayString (SIZE (0..42))
	ACCESS		read-only
	STATUS		mandatory
	DESCRIPTION	"Sensor Name of SafetyNet Series 5"
::= { ss5D20Sensor17 2 }

ss5D20Sensor17Reading OBJECT-TYPE
	SYNTAX  	INTEGER(0..1)
	ACCESS		read-only
	STATUS		mandatory
	DESCRIPTION	"SafetyNet Series 5 sensor reading.
				 1 = sensor in alarm condition
				 0 = sensor not in alarm condition"
::= { ss5D20Sensor17 3 }

ss5D20Sensor18Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D20Sensor18 1 }

ss5D20Sensor18Name OBJECT-TYPE
	SYNTAX		DisplayString (SIZE (0..42))
	ACCESS		read-only
	STATUS		mandatory
	DESCRIPTION	"Sensor Name of SafetyNet Series 5"
::= { ss5D20Sensor18 2 }

ss5D20Sensor18Reading OBJECT-TYPE
	SYNTAX  	INTEGER(0..1)
	ACCESS		read-only
	STATUS		mandatory
	DESCRIPTION	"SafetyNet Series 5 sensor reading.
				 1 = sensor in alarm condition
				 0 = sensor not in alarm condition"
::= { ss5D20Sensor18 3 }


ss5D20Sensor19Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D20Sensor19 1 }

ss5D20Sensor19Name OBJECT-TYPE
	SYNTAX		DisplayString (SIZE (0..42))
	ACCESS		read-only
	STATUS		mandatory
	DESCRIPTION	"Sensor Name of SafetyNet Series 5"
::= { ss5D20Sensor19 2 }

ss5D20Sensor19Reading OBJECT-TYPE
	SYNTAX  	INTEGER(0..1)
	ACCESS		read-only
	STATUS		mandatory
	DESCRIPTION	"SafetyNet Series 5 sensor reading.
				 1 = sensor in alarm condition
				 0 = sensor not in alarm condition"
::= { ss5D20Sensor19 3 }

ss5D20Sensor20Type OBJECT-TYPE
	SYNTAX  	INTEGER(0..4)
	ACCESS		read-only
	STATUS		mandatory
	DESCRIPTION	"Provides an identification for the sensor/input type
				0 = Digital
				1 = Fluid
				2 = Security
				3 = Zoned Security
				4 = Smoke"
::= { ss5D20Sensor20 1 }

ss5D20Sensor20Name OBJECT-TYPE
	SYNTAX		DisplayString (SIZE (0..42))
	ACCESS		read-only
	STATUS		mandatory
	DESCRIPTION	"Sensor Name of SafetyNet Series 5"
::= { ss5D20Sensor20 2 }

ss5D20Sensor20Reading OBJECT-TYPE
	SYNTAX  	INTEGER(0..1)
	ACCESS		read-only
	STATUS		mandatory
	DESCRIPTION	"SafetyNet Series 5 sensor reading.
				 1 = sensor in alarm condition
				 0 = sensor not in alarm condition"
::= { ss5D20Sensor20 3 }


ss5D20IpMonitoringReading OBJECT-TYPE
	SYNTAX  	INTEGER(0..1)
	ACCESS		read-only
	STATUS		mandatory
	DESCRIPTION	"SafetyNet Series 5 IP Monitoring Alarm.
				 1 = alarm condition
				 0 = not in alarm condition"
::= { ss5D20Readings 21 }

ss5D20LowBatteryReading OBJECT-TYPE
	SYNTAX  	INTEGER(0..1)
	ACCESS		read-only
	STATUS		mandatory
	DESCRIPTION	"SafetyNet Series 5 Low Battery.
				 1 = alarm condition
				 0 = not in alarm condition"
::= { ss5D20Readings 22 }

ss5D20MainsFailureReading OBJECT-TYPE
	SYNTAX  	INTEGER(0..1)
	ACCESS		read-only
	STATUS		mandatory
	DESCRIPTION	"SafetyNet Series 5 Mains Failure Alarm.
				 1 = alarm condition
				 0 = not in alarm condition"
::= { ss5D20Readings 23 }

ss5D20DialToneOrSIMErrorReading OBJECT-TYPE
	SYNTAX  	INTEGER(0..1)
	ACCESS		read-only
	STATUS		mandatory
	DESCRIPTION	"SafetyNet Series 5 Dial Tone Alarm for PSTN Modem Version. SafetyNet Series 5 GSM SIM Card Error Alarm for GSM Modem Version.
				 1 = alarm condition
				 0 = not in alarm condition"
::= { ss5D20Readings 25 }


ss5D20Relay OBJECT-TYPE
	SYNTAX  	INTEGER(0..1)
	ACCESS		read-only
	STATUS		mandatory
	DESCRIPTION	"SafetyNet Series 5 D20 Relay Status.
				 0 = Relay active
				 1 = Relay inactive"
::= { ss5D20Relays 1 }
	
-- SafetyNet Series 5 Combo description

ss5ComboUniversal01Type OBJECT-TYPE
	SYNTAX  	INTEGER(0..6)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid"
::= { ss5ComboUniversal01 1 }

ss5ComboUniversal01Name OBJECT-TYPE
	SYNTAX		DisplayString (SIZE (0..42))
	ACCESS		read-only
	STATUS		mandatory
	DESCRIPTION	"Sensor Name of SafetyNet Series 5 Combo"
::= { ss5ComboUniversal01 2 }

ss5ComboUniversal01Reading OBJECT-TYPE
	SYNTAX  	INTEGER(-200..1200)
	ACCESS		read-only
	STATUS		mandatory
	DESCRIPTION	"SafetyNet Series 5 Combo universal sensor one reading.
				 If sensor is Analogue use multiplier 0.1 for actual reading
				 If sensor is Smoke or Fluid,
				 1 = sensor in alarm condition
				 0 = sensor not in alarm condition"
::= { ss5ComboUniversal01 3 }

ss5ComboUniversal02Type OBJECT-TYPE
	SYNTAX  	INTEGER(0..6)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid"
::= { ss5ComboUniversal02 1 }

ss5ComboUniversal02Name OBJECT-TYPE
	SYNTAX		DisplayString (SIZE (0..42))
	ACCESS		read-only
	STATUS		mandatory
	DESCRIPTION	"Sensor Name of SafetyNet Series 5 Combo"
::= { ss5ComboUniversal02 2 }

ss5ComboUniversal02Reading OBJECT-TYPE
	SYNTAX  	INTEGER(-200..1200)
	ACCESS		read-only
	STATUS		mandatory
	DESCRIPTION	"SafetyNet Series 5 universal sensor two reading.
				 If sensor is Analogue use multiplier 0.1 for actual reading
				 If sensor is Smoke or Fluid,
				 1 = sensor in alarm condition
				 0 = sensor not in alarm condition"
::= { ss5ComboUniversal02 3 }

ss5ComboUniversal03Type OBJECT-TYPE
	SYNTAX  	INTEGER(0..6)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid"
::= { ss5ComboUniversal03 1 }

ss5ComboUniversal03Name OBJECT-TYPE
	SYNTAX		DisplayString (SIZE (0..42))
	ACCESS		read-only
	STATUS		mandatory
	DESCRIPTION	"Sensor Name of SafetyNet Series 5 Combo"
::= { ss5ComboUniversal03 2 }

ss5ComboUniversal03Reading OBJECT-TYPE
	SYNTAX  	INTEGER(-200..1200)
	ACCESS		read-only
	STATUS		mandatory
	DESCRIPTION	"SafetyNet Series 5 universal sensor three reading.
				 If sensor is Analogue use multiplier 0.1 for actual reading
				 If sensor is Smoke or Fluid,
				 1 = sensor in alarm condition
				 0 = sensor not in alarm condition"
::= { ss5ComboUniversal03 3 }

ss5ComboUniversal04Type OBJECT-TYPE
	SYNTAX  	INTEGER(0..6)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid"
::= { ss5ComboUniversal04 1 }

ss5ComboUniversal04Name OBJECT-TYPE
	SYNTAX		DisplayString (SIZE (0..42))
	ACCESS		read-only
	STATUS		mandatory
	DESCRIPTION	"Sensor Name of SafetyNet Series 5 Combo"
::= { ss5ComboUniversal04 2 }

ss5ComboUniversal04Reading OBJECT-TYPE
	SYNTAX  	INTEGER(-200..1200)
	ACCESS		read-only
	STATUS		mandatory
	DESCRIPTION	"SafetyNet Series 5 universal sensor four reading.
				 If sensor is Analogue use multiplier 0.1 for actual reading
				 If sensor is Smoke or Fluid,
				 1 = sensor in alarm condition
				 0 = sensor not in alarm condition"
::= { ss5ComboUniversal04 3 }

ss5ComboUniversal05Type OBJECT-TYPE
	SYNTAX  	INTEGER(0..6)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid"
::= { ss5ComboUniversal05 1 }

ss5ComboUniversal05Name OBJECT-TYPE
	SYNTAX		DisplayString (SIZE (0..42))
	ACCESS		read-only
	STATUS		mandatory
	DESCRIPTION	"Sensor Name of SafetyNet Series 5 Combo"
::= { ss5ComboUniversal05 2 }

ss5ComboUniversal05Reading OBJECT-TYPE
	SYNTAX  	INTEGER(-200..1200)
	ACCESS		read-only
	STATUS		mandatory
	DESCRIPTION	"SafetyNet Series 5 universal sensor five reading.
				 If sensor is Analogue use multiplier 0.1 for actual reading
				 If sensor is Smoke or Fluid,
				 1 = sensor in alarm condition
				 0 = sensor not in alarm condition"
::= { ss5ComboUniversal05 3 }

ss5ComboUniversal06Type OBJECT-TYPE
	SYNTAX  	INTEGER(0..7)
	ACCESS		read-only
	STATUS		mandatory
	DESCRIPTION	"Provides an identification for the sensor/input type
				0 = Temperature
				1 = Humidity
				2 = DC Voltage
				3 = AC Voltage
				4 = Temperature/Humidity Dual (Associated Temperature Sensor)
				5 = Smoke
				6 = Fluid"
::= { ss5ComboUniversal06 1 }

ss5ComboUniversal06Name OBJECT-TYPE
	SYNTAX		DisplayString (SIZE (0..42))
	ACCESS		read-only
	STATUS		mandatory
	DESCRIPTION	"Sensor Name of SafetyNet Series 5 Combo"
::= { ss5ComboUniversal06 2 }

ss5ComboUniversal06Reading OBJECT-TYPE
	SYNTAX  	INTEGER(-200..1200)
	ACCESS		read-only
	STATUS		mandatory
	DESCRIPTION	"SafetyNet Series 5 universal sensor six reading.
				 If sensor is Analogue use multiplier 0.1 for actual reading
				 If sensor is Smoke or Fluid,
				 1 = sensor in alarm condition
				 0 = sensor not in alarm condition"
::= { ss5ComboUniversal06 3 }

ss5ComboDigital01Type OBJECT-TYPE
	SYNTAX  	INTEGER(5..9)
	ACCESS		read-only
	STATUS		mandatory
	DESCRIPTION	"Provides an identification for the sensor/input type
				5 = Smoke
				6 = Fluid
				7 = Digital
				8 = Zoned Security
				9 = Security"
::= { ss5ComboDigital01 1 }

ss5ComboDigital01Name OBJECT-TYPE
	SYNTAX		DisplayString (SIZE (0..42))
	ACCESS		read-only
	STATUS		mandatory
	DESCRIPTION	"Sensor Name of SafetyNet Series 5 Combo"
::= { ss5ComboDigital01 2 }

ss5ComboDigital01Reading OBJECT-TYPE
	SYNTAX  	INTEGER(0..1)
	ACCESS		read-only
	STATUS		mandatory
	DESCRIPTION	"SafetyNet Series 5 Combo digital sensor 01 reading.
				 1 = sensor in alarm condition
				 0 = sensor not in alarm condition"
::= { ss5ComboDigital01 3 }

ss5ComboDigital02Type OBJECT-TYPE
	SYNTAX  	INTEGER(5..9)
	ACCESS		read-only
	STATUS		mandatory
	DESCRIPTION	"Provides an identification for the sensor/input type
				5 = Smoke
				6 = Fluid
				7 = Digital
				8 = Zoned Security
				9 = Security"
::= { ss5ComboDigital02 1 }

ss5ComboDigital02Name OBJECT-TYPE
	SYNTAX		DisplayString (SIZE (0..42))
	ACCESS		read-only
	STATUS		mandatory
	DESCRIPTION	"Sensor Name of SafetyNet Series 5 Combo"
::= { ss5ComboDigital02 2 }

ss5ComboDigital02Reading OBJECT-TYPE
	SYNTAX  	INTEGER(0..1)
	ACCESS		read-only
	STATUS		mandatory
	DESCRIPTION	"SafetyNet Series 5 Combo digital sensor 02 reading.
				 1 = sensor in alarm condition
				 0 = sensor not in alarm condition"
::= { ss5ComboDigital02 3 }

ss5ComboDigital03Type OBJECT-TYPE
	SYNTAX  	INTEGER(5..9)
	ACCESS		read-only
	STATUS		mandatory
	DESCRIPTION	"Provides an identification for the sensor/input type
				5 = Smoke
				6 = Fluid
				7 = Digital
				8 = Zoned Security
				9 = Security"
::= { ss5ComboDigital03 1 }

ss5ComboDigital03Name OBJECT-TYPE
	SYNTAX		DisplayString (SIZE (0..42))
	ACCESS		read-only
	STATUS		mandatory
	DESCRIPTION	"Sensor Name of SafetyNet Series 5 Combo"
::= { ss5ComboDigital03 2 }

ss5ComboDigital03Reading OBJECT-TYPE
	SYNTAX  	INTEGER(0..1)
	ACCESS		read-only
	STATUS		mandatory
	DESCRIPTION	"SafetyNet Series 5 Combo digital sensor 03 reading.
				 1 = sensor in alarm condition
				 0 = sensor not in alarm condition"
::= { ss5ComboDigital03 3 }

ss5ComboDigital04Type OBJECT-TYPE
	SYNTAX  	INTEGER(5..9)
	ACCESS		read-only
	STATUS		mandatory
	DESCRIPTION	"Provides an identification for the sensor/input type
				5 = Smoke
				6 = Fluid
				7 = Digital
				8 = Zoned Security
				9 = Security"
::= { ss5ComboDigital04 1 }

ss5ComboDigital04Name OBJECT-TYPE
	SYNTAX		DisplayString (SIZE (0..42))
	ACCESS		read-only
	STATUS		mandatory
	DESCRIPTION	"Sensor Name of SafetyNet Series 5 Combo"
::= { ss5ComboDigital04 2 }

ss5ComboDigital04Reading OBJECT-TYPE
	SYNTAX  	INTEGER(0..1)
	ACCESS		read-only
	STATUS		mandatory
	DESCRIPTION	"SafetyNet Series 5 Combo digital sensor 04 reading.
				 1 = sensor in alarm condition
				 0 = sensor not in alarm condition"
::= { ss5ComboDigital04 3 }

ss5ComboDigital05Type OBJECT-TYPE
	SYNTAX  	INTEGER(5..9)
	ACCESS		read-only
	STATUS		mandatory
	DESCRIPTION	"Provides an identification for the sensor/input type
				5 = Smoke
				6 = Fluid
				7 = Digital
				8 = Zoned Security
				9 = Security"
::= { ss5ComboDigital05 1 }

ss5ComboDigital05Name OBJECT-TYPE
	SYNTAX		DisplayString (SIZE (0..42))
	ACCESS		read-only
	STATUS		mandatory
	DESCRIPTION	"Sensor Name of SafetyNet Series 5 Combo"
::= { ss5ComboDigital05 2 }

ss5ComboDigital05Reading OBJECT-TYPE
	SYNTAX  	INTEGER(0..1)
	ACCESS		read-only
	STATUS		mandatory
	DESCRIPTION	"SafetyNet Series 5 Combo digital sensor 05 reading.
				 1 = sensor in alarm condition
				 0 = sensor not in alarm condition"
::= { ss5ComboDigital05 3 }

ss5ComboDigital06Type OBJECT-TYPE
	SYNTAX  	INTEGER(5..9)
	ACCESS		read-only
	STATUS		mandatory
	DESCRIPTION	"Provides an identification for the sensor/input type
				5 = Smoke
				6 = Fluid
				7 = Digital
				8 = Zoned Security
				9 = Security"
::= { ss5ComboDigital06 1 }

ss5ComboDigital06Name OBJECT-TYPE
	SYNTAX		DisplayString (SIZE (0..42))
	ACCESS		read-only
	STATUS		mandatory
	DESCRIPTION	"Sensor Name of SafetyNet Series 5 Combo"
::= { ss5ComboDigital06 2 }

ss5ComboDigital06Reading OBJECT-TYPE
	SYNTAX  	INTEGER(0..1)
	ACCESS		read-only
	STATUS		mandatory
	DESCRIPTION	"SafetyNet Series 5 Combo digital sensor 06 reading.
				 1 = sensor in alarm condition
				 0 = sensor not in alarm condition"
::= { ss5ComboDigital06 3 }

ss5ComboDigital07Type OBJECT-TYPE
	SYNTAX  	INTEGER(5..9)
	ACCESS		read-only
	STATUS		mandatory
	DESCRIPTION	"Provides an identification for the sensor/input type
				5 = Smoke
				6 = Fluid
				7 = Digital
				8 = Zoned Security
				9 = Security"
::= { ss5ComboDigital07 1 }

ss5ComboDigital07Name OBJECT-TYPE
	SYNTAX		DisplayString (SIZE (0..42))
	ACCESS		read-only
	STATUS		mandatory
	DESCRIPTION	"Sensor Name of SafetyNet Series 5 Combo"
::= { ss5ComboDigital07 2 }

ss5ComboDigital07Reading OBJECT-TYPE
	SYNTAX  	INTEGER(0..1)
	ACCESS		read-only
	STATUS		mandatory
	DESCRIPTION	"SafetyNet Series 5 Combo digital sensor 07 reading.
				 1 = sensor in alarm condition
				 0 = sensor not in alarm condition"
::= { ss5ComboDigital07 3 }

ss5ComboDigital08Type OBJECT-TYPE
	SYNTAX  	INTEGER(5..9)
	ACCESS		read-only
	STATUS		mandatory
	DESCRIPTION	"Provides an identification for the sensor/input type
				5 = Smoke
				6 = Fluid
				7 = Digital
				8 = Zoned Security
				9 = Security"
::= { ss5ComboDigital08 1 }

ss5ComboDigital08Name OBJECT-TYPE
	SYNTAX		DisplayString (SIZE (0..42))
	ACCESS		read-only
	STATUS		mandatory
	DESCRIPTION	"Sensor Name of SafetyNet Series 5 Combo"
::= { ss5ComboDigital08 2 }

ss5ComboDigital08Reading OBJECT-TYPE
	SYNTAX  	INTEGER(0..1)
	ACCESS		read-only
	STATUS		mandatory
	DESCRIPTION	"SafetyNet Series 5 Combo digital sensor 08 reading.
				 1 = sensor in alarm condition
				 0 = sensor not in alarm condition"
::= { ss5ComboDigital08 3 }

ss5ComboDigital09Type OBJECT-TYPE
	SYNTAX  	INTEGER(5..9)
	ACCESS		read-only
	STATUS		mandatory
	DESCRIPTION	"Provides an identification for the sensor/input type
				5 = Smoke
				6 = Fluid
				7 = Digital
				8 = Zoned Security
				9 = Security"
::= { ss5ComboDigital09 1 }

ss5ComboDigital09Name OBJECT-TYPE
	SYNTAX		DisplayString (SIZE (0..42))
	ACCESS		read-only
	STATUS		mandatory
	DESCRIPTION	"Sensor Name of SafetyNet Series 5 Combo"
::= { ss5ComboDigital09 2 }

ss5ComboDigital09Reading OBJECT-TYPE
	SYNTAX  	INTEGER(0..1)
	ACCESS		read-only
	STATUS		mandatory
	DESCRIPTION	"SafetyNet Series 5 Combo digital sensor 09 reading.
				 1 = sensor in alarm condition
				 0 = sensor not in alarm condition"
::= { ss5ComboDigital09 3 }

ss5ComboDigital10Type OBJECT-TYPE
	SYNTAX  	INTEGER(5..9)
	ACCESS		read-only
	STATUS		mandatory
	DESCRIPTION	"Provides an identification for the sensor/input type
				5 = Smoke
				6 = Fluid
				7 = Digital
				8 = Zoned Security
				9 = Security"
::= { ss5ComboDigital10 1 }

ss5ComboDigital10Name OBJECT-TYPE
	SYNTAX		DisplayString (SIZE (0..42))
	ACCESS		read-only
	STATUS		mandatory
	DESCRIPTION	"Sensor Name of SafetyNet Series 5 Combo"
::= { ss5ComboDigital10 2 }

ss5ComboDigital10Reading OBJECT-TYPE
	SYNTAX  	INTEGER(0..1)
	ACCESS		read-only
	STATUS		mandatory
	DESCRIPTION	"SafetyNet Series 5 Combo digital sensor 10 reading.
				 1 = sensor in alarm condition
				 0 = sensor not in alarm condition"
::= { ss5ComboDigital10 3 }

ss5ComboDigital11Type OBJECT-TYPE
	SYNTAX  	INTEGER(5..9)
	ACCESS		read-only
	STATUS		mandatory
	DESCRIPTION	"Provides an identification for the sensor/input type
				5 = Smoke
				6 = Fluid
				7 = Digital
				8 = Zoned Security
				9 = Security"
::= { ss5ComboDigital11 1 }

ss5ComboDigital11Name OBJECT-TYPE
	SYNTAX		DisplayString (SIZE (0..42))
	ACCESS		read-only
	STATUS		mandatory
	DESCRIPTION	"Sensor Name of SafetyNet Series 5 Combo"
::= { ss5ComboDigital11 2 }

ss5ComboDigital11Reading OBJECT-TYPE
	SYNTAX  	INTEGER(0..1)
	ACCESS		read-only
	STATUS		mandatory
	DESCRIPTION	"SafetyNet Series 5 Combo digital sensor 11 reading.
				 1 = sensor in alarm condition
				 0 = sensor not in alarm condition"
::= { ss5ComboDigital11 3 }

ss5ComboDigital12Type OBJECT-TYPE
	SYNTAX  	INTEGER(5..9)
	ACCESS		read-only
	STATUS		mandatory
	DESCRIPTION	"Provides an identification for the sensor/input type
				5 = Smoke
				6 = Fluid
				7 = Digital
				8 = Zoned Security
				9 = Security"
::= { ss5ComboDigital12 1 }

ss5ComboDigital12Name OBJECT-TYPE
	SYNTAX		DisplayString (SIZE (0..42))
	ACCESS		read-only
	STATUS		mandatory
	DESCRIPTION	"Sensor Name of SafetyNet Series 5 Combo"
::= { ss5ComboDigital12 2 }

ss5ComboDigital12Reading OBJECT-TYPE
	SYNTAX  	INTEGER(0..1)
	ACCESS		read-only
	STATUS		mandatory
	DESCRIPTION	"SafetyNet Series 5 Combo digital sensor 12 reading.
				 1 = sensor in alarm condition
				 0 = sensor not in alarm condition"
::= { ss5ComboDigital12 3 }

ss5ComboDigital13Type OBJECT-TYPE
	SYNTAX  	INTEGER(5..9)
	ACCESS		read-only
	STATUS		mandatory
	DESCRIPTION	"Provides an identification for the sensor/input type
				5 = Smoke
				6 = Fluid
				7 = Digital
				8 = Zoned Security
				9 = Security"
::= { ss5ComboDigital13 1 }

ss5ComboDigital13Name OBJECT-TYPE
	SYNTAX		DisplayString (SIZE (0..42))
	ACCESS		read-only
	STATUS		mandatory
	DESCRIPTION	"Sensor Name of SafetyNet Series 5 Combo"
::= { ss5ComboDigital13 2 }

ss5ComboDigital13Reading OBJECT-TYPE
	SYNTAX  	INTEGER(0..1)
	ACCESS		read-only
	STATUS		mandatory
	DESCRIPTION	"SafetyNet Series 5 Combo digital sensor 13 reading.
				 1 = sensor in alarm condition
				 0 = sensor not in alarm condition"
::= { ss5ComboDigital13 3 }

ss5ComboDigital14Type OBJECT-TYPE
	SYNTAX  	INTEGER(5..9)
	ACCESS		read-only
	STATUS		mandatory
	DESCRIPTION	"Provides an identification for the sensor/input type
				5 = Smoke
				6 = Fluid
				7 = Digital
				8 = Zoned Security
				9 = Security"
::= { ss5ComboDigital14 1 }

ss5ComboDigital14Name OBJECT-TYPE
	SYNTAX		DisplayString (SIZE (0..42))
	ACCESS		read-only
	STATUS		mandatory
	DESCRIPTION	"Sensor Name of SafetyNet Series 5 Combo"
::= { ss5ComboDigital14 2 }

ss5ComboDigital14Reading OBJECT-TYPE
	SYNTAX  	INTEGER(0..1)
	ACCESS		read-only
	STATUS		mandatory
	DESCRIPTION	"SafetyNet Series 5 Combo digital sensor 14 reading.
				 1 = sensor in alarm condition
				 0 = sensor not in alarm condition"
::= { ss5ComboDigital14 3 }

ss5ComboDigital15Type OBJECT-TYPE
	SYNTAX  	INTEGER(5..9)
	ACCESS		read-only
	STATUS		mandatory
	DESCRIPTION	"Provides an identification for the sensor/input type
				5 = Smoke
				6 = Fluid
				7 = Digital
				8 = Zoned Security
				9 = Security"
::= { ss5ComboDigital15 1 }

ss5ComboDigital15Name OBJECT-TYPE
	SYNTAX		DisplayString (SIZE (0..42))
	ACCESS		read-only
	STATUS		mandatory
	DESCRIPTION	"Sensor Name of SafetyNet Series 5 Combo"
::= { ss5ComboDigital15 2 }

ss5ComboDigital15Reading OBJECT-TYPE
	SYNTAX  	INTEGER(0..1)
	ACCESS		read-only
	STATUS		mandatory
	DESCRIPTION	"SafetyNet Series 5 Combo digital sensor 15 reading.
				 1 = sensor in alarm condition
				 0 = sensor not in alarm condition"
::= { ss5ComboDigital15 3 }

ss5ComboDigital16Type OBJECT-TYPE
	SYNTAX  	INTEGER(5..9)
	ACCESS		read-only
	STATUS		mandatory
	DESCRIPTION	"Provides an identification for the sensor/input type
				5 = Smoke
				6 = Fluid
				7 = Digital
				8 = Zoned Security
				9 = Security"
::= { ss5ComboDigital16 1 }

ss5ComboDigital16Name OBJECT-TYPE
	SYNTAX		DisplayString (SIZE (0..42))
	ACCESS		read-only
	STATUS		mandatory
	DESCRIPTION	"Sensor Name of SafetyNet Series 5 Combo"
::= { ss5ComboDigital16 2 }

ss5ComboDigital16Reading OBJECT-TYPE
	SYNTAX  	INTEGER(0..1)
	ACCESS		read-only
	STATUS		mandatory
	DESCRIPTION	"SafetyNet Series 5 Combo digital sensor 16 reading.
				 1 = sensor in alarm condition
				 0 = sensor not in alarm condition"
::= { ss5ComboDigital16 3 }

ss5ComboDigital17Type OBJECT-TYPE
	SYNTAX  	INTEGER(5..9)
	ACCESS		read-only
	STATUS		mandatory
	DESCRIPTION	"Provides an identification for the sensor/input type
				5 = Smoke
				6 = Fluid
				7 = Digital
				8 = Zoned Security
				9 = Security"
::= { ss5ComboDigital17 1 }

ss5ComboDigital17Name OBJECT-TYPE
	SYNTAX		DisplayString (SIZE (0..42))
	ACCESS		read-only
	STATUS		mandatory
	DESCRIPTION	"Sensor Name of SafetyNet Series 5 Combo"
::= { ss5ComboDigital17 2 }

ss5ComboDigital17Reading OBJECT-TYPE
	SYNTAX  	INTEGER(0..1)
	ACCESS		read-only
	STATUS		mandatory
	DESCRIPTION	"SafetyNet Series 5 Combo digital sensor 17 reading.
				 1 = sensor in alarm condition
				 0 = sensor not in alarm condition"
::= { ss5ComboDigital17 3 }

ss5ComboDigital18Type OBJECT-TYPE
	SYNTAX  	INTEGER(5..9)
	ACCESS		read-only
	STATUS		mandatory
	DESCRIPTION	"Provides an identification for the sensor/input type
				5 = Smoke
				6 = Fluid
				7 = Digital
				8 = Zoned Security
				9 = Security"
::= { ss5ComboDigital18 1 }

ss5ComboDigital18Name OBJECT-TYPE
	SYNTAX		DisplayString (SIZE (0..42))
	ACCESS		read-only
	STATUS		mandatory
	DESCRIPTION	"Sensor Name of SafetyNet Series 5 Combo"
::= { ss5ComboDigital18 2 }

ss5ComboDigital18Reading OBJECT-TYPE
	SYNTAX  	INTEGER(0..1)
	ACCESS		read-only
	STATUS		mandatory
	DESCRIPTION	"SafetyNet Series 5 Combo digital sensor 18 reading.
				 1 = sensor in alarm condition
				 0 = sensor not in alarm condition"
::= { ss5ComboDigital18 3 }

ss5ComboDigital19Type OBJECT-TYPE
	SYNTAX  	INTEGER(5..9)
	ACCESS		read-only
	STATUS		mandatory
	DESCRIPTION	"Provides an identification for the sensor/input type
				5 = Smoke
				6 = Fluid
				7 = Digital
				8 = Zoned Security
				9 = Security"
::= { ss5ComboDigital19 1 }

ss5ComboDigital19Name OBJECT-TYPE
	SYNTAX		DisplayString (SIZE (0..42))
	ACCESS		read-only
	STATUS		mandatory
	DESCRIPTION	"Sensor Name of SafetyNet Series 5 Combo"
::= { ss5ComboDigital19 2 }

ss5ComboDigital19Reading OBJECT-TYPE
	SYNTAX  	INTEGER(0..1)
	ACCESS		read-only
	STATUS		mandatory
	DESCRIPTION	"SafetyNet Series 5 Combo digital sensor 19 reading.
				 1 = sensor in alarm condition
				 0 = sensor not in alarm condition"
::= { ss5ComboDigital19 3 }

ss5ComboDigital20Type OBJECT-TYPE
	SYNTAX  	INTEGER(5..9)
	ACCESS		read-only
	STATUS		mandatory
	DESCRIPTION	"Provides an identification for the sensor/input type
				5 = Smoke
				6 = Fluid
				7 = Digital
				8 = Zoned Security
				9 = Security"
::= { ss5ComboDigital20 1 }

ss5ComboDigital20Name OBJECT-TYPE
	SYNTAX		DisplayString (SIZE (0..42))
	ACCESS		read-only
	STATUS		mandatory
	DESCRIPTION	"Sensor Name of SafetyNet Series 5 Combo"
::= { ss5ComboDigital20 2 }

ss5ComboDigital20Reading OBJECT-TYPE
	SYNTAX  	INTEGER(0..1)
	ACCESS		read-only
	STATUS		mandatory
	DESCRIPTION	"SafetyNet Series 5 Combo digital sensor 20 reading.
				 1 = sensor in alarm condition
				 0 = sensor not in alarm condition"
::= { ss5ComboDigital20 3 }


ss5ComboIpMonitoringReading OBJECT-TYPE
	SYNTAX  	INTEGER(0..1)
	ACCESS		read-only
	STATUS		mandatory
	DESCRIPTION	"SafetyNet Series 5 Combo IP Monitoring Alarm.
				 1 = alarm condition
				 0 = not in alarm condition"
::= { ss5ComboReadings 27 }

ss5ComboLowBatteryReading OBJECT-TYPE
	SYNTAX  	INTEGER(0..1)
	ACCESS		read-only
	STATUS		mandatory
	DESCRIPTION	"SafetyNet Series 5 Combo Low Battery.
				 1 = alarm condition
				 0 = not in alarm condition"
::= { ss5ComboReadings 28 }

ss5ComboMainsFailureReading OBJECT-TYPE
	SYNTAX  	INTEGER(0..1)
	ACCESS		read-only
	STATUS		mandatory
	DESCRIPTION	"SafetyNet Series 5 Combo Mains Failure Alarm.
				 1 = alarm condition
				 0 = not in alarm condition"
::= { ss5ComboReadings 29 }

ss5ComboFaultySensorReading OBJECT-TYPE
	SYNTAX  	INTEGER(0..1)
	ACCESS		read-only
	STATUS		mandatory
	DESCRIPTION	"SafetyNet Series 5 Combo Faulty Sensor(s) Alarm.
				 1 = alarm condition
				 0 = not in alarm condition"
::= { ss5ComboReadings 30 }

ss5ComboSIMErrorReading OBJECT-TYPE
	SYNTAX  	INTEGER(0..1)
	ACCESS		read-only
	STATUS		mandatory
	DESCRIPTION	"SafetyNet Series 5 Combo SIM Card Error Alarm.
				 1 = alarm condition
				 0 = not in alarm condition"
::= { ss5ComboReadings 31 }

ss5ComboRelayOne OBJECT-TYPE
	SYNTAX  	INTEGER(0..1)
	ACCESS		read-only
	STATUS		mandatory
	DESCRIPTION	"SafetyNet Series 5 Combo Relay One Status.
				 0 = Relay active
				 1 = Relay inactive"
::= { ss5ComboRelays 1 }
	
ss5ComboRelayTwo OBJECT-TYPE
	SYNTAX  	INTEGER(0..1)
	ACCESS		read-only
	STATUS		mandatory
	DESCRIPTION	"SafetyNet Series 5 Combo Relay Two Status.
				 0 = Relay active
				 1 = Relay inactive"
::= { ss5ComboRelays 2 }


-- OEM product description

sentinel20_outlet1 OBJECT-TYPE
	SYNTAX  	INTEGER(0..3)
	ACCESS		read-only
	STATUS 		mandatory
	DESCRIPTION	"Sentinel Outlet 1 Status
	00 = OUTLET OFF
	01 = OUTLET ON
	02 = OUTLET REBOOTING
	03 = STARTING UP
	"
::= { sentinel20_outletReading 1 } 

sentinel20_outlet2 OBJECT-TYPE
	SYNTAX  	INTEGER(0..3)
	ACCESS		read-only
	STATUS 		mandatory
	DESCRIPTION	"Sentinel Outlet 2 Status
	00 = OUTLET OFF
	01 = OUTLET ON
	02 = OUTLET REBOOTING
	03 = STARTING UP
	"
::= { sentinel20_outletReading 2 } 

sentinel20_outlet3 OBJECT-TYPE
	SYNTAX  	INTEGER(0..3)
	ACCESS		read-only
	STATUS 		mandatory
	DESCRIPTION	"Sentinel Outlet 3 Status
	00 = OUTLET OFF
	01 = OUTLET ON
	02 = OUTLET REBOOTING
	03 = STARTING UP
	"
::= { sentinel20_outletReading 3 }

sentinel20_outlet4 OBJECT-TYPE
	SYNTAX  	INTEGER(0..3)
	ACCESS		read-only
	STATUS 		mandatory
	DESCRIPTION	"Sentinel Outlet 4 Status
	00 = OUTLET OFF
	01 = OUTLET ON
	02 = OUTLET REBOOTING
	03 = STARTING UP
	"
::= { sentinel20_outletReading 4 } 

sentinel20_outlet5 OBJECT-TYPE
	SYNTAX  	INTEGER(0..3)
	ACCESS		read-only
	STATUS 		mandatory
	DESCRIPTION	"Sentinel Outlet 5 Status
	00 = OUTLET OFF
	01 = OUTLET ON
	02 = OUTLET REBOOTING
	03 = STARTING UP
	"
::= { sentinel20_outletReading 5 }

sentinel20_outlet6 OBJECT-TYPE
	SYNTAX  	INTEGER(0..3)
	ACCESS		read-only
	STATUS 		mandatory
	DESCRIPTION	"Sentinel Outlet 6 Status
	00 = OUTLET OFF
	01 = OUTLET ON
	02 = OUTLET REBOOTING
	03 = STARTING UP
	"
::= { sentinel20_outletReading 6 } 


sentinel20_outlet7 OBJECT-TYPE
	SYNTAX  	INTEGER(0..3)
	ACCESS		read-only
	STATUS 		mandatory
	DESCRIPTION	"Sentinel Outlet 7 Status
	00 = OUTLET OFF
	01 = OUTLET ON
	02 = OUTLET REBOOTING
	03 = STARTING UP
	"
::= { sentinel20_outletReading 7 } 

 
sentinel20_outlet8 OBJECT-TYPE
	SYNTAX  	INTEGER(0..3)
	ACCESS		read-only
	STATUS 		mandatory
	DESCRIPTION	"Sentinel Outlet 8 Status
	00 = OUTLET OFF
	01 = OUTLET ON
	02 = OUTLET REBOOTING
	03 = STARTING UP
	"
::= { sentinel20_outletReading 8 } 


sentinel20_outlet9 OBJECT-TYPE
	SYNTAX  	INTEGER(0..3)
	ACCESS		read-only
	STATUS 		mandatory
	DESCRIPTION	"Sentinel Outlet 9 Status
	00 = OUTLET OFF
	01 = OUTLET ON
	02 = OUTLET REBOOTING
	03 = STARTING UP
	"
::= { sentinel20_outletReading 9 } 

sentinel20_outlet10 OBJECT-TYPE
	SYNTAX  	INTEGER(0..3)
	ACCESS		read-only
	STATUS 		mandatory
	DESCRIPTION	"Sentinel Outlet 10 Status
	00 = OUTLET OFF
	01 = OUTLET ON
	02 = OUTLET REBOOTING
	03 = STARTING UP
	"
::= { sentinel20_outletReading 10 } 


sentinel20_outlet11 OBJECT-TYPE
	SYNTAX  	INTEGER(0..3)
	ACCESS		read-only
	STATUS 		mandatory
	DESCRIPTION	"Sentinel Outlet 11 Status
	00 = OUTLET OFF
	01 = OUTLET ON
	02 = OUTLET REBOOTING
	03 = STARTING UP
	"
::= { sentinel20_outletReading 11 } 


sentinel20_outlet12 OBJECT-TYPE
	SYNTAX  	INTEGER(0..3)
	ACCESS		read-only
	STATUS 		mandatory
	DESCRIPTION	"Sentinel Outlet 12 Status
	00 = OUTLET OFF
	01 = OUTLET ON
	02 = OUTLET REBOOTING
	03 = STARTING UP
	"
::= { sentinel20_outletReading 12 } 


sentinel20_outlet13 OBJECT-TYPE
	SYNTAX  	INTEGER(0..3)
	ACCESS		read-only
	STATUS 		mandatory
	DESCRIPTION	"Sentinel Outlet 13 Status
	00 = OUTLET OFF
	01 = OUTLET ON
	02 = OUTLET REBOOTING
	03 = STARTING UP
	"
::= { sentinel20_outletReading 13 } 
 

sentinel20_outlet14 OBJECT-TYPE
	SYNTAX  	INTEGER(0..3)
	ACCESS		read-only
	STATUS 		mandatory
	DESCRIPTION	"Sentinel Outlet 14 Status
	00 = OUTLET OFF
	01 = OUTLET ON
	02 = OUTLET REBOOTING
	03 = STARTING UP
	"
::= { sentinel20_outletReading 14 } 


sentinel20_outlet15 OBJECT-TYPE
	SYNTAX  	INTEGER(0..3)
	ACCESS		read-only
	STATUS 		mandatory
	DESCRIPTION	"Sentinel Outlet 15 Status
	00 = OUTLET OFF
	01 = OUTLET ON
	02 = OUTLET REBOOTING
	03 = STARTING UP
	"
::= { sentinel20_outletReading 15 } 

sentinel20_outlet16 OBJECT-TYPE
	SYNTAX  	INTEGER(0..3)
	ACCESS		read-only
	STATUS 		mandatory
	DESCRIPTION	"Sentinel Outlet 16 Status
	00 = OUTLET OFF
	01 = OUTLET ON
	02 = OUTLET REBOOTING
	03 = STARTING UP
	"
::= { sentinel20_outletReading 16 } 

sentinel20_outlet17 OBJECT-TYPE
	SYNTAX  	INTEGER(0..3)
	ACCESS		read-only
	STATUS 		mandatory
	DESCRIPTION	"Sentinel Outlet 17 Status
	00 = OUTLET OFF
	01 = OUTLET ON
	02 = OUTLET REBOOTING
	03 = STARTING UP
	"
::= { sentinel20_outletReading 17 } 


sentinel20_outlet18 OBJECT-TYPE
	SYNTAX  	INTEGER(0..3)
	ACCESS		read-only
	STATUS 		mandatory
	DESCRIPTION	"Sentinel Outlet 18 Status
	00 = OUTLET OFF
	01 = OUTLET ON
	02 = OUTLET REBOOTING
	03 = STARTING UP
	"
::= { sentinel20_outletReading 18 } 

sentinel20_outlet19 OBJECT-TYPE
	SYNTAX  	INTEGER(0..3)
	ACCESS		read-only
	STATUS 		mandatory
	DESCRIPTION	"Sentinel Outlet 19 Status
	00 = OUTLET OFF
	01 = OUTLET ON
	02 = OUTLET REBOOTING
	03 = STARTING UP
	"
::= { sentinel20_outletReading 19 }


sentinel20_outlet20 OBJECT-TYPE
	SYNTAX  	INTEGER(0..3)
	ACCESS		read-only
	STATUS 		mandatory
	DESCRIPTION	"Sentinel Outlet 20 Status
	00 = OUTLET OFF
	01 = OUTLET ON
	02 = OUTLET REBOOTING
	03 = STARTING UP
	"
::= { sentinel20_outletReading 20 }  

-- sentinel20_sensorReading tree
sentinel20_currentConsumption	OBJECT IDENTIFIER ::= { sentinel20_sensorReading  1 }  
sentinel20_temperature			OBJECT IDENTIFIER ::= { sentinel20_sensorReading  2 }  
sentinel20_humidity				OBJECT IDENTIFIER ::= { sentinel20_sensorReading  3 }  
sentinel20_digital_1			OBJECT IDENTIFIER ::= { sentinel20_sensorReading  4 }  
sentinel20_digital_2			OBJECT IDENTIFIER ::= { sentinel20_sensorReading  5 }  


sentinel20_currentConsumption_Reading OBJECT-TYPE
	SYNTAX		INTEGER(0..40000)
	ACCESS		read-only
	STATUS		mandatory
	DESCRIPTION	"Total current consumption - Sentinel 20
	This value is in milli amperes. To convert to Amperes, multiply by 1000"
::= { sentinel20_currentConsumption 1 }


sentinel20_currentConsumption_Status OBJECT-TYPE
	SYNTAX  	INTEGER(0..4)
	ACCESS		read-only
	STATUS		mandatory
	DESCRIPTION	"Alarm for Current Load Sensor
	0 = level OK
	1 = level at warning level
	2 = level at alarm level
	3 = level at critical level"
::= { sentinel20_currentConsumption 2 }

sentinel20_temperature_Name OBJECT-TYPE
	SYNTAX		DisplayString (SIZE (0..42))
	ACCESS		read-only
	STATUS		mandatory
	DESCRIPTION	"Temperature Sensor Name - Sentinel 20"
::= { sentinel20_temperature 1 }

sentinel20_temperature_Reading OBJECT-TYPE
	SYNTAX  	INTEGER(-20..120)
	ACCESS		read-only
	STATUS		mandatory
	DESCRIPTION	"Temperature Sensor Reading - Sentinel 20
	Use multiplier 0.1 for actual reading"
::= { sentinel20_temperature 2 }

sentinel20_temperature_Status OBJECT-TYPE
	SYNTAX  	INTEGER(0..6)
	ACCESS		read-only
	STATUS		mandatory
	DESCRIPTION	"Alarm for Temperature Sensor
0 = level OK
1 = level at high warning level
2 = level at high alarm level
3 = level at high shutdown level
4 = level at low warning level
5 = level at low alarm level
6 = level at low shutdown level"
::= { sentinel20_temperature 3 }


sentinel20_humidity_Name OBJECT-TYPE
	SYNTAX		DisplayString (SIZE (0..42))
	ACCESS		read-only
	STATUS		mandatory
	DESCRIPTION	"Humidity Sensor Name - Sentinel 20"
::= { sentinel20_humidity 1 }

sentinel20_humidity_Reading OBJECT-TYPE
	SYNTAX  	INTEGER(-20..120)
	ACCESS		read-only
	STATUS		mandatory
	DESCRIPTION	"Humidity Sensor Reading - Sentinel 20
	Use multiplier 0.1 for actual reading"
::= { sentinel20_humidity 2 }

sentinel20_humidity_Status OBJECT-TYPE
	SYNTAX  	INTEGER(0..6)
	ACCESS		read-only
	STATUS		mandatory
	DESCRIPTION	"Alarm for Humidity Sensor
0 = level OK
1 = level at high warning level
2 = level at high alarm level
3 = level at high shutdown level
4 = level at low warning level
5 = level at low alarm level
6 = level at low shutdown level"
::= { sentinel20_humidity 3 }

sentinel20_digital_1_Name OBJECT-TYPE
	SYNTAX		DisplayString (SIZE (0..42))
	ACCESS		read-only
	STATUS		mandatory
	DESCRIPTION	"Digital Sensor One Name - Sentinel 20"
::= { sentinel20_digital_1 1 }

sentinel20_digital_1_Reading OBJECT-TYPE
	SYNTAX  	INTEGER(0..1)
	ACCESS		read-only
	STATUS		mandatory
	DESCRIPTION	"Digital Sensor One Reading - Sentinel 20
	1 = sensor in alarm condition
	0 = sensor not in alarm condition"
::= { sentinel20_digital_1 2 }


sentinel20_digital_2_Name OBJECT-TYPE
	SYNTAX		DisplayString (SIZE (0..42))
	ACCESS		read-only
	STATUS		mandatory
	DESCRIPTION	"Digital Sensor Two Name - Sentinel 20"
::= { sentinel20_digital_2 1 }

sentinel20_digital_2_Reading OBJECT-TYPE
	SYNTAX  	INTEGER(0..1)
	ACCESS		read-only
	STATUS		mandatory
	DESCRIPTION	"Digital Sensor Two Reading - Sentinel 20
	1 = sensor in alarm condition
	0 = sensor not in alarm condition"
::= { sentinel20_digital_2 2 }

-- Sentinet 10 OIDs


sentinel10_outlet1 OBJECT-TYPE
	SYNTAX  	INTEGER(0..3)
	ACCESS		read-only
	STATUS 		mandatory
	DESCRIPTION	"Sentinel Outlet 1 Status
	00 = OUTLET OFF
	01 = OUTLET ON
	02 = OUTLET REBOOTING
	03 = STARTING UP
	"
::= { sentinel10_outletReading 1 } 

sentinel10_outlet2 OBJECT-TYPE
	SYNTAX  	INTEGER(0..3)
	ACCESS		read-only
	STATUS 		mandatory
	DESCRIPTION	"Sentinel Outlet 2 Status
	00 = OUTLET OFF
	01 = OUTLET ON
	02 = OUTLET REBOOTING
	03 = STARTING UP
	"
::= { sentinel10_outletReading 2 } 

sentinel10_outlet3 OBJECT-TYPE
	SYNTAX  	INTEGER(0..3)
	ACCESS		read-only
	STATUS 		mandatory
	DESCRIPTION	"Sentinel Outlet 3 Status
	00 = OUTLET OFF
	01 = OUTLET ON
	02 = OUTLET REBOOTING
	03 = STARTING UP
	"
::= { sentinel10_outletReading 3 }

sentinel10_outlet4 OBJECT-TYPE
	SYNTAX  	INTEGER(0..3)
	ACCESS		read-only
	STATUS 		mandatory
	DESCRIPTION	"Sentinel Outlet 4 Status
	00 = OUTLET OFF
	01 = OUTLET ON
	02 = OUTLET REBOOTING
	03 = STARTING UP
	"
::= { sentinel10_outletReading 4 } 

sentinel10_outlet5 OBJECT-TYPE
	SYNTAX  	INTEGER(0..3)
	ACCESS		read-only
	STATUS 		mandatory
	DESCRIPTION	"Sentinel Outlet 5 Status
	00 = OUTLET OFF
	01 = OUTLET ON
	02 = OUTLET REBOOTING
	03 = STARTING UP
	"
::= { sentinel10_outletReading 5 }

sentinel10_outlet6 OBJECT-TYPE
	SYNTAX  	INTEGER(0..3)
	ACCESS		read-only
	STATUS 		mandatory
	DESCRIPTION	"Sentinel Outlet 6 Status
	00 = OUTLET OFF
	01 = OUTLET ON
	02 = OUTLET REBOOTING
	03 = STARTING UP
	"
::= { sentinel10_outletReading 6 } 


sentinel10_outlet7 OBJECT-TYPE
	SYNTAX  	INTEGER(0..3)
	ACCESS		read-only
	STATUS 		mandatory
	DESCRIPTION	"Sentinel Outlet 7 Status
	00 = OUTLET OFF
	01 = OUTLET ON
	02 = OUTLET REBOOTING
	03 = STARTING UP
	"
::= { sentinel10_outletReading 7 } 

 
sentinel10_outlet8 OBJECT-TYPE
	SYNTAX  	INTEGER(0..3)
	ACCESS		read-only
	STATUS 		mandatory
	DESCRIPTION	"Sentinel Outlet 8 Status
	00 = OUTLET OFF
	01 = OUTLET ON
	02 = OUTLET REBOOTING
	03 = STARTING UP
	"
::= { sentinel10_outletReading 8 } 


sentinel10_outlet9 OBJECT-TYPE
	SYNTAX  	INTEGER(0..3)
	ACCESS		read-only
	STATUS 		mandatory
	DESCRIPTION	"Sentinel Outlet 9 Status
	00 = OUTLET OFF
	01 = OUTLET ON
	02 = OUTLET REBOOTING
	03 = STARTING UP
	"
::= { sentinel10_outletReading 9 } 

sentinel10_outlet10 OBJECT-TYPE
	SYNTAX  	INTEGER(0..3)
	ACCESS		read-only
	STATUS 		mandatory
	DESCRIPTION	"Sentinel Outlet 10 Status
	00 = OUTLET OFF
	01 = OUTLET ON
	02 = OUTLET REBOOTING
	03 = STARTING UP
	"
::= { sentinel10_outletReading 10 } 

-- sentinel10_sensorReading tree
sentinel10_currentConsumption	OBJECT IDENTIFIER ::= { sentinel10_sensorReading  1 }  
sentinel10_temperature			OBJECT IDENTIFIER ::= { sentinel10_sensorReading  2 }  
sentinel10_humidity				OBJECT IDENTIFIER ::= { sentinel10_sensorReading  3 }  
sentinel10_digital_1			OBJECT IDENTIFIER ::= { sentinel10_sensorReading  4 }  
sentinel10_digital_2			OBJECT IDENTIFIER ::= { sentinel10_sensorReading  5 }  


sentinel10_currentConsumption_Reading OBJECT-TYPE
	SYNTAX		INTEGER(0..40000)
	ACCESS		read-only
	STATUS		mandatory
	DESCRIPTION	"Total current consumption - Sentinel 20
	This value is in milli amperes. To convert to Amperes, multiply by 1000"
::= { sentinel10_currentConsumption 1 }


sentinel10_currentConsumption_Status OBJECT-TYPE
	SYNTAX  	INTEGER(0..4)
	ACCESS		read-only
	STATUS		mandatory
	DESCRIPTION	"Alarm for Current Load Sensor
	0 = level OK
	1 = level at warning level
	2 = level at alarm level
	3 = level at critical level"
::= { sentinel10_currentConsumption 2 }

sentinel10_temperature_Name OBJECT-TYPE
	SYNTAX		DisplayString (SIZE (0..42))
	ACCESS		read-only
	STATUS		mandatory
	DESCRIPTION	"Temperature Sensor Name - Sentinel 20"
::= { sentinel10_temperature 1 }

sentinel10_temperature_Reading OBJECT-TYPE
	SYNTAX  	INTEGER(-20..120)
	ACCESS		read-only
	STATUS		mandatory
	DESCRIPTION	"Temperature Sensor Reading - Sentinel 20
	Use multiplier 0.1 for actual reading"
::= { sentinel10_temperature 2 }

sentinel10_temperature_Status OBJECT-TYPE
	SYNTAX  	INTEGER(0..6)
	ACCESS		read-only
	STATUS		mandatory
	DESCRIPTION	"Alarm for Temperature Sensor
0 = level OK
1 = level at high warning level
2 = level at high alarm level
3 = level at high shutdown level
4 = level at low warning level
5 = level at low alarm level
6 = level at low shutdown level"
::= { sentinel10_temperature 3 }


sentinel10_humidity_Name OBJECT-TYPE
	SYNTAX		DisplayString (SIZE (0..42))
	ACCESS		read-only
	STATUS		mandatory
	DESCRIPTION	"Humidity Sensor Name - Sentinel 20"
::= { sentinel10_humidity 1 }

sentinel10_humidity_Reading OBJECT-TYPE
	SYNTAX  	INTEGER(-20..120)
	ACCESS		read-only
	STATUS		mandatory
	DESCRIPTION	"Humidity Sensor Reading - Sentinel 20
	Use multiplier 0.1 for actual reading"
::= { sentinel10_humidity 2 }

sentinel10_humidity_Status OBJECT-TYPE
	SYNTAX  	INTEGER(0..6)
	ACCESS		read-only
	STATUS		mandatory
	DESCRIPTION	"Alarm for Humidity Sensor
0 = level OK
1 = level at high warning level
2 = level at high alarm level
3 = level at high shutdown level
4 = level at low warning level
5 = level at low alarm level
6 = level at low shutdown level"
::= { sentinel10_humidity 3 }

sentinel10_digital_1_Name OBJECT-TYPE
	SYNTAX		DisplayString (SIZE (0..42))
	ACCESS		read-only
	STATUS		mandatory
	DESCRIPTION	"Digital Sensor One Name - Sentinel 20"
::= { sentinel10_digital_1 1 }

sentinel10_digital_1_Reading OBJECT-TYPE
	SYNTAX  	INTEGER(0..1)
	ACCESS		read-only
	STATUS		mandatory
	DESCRIPTION	"Digital Sensor One Reading - Sentinel 20
	1 = sensor in alarm condition
	0 = sensor not in alarm condition"
::= { sentinel10_digital_1 2 }


sentinel10_digital_2_Name OBJECT-TYPE
	SYNTAX		DisplayString (SIZE (0..42))
	ACCESS		read-only
	STATUS		mandatory
	DESCRIPTION	"Digital Sensor Two Name - Sentinel 20"
::= { sentinel10_digital_2 1 }

sentinel10_digital_2_Reading OBJECT-TYPE
	SYNTAX  	INTEGER(0..1)
	ACCESS		read-only
	STATUS		mandatory
	DESCRIPTION	"Digital Sensor Two Reading - Sentinel 20
	1 = sensor in alarm condition
	0 = sensor not in alarm condition"
::= { sentinel10_digital_2 2 }



-- Trap Control Tree defined here

trapDescr OBJECT-TYPE
	SYNTAX		DisplayString (SIZE (0..80))
	ACCESS		read-only
	STATUS		mandatory
	DESCRIPTION	"Textual message giving more detailed information on alarms/alerts/notifications on SNMP agent"
::= { trapControl 2 }
                       
sensorID OBJECT-TYPE
	SYNTAX  	INTEGER(0..26)
	ACCESS		read-only
	STATUS		mandatory
	DESCRIPTION	"Provides an identification for the sensor/input in alarm or alarm clearance
				0 = first sensor	
				1 = second sensor
				...
				n = sensor n+1
				
				For product safetynetseries5Combo: 
					0 to 5 = Universal Sensors 1 to 6
					6 to 25 = Digital Sensors 1 to 20
				"
	::= { trapControl 3 }
	
sensorValue OBJECT-TYPE
	SYNTAX  	INTEGER(-200..1200)
	ACCESS		read-only
	STATUS		mandatory
	DESCRIPTION	"Sensor reading for analogue type sensors
	
				(use multiplier 0.1 for actual reading)"
::= { trapControl 4 }

currentConsumption OBJECT-TYPE
	SYNTAX  	INTEGER(0..40000)
	ACCESS		read-only
	STATUS		mandatory
	DESCRIPTION	"Current Consumption Sensor reading.
	Value is in milli-Amperes. For value in Amperes, multiply by 1000"
::= { trapControl 5 }

outletID OBJECT-TYPE
	SYNTAX  	INTEGER(0..20)
	ACCESS		read-only
	STATUS		mandatory
	DESCRIPTION	"Provides an identification for outlet, where an event occurred.
				0 = first outlet	
				1 = second outlet
				...
				n = outlet n+1
				"
	::= { trapControl 6 }

outletName OBJECT-TYPE
	SYNTAX		DisplayString (SIZE (0..33))
	ACCESS		read-only
	STATUS		mandatory
	DESCRIPTION	"Outlet name where event occurred"
	::= { trapControl 7 }	


-- ****************************************************************************
-- ****************************************************************************
--
-- Traps from trapControl:
--
clearTemperatureSensor TRAP-TYPE
    ENTERPRISE trapControl
    VARIABLES   { trapSource, trapDescr, sensorID, sensorValue }
    DESCRIPTION
    "Trap origin is from trapSource.
	Temperature sensor sensorID alarm is cleared.
	Sensor reading is sensorValue.		
	"
    ::= 20
	
warningHighTemperatureSensor TRAP-TYPE
    ENTERPRISE trapControl
    VARIABLES   { trapSource, trapDescr, sensorID, sensorValue }
    DESCRIPTION
    "Trap origin is from trapSource.
	Temperature sensor sensorID has triggered a high warning.
	Sensor reading is sensorValue"
    ::= 21
	
warningLowTemperatureSensor TRAP-TYPE
    ENTERPRISE trapControl
    VARIABLES   { trapSource, trapDescr, sensorID, sensorValue }
    DESCRIPTION
    "Trap origin is from trapSource.
	Temperature sensor sensorID has triggered a low warning.
	Sensor reading is sensorValue"
    ::= 22

alarmHighTemperatureSensor TRAP-TYPE
    ENTERPRISE trapControl
    VARIABLES   { trapSource, trapDescr, sensorID, sensorValue}
    DESCRIPTION
    "Trap origin is from trapSource.
	Temperature sensor sensorID has triggered a high alarm.
	Sensor reading is sensorValue"
    ::= 23	

alarmLowTemperatureSensor TRAP-TYPE
    ENTERPRISE trapControl
    VARIABLES   { trapSource, trapDescr, sensorID, sensorValue }
    DESCRIPTION
    "Trap origin is from trapSource.
	Temperature sensor sensorID has triggered a low alarm.
	Sensor reading is sensorValue"
    ::= 24
	
clearHumiditySensor TRAP-TYPE
    ENTERPRISE trapControl
    VARIABLES   { trapSource, trapDescr, sensorID, sensorValue }
    DESCRIPTION
    "Trap origin is from trapSource.
	Humidity sensor sensorID alarm is cleared.
	Sensor reading is sensorValue"
    ::= 25
	
warningHighHumiditySensor TRAP-TYPE
    ENTERPRISE trapControl
    VARIABLES   { trapSource, trapDescr, sensorID, sensorValue }
    DESCRIPTION
    "Trap origin is from trapSource.
	Humidity sensor sensorID has triggered a high warning.
	Sensor reading is sensorValue"
    ::= 26
	
warningLowHumiditySensor TRAP-TYPE
    ENTERPRISE trapControl
    VARIABLES   { trapSource, trapDescr, sensorID, sensorValue }
    DESCRIPTION
    "Trap origin is from trapSource.
	Humidity sensor sensorID has triggered a low warning.
	Sensor reading is sensorValue"
    ::= 27

alarmHighHumiditySensor TRAP-TYPE
    ENTERPRISE trapControl
    VARIABLES   { trapSource, trapDescr, sensorID, sensorValue}
    DESCRIPTION
    "Trap origin is from trapSource.
	Humidity sensor sensorID has triggered a high alarm.
	Sensor reading is sensorValue"
    ::= 28	

alarmLowHumiditySensor TRAP-TYPE
    ENTERPRISE trapControl
    VARIABLES   { trapSource, trapDescr, sensorID, sensorValue }
    DESCRIPTION
    "Humidity sensor sensorID has triggered a low alarm.
	Sensor reading is sensorValue"
    ::= 29

clearDCVoltageSensor TRAP-TYPE
    ENTERPRISE trapControl
    VARIABLES   { trapSource, trapDescr, sensorID, sensorValue }
    DESCRIPTION
    "Trap origin is from trapSource.
	DC Voltage sensor sensorID alarm is cleared.
	Sensor reading is sensorValue"
    ::= 30
	
warningHighDCVoltageSensor TRAP-TYPE
    ENTERPRISE trapControl
    VARIABLES   { trapSource, trapDescr, sensorID, sensorValue }
    DESCRIPTION
    "Trap origin is from trapSource.
	DC Voltage sensor sensorID has triggered a high warning.
	Sensor reading is sensorValue"
    ::= 31
	
warningLowDCVoltageSensor TRAP-TYPE
    ENTERPRISE trapControl
    VARIABLES   { trapSource, trapDescr, sensorID, sensorValue }
    DESCRIPTION
    "Trap origin is from trapSource.
	DC Voltage sensor sensorID has triggered a low warning.
	Sensor reading is sensorValue"
    ::= 32

alarmHighDCVoltageSensor TRAP-TYPE
    ENTERPRISE trapControl
    VARIABLES   { trapSource, trapDescr, sensorID, sensorValue}
    DESCRIPTION
    "Trap origin is from trapSource.
	DC Voltage sensor sensorID has triggered a high alarm.
	Sensor reading is sensorValue"
    ::= 33	

alarmLowDCVoltageSensor TRAP-TYPE
    ENTERPRISE trapControl
    VARIABLES   { trapSource, trapDescr, sensorID, sensorValue }
    DESCRIPTION
    "Trap origin is from trapSource.
	DC Voltage sensor sensorID has triggered a low alarm.
	Sensor reading is sensorValue"
    ::= 34

alarmSmokeSensor TRAP-TYPE
    ENTERPRISE trapControl
    VARIABLES   { trapSource, trapDescr, sensorID }
    DESCRIPTION
    "Trap origin is from trapSource.
	Smoke sensor sensorID has triggered an alarm"
    ::= 35

clearSmokeSensor TRAP-TYPE
    ENTERPRISE trapControl
    VARIABLES   { trapSource, trapDescr, sensorID }
    DESCRIPTION
    "Trap origin is from trapSource.
	Smoke sensor sensorID has cleared an alarm"
    ::= 36

alarmFluidSensor TRAP-TYPE
    ENTERPRISE trapControl
    VARIABLES   { trapSource, trapDescr, sensorID }
    DESCRIPTION
    "Trap origin is from trapSource.
	Fluid sensor sensorID has triggered an alarm"
    ::= 37

clearFluidSensor TRAP-TYPE
    ENTERPRISE trapControl
    VARIABLES   { trapSource, trapDescr, sensorID }
    DESCRIPTION
    "Trap origin is from trapSource.
	Fluid sensor sensorID has cleared an alarm"
    ::= 38

alarmDigitalSensor TRAP-TYPE
    ENTERPRISE trapControl
    VARIABLES   { trapSource, trapDescr, sensorID }
    DESCRIPTION
    "Digital sensor sensorID has triggered an alarm"
    ::= 39

clearDigitalSensor TRAP-TYPE
    ENTERPRISE trapControl
    VARIABLES   { trapSource, trapDescr, sensorID }
    DESCRIPTION
    "Trap origin is from trapSource.
	Digital sensor sensorID has cleared an alarm"
    ::= 40	

alarmZonedSecuritySensor TRAP-TYPE
    ENTERPRISE trapControl
    VARIABLES   { trapSource, trapDescr, sensorID }
    DESCRIPTION
    "Trap origin is from trapSource.
	Zoned Security sensor sensorID has triggered an alarm"
    ::= 41

clearZonedSecuritySensor TRAP-TYPE
    ENTERPRISE trapControl
    VARIABLES   { trapSource, trapDescr, sensorID }
    DESCRIPTION
    "Trap origin is from trapSource.
	Zoned Security sensor sensorID has cleared an alarm"
    ::= 42

alarmSecuritySensor TRAP-TYPE
    ENTERPRISE trapControl
    VARIABLES   { trapSource, trapDescr, sensorID }
    DESCRIPTION
    "Trap origin is from trapSource.
	Security sensor sensorID has triggered an alarm"
    ::= 43

clearSecuritySensor TRAP-TYPE
    ENTERPRISE trapControl
    VARIABLES   { trapSource, trapDescr, sensorID }
    DESCRIPTION
    "Trap origin is from trapSource.
	Security sensor sensorID has cleared an alarm"
    ::= 44	
	
alarmIPMonitoring TRAP-TYPE
    ENTERPRISE trapControl
    VARIABLES   { trapSource, trapDescr }
    DESCRIPTION
    "Trap origin is from trapSource.
	IP monitoring alarm has been triggered"
    ::= 45

clearIPMonitoring TRAP-TYPE
    ENTERPRISE trapControl
    VARIABLES   { trapSource, trapDescr }
    DESCRIPTION
    "Trap origin is from trapSource.
	IP monitoring alarm has been cleared"
    ::= 46

alarmLowBattery TRAP-TYPE
    ENTERPRISE trapControl
    VARIABLES   { trapSource, trapDescr }
    DESCRIPTION
    "Trap origin is from trapSource.
	Low battery alarm has been triggered"
    ::= 47

clearLowBattery TRAP-TYPE
    ENTERPRISE trapControl
    VARIABLES   { trapSource, trapDescr }
    DESCRIPTION
    "Trap origin is from trapSource.
	Low battery alarm has been cleared"
    ::= 48

alarmMainsFailure TRAP-TYPE
    ENTERPRISE trapControl
    VARIABLES   { trapSource, trapDescr }
    DESCRIPTION
    "Trap origin is from trapSource.
	Mains failure alarm has been triggered"
    ::= 49

clearMainsFailure TRAP-TYPE
    ENTERPRISE trapControl
    VARIABLES   { trapSource, trapDescr }
    DESCRIPTION
    "Trap origin is from trapSource.
	Mains failure alarm has been cleared"
    ::= 50	

alarmDialTone TRAP-TYPE
    ENTERPRISE trapControl
    VARIABLES   { trapSource, trapDescr }
    DESCRIPTION
    "Trap origin is from trapSource.
	Dial tone failure alarm has been triggered"
    ::= 51

clearDialTone TRAP-TYPE
    ENTERPRISE trapControl
    VARIABLES   { trapSource, trapDescr }
    DESCRIPTION
    "Trap origin is from trapSource.
	Dial tone has been restored. Alarm has been cleared"
    ::= 52

alarmFaultyAnalogueSensor TRAP-TYPE
    ENTERPRISE trapControl
    VARIABLES   { trapSource, trapDescr }
    DESCRIPTION
    "Trap origin is from trapSource.
	Faulty analogue sensor alarm has been triggered"
    ::= 53

clearFaultyAnalogueSensor TRAP-TYPE
    ENTERPRISE trapControl
    VARIABLES   { trapSource, trapDescr }
    DESCRIPTION
    "Trap origin is from trapSource.
	Faulty analogue sensor alarm has been cleared"
    ::= 54	

alarmModemInitialisationError TRAP-TYPE
    ENTERPRISE trapControl
    VARIABLES   { trapSource, trapDescr }
    DESCRIPTION
    "Trap origin is from trapSource.
	Modem initialisation caused an error"
    ::= 55
alarmSimCardError TRAP-TYPE
    ENTERPRISE trapControl
    VARIABLES   { trapSource, trapDescr }
    DESCRIPTION
    "Trap origin is from trapSource.
	SIM card caused an error"
    ::= 56	

clearSimCardError TRAP-TYPE
    ENTERPRISE trapControl
    VARIABLES   { trapSource, trapDescr }
    DESCRIPTION
    "Trap origin is from trapSource.
	SIM card error cleared"
    ::= 57	
	
clearEthernetConnection TRAP-TYPE
    ENTERPRISE trapControl
    VARIABLES   { trapSource, trapDescr }
    DESCRIPTION
    "Trap origin is from trapSource.
	Ethernet Connection error is cleared"
    ::= 58
	
clearACVoltageSensor TRAP-TYPE
    ENTERPRISE trapControl
    VARIABLES   { trapSource, trapDescr, sensorID, sensorValue }
    DESCRIPTION
    "Trap origin is from trapSource.
	AC Voltage sensor sensorID alarm is cleared.
	Sensor reading is sensorValue"
    ::= 59
	
warningHighACVoltageSensor TRAP-TYPE
    ENTERPRISE trapControl
    VARIABLES   { trapSource, trapDescr, sensorID, sensorValue }
    DESCRIPTION
    "Trap origin is from trapSource.
	AC Voltage sensor sensorID has triggered a high warning.
	Sensor reading is sensorValue"
    ::= 60
	
warningLowACVoltageSensor TRAP-TYPE
    ENTERPRISE trapControl
    VARIABLES   { trapSource, trapDescr, sensorID, sensorValue }
    DESCRIPTION
    "Trap origin is from trapSource.
	AC Voltage sensor sensorID has triggered a low warning.
	Sensor reading is sensorValue"
    ::= 61

alarmHighACVoltageSensor TRAP-TYPE
    ENTERPRISE trapControl
    VARIABLES   { trapSource, trapDescr, sensorID, sensorValue}
    DESCRIPTION
    "Trap origin is from trapSource.
	AC Voltage sensor sensorID has triggered a high alarm.
	Sensor reading is sensorValue"
    ::= 62	

alarmLowACVoltageSensor TRAP-TYPE
    ENTERPRISE trapControl
    VARIABLES   { trapSource, trapDescr, sensorID, sensorValue }
    DESCRIPTION
    "Trap origin is from trapSource.
	AC Voltage sensor sensorID has triggered a low alarm.
	Sensor reading is sensorValue"
    ::= 63	
	
clearCurrentConsumptionSensor TRAP-TYPE
    ENTERPRISE trapControl
    VARIABLES   { trapSource, trapDescr, currentConsumption }
    DESCRIPTION
    "Trap origin is from trapSource.
	Current Consumption alarm is cleared.
	Sensor reading is 'currentConsumption'"
    ::= 64
	
warningCurrentConsumptionSensor TRAP-TYPE
    ENTERPRISE trapControl
    VARIABLES   { trapSource, trapDescr, currentConsumption }
    DESCRIPTION
    "Trap origin is from trapSource.
	Current Consumption has reached warning level.
	Sensor reading is 'currentConsumption'"
    ::= 65	

alarmCurrentConsumptionSensor TRAP-TYPE
    ENTERPRISE trapControl
    VARIABLES   { trapSource, trapDescr, currentConsumption }
    DESCRIPTION
    "Trap origin is from trapSource.
	Current Consumption has reached alarm level.
	Sensor reading is 'currentConsumption'"
    ::= 66

criticalCurrentConsumptionSensor TRAP-TYPE
    ENTERPRISE trapControl
    VARIABLES   { trapSource, trapDescr, currentConsumption }
    DESCRIPTION
    "Trap origin is from trapSource.
	Current Consumption has reached critical level.
	Sensor reading is 'currentConsumption'"
    ::= 67

shutdownHighTemperatureSensor TRAP-TYPE
    ENTERPRISE trapControl
    VARIABLES   { trapSource, trapDescr, sensorID, sensorValue}
    DESCRIPTION
    "Trap origin is from trapSource.
	Temperature sensor sensorID has triggered a high shutdown alarm.
	Sensor reading is sensorValue"
    ::= 68	

shutdownLowTemperatureSensor TRAP-TYPE
    ENTERPRISE trapControl
    VARIABLES   { trapSource, trapDescr, sensorID, sensorValue }
    DESCRIPTION
    "Trap origin is from trapSource.
	Temperature sensor sensorID has triggered a low shutdown alarm.
	Sensor reading is sensorValue"
    ::= 69


shutdownHighHumiditySensor TRAP-TYPE
    ENTERPRISE trapControl
    VARIABLES   { trapSource, trapDescr, sensorID, sensorValue}
    DESCRIPTION
    "Trap origin is from trapSource.
	Humidity sensor sensorID has triggered a high shutdown alarm.
	Sensor reading is sensorValue"
    ::= 70	

shutdownLowHumiditySensor TRAP-TYPE
    ENTERPRISE trapControl
    VARIABLES   { trapSource, trapDescr, sensorID, sensorValue }
    DESCRIPTION
    "Humidity sensor sensorID has triggered a low shutdown alarm.
	Sensor reading is sensorValue"
    ::= 71	
	
	
eventGraphsCleared TRAP-TYPE
    ENTERPRISE trapControl
    VARIABLES   { trapSource, trapDescr }
    DESCRIPTION
    "Trap origin is from trapSource.
	Event 'Graph data cleared by Administrator' triggered"
    ::= 100		

eventSNMPUpdate TRAP-TYPE
    ENTERPRISE trapControl
    VARIABLES   { trapSource, trapDescr }
    DESCRIPTION
    "Trap origin is from trapSource.
	Event 'SNMP settings updated' triggered"
    ::= 101	
	
eventEmailUpdate TRAP-TYPE
    ENTERPRISE trapControl
    VARIABLES   { trapSource, trapDescr }
    DESCRIPTION
    "Trap origin is from trapSource.
	Event 'Email settings updated' triggered"
    ::= 102
	
eventSensorSettingsUpdate TRAP-TYPE
    ENTERPRISE trapControl
    VARIABLES   { trapSource, trapDescr }
    DESCRIPTION
    "Trap origin is from trapSource.
	Event 'Sensor settings updated' triggered"
    ::= 103

eventDeviceRebootSuccessful TRAP-TYPE
    ENTERPRISE trapControl
    VARIABLES   { trapSource, trapDescr }
    DESCRIPTION
    "Trap origin is from trapSource.
	Event 'Device reboot successful' occured"
    ::= 104

eventDefaultsLoad TRAP-TYPE
    ENTERPRISE trapControl
    VARIABLES   { trapSource, trapDescr }
    DESCRIPTION
    "Trap origin is from trapSource.
	Event 'Defaults loaded' triggered"
    ::= 105

eventFlashCorruptionDetection TRAP-TYPE
    ENTERPRISE trapControl
    VARIABLES   { trapSource, trapDescr }
    DESCRIPTION
    "Trap origin is from trapSource.
	Event 'Falsh Corruption discovered. Loaded defaults' triggered"
    ::= 106

eventPasswordUpdate TRAP-TYPE
    ENTERPRISE trapControl
    VARIABLES   { trapSource, trapDescr }
    DESCRIPTION
    "Trap origin is from trapSource.
	Event 'Password changed' triggered"
    ::= 107	

eventDeviceReset TRAP-TYPE
    ENTERPRISE trapControl
    VARIABLES   { trapSource, trapDescr }
    DESCRIPTION
    "Trap origin is from trapSource.
	Event 'Device reset via web interface' triggered"
    ::= 108

eventTimeDateUpdate TRAP-TYPE
    ENTERPRISE trapControl
    VARIABLES   { trapSource, trapDescr }
    DESCRIPTION
    "Trap origin is from trapSource.
	Event 'Date/Time updated' triggered"
    ::= 109	

eventDeviceParamsUpdate TRAP-TYPE
    ENTERPRISE trapControl
    VARIABLES   { trapSource, trapDescr }
    DESCRIPTION
    "Trap origin is from trapSource.
	Event 'Device name/location updated' triggered"
    ::= 110

eventNetworkParamsUpdate TRAP-TYPE
    ENTERPRISE trapControl
    VARIABLES   { trapSource, trapDescr }
    DESCRIPTION
    "Trap origin is from trapSource.
	Event 'Network parameters changed' triggered"
    ::= 111

eventModemUpdate TRAP-TYPE
    ENTERPRISE trapControl
    VARIABLES   { trapSource, trapDescr }
    DESCRIPTION
    "Trap origin is from trapSource.
	Event 'SMS/Modem parameters changed' triggered"
    ::= 112	

eventIPMonitoringUpdate TRAP-TYPE
    ENTERPRISE trapControl
    VARIABLES   { trapSource, trapDescr }
    DESCRIPTION
    "Trap origin is from trapSource.
	Event 'Network monitoring settings changed' triggered"
    ::= 113	

eventRelayUpdate TRAP-TYPE
    ENTERPRISE trapControl
    VARIABLES   { trapSource, trapDescr }
    DESCRIPTION
    "Trap origin is from trapSource.
	Event 'Relay settings updated' triggered"
    ::= 114		
	
eventSensorTriggerActionUpdate TRAP-TYPE
    ENTERPRISE trapControl
    VARIABLES   { trapSource, trapDescr }
    DESCRIPTION
    "Trap origin is from trapSource.
	Event 'Sensor trigger action settings updated' triggered"
    ::= 115
	
eventLogCleared TRAP-TYPE
    ENTERPRISE trapControl
    VARIABLES   { trapSource, trapDescr }
    DESCRIPTION
    "Trap origin is from trapSource.
	Event 'Alarm and Event log cleared' triggered"
    ::= 116
	
eventRelayThermostatOn TRAP-TYPE
    ENTERPRISE trapControl
    VARIABLES   {trapSource,  trapDescr }
    DESCRIPTION
    "Trap origin is from trapSource.
	Event 'Relay  - Thermostat On' triggered"
    ::= 117

eventRelayThermostatOff TRAP-TYPE
    ENTERPRISE trapControl
    VARIABLES   { trapSource, trapDescr }
    DESCRIPTION
    "Trap origin is from trapSource.
	Event 'Relay  - Thermostat Off' triggered"
    ::= 118	
	
eventCameraUpdate TRAP-TYPE
    ENTERPRISE trapControl
    VARIABLES   { trapSource, trapDescr }
    DESCRIPTION
    "Trap origin is from trapSource.
	Event 'Camera settings updated' triggered"
    ::= 119	
	
eventRelayTurnedOn TRAP-TYPE
    ENTERPRISE trapControl
    VARIABLES   { trapSource, trapDescr }
    DESCRIPTION
    "Trap origin is from trapSource.
	Event 'Relay turned on' triggered"
    ::= 120

eventRelayTurnedOff TRAP-TYPE
    ENTERPRISE trapControl
    VARIABLES   { trapSource, trapDescr }
    DESCRIPTION
    "Trap origin is from trapSource.
	Event 'Relay turned off' triggered"
    ::= 121

eventRelayLatchReset TRAP-TYPE
    ENTERPRISE trapControl
    VARIABLES   { trapSource, trapDescr }
    DESCRIPTION
    "Trap origin is from trapSource.
	Event 'Relay latch reset' triggered"
    ::= 122

eventTestSNMP TRAP-TYPE
    ENTERPRISE trapControl
    VARIABLES   { trapSource, trapDescr }
    DESCRIPTION
    "Trap origin is from trapSource.
	Event 'Test SNMP Traps' triggered"
    ::= 123

eventTestSMS TRAP-TYPE
    ENTERPRISE trapControl
    VARIABLES   { trapSource, trapDescr }
    DESCRIPTION
    "Trap origin is from trapSource.
	Event 'Test SMS' triggered"
    ::= 124

eventTestEmail TRAP-TYPE
    ENTERPRISE trapControl
    VARIABLES   { trapSource, trapDescr }
    DESCRIPTION
    "Trap origin is from trapSource.
	Event 'Test Email' triggered"
    ::= 125

eventOutletTurnedOn TRAP-TYPE
    ENTERPRISE trapControl
    VARIABLES   { trapSource, trapDescr, outletID, outletName }
    DESCRIPTION
    "Trap origin is from trapSource. 
	Event 'Outlet Turned On' triggered. Outlet id is denoted by outletID. Outlet name is outletName"
    ::= 126

eventOutletTurnedOff TRAP-TYPE
    ENTERPRISE trapControl
    VARIABLES   { trapSource, trapDescr, outletID, outletName }
    DESCRIPTION
    "Trap origin is from trapSource. 
	Event 'Outlet Turned Off' triggered. Outlet id is denoted by outletID. Outlet name is outletName"
    ::= 127	

eventOutletTurnedRebooted TRAP-TYPE
    ENTERPRISE trapControl
    VARIABLES   { trapSource, trapDescr, outletID, outletName }
    DESCRIPTION
    "Trap origin is from trapSource. 
	Event 'Outlet Rebooted' triggered. Outlet id is denoted by outletID. Outlet name is outletName"
    ::= 128
	
eventGlobalOutletOn TRAP-TYPE
    ENTERPRISE trapControl
    VARIABLES   { trapSource, trapDescr }
    DESCRIPTION
    "Trap origin is from trapSource. 
	Event 'Global Outlets Turned On' triggered"
    ::= 129

eventGlobalOutletOff TRAP-TYPE
    ENTERPRISE trapControl
    VARIABLES   { trapSource, trapDescr }
    DESCRIPTION
    "Trap origin is from trapSource. 
	Event 'Global Outlets Turned Off' triggered"
    ::= 130
	
eventGlobalOutletReboot TRAP-TYPE
    ENTERPRISE trapControl
    VARIABLES   { trapSource, trapDescr }
    DESCRIPTION
    "Trap origin is from trapSource. 
	Event 'Global Reboot on Outlets' triggered"
    ::= 131	

eventOutletConfigured TRAP-TYPE
    ENTERPRISE trapControl
    VARIABLES   { trapSource, trapDescr, outletID }
    DESCRIPTION
    "Trap origin is from trapSource. 
	Outlet bearing 'outletID' has been configured"
    ::= 132

eventCurrentThresholdUpdate TRAP-TYPE
    ENTERPRISE trapControl
    VARIABLES   { trapSource, trapDescr }
    DESCRIPTION
    "Trap origin is from trapSource. 
	Current Sensor threshold values updated"
    ::= 133	
	
eventSerialPortParamsUpdate TRAP-TYPE
    ENTERPRISE trapControl
    VARIABLES   { trapSource, trapDescr }
    DESCRIPTION
    "Trap origin is from trapSource. 
	Serial Port Settings Updated"
    ::= 134
	
eventUserParamsUpdate TRAP-TYPE
    ENTERPRISE trapControl
    VARIABLES   { trapSource, trapDescr }
    DESCRIPTION
    "Trap origin is from trapSource. 
	User Parameters updated. User names or passwords have been updated"
    ::= 135

eventAdminUserParamsUpdate TRAP-TYPE
    ENTERPRISE trapControl
    VARIABLES   { trapSource, trapDescr }
    DESCRIPTION
    "Trap origin is from trapSource. 
	Administrator User Parameters updated"
    ::= 136

eventConfigurationLogCleared TRAP-TYPE
    ENTERPRISE trapControl
    VARIABLES   { trapSource, trapDescr }
    DESCRIPTION
    "Trap origin is from trapSource. 
	Configuration Log Cleared"
    ::= 137
	
END
