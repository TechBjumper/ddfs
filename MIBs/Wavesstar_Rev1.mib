--------------------------------------------------------------------------------
-- PDI WAVESTAR REV1 SNMP MIB
--
-- August 8, 2006
--------------------------------------------------------------------------------

Wavestar_Rev1 DEFINITIONS ::= BEGIN

IMPORTS
    OBJECT-TYPE
        FROM RFC-1212
    enterprises
        FROM RFC1155-SMI;

AnalogHundredths ::= TEXTUAL-CONVENTION
    DISPLAY-HINT    "d-2"
    STATUS          current
    DESCRIPTION     "Used for Power factor, etc"
    SYNTAX          INTEGER


AnalogAlarm ::= INTEGER {not_used (1),
                         invalid (2),
                         not_alarm (3),
                         ok (4),
                         low (5),
                         high (6)
                        }

DigitalValueSwitch ::= INTEGER {not_used (1),
			  invalid (2),
			  open (3),
			  closed (4)
		     }

DigitalValueScr ::= INTEGER {not_used (1),
			  invalid (2),
			  off (3),
			  on (4)
		     }


DigitalAlarm ::= INTEGER {not_used (1),
                          invalid (2),
                          not_alarm (3),
			  ok (4),
			  alarm (5)
		     }

                      
--------------------------------------------------------------------------------
-- OID hierarchy
--------------------------------------------------------------------------------

pdi			OBJECT IDENTIFIER ::= { enterprises 11273 }
wavestar		OBJECT IDENTIFIER ::= { pdi 1 }
config			OBJECT IDENTIFIER ::= { wavestar 2 }
variation		OBJECT IDENTIFIER ::= { config 1 }
analog_values		OBJECT IDENTIFIER ::= { variation 1 }
analog_alarms		OBJECT IDENTIFIER ::= { variation 2 }
digital_values		OBJECT IDENTIFIER ::= { variation 3 }
digital_alarms		OBJECT IDENTIFIER ::= { variation 4 }
traps			OBJECT IDENTIFIER ::= { variation 9 }

--------------------------------------------------------------------------------
-- Traps
--------------------------------------------------------------------------------

alarming  TRAP-TYPE
	  ENTERPRISE	traps
	  VARIABLES		{ alarmCount }
	  DESCRIPTION	"An alarm condition exists"
	  ::= 0

--------------------------------------------------------------------------------
-- Analog Values
--------------------------------------------------------------------------------

S1_Volts_AB OBJECT-TYPE
	SYNTAX  INTEGER
	ACCESS  read-only
	STATUS  mandatory
	DESCRIPTION "S1 Volts AB"
		::= { analog_values 1 }

S1_Volts_AB_Alarm OBJECT-TYPE
	SYNTAX  AnalogAlarm
	ACCESS  read-only
	STATUS  mandatory
	DESCRIPTION "S1 Volts AB Alarm"
		::= { analog_alarms 1 }


S1_Volts_BC OBJECT-TYPE
	SYNTAX  INTEGER
	ACCESS  read-only
	STATUS  mandatory
	DESCRIPTION "S1 Volts BC"
		::= { analog_values 2 }

S1_Volts_BC_Alarm OBJECT-TYPE
	SYNTAX  AnalogAlarm
	ACCESS  read-only
	STATUS  mandatory
	DESCRIPTION "S1 Volts BC Alarm"
		::= { analog_alarms 2 }

S1_Volts_CA OBJECT-TYPE
	SYNTAX  INTEGER
	ACCESS  read-only
	STATUS  mandatory
	DESCRIPTION "S1 Volts CA"
		::= { analog_values 3 }

S1_Volts_CA_Alarm OBJECT-TYPE
	SYNTAX  AnalogAlarm
	ACCESS  read-only
	STATUS  mandatory
	DESCRIPTION "S1 Volts CA Alarm"
		::= { analog_alarms 3 }

S2_Volts_AB OBJECT-TYPE
	SYNTAX  INTEGER
	ACCESS  read-only
	STATUS  mandatory
	DESCRIPTION "S2 Volts AB"
		::= { analog_values 4 }

S2_Volts_AB_Alarm OBJECT-TYPE
	SYNTAX  AnalogAlarm
	ACCESS  read-only
	STATUS  mandatory
	DESCRIPTION "S2 Volts AB Alarm"
		::= { analog_alarms 4 }

S2_Volts_BC OBJECT-TYPE
	SYNTAX  INTEGER
	ACCESS  read-only
	STATUS  mandatory
	DESCRIPTION "S2 Volts BC"
		::= { analog_values 5 }

S2_Volts_BC_Alarm OBJECT-TYPE
	SYNTAX  AnalogAlarm
	ACCESS  read-only
	STATUS  mandatory
	DESCRIPTION "S2 Volts BC Alarm"
		::= { analog_alarms 5 }

S2_Volts_CA OBJECT-TYPE
	SYNTAX  INTEGER
	ACCESS  read-only
	STATUS  mandatory
	DESCRIPTION "S2 Volts CA"
		::= { analog_values 6 }

S2_Volts_CA_Alarm OBJECT-TYPE
	SYNTAX  AnalogAlarm
	ACCESS  read-only
	STATUS  mandatory
	DESCRIPTION "S2 Volts CA Alarm"
		::= { analog_alarms 6 }

Output_Volts_AB OBJECT-TYPE
	SYNTAX  INTEGER
	ACCESS  read-only
	STATUS  mandatory
	DESCRIPTION "Output Volts AB"
		::= { analog_values 7 }

Output_Volts_AB_Alarm OBJECT-TYPE
	SYNTAX  AnalogAlarm
	ACCESS  read-only
	STATUS  mandatory
	DESCRIPTION "Output Volts AB Alarm"
		::= { analog_alarms 7 }

Output_Volts_BC OBJECT-TYPE
	SYNTAX  INTEGER
	ACCESS  read-only
	STATUS  mandatory
	DESCRIPTION "Output Volts BC"
		::= { analog_values 8 }

Output_Volts_BC_Alarm OBJECT-TYPE
	SYNTAX  AnalogAlarm
	ACCESS  read-only
	STATUS  mandatory
	DESCRIPTION "Output Volts BC Alarm"
		::= { analog_alarms 8 }

Output_Volts_CA OBJECT-TYPE
	SYNTAX  INTEGER
	ACCESS  read-only
	STATUS  mandatory
	DESCRIPTION "Output Volts CA"
		::= { analog_values 9 }

Output_Volts_CA_Alarm OBJECT-TYPE
	SYNTAX  AnalogAlarm
	ACCESS  read-only
	STATUS  mandatory
	DESCRIPTION "Output Volts CA Alarm"
		::= { analog_alarms 9 }

Output_Amps_A OBJECT-TYPE
	SYNTAX  INTEGER
	ACCESS  read-only
	STATUS  mandatory
	DESCRIPTION "Output Amps A"
		::= { analog_values 10 }

Output_Amps_A_Alarm OBJECT-TYPE
	SYNTAX  AnalogAlarm
	ACCESS  read-only
	STATUS  mandatory
	DESCRIPTION "Output Amps A Alarm"
		::= { analog_alarms 10 }

Output_Amps_B OBJECT-TYPE
	SYNTAX  INTEGER
	ACCESS  read-only
	STATUS  mandatory
	DESCRIPTION "Output Amps B"
		::= { analog_values 11 }

Output_Amps_B_Alarm OBJECT-TYPE
	SYNTAX  AnalogAlarm
	ACCESS  read-only
	STATUS  mandatory
	DESCRIPTION "Output Amps B Alarm"
		::= { analog_alarms 11 }

Output_Amps_C OBJECT-TYPE
	SYNTAX  INTEGER
	ACCESS  read-only
	STATUS  mandatory
	DESCRIPTION "Output Amps C"
		::= { analog_values 12 }

Output_Amps_C_Alarm OBJECT-TYPE
	SYNTAX  AnalogAlarm
	ACCESS  read-only
	STATUS  mandatory
	DESCRIPTION "Output Amps C Alarm"
		::= { analog_alarms 12 }

Output_Amps_N OBJECT-TYPE
	SYNTAX  INTEGER
	ACCESS  read-only
	STATUS  mandatory
	DESCRIPTION "Output Amps N"
		::= { analog_values 13 }

Output_Amps_N_Alarm OBJECT-TYPE
	SYNTAX  AnalogAlarm
	ACCESS  read-only
	STATUS  mandatory
	DESCRIPTION "Output Amps N Alarm"
		::= { analog_alarms 13 }

Output_KVA_A OBJECT-TYPE
	SYNTAX  INTEGER
	ACCESS  read-only
	STATUS  mandatory
	DESCRIPTION "Output KVA A"
		::= { analog_values 14 }

Output_KVA_A_Alarm OBJECT-TYPE
	SYNTAX  AnalogAlarm
	ACCESS  read-only
	STATUS  mandatory
	DESCRIPTION "Output KVA A Alarm"
		::= { analog_alarms 14 }

Output_KVA_B OBJECT-TYPE
	SYNTAX  INTEGER
	ACCESS  read-only
	STATUS  mandatory
	DESCRIPTION "Output KVA B"
		::= { analog_values 15 }

Output_KVA_B_Alarm OBJECT-TYPE
	SYNTAX  AnalogAlarm
	ACCESS  read-only
	STATUS  mandatory
	DESCRIPTION "Output KVA B Alarm"
		::= { analog_alarms 15 }

Output_KVA_C OBJECT-TYPE
	SYNTAX  INTEGER
	ACCESS  read-only
	STATUS  mandatory
	DESCRIPTION "Output KVA C"
		::= { analog_values 16 }

Output_KVA_C_Alarm OBJECT-TYPE
	SYNTAX  AnalogAlarm
	ACCESS  read-only
	STATUS  mandatory
	DESCRIPTION "Output KVA C Alarm"
		::= { analog_alarms 16 }

S1_Amps_A OBJECT-TYPE
	SYNTAX  INTEGER
	ACCESS  read-only
	STATUS  mandatory
	DESCRIPTION "S1 Amps A"
		::= { analog_values 17 }

S1_Amps_A_Alarm OBJECT-TYPE
	SYNTAX  AnalogAlarm
	ACCESS  read-only
	STATUS  mandatory
	DESCRIPTION "S1 Amps A Alarm"
		::= { analog_alarms 17 }

S1_Amps_B OBJECT-TYPE
	SYNTAX  INTEGER
	ACCESS  read-only
	STATUS  mandatory
	DESCRIPTION "S1 Amps B"
		::= { analog_values 18 }

S1_Amps_B_Alarm OBJECT-TYPE
	SYNTAX  AnalogAlarm
	ACCESS  read-only
	STATUS  mandatory
	DESCRIPTION "S1 Amps B Alarm"
		::= { analog_alarms 18 }

S1_Amps_C OBJECT-TYPE
	SYNTAX  INTEGER
	ACCESS  read-only
	STATUS  mandatory
	DESCRIPTION "S1 Amps C"
		::= { analog_values 19 }

S1_Amps_C_Alarm OBJECT-TYPE
	SYNTAX  AnalogAlarm
	ACCESS  read-only
	STATUS  mandatory
	DESCRIPTION "S1 Amps C Alarm"
		::= { analog_alarms 19 }

S2_Amps_A OBJECT-TYPE
	SYNTAX  INTEGER
	ACCESS  read-only
	STATUS  mandatory
	DESCRIPTION "S2 Amps A"
		::= { analog_values 20 }

S2_Amps_A_Alarm OBJECT-TYPE
	SYNTAX  AnalogAlarm
	ACCESS  read-only
	STATUS  mandatory
	DESCRIPTION "S2 Amps A Alarm"
		::= { analog_alarms 20 }

S2_Amps_B OBJECT-TYPE
	SYNTAX  INTEGER
	ACCESS  read-only
	STATUS  mandatory
	DESCRIPTION "S2 Amps B"
		::= { analog_values 21 }

S2_Amps_B_Alarm OBJECT-TYPE
	SYNTAX  AnalogAlarm
	ACCESS  read-only
	STATUS  mandatory
	DESCRIPTION "S2 Amps B Alarm"
		::= { analog_alarms 21 }

S2_Amps_C OBJECT-TYPE
	SYNTAX  INTEGER
	ACCESS  read-only
	STATUS  mandatory
	DESCRIPTION "S2 Amps C"
		::= { analog_values 22 }

S2_Amps_C_Alarm OBJECT-TYPE
	SYNTAX  AnalogAlarm
	ACCESS  read-only
	STATUS  mandatory
	DESCRIPTION "S2 Amps C Alarm"
		::= { analog_alarms 22 }

Output_Volts_AN OBJECT-TYPE
	SYNTAX  INTEGER
	ACCESS  read-only
	STATUS  mandatory
	DESCRIPTION "Output Volts AN"
		::= { analog_values 23 }

Output_Volts_AN_Alarm OBJECT-TYPE
	SYNTAX  AnalogAlarm
	ACCESS  read-only
	STATUS  mandatory
	DESCRIPTION "Output Volts AN Alarm"
		::= { analog_alarms 23 }

Output_Volts_BN OBJECT-TYPE
	SYNTAX  INTEGER
	ACCESS  read-only
	STATUS  mandatory
	DESCRIPTION "Output Volts BN"
		::= { analog_values 24 }

Output_Volts_BN_Alarm OBJECT-TYPE
	SYNTAX  AnalogAlarm
	ACCESS  read-only
	STATUS  mandatory
	DESCRIPTION "Output Volts BN Alarm"
		::= { analog_alarms 24 }

Output_Volts_CN OBJECT-TYPE
	SYNTAX  INTEGER
	ACCESS  read-only
	STATUS  mandatory
	DESCRIPTION "Output Volts CN"
		::= { analog_values 25 }

Output_Volts_CN_Alarm OBJECT-TYPE
	SYNTAX  AnalogAlarm
	ACCESS  read-only
	STATUS  mandatory
	DESCRIPTION "Output Volts CN Alarm"
		::= { analog_alarms 25 }

Ground_Amps OBJECT-TYPE
	SYNTAX  INTEGER
	ACCESS  read-only
	STATUS  mandatory
	DESCRIPTION "Ground Amps"
		::= { analog_values 26 }

Ground_Amps_Alarm OBJECT-TYPE
	SYNTAX  AnalogAlarm
	ACCESS  read-only
	STATUS  mandatory
	DESCRIPTION "Ground Amps Alarm"
		::= { analog_alarms 26 }

KW_Out_A OBJECT-TYPE
	SYNTAX  INTEGER
	ACCESS  read-only
	STATUS  mandatory
	DESCRIPTION "KW Out A"
		::= { analog_values 27 }

KW_Out_A_Alarm OBJECT-TYPE
	SYNTAX  AnalogAlarm
	ACCESS  read-only
	STATUS  mandatory
	DESCRIPTION "KW Out A Alarm"
		::= { analog_alarms 27 }

KW_Out_B OBJECT-TYPE
	SYNTAX  INTEGER
	ACCESS  read-only
	STATUS  mandatory
	DESCRIPTION "KW Out B"
		::= { analog_values 28 }

KW_Out_B_Alarm OBJECT-TYPE
	SYNTAX  AnalogAlarm
	ACCESS  read-only
	STATUS  mandatory
	DESCRIPTION "KW Out A Alarm"
		::= { analog_alarms 28 }

KW_Out_C OBJECT-TYPE
	SYNTAX  INTEGER
	ACCESS  read-only
	STATUS  mandatory
	DESCRIPTION "KW Out C"
		::= { analog_values 29 }

KW_Out_C_Alarm OBJECT-TYPE
	SYNTAX  AnalogAlarm
	ACCESS  read-only
	STATUS  mandatory
	DESCRIPTION "KW Out C Alarm"
		::= { analog_alarms 29 }

Out_Frequency OBJECT-TYPE
	SYNTAX  AnalogHundredths
	ACCESS  read-only
	STATUS  mandatory
	DESCRIPTION "Out Frequency"
		::= { analog_values 30 }

Out_Frequency_Alarm OBJECT-TYPE
	SYNTAX  AnalogAlarm
	ACCESS  read-only
	STATUS  mandatory
	DESCRIPTION "Out Frequency Alarm"
		::= { analog_alarms 30 }

S1_Frequency OBJECT-TYPE
	SYNTAX  AnalogHundredths
	ACCESS  read-only
	STATUS  mandatory
	DESCRIPTION "Source 1 Frequency"
		::= { analog_values 31 }

S1_Frequency_Alarm OBJECT-TYPE
	SYNTAX  AnalogAlarm
	ACCESS  read-only
	STATUS  mandatory
	DESCRIPTION "Source 1 Frequency Alarm"
		::= { analog_alarms 31 }

S2_Frequency OBJECT-TYPE
	SYNTAX  AnalogHundredths
	ACCESS  read-only
	STATUS  mandatory
	DESCRIPTION "Source 2 Frequency"
		::= { analog_values 32 }

S2_Frequency_Alarm OBJECT-TYPE
	SYNTAX  AnalogAlarm
	ACCESS  read-only
	STATUS  mandatory
	DESCRIPTION "Source 2 Frequency Alarm"
		::= { analog_alarms 32 }

Phase OBJECT-TYPE
	SYNTAX  INTEGER
	ACCESS  read-only
	STATUS  mandatory
	DESCRIPTION "Phase between Source 1 and Source 2"
		::= { analog_values 33 }

Phase_Alarm OBJECT-TYPE
	SYNTAX  AnalogAlarm
	ACCESS  read-only
	STATUS  mandatory
	DESCRIPTION "Phase between Source 1 and Source 2 Alarm"
		::= { analog_alarms 33 }

Output_Percent_KVA_A OBJECT-TYPE
	SYNTAX  INTEGER
	ACCESS  read-only
	STATUS  mandatory
	DESCRIPTION "Output Percent KVA A"
		::= { analog_values 34 }

Output_Percent_KVA_A_Alarm OBJECT-TYPE
	SYNTAX  AnalogAlarm
	ACCESS  read-only
	STATUS  mandatory
	DESCRIPTION "Output Percent KVA A Alarm"
		::= { analog_alarms 34 }

Output_Percent_KVA_B OBJECT-TYPE
	SYNTAX  INTEGER
	ACCESS  read-only
	STATUS  mandatory
	DESCRIPTION "Output Percent KVA B"
		::= { analog_values 35 }

Output_Percent_KVA_B_Alarm OBJECT-TYPE
	SYNTAX  AnalogAlarm
	ACCESS  read-only
	STATUS  mandatory
	DESCRIPTION "Output Percent KVA B Alarm"
		::= { analog_alarms 35 }

Output_Percent_KVA_C OBJECT-TYPE
	SYNTAX  INTEGER
	ACCESS  read-only
	STATUS  mandatory
	DESCRIPTION "Output Percent KVA C"
		::= { analog_values 36 }

Output_Percent_KVA_C_Alarm OBJECT-TYPE
	SYNTAX  AnalogAlarm
	ACCESS  read-only
	STATUS  mandatory
	DESCRIPTION "Output Percent KVA C Alarm"
		::= { analog_alarms 36 }

Peak_Total_KVA OBJECT-TYPE
	SYNTAX  INTEGER
	ACCESS  read-only
	STATUS  mandatory
	DESCRIPTION "Peak Total KVA"
		::= { analog_values 37 }

Peak_Total_KVA_Alarm OBJECT-TYPE
	SYNTAX  AnalogAlarm
	ACCESS  read-only
	STATUS  mandatory
	DESCRIPTION "Peak Total KVA Alarm"
		::= { analog_alarms 37 }

Output_PF_A OBJECT-TYPE
	SYNTAX  AnalogHundredths
	ACCESS  read-only
	STATUS  mandatory
	DESCRIPTION "Output PF A"
		::= { analog_values 38 }

Output_PF_A_Alarm OBJECT-TYPE
	SYNTAX  AnalogAlarm
	ACCESS  read-only
	STATUS  mandatory
	DESCRIPTION "Output PF A Alarm"
		::= { analog_alarms 38 }

Output_PF_B OBJECT-TYPE
	SYNTAX  AnalogHundredths
	ACCESS  read-only
	STATUS  mandatory
	DESCRIPTION "Output PF B"
		::= { analog_values 39 }

Output_PF_B_Alarm OBJECT-TYPE
	SYNTAX  AnalogAlarm
	ACCESS  read-only
	STATUS  mandatory
	DESCRIPTION "Output PF B Alarm"
		::= { analog_alarms 39 }

Output_PF_C OBJECT-TYPE
	SYNTAX  AnalogHundredths
	ACCESS  read-only
	STATUS  mandatory
	DESCRIPTION "Output PF C"
		::= { analog_values 40 }

Output_PF_C_Alarm OBJECT-TYPE
	SYNTAX  AnalogAlarm
	ACCESS  read-only
	STATUS  mandatory
	DESCRIPTION "Output PF C Alarm"
		::= { analog_alarms 40 }

Total_KW OBJECT-TYPE
	SYNTAX  INTEGER
	ACCESS  read-only
	STATUS  mandatory
	DESCRIPTION "Total KW"
		::= { analog_values 41 }

Total_KW_Alarm OBJECT-TYPE
	SYNTAX  AnalogAlarm
	ACCESS  read-only
	STATUS  mandatory
	DESCRIPTION "Total KW Alarm"
		::= { analog_alarms 41 }

Xfer_Total OBJECT-TYPE
	SYNTAX  INTEGER
	ACCESS  read-only
	STATUS  mandatory
	DESCRIPTION "Xfers Total"
		::= { analog_values 42 }

Xfer-Total_Alarm OBJECT-TYPE
	SYNTAX  AnalogAlarm
	ACCESS  read-only
	STATUS  mandatory
	DESCRIPTION "Xfer Total Alarm"
		::= { analog_alarms 42 }

Xfer_Since_Clr OBJECT-TYPE
	SYNTAX  INTEGER
	ACCESS  read-only
	STATUS  mandatory
	DESCRIPTION "Xfers Since Clr"
		::= { analog_values 43 }

Xfer-Since_Clr_Alarm OBJECT-TYPE
	SYNTAX  AnalogAlarm
	ACCESS  read-only
	STATUS  mandatory
	DESCRIPTION "Xfer Since Clr Alarm"
		::= { analog_alarms 43 }


Out_Volts_THD_A OBJECT-TYPE
	SYNTAX  INTEGER
	ACCESS  read-only
	STATUS  mandatory
	DESCRIPTION "Out Volts THD A"
		::= { analog_values 44 }
OUt_Volts_THD_A_Alarm OBJECT-TYPE
	SYNTAX  AnalogAlarm
	ACCESS  read-only
	STATUS  mandatory
	DESCRIPTION "OUt Volts THD A Alarm"
		::= { analog_alarms 44 }

Out_Volts_A_3rd OBJECT-TYPE
	SYNTAX  AnalogHundredths
	ACCESS  read-only
	STATUS  mandatory
	DESCRIPTION "Out Volts A 3rd"
		::= { analog_values 45 }
OUt_Volts_A_3rd_Alarm OBJECT-TYPE
	SYNTAX  AnalogAlarm
	ACCESS  read-only
	STATUS  mandatory
	DESCRIPTION "OUt Volts A 3rd Alarm"
		::= { analog_alarms 45 }

Out_Volts_A_5th OBJECT-TYPE
	SYNTAX  AnalogHundredths
	ACCESS  read-only
	STATUS  mandatory
	DESCRIPTION "Out Volts A 5th"
		::= { analog_values 46 }

Out_Volts_A_5th_Alarm OBJECT-TYPE
	SYNTAX  AnalogAlarm
	ACCESS  read-only
	STATUS  mandatory
	DESCRIPTION "Out Volts A 5th Alarm"
		::= { analog_alarms 46 }

Out_Volts_A_7th OBJECT-TYPE
	SYNTAX  AnalogHundredths
	ACCESS  read-only
	STATUS  mandatory
	DESCRIPTION "Out Volts A 7th"
		::= { analog_values 47 }

Out_Volts_A_7th_Alarm OBJECT-TYPE
	SYNTAX  AnalogAlarm
	ACCESS  read-only
	STATUS  mandatory
	DESCRIPTION "Out Volts A 7th Alarm"
		::= { analog_alarms 47 }

Out_Volts_A_9th OBJECT-TYPE
	SYNTAX  AnalogHundredths
	ACCESS  read-only
	STATUS  mandatory
	DESCRIPTION "Out Volts A 9th"
		::= { analog_values 48 }

Out_Volts_A_9th_Alarm OBJECT-TYPE
	SYNTAX  AnalogAlarm
	ACCESS  read-only
	STATUS  mandatory
	DESCRIPTION "Out Volts A 9th Alarm"
		::= { analog_alarms 48 }

Out_Volts_A_11th OBJECT-TYPE
	SYNTAX  AnalogHundredths
	ACCESS  read-only
	STATUS  mandatory
	DESCRIPTION "Out Volts A 11th"
		::= { analog_values 49 }

Out_Volts_A_11th_Alarm OBJECT-TYPE
	SYNTAX  AnalogAlarm
	ACCESS  read-only
	STATUS  mandatory
	DESCRIPTION "Out Volts A 11th Alarm"
		::= { analog_alarms 49 }

Out_Volts_A_13th OBJECT-TYPE
	SYNTAX  AnalogHundredths
	ACCESS  read-only
	STATUS  mandatory
	DESCRIPTION "Out Volts A 13th"
		::= { analog_values 50 }

Out_Volts_A_13th_Alarm OBJECT-TYPE
	SYNTAX  AnalogAlarm
	ACCESS  read-only
	STATUS  mandatory
	DESCRIPTION "Out Volts A 13th Alarm"
		::= { analog_alarms 50 }

Out_Volts_THD_B OBJECT-TYPE
	SYNTAX  AnalogHundredths
	ACCESS  read-only
	STATUS  mandatory
	DESCRIPTION "Out Volts THD B"
		::= { analog_values 51 }

Out_Volts_THD_B_Alarm OBJECT-TYPE
	SYNTAX  AnalogAlarm
	ACCESS  read-only
	STATUS  mandatory
	DESCRIPTION "Out Volts THD B Alarm"
		::= { analog_alarms 51 }

Out_Volts_B_3rd OBJECT-TYPE
	SYNTAX  AnalogHundredths
	ACCESS  read-only
	STATUS  mandatory
	DESCRIPTION "Out Volts B 3rd"
		::= { analog_values 52 }

Out_Volts_B_3rd_Alarm OBJECT-TYPE
	SYNTAX  AnalogAlarm
	ACCESS  read-only
	STATUS  mandatory
	DESCRIPTION "Out Volts B 3rd Alarm"
		::= { analog_alarms 52 }

Out_Volts_B_5th OBJECT-TYPE
	SYNTAX  AnalogHundredths
	ACCESS  read-only
	STATUS  mandatory
	DESCRIPTION "Out Volts B 5th"
		::= { analog_values 53 }

Out_Volts_B_5th_Alarm OBJECT-TYPE
	SYNTAX  AnalogAlarm
	ACCESS  read-only
	STATUS  mandatory
	DESCRIPTION "Out Volts B 5th Alarm"
		::= { analog_alarms 53 }

Out_Volts_B_7th OBJECT-TYPE
	SYNTAX  AnalogHundredths
	ACCESS  read-only
	STATUS  mandatory
	DESCRIPTION "Out Volts B 7th"
		::= { analog_values 54 }

Out_Volts_B_7th_Alarm OBJECT-TYPE
	SYNTAX  AnalogAlarm
	ACCESS  read-only
	STATUS  mandatory
	DESCRIPTION "Out Volts B 7th Alarm"
		::= { analog_alarms 54 }

Out_Volts_B_9th OBJECT-TYPE
	SYNTAX  AnalogHundredths
	ACCESS  read-only
	STATUS  mandatory
	DESCRIPTION "Out Volts B 9th"
		::= { analog_values 55 }

Out_Volts_B_9th_Alarm OBJECT-TYPE
	SYNTAX  AnalogAlarm
	ACCESS  read-only
	STATUS  mandatory
	DESCRIPTION "Out Volts B 9th Alarm"
		::= { analog_alarms 55 }


Out_Volts_B_11th OBJECT-TYPE
	SYNTAX  AnalogHundredths
	ACCESS  read-only
	STATUS  mandatory
	DESCRIPTION "Out Volts B 11th"
		::= { analog_values 56 }

Out_Volts_B_11th_Alarm OBJECT-TYPE
	SYNTAX  AnalogAlarm
	ACCESS  read-only
	STATUS  mandatory
	DESCRIPTION "Out Volts B 11th Alarm"
		::= { analog_alarms 56 }

Out_Volts_B_13th OBJECT-TYPE
	SYNTAX  AnalogHundredths
	ACCESS  read-only
	STATUS  mandatory
	DESCRIPTION "Out Volts B 13th"
		::= { analog_values 57 }

Out_Volts_B_13th_Alarm OBJECT-TYPE
	SYNTAX  AnalogAlarm
	ACCESS  read-only
	STATUS  mandatory
	DESCRIPTION "Out Volts B 13th Alarm"
		::= { analog_alarms 57 }

Out_Volts_THD_C OBJECT-TYPE
	SYNTAX  AnalogHundredths
	ACCESS  read-only
	STATUS  mandatory
	DESCRIPTION "Out Volts THD C"
		::= { analog_values 58 }

Out_Volts_THD_C_Alarm OBJECT-TYPE
	SYNTAX  AnalogAlarm
	ACCESS  read-only
	STATUS  mandatory
	DESCRIPTION "Out Volts THD C Alarm"
		::= { analog_alarms 58 }

Out_Volts_C_3rd OBJECT-TYPE
	SYNTAX  AnalogHundredths
	ACCESS  read-only
	STATUS  mandatory
	DESCRIPTION "Out Volts C 3rd"
		::= { analog_values 59 }

Out_Volts_C_3rd_Alarm OBJECT-TYPE
	SYNTAX  AnalogAlarm
	ACCESS  read-only
	STATUS  mandatory
	DESCRIPTION "Out Volts C 3rd Alarm"
		::= { analog_alarms 59 }


Out_Volts_C_5th OBJECT-TYPE
	SYNTAX  AnalogHundredths
	ACCESS  read-only
	STATUS  mandatory
	DESCRIPTION "Out Volts C 5th"
		::= { analog_values 60 }

Out_Volts_C_5th_Alarm OBJECT-TYPE
	SYNTAX  AnalogAlarm
	ACCESS  read-only
	STATUS  mandatory
	DESCRIPTION "Out Volts C 5th Alarm"
		::= { analog_alarms 60 }

Out_Volts_C_7th OBJECT-TYPE
	SYNTAX  AnalogHundredths
	ACCESS  read-only
	STATUS  mandatory
	DESCRIPTION "Out Volts C 7th"
		::= { analog_values 61 }

Out_Volts_C_7th_Alarm OBJECT-TYPE
	SYNTAX  AnalogAlarm
	ACCESS  read-only
	STATUS  mandatory
	DESCRIPTION "Out Volts C 7th Alarm"
		::= { analog_alarms 61 }

Out_Volts_C_9th OBJECT-TYPE
	SYNTAX  AnalogHundredths
	ACCESS  read-only
	STATUS  mandatory
	DESCRIPTION "Out Volts C 9th"
		::= { analog_values 62 }

Out_Volts_C_9th_Alarm OBJECT-TYPE
	SYNTAX  AnalogAlarm
	ACCESS  read-only
	STATUS  mandatory
	DESCRIPTION "Out Volts C 9th Alarm"
		::= { analog_alarms 62 }

Out_Volts_C_11th OBJECT-TYPE
	SYNTAX  AnalogHundredths
	ACCESS  read-only
	STATUS  mandatory
	DESCRIPTION "Out Volts C 11th"
		::= { analog_values 63 }

Out_Volts_C_11th_Alarm OBJECT-TYPE
	SYNTAX  AnalogAlarm
	ACCESS  read-only
	STATUS  mandatory
	DESCRIPTION "Out Volts C 11th Alarm"
		::= { analog_alarms 63 }

Out_Volts_C_13th OBJECT-TYPE
	SYNTAX  AnalogHundredths
	ACCESS  read-only
	STATUS  mandatory
	DESCRIPTION "Out Volts C 13th"
		::= { analog_values 64 }

Out_Volts_C_13th_Alarm OBJECT-TYPE
	SYNTAX  AnalogAlarm
	ACCESS  read-only
	STATUS  mandatory
	DESCRIPTION "Out Volts C 13th Alarm"
		::= { analog_alarms 64 }

Out_Amps_THD_A OBJECT-TYPE
	SYNTAX  AnalogHundredths
	ACCESS  read-only
	STATUS  mandatory
	DESCRIPTION "Out Amps THD A"
		::= { analog_values 65 }

Out_Amps_THD_A_Alarm OBJECT-TYPE
	SYNTAX  AnalogAlarm
	ACCESS  read-only
	STATUS  mandatory
	DESCRIPTION "Out Amps THD Alarm"
		::= { analog_alarms 65 }

Out_Amps_A_3rd OBJECT-TYPE
	SYNTAX  AnalogHundredths
	ACCESS  read-only
	STATUS  mandatory
	DESCRIPTION "Out Amps A 3rd"
		::= { analog_values 66 }

Out_Amps_A_3rd_Alarm OBJECT-TYPE
	SYNTAX  AnalogAlarm
	ACCESS  read-only
	STATUS  mandatory
	DESCRIPTION "Out Amps 3rd Alarm"
		::= { analog_alarms 66 }

Out_Amps_A_5th OBJECT-TYPE
	SYNTAX  AnalogHundredths
	ACCESS  read-only
	STATUS  mandatory
	DESCRIPTION "Out Amps A 5th"
		::= { analog_values 67 }

Out_Amps_A_5th_Alarm OBJECT-TYPE
	SYNTAX  AnalogAlarm
	ACCESS  read-only
	STATUS  mandatory
	DESCRIPTION "Out Amps 5th Alarm"
		::= { analog_alarms 67 }

Out_Amps_A_7th OBJECT-TYPE
	SYNTAX  AnalogHundredths
	ACCESS  read-only
	STATUS  mandatory
	DESCRIPTION "Out Amps A 7th"
		::= { analog_values 68 }

Out_Amps_A_7th_Alarm OBJECT-TYPE
	SYNTAX  AnalogAlarm
	ACCESS  read-only
	STATUS  mandatory
	DESCRIPTION "Out Amps 7th Alarm"
		::= { analog_alarms 68 }

Out_Amps_A_9th OBJECT-TYPE
	SYNTAX  AnalogHundredths
	ACCESS  read-only
	STATUS  mandatory
	DESCRIPTION "Out Amps A 9th"
		::= { analog_values 69 }

Out_Amps_A_9th_Alarm OBJECT-TYPE
	SYNTAX  AnalogAlarm
	ACCESS  read-only
	STATUS  mandatory
	DESCRIPTION "Out Amps 9th Alarm"
		::= { analog_alarms 69 }

Out_Amps_A_11th OBJECT-TYPE
	SYNTAX  AnalogHundredths
	ACCESS  read-only
	STATUS  mandatory
	DESCRIPTION "Out Amps A 11th"
		::= { analog_values 70 }

Out_Amps_A_11th_Alarm OBJECT-TYPE
	SYNTAX  AnalogAlarm
	ACCESS  read-only
	STATUS  mandatory
	DESCRIPTION "Out Amps 11th Alarm"
		::= { analog_alarms 70 }

Out_Amps_A_13th OBJECT-TYPE
	SYNTAX  AnalogHundredths
	ACCESS  read-only
	STATUS  mandatory
	DESCRIPTION "Out Amps A 13th"
		::= { analog_values 71 }

Out_Amps_A_13th_Alarm OBJECT-TYPE
	SYNTAX  AnalogAlarm
	ACCESS  read-only
	STATUS  mandatory
	DESCRIPTION "Out Amps 13th Alarm"
		::= { analog_alarms 71 }


Out_Amps_THD_B OBJECT-TYPE
	SYNTAX  AnalogHundredths
	ACCESS  read-only
	STATUS  mandatory
	DESCRIPTION "Out Amps THD B"
		::= { analog_values 72 }

Out_Amps_THD_B_Alarm OBJECT-TYPE
	SYNTAX  AnalogAlarm
	ACCESS  read-only
	STATUS  mandatory
	DESCRIPTION "Out Amps THD B Alarm"
		::= { analog_alarms 72 }

Out_Amps_B_3rd OBJECT-TYPE
	SYNTAX  AnalogHundredths
	ACCESS  read-only
	STATUS  mandatory
	DESCRIPTION "Out Amps B 3rd"
		::= { analog_values 73 }

Out_Amps_B_3rd_Alarm OBJECT-TYPE
	SYNTAX  AnalogAlarm
	ACCESS  read-only
	STATUS  mandatory
	DESCRIPTION "Out Amps B 3rd Alarm"
		::= { analog_alarms 73 }

Out_Amps_B_5th OBJECT-TYPE
	SYNTAX  AnalogHundredths
	ACCESS  read-only
	STATUS  mandatory
	DESCRIPTION "Out Amps B 5th"
		::= { analog_values 74 }

Out_Amps_B_5th_Alarm OBJECT-TYPE
	SYNTAX  AnalogAlarm
	ACCESS  read-only
	STATUS  mandatory
	DESCRIPTION "Out Amps B 5th Alarm"
		::= { analog_alarms 74 }

Out_Amps_B_7th OBJECT-TYPE
	SYNTAX  AnalogHundredths
	ACCESS  read-only
	STATUS  mandatory
	DESCRIPTION "Out Amps B 7th"
		::= { analog_values 75 }

Out_Amps_B_7th_Alarm OBJECT-TYPE
	SYNTAX  AnalogAlarm
	ACCESS  read-only
	STATUS  mandatory
	DESCRIPTION "Out Amps B 7th Alarm"
		::= { analog_alarms 75 }

Out_Amps_B_9th OBJECT-TYPE
	SYNTAX  AnalogHundredths
	ACCESS  read-only
	STATUS  mandatory
	DESCRIPTION "Out Amps B 9th"
		::= { analog_values 76 }

Out_Amps_B_9th_Alarm OBJECT-TYPE
	SYNTAX  AnalogAlarm
	ACCESS  read-only
	STATUS  mandatory
	DESCRIPTION "Out Amps B 9th Alarm"
		::= { analog_alarms 76 }

Out_Amps_B_11th OBJECT-TYPE
	SYNTAX  AnalogHundredths
	ACCESS  read-only
	STATUS  mandatory
	DESCRIPTION "Out Amps B 11th"
		::= { analog_values 77 }

Out_Amps_B_11th_Alarm OBJECT-TYPE
	SYNTAX  AnalogAlarm
	ACCESS  read-only
	STATUS  mandatory
	DESCRIPTION "OUt Amps B 11th Alarm"
		::= { analog_alarms 77 }

Out_Amps_B_13th OBJECT-TYPE
	SYNTAX  AnalogHundredths
	ACCESS  read-only
	STATUS  mandatory
	DESCRIPTION "Out Amps B 13th"
		::= { analog_values 78 }

Out_Amps_B_13th_Alarm OBJECT-TYPE
	SYNTAX  AnalogAlarm
	ACCESS  read-only
	STATUS  mandatory
	DESCRIPTION "Out Amps B 13th Alarm"
		::= { analog_alarms 78 }

Out_Amps_THD_C OBJECT-TYPE
	SYNTAX  AnalogHundredths
	ACCESS  read-only
	STATUS  mandatory
	DESCRIPTION "Out Amps THD C"
		::= { analog_values 79 }

Out_Amps_THD_C_Alarm OBJECT-TYPE
	SYNTAX  AnalogAlarm
	ACCESS  read-only
	STATUS  mandatory
	DESCRIPTION "Out Amps THD C Alarm"
		::= { analog_alarms 79 }

Out_Amps_C_3rd OBJECT-TYPE
	SYNTAX  AnalogHundredths
	ACCESS  read-only
	STATUS  mandatory
	DESCRIPTION "Out Amps C 3rd"
		::= { analog_values 80 }

Out_Amps_C_3rd_Alarm OBJECT-TYPE
	SYNTAX  AnalogAlarm
	ACCESS  read-only
	STATUS  mandatory
	DESCRIPTION "Out Amps C 3rd Alarm"
		::= { analog_alarms 80 }

Out_Amps_C_5th OBJECT-TYPE
	SYNTAX  AnalogHundredths
	ACCESS  read-only
	STATUS  mandatory
	DESCRIPTION "Out Amps C 5th"
		::= { analog_values 81 }

Out_Amps_C_5th_Alarm OBJECT-TYPE
	SYNTAX  AnalogAlarm
	ACCESS  read-only
	STATUS  mandatory
	DESCRIPTION "Out Amps C 5th Alarm"
		::= { analog_alarms 81 }

Out_Amps_C_7th OBJECT-TYPE
	SYNTAX  AnalogHundredths
	ACCESS  read-only
	STATUS  mandatory
	DESCRIPTION "Out Amps C 7th"
		::= { analog_values 82 }

Out_Amps_C_7th_Alarm OBJECT-TYPE
	SYNTAX  AnalogAlarm
	ACCESS  read-only
	STATUS  mandatory
	DESCRIPTION "Out Amps C 7th Alarm"
		::= { analog_alarms 82 }

Out_Amps_C_9th OBJECT-TYPE
	SYNTAX  AnalogHundredths
	ACCESS  read-only
	STATUS  mandatory
	DESCRIPTION "Out Amps C 9th"
		::= { analog_values 83 }

Out_Amps_C_9th_Alarm OBJECT-TYPE
	SYNTAX  AnalogAlarm
	ACCESS  read-only
	STATUS  mandatory
	DESCRIPTION "Out Amps C 9th Alarm"
		::= { analog_alarms 83 }

Out_Amps_C_11th OBJECT-TYPE
	SYNTAX  AnalogHundredths
	ACCESS  read-only
	STATUS  mandatory
	DESCRIPTION "Out Amps C 11th"
		::= { analog_values 84 }

Out_Amps_C_11th_Alarm OBJECT-TYPE
	SYNTAX  AnalogAlarm
	ACCESS  read-only
	STATUS  mandatory
	DESCRIPTION "Out Amps C 11th Alarm"
		::= { analog_alarms 84 }

Out_Amps_C_13th OBJECT-TYPE
	SYNTAX  AnalogHundredths
	ACCESS  read-only
	STATUS  mandatory
	DESCRIPTION "Out Amps C 13th"
		::= { analog_values 85 }

Out_Amps_C_13th_Alarm OBJECT-TYPE
	SYNTAX  AnalogAlarm
	ACCESS  read-only
	STATUS  mandatory
	DESCRIPTION "Out Amps C 13th Alarm"
		::= { analog_alarms 85 }

Peak_Total_KVA OBJECT-TYPE
	SYNTAX  INTEGER
	ACCESS  read-only
	STATUS  mandatory
	DESCRIPTION "Peak Total KVA"
		::= { analog_values 86 }

Peak_Total_KVA_Alarm OBJECT-TYPE
	SYNTAX  AnalogAlarm
	ACCESS  read-only
	STATUS  mandatory
	DESCRIPTION "Peak Total KVA Alarm"
		::= { analog_alarms 86 }

S1_Peak_A_Amp OBJECT-TYPE
	SYNTAX  INTEGER
	ACCESS  read-only
	STATUS  mandatory
	DESCRIPTION "S1 Peak A Amp"
		::= { analog_values 87 }
S1_Peak_A_Amp_Alarm OBJECT-TYPE
	SYNTAX  AnalogAlarm
	ACCESS  read-only
	STATUS  mandatory
	DESCRIPTION "S1 Peak A Amp Alarm"
		::= { analog_alarms 87 }

S1_Peak_B_Amp OBJECT-TYPE
	SYNTAX  INTEGER
	ACCESS  read-only
	STATUS  mandatory
	DESCRIPTION "S1 Peak B Amp"
		::= { analog_values 88 }

S1_Peak_B_Amp_Alarm OBJECT-TYPE
	SYNTAX  AnalogAlarm
	ACCESS  read-only
	STATUS  mandatory
	DESCRIPTION "S1 Peak B Amp Alarm"
		::= { analog_alarms 88 }

S1_Peak_C_Amp OBJECT-TYPE
	SYNTAX  INTEGER
	ACCESS  read-only
	STATUS  mandatory
	DESCRIPTION "S1 Peak C Amp"
		::= { analog_values 89 }

S1_Peak_C_Amp_Alarm OBJECT-TYPE
	SYNTAX  AnalogAlarm
	ACCESS  read-only
	STATUS  mandatory
	DESCRIPTION "S1 Peak C Amp Alarm"
		::= { analog_alarms 89 }

S2_Peak_A_Amp OBJECT-TYPE
	SYNTAX  INTEGER
	ACCESS  read-only
	STATUS  mandatory
	DESCRIPTION "S2 Peak A Amp"
		::= { analog_values 90 }

S2_Peak_A_Amp_Alarm OBJECT-TYPE
	SYNTAX  AnalogAlarm
	ACCESS  read-only
	STATUS  mandatory
	DESCRIPTION "S2 Peak A Amp Alarm"
		::= { analog_alarms 90 }

S2_Peak_B_Amp OBJECT-TYPE
	SYNTAX  INTEGER
	ACCESS  read-only
	STATUS  mandatory
	DESCRIPTION "S2 Peak B Amp"
		::= { analog_values 91 }
S2_Peak_B_Amp_Alarm OBJECT-TYPE
	SYNTAX  AnalogAlarm
	ACCESS  read-only
	STATUS  mandatory
	DESCRIPTION "S2 Peak B Amp Alarm"
		::= { analog_alarms 91 }

S2_Peak_C_Amp OBJECT-TYPE
	SYNTAX  INTEGER
	ACCESS  read-only
	STATUS  mandatory
	DESCRIPTION "S2 Peak C Amp"
		::= { analog_values 92 }

S2_Peak_C_Amp_Alarm OBJECT-TYPE
	SYNTAX  AnalogAlarm
	ACCESS  read-only
	STATUS  mandatory
	DESCRIPTION "S2 Peak C Amp Alarm"
		::= { analog_alarms 92 }

Rated_Total_KVA OBJECT-TYPE
	SYNTAX  INTEGER
	ACCESS  read-only
	STATUS  mandatory
	DESCRIPTION "Rated total KVA"
		::= { analog_values 93 }

Rated_Phase_Amp OBJECT-TYPE
	SYNTAX  INTEGER
	ACCESS  read-only
	STATUS  mandatory
	DESCRIPTION "Rated amps per phase"
		::= { analog_values 94 }

alarmCount OBJECT-TYPE
	SYNTAX  INTEGER
	ACCESS  read-only
	STATUS  mandatory
	DESCRIPTION "Total number of alarms"
		::= { analog_values 95 }

PDU_1_Volts_AB OBJECT-TYPE
	SYNTAX  INTEGER
	ACCESS  read-only
	STATUS  mandatory
	DESCRIPTION "PDU 1 Volts AB"
		::= { analog_values 96 }

PDU_1_Volts_AB_Alarm OBJECT-TYPE
	SYNTAX  AnalogAlarm
	ACCESS  read-only
	STATUS  mandatory
	DESCRIPTION "PDU 1 Volts AB Alarm"
		::= { analog_alarms 96 }

PDU_1_Volts_BC OBJECT-TYPE
	SYNTAX  INTEGER
	ACCESS  read-only
	STATUS  mandatory
	DESCRIPTION "PDU 1 Volts BC"
		::= { analog_values 97 }

PDU_1_Volts_BC_Alarm OBJECT-TYPE
	SYNTAX  AnalogAlarm
	ACCESS  read-only
	STATUS  mandatory
	DESCRIPTION "PDU 1 Volts BC Alarm"
		::= { analog_alarms 97 }

PDU_1_Volts_CA OBJECT-TYPE
	SYNTAX  INTEGER
	ACCESS  read-only
	STATUS  mandatory
	DESCRIPTION "PDU 1 Volts CA"
		::= { analog_values 98 }

PDU_1_Volts_CA_Alarm OBJECT-TYPE
	SYNTAX  AnalogAlarm
	ACCESS  read-only
	STATUS  mandatory
	DESCRIPTION "PDU 1 Volts CA Alarm"
		::= { analog_alarms 98 }

PDU_1_Volts_AN OBJECT-TYPE
	SYNTAX  INTEGER
	ACCESS  read-only
	STATUS  mandatory
	DESCRIPTION "PDU 1 Volts AN"
		::= { analog_values 99 }

PDU_1_Volts_AN_Alarm OBJECT-TYPE
	SYNTAX  AnalogAlarm
	ACCESS  read-only
	STATUS  mandatory
	DESCRIPTION "PDU 1 Volts AN Alarm"
		::= { analog_alarms 99 }

PDU_1_Volts_BN OBJECT-TYPE
	SYNTAX  INTEGER
	ACCESS  read-only
	STATUS  mandatory
	DESCRIPTION "PDU 1 Volts BN"
		::= { analog_values 100 }

PDU_1_Volts_BN_Alarm OBJECT-TYPE
	SYNTAX  AnalogAlarm
	ACCESS  read-only
	STATUS  mandatory
	DESCRIPTION "PDU 1 Volts BN Alarm"
		::= { analog_alarms 100 }

PDU_1_Volts_CN OBJECT-TYPE
	SYNTAX  INTEGER
	ACCESS  read-only
	STATUS  mandatory
	DESCRIPTION "PDU 1 Volts CN"
		::= { analog_values 101 }

PDU_1_Volts_CN_Alarm OBJECT-TYPE
	SYNTAX  AnalogAlarm
	ACCESS  read-only
	STATUS  mandatory
	DESCRIPTION "PDU 1 Volts CN Alarm"
		::= { analog_alarms 101 }

PDU_1_Amps_A OBJECT-TYPE
	SYNTAX  INTEGER
	ACCESS  read-only
	STATUS  mandatory
	DESCRIPTION "PDU 1 Amps A"
		::= { analog_values 102 }

PDU_1_Amps_A_Alarm OBJECT-TYPE
	SYNTAX  AnalogAlarm
	ACCESS  read-only
	STATUS  mandatory
	DESCRIPTION "PDU 1 Amps A Alarm"
		::= { analog_alarms 102 }

PDU_1_Amps_B OBJECT-TYPE
	SYNTAX  INTEGER
	ACCESS  read-only
	STATUS  mandatory
	DESCRIPTION "PDU 1 Amps B"
		::= { analog_values 103 }

PDU_1_Amps_B_Alarm OBJECT-TYPE
	SYNTAX  AnalogAlarm
	ACCESS  read-only
	STATUS  mandatory
	DESCRIPTION "PDU 1 Amps B Alarm"
		::= { analog_alarms 103 }


PDU_1_Amps_C OBJECT-TYPE
	SYNTAX  INTEGER
	ACCESS  read-only
	STATUS  mandatory
	DESCRIPTION "PDU 1 Amps C"
		::= { analog_values 104 }

PDU_1_Amps_C_Alarm OBJECT-TYPE
	SYNTAX  AnalogAlarm
	ACCESS  read-only
	STATUS  mandatory
	DESCRIPTION "PDU 1 Amps C Alarm"
		::= { analog_alarms 104 }

PDU_1_KVA_A OBJECT-TYPE
	SYNTAX  INTEGER
	ACCESS  read-only
	STATUS  mandatory
	DESCRIPTION "PDU 1 KVA A"
		::= { analog_values 105 }

PDU_1_KVA_A_Alarm OBJECT-TYPE
	SYNTAX  AnalogAlarm
	ACCESS  read-only
	STATUS  mandatory
	DESCRIPTION "PDU 1 KVA A Alarm"
		::= { analog_alarms 105 }

PDU_1_KVA_B OBJECT-TYPE
	SYNTAX  INTEGER
	ACCESS  read-only
	STATUS  mandatory
	DESCRIPTION "PDU 1 KVA B"
		::= { analog_values 106 }

PDU_1_KVA_B_Alarm OBJECT-TYPE
	SYNTAX  AnalogAlarm
	ACCESS  read-only
	STATUS  mandatory
	DESCRIPTION "PDU 1 KVA B Alarm"
		::= { analog_alarms 106 }

PDU_1_KVA_C OBJECT-TYPE
	SYNTAX  INTEGER
	ACCESS  read-only
	STATUS  mandatory
	DESCRIPTION "PDU 1 KVA C"
		::= { analog_values 107 }

PDU_1_KVA_C_Alarm OBJECT-TYPE
	SYNTAX  AnalogAlarm
	ACCESS  read-only
	STATUS  mandatory
	DESCRIPTION "PDU 1 KVA C Alarm"
		::= { analog_alarms 107 }

PDU_1_Total_KVA OBJECT-TYPE
	SYNTAX  INTEGER
	ACCESS  read-only
	STATUS  mandatory
	DESCRIPTION "PDU 1 Total KVA"
		::= { analog_values 108 }

PDU_1_Total_KVA_Alarm OBJECT-TYPE
	SYNTAX  AnalogAlarm
	ACCESS  read-only
	STATUS  mandatory
	DESCRIPTION "PDU 1 Total KVA Alarm"
		::= {analog_alarms 108 }

PDU_1_Peak_Total_KVA OBJECT-TYPE
	SYNTAX  INTEGER
	ACCESS  read-only
	STATUS  mandatory
	DESCRIPTION "PDU 1 Peak Total KVA"
		::= { analog_values 109 }

PDU_1_%KVA_A OBJECT-TYPE
	SYNTAX  INTEGER
	ACCESS  read-only
	STATUS  mandatory
	DESCRIPTION "PDU 1 %KVA A"
		::= { analog_values 110 }

PDU_1_%KVA_A_Alarm OBJECT-TYPE
	SYNTAX  AnalogAlarm
	ACCESS  read-only
	STATUS  mandatory
	DESCRIPTION "PDU 1 %KVA A Alarm"
		::= { analog_alarms 110 }

PDU_1_%KVA_B OBJECT-TYPE
	SYNTAX  INTEGER
	ACCESS  read-only
	STATUS  mandatory
	DESCRIPTION "PDU 1 %KVA B"
		::= { analog_values 111 }

PDU_1_%KVA_B_Alarm OBJECT-TYPE
	SYNTAX  AnalogAlarm
	ACCESS  read-only
	STATUS  mandatory
	DESCRIPTION "PDU 1 %KVA A Alarm"
		::= { analog_alarms 111 }

PDU_1_%KVA_C OBJECT-TYPE
	SYNTAX  INTEGER
	ACCESS  read-only
	STATUS  mandatory
	DESCRIPTION "PDU 1 %KVA C"
		::= { analog_values 112 }

PDU_1_%KVA_C_Alarm OBJECT-TYPE
	SYNTAX  AnalogAlarm
	ACCESS  read-only
	STATUS  mandatory
	DESCRIPTION "PDU 1 %KVA C Alarm"
		::= { analog_alarms 112 }

PDU_1_Total_%KVA OBJECT-TYPE
	SYNTAX  INTEGER
	ACCESS  read-only
	STATUS  mandatory
	DESCRIPTION "PDU 1 Total %KVA"
		::= { analog_values 113 }

PDU_1_Total_%KVA_Alarm OBJECT-TYPE
	SYNTAX  AnalogAlarm
	ACCESS  read-only
	STATUS  mandatory
	DESCRIPTION "PDU 1 Total %KVA Alarm"
		::= { analog_alarms 113 }

PDU_1_KW_A OBJECT-TYPE
	SYNTAX  INTEGER
	ACCESS  read-only
	STATUS  mandatory
	DESCRIPTION "PDU 1 KW A"
		::= { analog_values 114 }

PDU_1_KW_A_Alarm OBJECT-TYPE
	SYNTAX  AnalogAlarm
	ACCESS  read-only
	STATUS  mandatory
	DESCRIPTION "PDU 1 KW A Alarm"
		::= { analog_alarms 114 }

PDU_1_KW_B OBJECT-TYPE
	SYNTAX  INTEGER
	ACCESS  read-only
	STATUS  mandatory
	DESCRIPTION "PDU 1 KW B"
		::= { analog_values 115 }

PDU_1_KW_B_Alarm OBJECT-TYPE
	SYNTAX  AnalogAlarm
	ACCESS  read-only
	STATUS  mandatory
	DESCRIPTION "PDU 1 KW B Alarm"
		::= { analog_alarms 115 }

PDU_1_KW_C OBJECT-TYPE
	SYNTAX  INTEGER
	ACCESS  read-only
	STATUS  mandatory
	DESCRIPTION "PDU 1 KW C"
		::= { analog_values 116 }

PDU_1_KW_C_Alarm OBJECT-TYPE
	SYNTAX  AnalogAlarm
	ACCESS  read-only
	STATUS  mandatory
	DESCRIPTION "PDU 1 KW C Alarm"
		::= { analog_alarms 116 }

PDU_1_Total_KW OBJECT-TYPE
	SYNTAX  INTEGER
	ACCESS  read-only
	STATUS  mandatory
	DESCRIPTION "PDU 1 Total KW"
		::= { analog_values 117 }

PDU_1_Total_KW_Alarm OBJECT-TYPE
	SYNTAX  AnalogAlarm
	ACCESS  read-only
	STATUS  mandatory
	DESCRIPTION "PDU 1 Total KW Alarm"
		::= { analog_alarms 117 }

PDU_1_PF_A OBJECT-TYPE
	SYNTAX  AnalogHundredths
	ACCESS  read-only
	STATUS  mandatory
	DESCRIPTION "PDU 1 PF A"
		::= { analog_values 118 }

PDU_1_PF_A_Alarm OBJECT-TYPE
	SYNTAX  AnalogAlarm
	ACCESS  read-only
	STATUS  mandatory
	DESCRIPTION "PDU 1 PF A Alarm"
		::= { analog_alarms 118 }

PDU_1_PF_B OBJECT-TYPE
	SYNTAX  AnalogHundredths
	ACCESS  read-only
	STATUS  mandatory
	DESCRIPTION "PDU 1 PF B"
		::= { analog_values 119 }

PDU_1_PF_B_Alarm OBJECT-TYPE
	SYNTAX  AnalogAlarm
	ACCESS  read-only
	STATUS  mandatory
	DESCRIPTION "PDU 1 PF B Alarm"
		::= { analog_alarms 119 }

PDU_1_PF_C OBJECT-TYPE
	SYNTAX  AnalogHundredths
	ACCESS  read-only
	STATUS  mandatory
	DESCRIPTION "PDU 1 PF C"
		::= { analog_values 120 }

PDU_1_PF_C_Alarm OBJECT-TYPE
	SYNTAX  AnalogAlarm
	ACCESS  read-only
	STATUS  mandatory
	DESCRIPTION "PDU 1 PF C Alarm"
		::= { analog_alarms 120 }

PDU_2_Volts_AB OBJECT-TYPE
	SYNTAX  INTEGER
	ACCESS  read-only
	STATUS  mandatory
	DESCRIPTION "PDU 2 Volts AB"
		::= { analog_values 121 }

PDU_2_Volts_AB_Alarm OBJECT-TYPE
	SYNTAX  AnalogAlarm
	ACCESS  read-only
	STATUS  mandatory
	DESCRIPTION "PDU 2 Volts AB Alarm"
		::= { analog_alarms 121 }

PDU_2_Volts_BC OBJECT-TYPE
	SYNTAX  INTEGER
	ACCESS  read-only
	STATUS  mandatory
	DESCRIPTION "PDU 2 Volts BC"
		::= { analog_values 122 }

PDU_2_Volts_BC_Alarm OBJECT-TYPE
	SYNTAX  AnalogAlarm
	ACCESS  read-only
	STATUS  mandatory
	DESCRIPTION "PDU 2 Volts BC Alarm"
		::= { analog_alarms 122 }

PDU_2_Volts_CA OBJECT-TYPE
	SYNTAX  INTEGER
	ACCESS  read-only
	STATUS  mandatory
	DESCRIPTION "PDU 2 Volts CA"
		::= { analog_values 123 }

PDU_2_Volts_CA_Alarm OBJECT-TYPE
	SYNTAX  AnalogAlarm
	ACCESS  read-only
	STATUS  mandatory
	DESCRIPTION "PDU 2 Volts CA Alarm"
		::= { analog_alarms 123 }

PDU_2_Volts_AN OBJECT-TYPE
	SYNTAX  INTEGER
	ACCESS  read-only
	STATUS  mandatory
	DESCRIPTION "PDU 2 Volts AN"
		::= { analog_values 124 }

PDU_2_Volts_AN_Alarm OBJECT-TYPE
	SYNTAX  AnalogAlarm
	ACCESS  read-only
	STATUS  mandatory
	DESCRIPTION "PDU 2 Volts AN Alarm"
		::= { analog_alarms 124 }

PDU_2_Volts_BN OBJECT-TYPE
	SYNTAX  INTEGER
	ACCESS  read-only
	STATUS  mandatory
	DESCRIPTION "PDU 2 Volts BN"
		::= { analog_values 125 }

PDU_2_Volts_BN_Alarm OBJECT-TYPE
	SYNTAX  AnalogAlarm
	ACCESS  read-only
	STATUS  mandatory
	DESCRIPTION "PDU 2 Volts BN Alarm"
		::= { analog_alarms 125 }

PDU_2_Volts_CN OBJECT-TYPE
	SYNTAX  INTEGER
	ACCESS  read-only
	STATUS  mandatory
	DESCRIPTION "PDU 2 Volts CN"
		::= { analog_values 126 }

PDU_2_Volts_CN_Alarm OBJECT-TYPE
	SYNTAX  AnalogAlarm
	ACCESS  read-only
	STATUS  mandatory
	DESCRIPTION "PDU 2 Volts CN Alarm"
		::= { analog_alarms 126 }

PDU_2_Amps_A OBJECT-TYPE
	SYNTAX  INTEGER
	ACCESS  read-only
	STATUS  mandatory
	DESCRIPTION "PDU 2 Amps A"
		::= { analog_values 127 }

PDU_2_Amps_A_Alarm OBJECT-TYPE
	SYNTAX  AnalogAlarm
	ACCESS  read-only
	STATUS  mandatory
	DESCRIPTION "PDU 2 Amps A Alarm"
		::= { analog_alarms 127 }

PDU_2_Amps_B OBJECT-TYPE
	SYNTAX  INTEGER
	ACCESS  read-only
	STATUS  mandatory
	DESCRIPTION "PDU 2 Amps B"
		::= { analog_values 128 }

PDU_2_Amps_B_Alarm OBJECT-TYPE
	SYNTAX  AnalogAlarm
	ACCESS  read-only
	STATUS  mandatory
	DESCRIPTION "PDU 2 Amps B Alarm"
		::= { analog_alarms 128 }


PDU_2_Amps_C OBJECT-TYPE
	SYNTAX  INTEGER
	ACCESS  read-only
	STATUS  mandatory
	DESCRIPTION "PDU 2 Amps C"
		::= { analog_values 129 }

PDU_2_Amps_C_Alarm OBJECT-TYPE
	SYNTAX  AnalogAlarm
	ACCESS  read-only
	STATUS  mandatory
	DESCRIPTION "PDU 2 Amps C Alarm"
		::= { analog_alarms 129 }

PDU_2_KVA_A OBJECT-TYPE
	SYNTAX  INTEGER
	ACCESS  read-only
	STATUS  mandatory
	DESCRIPTION "PDU 2 KVA A"
		::= { analog_values 130 }

PDU_2_KVA_A_Alarm OBJECT-TYPE
	SYNTAX  AnalogAlarm
	ACCESS  read-only
	STATUS  mandatory
	DESCRIPTION "PDU 2 KVA A Alarm"
		::= { analog_alarms 130 }

PDU_2_KVA_B OBJECT-TYPE
	SYNTAX  INTEGER
	ACCESS  read-only
	STATUS  mandatory
	DESCRIPTION "PDU 2 KVA B"
		::= { analog_values 131 }

PDU_2_KVA_B_Alarm OBJECT-TYPE
	SYNTAX  AnalogAlarm
	ACCESS  read-only
	STATUS  mandatory
	DESCRIPTION "PDU 2 KVA B Alarm"
		::= { analog_alarms 131 }

PDU_2_KVA_C OBJECT-TYPE
	SYNTAX  INTEGER
	ACCESS  read-only
	STATUS  mandatory
	DESCRIPTION "PDU 2 KVA C"
		::= { analog_values 132 }

PDU_2_KVA_C_Alarm OBJECT-TYPE
	SYNTAX  AnalogAlarm
	ACCESS  read-only
	STATUS  mandatory
	DESCRIPTION "PDU 2 KVA C Alarm"
		::= { analog_alarms 132 }

PDU_2_Total_KVA OBJECT-TYPE
	SYNTAX  INTEGER
	ACCESS  read-only
	STATUS  mandatory
	DESCRIPTION "PDU 2 Total KVA"
		::= { analog_values 133 }

PDU_2_Total_KVA_Alarm OBJECT-TYPE
	SYNTAX  AnalogAlarm
	ACCESS  read-only
	STATUS  mandatory
	DESCRIPTION "PDU 2 Total KVA Alarm"
		::= {analog_alarms 133 }

PDU_2_Peak_Total_KVA OBJECT-TYPE
	SYNTAX  INTEGER
	ACCESS  read-only
	STATUS  mandatory
	DESCRIPTION "PDU 2 Peak Total KVA"
		::= { analog_values 134 }

PDU_2_%KVA_A OBJECT-TYPE
	SYNTAX  INTEGER
	ACCESS  read-only
	STATUS  mandatory
	DESCRIPTION "PDU 2 %KVA A"
		::= { analog_values 135 }

PDU_2_%KVA_A_Alarm OBJECT-TYPE
	SYNTAX  AnalogAlarm
	ACCESS  read-only
	STATUS  mandatory
	DESCRIPTION "PDU 2 %KVA A Alarm"
		::= { analog_alarms 135 }

PDU_2_%KVA_B OBJECT-TYPE
	SYNTAX  INTEGER
	ACCESS  read-only
	STATUS  mandatory
	DESCRIPTION "PDU 2 %KVA B"
		::= { analog_values 136 }

PDU_2_%KVA_B_Alarm OBJECT-TYPE
	SYNTAX  AnalogAlarm
	ACCESS  read-only
	STATUS  mandatory
	DESCRIPTION "PDU 2 %KVA A Alarm"
		::= { analog_alarms 136 }

PDU_2_%KVA_C OBJECT-TYPE
	SYNTAX  INTEGER
	ACCESS  read-only
	STATUS  mandatory
	DESCRIPTION "PDU 2 %KVA C"
		::= { analog_values 137 }

PDU_2_%KVA_C_Alarm OBJECT-TYPE
	SYNTAX  AnalogAlarm
	ACCESS  read-only
	STATUS  mandatory
	DESCRIPTION "PDU 2 %KVA C Alarm"
		::= { analog_alarms 137 }

PDU_2_Total_%KVA OBJECT-TYPE
	SYNTAX  INTEGER
	ACCESS  read-only
	STATUS  mandatory
	DESCRIPTION "PDU 2 Total %KVA"
		::= { analog_values 138 }

PDU_2_Total_%KVA_Alarm OBJECT-TYPE
	SYNTAX  AnalogAlarm
	ACCESS  read-only
	STATUS  mandatory
	DESCRIPTION "PDU 2 Total %KVA Alarm"
		::= { analog_alarms 138 }

PDU_2_KW_A OBJECT-TYPE
	SYNTAX  INTEGER
	ACCESS  read-only
	STATUS  mandatory
	DESCRIPTION "PDU 2 KW A"
		::= { analog_values 139 }

PDU_2_KW_A_Alarm OBJECT-TYPE
	SYNTAX  AnalogAlarm
	ACCESS  read-only
	STATUS  mandatory
	DESCRIPTION "PDU 2 KW A Alarm"
		::= { analog_alarms 139 }

PDU_2_KW_B OBJECT-TYPE
	SYNTAX  INTEGER
	ACCESS  read-only
	STATUS  mandatory
	DESCRIPTION "PDU 2 KW B"
		::= { analog_values 140 }

PDU_2_KW_B_Alarm OBJECT-TYPE
	SYNTAX  AnalogAlarm
	ACCESS  read-only
	STATUS  mandatory
	DESCRIPTION "PDU 2 KW B Alarm"
		::= { analog_alarms 140 }

PDU_2_KW_C OBJECT-TYPE
	SYNTAX  INTEGER
	ACCESS  read-only
	STATUS  mandatory
	DESCRIPTION "PDU 2 KW C"
		::= { analog_values 141 }

PDU_2_KW_C_Alarm OBJECT-TYPE
	SYNTAX  AnalogAlarm
	ACCESS  read-only
	STATUS  mandatory
	DESCRIPTION "PDU 2 KW C Alarm"
		::= { analog_alarms 141 }

PDU_2_Total_KW OBJECT-TYPE
	SYNTAX  INTEGER
	ACCESS  read-only
	STATUS  mandatory
	DESCRIPTION "PDU 2 Total KW"
		::= { analog_values 142 }

PDU_2_Total_KW_Alarm OBJECT-TYPE
	SYNTAX  AnalogAlarm
	ACCESS  read-only
	STATUS  mandatory
	DESCRIPTION "PDU 2 Total KW Alarm"
		::= { analog_alarms 142 }

PDU_2_PF_A OBJECT-TYPE
	SYNTAX  AnalogHundredths
	ACCESS  read-only
	STATUS  mandatory
	DESCRIPTION "PDU 2 PF A"
		::= { analog_values 143 }

PDU_2_PF_A_Alarm OBJECT-TYPE
	SYNTAX  AnalogAlarm
	ACCESS  read-only
	STATUS  mandatory
	DESCRIPTION "PDU 2 PF A Alarm"
		::= { analog_alarms 143 }

PDU_2_PF_B OBJECT-TYPE
	SYNTAX  AnalogHundredths
	ACCESS  read-only
	STATUS  mandatory
	DESCRIPTION "PDU 2 PF B"
		::= { analog_values 144 }

PDU_2_PF_B_Alarm OBJECT-TYPE
	SYNTAX  AnalogAlarm
	ACCESS  read-only
	STATUS  mandatory
	DESCRIPTION "PDU 2 PF B Alarm"
		::= { analog_alarms 144 }

PDU_2_PF_C OBJECT-TYPE
	SYNTAX  AnalogHundredths
	ACCESS  read-only
	STATUS  mandatory
	DESCRIPTION "PDU 2 PF C"
		::= { analog_values 145 }

PDU_2_PF_C_Alarm OBJECT-TYPE
	SYNTAX  AnalogAlarm
	ACCESS  read-only
	STATUS  mandatory
	DESCRIPTION "PDU 2 PF C Alarm"
		::= { analog_alarms 145 }

I_Line_1_Volts_AB OBJECT-TYPE
	SYNTAX  INTEGER
	ACCESS  read-only
	STATUS  mandatory
	DESCRIPTION "I Line 1 Volts AB"
		::= { analog_values 146 }

I_Line_1_Volts_AB_Alarm OBJECT-TYPE
	SYNTAX  AnalogAlarm
	ACCESS  read-only
	STATUS  mandatory
	DESCRIPTION "I Line 1 Volts AB Alarm"
		::= { analog_alarms 146 }

I_Line_1_Volts_BC OBJECT-TYPE
	SYNTAX  INTEGER
	ACCESS  read-only
	STATUS  mandatory
	DESCRIPTION "I Line 1 Volts BC"
		::= { analog_values 147 }

I_Line_1_Volts_BC_Alarm OBJECT-TYPE
	SYNTAX  AnalogAlarm
	ACCESS  read-only
	STATUS  mandatory
	DESCRIPTION "I Line 1 Volts BC Alarm"
		::= { analog_alarms 147 }

I_Line_1_Volts_CA OBJECT-TYPE
	SYNTAX  INTEGER
	ACCESS  read-only
	STATUS  mandatory
	DESCRIPTION "I Line 1 Volts CA"
		::= { analog_values 148 }

I_Line_1_Volts_CA_Alarm OBJECT-TYPE
	SYNTAX  AnalogAlarm
	ACCESS  read-only
	STATUS  mandatory
	DESCRIPTION "I Line 1 Volts CA Alarm"
		::= { analog_alarms 148 }

I_Line_1_Volts_AN OBJECT-TYPE
	SYNTAX  INTEGER
	ACCESS  read-only
	STATUS  mandatory
	DESCRIPTION "I Line 1 Volts AN"
		::= { analog_values 149 }

I_Line_1_Volts_AN_Alarm OBJECT-TYPE
	SYNTAX  AnalogAlarm
	ACCESS  read-only
	STATUS  mandatory
	DESCRIPTION "I Line 1 Volts AN Alarm"
		::= { analog_alarms 149 }

I_Line_1_Volts_BN OBJECT-TYPE
	SYNTAX  INTEGER
	ACCESS  read-only
	STATUS  mandatory
	DESCRIPTION "I Line 1 Volts BN"
		::= { analog_values 150 }

I_Line_1_Volts_BN_Alarm OBJECT-TYPE
	SYNTAX  AnalogAlarm
	ACCESS  read-only
	STATUS  mandatory
	DESCRIPTION "I Line 1 Volts BN Alarm"
		::= { analog_alarms 150 }

I_Line_1_Volts_CN OBJECT-TYPE
	SYNTAX  INTEGER
	ACCESS  read-only
	STATUS  mandatory
	DESCRIPTION "I Line 1 Volts CN"
		::= { analog_values 151 }

I_Line_1_Volts_CN_Alarm OBJECT-TYPE
	SYNTAX  AnalogAlarm
	ACCESS  read-only
	STATUS  mandatory
	DESCRIPTION "I Line 1 Volts CN Alarm"
		::= { analog_alarms 151 }

I_Line_1_Amps_A OBJECT-TYPE
	SYNTAX  INTEGER
	ACCESS  read-only
	STATUS  mandatory
	DESCRIPTION "I Line 1 Amps A"
		::= { analog_values 152 }

I_Line_1_Amps_A_Alarm OBJECT-TYPE
	SYNTAX  AnalogAlarm
	ACCESS  read-only
	STATUS  mandatory
	DESCRIPTION "I Line 1 Amps A Alarm"
		::= { analog_alarms 152 }

I_Line_1_Amps_B OBJECT-TYPE
	SYNTAX  INTEGER
	ACCESS  read-only
	STATUS  mandatory
	DESCRIPTION "I Line 1 Amps B"
		::= { analog_values 153 }

I_Line_1_Amps_B_Alarm OBJECT-TYPE
	SYNTAX  AnalogAlarm
	ACCESS  read-only
	STATUS  mandatory
	DESCRIPTION "I Line 1 Amps B Alarm"
		::= { analog_alarms 153 }

I_Line_1_Amps_C OBJECT-TYPE
	SYNTAX  INTEGER
	ACCESS  read-only
	STATUS  mandatory
	DESCRIPTION "I Line 1 Amps C"
		::= { analog_values 154 }

I_Line_1_Amps_C_Alarm OBJECT-TYPE
	SYNTAX  AnalogAlarm
	ACCESS  read-only
	STATUS  mandatory
	DESCRIPTION "I Line 1 Amps C Alarm"
		::= { analog_alarms 154 }

I_Line_1_KVA_A OBJECT-TYPE
	SYNTAX  INTEGER
	ACCESS  read-only
	STATUS  mandatory
	DESCRIPTION "I Line 1 KVA A"
		::= { analog_values 155 }

I_Line_1_KVA_A_Alarm OBJECT-TYPE
	SYNTAX  AnalogAlarm
	ACCESS  read-only
	STATUS  mandatory
	DESCRIPTION "I Line 1 KVA A Alarm"
		::= { analog_alarms 155 }

I_Line_1_KVA_B OBJECT-TYPE
	SYNTAX  INTEGER
	ACCESS  read-only
	STATUS  mandatory
	DESCRIPTION "I Line 1 KVA B"
		::= { analog_values 156 }

I_Line_1_KVA_B_Alarm OBJECT-TYPE
	SYNTAX  AnalogAlarm
	ACCESS  read-only
	STATUS  mandatory
	DESCRIPTION "I Line 1 KVA B Alarm"
		::= { analog_alarms 156 }

I_Line_1_KVA_C OBJECT-TYPE
	SYNTAX  INTEGER
	ACCESS  read-only
	STATUS  mandatory
	DESCRIPTION "I Line 1 KVA C"
		::= { analog_values 157 }

I_Line_1_KVA_C_Alarm OBJECT-TYPE
	SYNTAX  AnalogAlarm
	ACCESS  read-only
	STATUS  mandatory
	DESCRIPTION "I Line 1 KVA C Alarm"
		::= { analog_alarms 157 }

I_Line_1_Total_KVA OBJECT-TYPE
	SYNTAX  INTEGER
	ACCESS  read-only
	STATUS  mandatory
	DESCRIPTION "I Line 1 Total KVA"
		::= { analog_values 158 }

I_Line_1_Total_KVA_Alarm OBJECT-TYPE
	SYNTAX  AnalogAlarm
	ACCESS  read-only
	STATUS  mandatory
	DESCRIPTION "I Line 1 Total KVA Alarm"
		::= { analog_alarms 158 }

I_Line_1_Total_%KVA OBJECT-TYPE
	SYNTAX  INTEGER
	ACCESS  read-only
	STATUS  mandatory
	DESCRIPTION "I Line 1 Total %KVA"
		::= { analog_values 159 }

I_Line_1_Total_%KVA_Alarm OBJECT-TYPE
	SYNTAX  AnalogAlarm
	ACCESS  read-only
	STATUS  mandatory
	DESCRIPTION "I Line 1 Total %KVA Alarm"
		::= { analog_alarms 159 }

I_Line_1_KW_A OBJECT-TYPE
	SYNTAX  INTEGER
	ACCESS  read-only
	STATUS  mandatory
	DESCRIPTION "I Line 1 KW A"
		::= { analog_values 160 }

I_Line_1_KW_A_Alarm OBJECT-TYPE
	SYNTAX  AnalogAlarm
	ACCESS  read-only
	STATUS  mandatory
	DESCRIPTION "I Line 1 KW A Alarm"
		::= { analog_alarms 160 }

I_Line_1_KW_B OBJECT-TYPE
	SYNTAX  INTEGER
	ACCESS  read-only
	STATUS  mandatory
	DESCRIPTION "I Line 1 KW B"
		::= { analog_values 161 }

I_Line_1_KW_B_Alarm OBJECT-TYPE
	SYNTAX  AnalogAlarm
	ACCESS  read-only
	STATUS  mandatory
	DESCRIPTION "I Line 1 KW B Alarm"
		::= { analog_alarms 161 }

I_Line_1_KW_C OBJECT-TYPE
	SYNTAX  INTEGER
	ACCESS  read-only
	STATUS  mandatory
	DESCRIPTION "I Line 1 KW C"
		::= { analog_values 162 }

I_Line_1_KW_C_Alarm OBJECT-TYPE
	SYNTAX  AnalogAlarm
	ACCESS  read-only
	STATUS  mandatory
	DESCRIPTION "I Line 1 KW C Alarm"
		::= { analog_alarms 162 }

I_Line_1_Total_KW OBJECT-TYPE
	SYNTAX  INTEGER
	ACCESS  read-only
	STATUS  mandatory
	DESCRIPTION "I Line 1 Total KW"
		::= { analog_values 163 }

I_Line_1_Total_KW_Alarm OBJECT-TYPE
	SYNTAX  AnalogAlarm
	ACCESS  read-only
	STATUS  mandatory
	DESCRIPTION "I Line 1 Total KW Alarm"
		::= { analog_alarms 163 }

I_Line_1_PF_A OBJECT-TYPE
	SYNTAX  AnalogHundredths
	ACCESS  read-only
	STATUS  mandatory
	DESCRIPTION "I Line 1 PF A"
		::= { analog_values 164 }

I_Line_1_PF_A_Alarm OBJECT-TYPE
	SYNTAX  AnalogAlarm
	ACCESS  read-only
	STATUS  mandatory
	DESCRIPTION "I Line 1 PF A Alarm"
		::= { analog_alarms 164 }

I_Line_1_PF_B OBJECT-TYPE
	SYNTAX  AnalogHundredths
	ACCESS  read-only
	STATUS  mandatory
	DESCRIPTION "I Line 1 PF B"
		::= { analog_values 165 }

I_Line_1_PF_B_Alarm OBJECT-TYPE
	SYNTAX  AnalogAlarm
	ACCESS  read-only
	STATUS  mandatory
	DESCRIPTION "I Line 1 PF B Alarm"
		::= { analog_alarms 165 }

I_Line_1_PF_C OBJECT-TYPE
	SYNTAX  AnalogHundredths
	ACCESS  read-only
	STATUS  mandatory
	DESCRIPTION "I Line 1 PF C"
		::= { analog_values 166 }

I_Line_1_PF_C_Alarm OBJECT-TYPE
	SYNTAX  AnalogAlarm
	ACCESS  read-only
	STATUS  mandatory
	DESCRIPTION "I Line 1 PF C Alarm"
		::= { analog_alarms 166 }

I_Line_2_Volts_AB OBJECT-TYPE
	SYNTAX  INTEGER
	ACCESS  read-only
	STATUS  mandatory
	DESCRIPTION "I Line 2 Volts AB"
		::= { analog_values 167 }

I_Line_2_Volts_AB_Alarm OBJECT-TYPE
	SYNTAX  AnalogAlarm
	ACCESS  read-only
	STATUS  mandatory
	DESCRIPTION "I Line 2 Volts AB Alarm"
		::= { analog_alarms 167 }

I_Line_2_Volts_BC OBJECT-TYPE
	SYNTAX  INTEGER
	ACCESS  read-only
	STATUS  mandatory
	DESCRIPTION "I Line 2 Volts BC"
		::= { analog_values 168 }

I_Line_2_Volts_BC_Alarm OBJECT-TYPE
	SYNTAX  AnalogAlarm
	ACCESS  read-only
	STATUS  mandatory
	DESCRIPTION "I Line 2 Volts BC Alarm"
		::= { analog_alarms 168 }

I_Line_2_Volts_CA OBJECT-TYPE
	SYNTAX  INTEGER
	ACCESS  read-only
	STATUS  mandatory
	DESCRIPTION "I Line 2 Volts CA"
		::= { analog_values 169 }

I_Line_2_Volts_CA_Alarm OBJECT-TYPE
	SYNTAX  AnalogAlarm
	ACCESS  read-only
	STATUS  mandatory
	DESCRIPTION "I Line 2 Volts CA Alarm"
		::= { analog_alarms 169 }

I_Line_2_Volts_AN OBJECT-TYPE
	SYNTAX  INTEGER
	ACCESS  read-only
	STATUS  mandatory
	DESCRIPTION "I Line 2 Volts AN"
		::= { analog_values 170 }

I_Line_2_Volts_AN_Alarm OBJECT-TYPE
	SYNTAX  AnalogAlarm
	ACCESS  read-only
	STATUS  mandatory
	DESCRIPTION "I Line 2 Volts AN Alarm"
		::= { analog_alarms 170 }

I_Line_2_Volts_BN OBJECT-TYPE
	SYNTAX  INTEGER
	ACCESS  read-only
	STATUS  mandatory
	DESCRIPTION "I Line 2 Volts BN"
		::= { analog_values 171 }

I_Line_2_Volts_BN_Alarm OBJECT-TYPE
	SYNTAX  AnalogAlarm
	ACCESS  read-only
	STATUS  mandatory
	DESCRIPTION "I Line 2 Volts BN Alarm"
		::= { analog_alarms 171 }

I_Line_2_Volts_CN OBJECT-TYPE
	SYNTAX  INTEGER
	ACCESS  read-only
	STATUS  mandatory
	DESCRIPTION "I Line 2 Volts CN"
		::= { analog_values 172 }

I_Line_2_Volts_CN_Alarm OBJECT-TYPE
	SYNTAX  AnalogAlarm
	ACCESS  read-only
	STATUS  mandatory
	DESCRIPTION "I Line 2 Volts CN Alarm"
		::= { analog_alarms 172 }

I_Line_2_Amps_A OBJECT-TYPE
	SYNTAX  INTEGER
	ACCESS  read-only
	STATUS  mandatory
	DESCRIPTION "I Line 2 Amps A"
		::= { analog_values 173 }

I_Line_2_Amps_A_Alarm OBJECT-TYPE
	SYNTAX  AnalogAlarm
	ACCESS  read-only
	STATUS  mandatory
	DESCRIPTION "I Line 2 Amps A Alarm"
		::= { analog_alarms 173 }

I_Line_2_Amps_B OBJECT-TYPE
	SYNTAX  INTEGER
	ACCESS  read-only
	STATUS  mandatory
	DESCRIPTION "I Line 2 Amps B"
		::= { analog_values 174 }

I_Line_2_Amps_B_Alarm OBJECT-TYPE
	SYNTAX  AnalogAlarm
	ACCESS  read-only
	STATUS  mandatory
	DESCRIPTION "I Line 2 Amps B Alarm"
		::= { analog_alarms 174 }

I_Line_2_Amps_C OBJECT-TYPE
	SYNTAX  INTEGER
	ACCESS  read-only
	STATUS  mandatory
	DESCRIPTION "I Line 2 Amps C"
		::= { analog_values 175 }

I_Line_2_Amps_C_Alarm OBJECT-TYPE
	SYNTAX  AnalogAlarm
	ACCESS  read-only
	STATUS  mandatory
	DESCRIPTION "I Line 2 Amps C Alarm"
		::= { analog_alarms 175 }

I_Line_2_KVA_A OBJECT-TYPE
	SYNTAX  INTEGER
	ACCESS  read-only
	STATUS  mandatory
	DESCRIPTION "I Line 2 KVA A"
		::= { analog_values 176 }

I_Line_2_KVA_A_Alarm OBJECT-TYPE
	SYNTAX  AnalogAlarm
	ACCESS  read-only
	STATUS  mandatory
	DESCRIPTION "I Line 2 KVA A Alarm"
		::= { analog_alarms 176 }

I_Line_2_KVA_B OBJECT-TYPE
	SYNTAX  INTEGER
	ACCESS  read-only
	STATUS  mandatory
	DESCRIPTION "I Line 2 KVA B"
		::= { analog_values 177 }

I_Line_2_KVA_B_Alarm OBJECT-TYPE
	SYNTAX  AnalogAlarm
	ACCESS  read-only
	STATUS  mandatory
	DESCRIPTION "I Line 2 KVA B Alarm"
		::= { analog_alarms 177 }

I_Line_2_KVA_C OBJECT-TYPE
	SYNTAX  INTEGER
	ACCESS  read-only
	STATUS  mandatory
	DESCRIPTION "I Line 2 KVA C"
		::= { analog_values 178 }

I_Line_2_KVA_C_Alarm OBJECT-TYPE
	SYNTAX  AnalogAlarm
	ACCESS  read-only
	STATUS  mandatory
	DESCRIPTION "I Line 2 KVA C Alarm"
		::= { analog_alarms 178 }

I_Line_2_Total_KVA OBJECT-TYPE
	SYNTAX  INTEGER
	ACCESS  read-only
	STATUS  mandatory
	DESCRIPTION "I Line 2 Total KVA"
		::= { analog_values 179 }

I_Line_2_Total_KVA_Alarm OBJECT-TYPE
	SYNTAX  AnalogAlarm
	ACCESS  read-only
	STATUS  mandatory
	DESCRIPTION "I Line 2 Total KVA Alarm"
		::= { analog_alarms 179 }

I_Line_2_Total_%KVA OBJECT-TYPE
	SYNTAX  INTEGER
	ACCESS  read-only
	STATUS  mandatory
	DESCRIPTION "I Line 2 Total %KVA"
		::= { analog_values 180 }

I_Line_2_Total_%KVA_Alarm OBJECT-TYPE
	SYNTAX  AnalogAlarm
	ACCESS  read-only
	STATUS  mandatory
	DESCRIPTION "I Line 2 Total %KVA Alarm"
		::= { analog_alarms 180 }

I_Line_2_KW_A OBJECT-TYPE
	SYNTAX  INTEGER
	ACCESS  read-only
	STATUS  mandatory
	DESCRIPTION "I Line 2 KW A"
		::= { analog_values 181 }

I_Line_2_KW_A_Alarm OBJECT-TYPE
	SYNTAX  AnalogAlarm
	ACCESS  read-only
	STATUS  mandatory
	DESCRIPTION "I Line 2 KW A Alarm"
		::= { analog_alarms 181 }

I_Line_2_KW_B OBJECT-TYPE
	SYNTAX  INTEGER
	ACCESS  read-only
	STATUS  mandatory
	DESCRIPTION "I Line 2 KW B"
		::= { analog_values 182 }

I_Line_2_KW_B_Alarm OBJECT-TYPE
	SYNTAX  AnalogAlarm
	ACCESS  read-only
	STATUS  mandatory
	DESCRIPTION "I Line 2 KW B Alarm"
		::= { analog_alarms 182 }

I_Line_2_KW_C OBJECT-TYPE
	SYNTAX  INTEGER
	ACCESS  read-only
	STATUS  mandatory
	DESCRIPTION "I Line 2 KW C"
		::= { analog_values 183 }

I_Line_2_KW_C_Alarm OBJECT-TYPE
	SYNTAX  AnalogAlarm
	ACCESS  read-only
	STATUS  mandatory
	DESCRIPTION "I Line 2 KW C Alarm"
		::= { analog_alarms 183 }

I_Line_2_Total_KW OBJECT-TYPE
	SYNTAX  INTEGER
	ACCESS  read-only
	STATUS  mandatory
	DESCRIPTION "I Line 2 Total KW"
		::= { analog_values 184 }

I_Line_2_Total_KW_Alarm OBJECT-TYPE
	SYNTAX  AnalogAlarm
	ACCESS  read-only
	STATUS  mandatory
	DESCRIPTION "I Line 2 Total KW Alarm"
		::= { analog_alarms 184 }

I_Line_2_PF_A OBJECT-TYPE
	SYNTAX  AnalogHundredths
	ACCESS  read-only
	STATUS  mandatory
	DESCRIPTION "I Line 2 PF A"
		::= { analog_values 185 }

I_Line_2_PF_A_Alarm OBJECT-TYPE
	SYNTAX  AnalogAlarm
	ACCESS  read-only
	STATUS  mandatory
	DESCRIPTION "I Line 2 PF A Alarm"
		::= { analog_alarms 185 }

I_Line_2_PF_B OBJECT-TYPE
	SYNTAX  AnalogHundredths
	ACCESS  read-only
	STATUS  mandatory
	DESCRIPTION "I Line 2 PF B"
		::= { analog_values 186 }

I_Line_2_PF_B_Alarm OBJECT-TYPE
	SYNTAX  AnalogAlarm
	ACCESS  read-only
	STATUS  mandatory
	DESCRIPTION "I Line 2 PF B Alarm"
		::= { analog_alarms 186 }

I_Line_2_PF_C OBJECT-TYPE
	SYNTAX  AnalogHundredths
	ACCESS  read-only
	STATUS  mandatory
	DESCRIPTION "I Line 2 PF C"
		::= { analog_values 187 }

I_Line_2_PF_C_Alarm OBJECT-TYPE
	SYNTAX  AnalogAlarm
	ACCESS  read-only
	STATUS  mandatory
	DESCRIPTION "I Line 2 PF C Alarm"
		::= { analog_alarms 187 }

I_Line_3_Volts_AB OBJECT-TYPE
	SYNTAX  INTEGER
	ACCESS  read-only
	STATUS  mandatory
	DESCRIPTION "I Line 3 Volts AB"
		::= { analog_values 188 }

I_Line_3_Volts_AB_Alarm OBJECT-TYPE
	SYNTAX  AnalogAlarm
	ACCESS  read-only
	STATUS  mandatory
	DESCRIPTION "I Line 3 Volts AB Alarm"
		::= { analog_alarms 188 }

I_Line_3_Volts_BC OBJECT-TYPE
	SYNTAX  INTEGER
	ACCESS  read-only
	STATUS  mandatory
	DESCRIPTION "I Line 3 Volts BC"
		::= { analog_values 189 }

I_Line_3_Volts_BC_Alarm OBJECT-TYPE
	SYNTAX  AnalogAlarm
	ACCESS  read-only
	STATUS  mandatory
	DESCRIPTION "I Line 3 Volts BC Alarm"
		::= { analog_alarms 189 }

I_Line_3_Volts_CA OBJECT-TYPE
	SYNTAX  INTEGER
	ACCESS  read-only
	STATUS  mandatory
	DESCRIPTION "I Line 3 Volts CA"
		::= { analog_values 190 }

I_Line_3_Volts_CA_Alarm OBJECT-TYPE
	SYNTAX  AnalogAlarm
	ACCESS  read-only
	STATUS  mandatory
	DESCRIPTION "I Line 3 Volts CA Alarm"
		::= { analog_alarms 190 }

I_Line_3_Volts_AN OBJECT-TYPE
	SYNTAX  INTEGER
	ACCESS  read-only
	STATUS  mandatory
	DESCRIPTION "I Line 3 Volts AN"
		::= { analog_values 191 }

I_Line_3_Volts_AN_Alarm OBJECT-TYPE
	SYNTAX  AnalogAlarm
	ACCESS  read-only
	STATUS  mandatory
	DESCRIPTION "I Line 3 Volts AN Alarm"
		::= { analog_alarms 191 }

I_Line_3_Volts_BN OBJECT-TYPE
	SYNTAX  INTEGER
	ACCESS  read-only
	STATUS  mandatory
	DESCRIPTION "I Line 3 Volts BN"
		::= { analog_values 192 }

I_Line_3_Volts_BN_Alarm OBJECT-TYPE
	SYNTAX  AnalogAlarm
	ACCESS  read-only
	STATUS  mandatory
	DESCRIPTION "I Line 3 Volts BN Alarm"
		::= { analog_alarms 192 }

I_Line_3_Volts_CN OBJECT-TYPE
	SYNTAX  INTEGER
	ACCESS  read-only
	STATUS  mandatory
	DESCRIPTION "I Line 3 Volts CN"
		::= { analog_values 193 }

I_Line_3_Volts_CN_Alarm OBJECT-TYPE
	SYNTAX  AnalogAlarm
	ACCESS  read-only
	STATUS  mandatory
	DESCRIPTION "I Line 3 Volts CN Alarm"
		::= { analog_alarms 193 }

I_Line_3_Amps_A OBJECT-TYPE
	SYNTAX  INTEGER
	ACCESS  read-only
	STATUS  mandatory
	DESCRIPTION "I Line 3 Amps A"
		::= { analog_values 194 }

I_Line_3_Amps_A_Alarm OBJECT-TYPE
	SYNTAX  AnalogAlarm
	ACCESS  read-only
	STATUS  mandatory
	DESCRIPTION "I Line 3 Amps A Alarm"
		::= { analog_alarms 194 }

I_Line_3_Amps_B OBJECT-TYPE
	SYNTAX  INTEGER
	ACCESS  read-only
	STATUS  mandatory
	DESCRIPTION "I Line 3 Amps B"
		::= { analog_values 195 }

I_Line_3_Amps_B_Alarm OBJECT-TYPE
	SYNTAX  AnalogAlarm
	ACCESS  read-only
	STATUS  mandatory
	DESCRIPTION "I Line 3 Amps B Alarm"
		::= { analog_alarms 195 }

I_Line_3_Amps_C OBJECT-TYPE
	SYNTAX  INTEGER
	ACCESS  read-only
	STATUS  mandatory
	DESCRIPTION "I Line 3 Amps C"
		::= { analog_values 196 }

I_Line_3_Amps_C_Alarm OBJECT-TYPE
	SYNTAX  AnalogAlarm
	ACCESS  read-only
	STATUS  mandatory
	DESCRIPTION "I Line 3 Amps C Alarm"
		::= { analog_alarms 196 }

I_Line_3_KVA_A OBJECT-TYPE
	SYNTAX  INTEGER
	ACCESS  read-only
	STATUS  mandatory
	DESCRIPTION "I Line 3 KVA A"
		::= { analog_values 197 }

I_Line_3_KVA_A_Alarm OBJECT-TYPE
	SYNTAX  AnalogAlarm
	ACCESS  read-only
	STATUS  mandatory
	DESCRIPTION "I Line 3 KVA A Alarm"
		::= { analog_alarms 197 }

I_Line_3_KVA_B OBJECT-TYPE
	SYNTAX  INTEGER
	ACCESS  read-only
	STATUS  mandatory
	DESCRIPTION "I Line 3 KVA B"
		::= { analog_values 198 }

I_Line_3_KVA_B_Alarm OBJECT-TYPE
	SYNTAX  AnalogAlarm
	ACCESS  read-only
	STATUS  mandatory
	DESCRIPTION "I Line 3 KVA B Alarm"
		::= { analog_alarms 198 }

I_Line_3_KVA_C OBJECT-TYPE
	SYNTAX  INTEGER
	ACCESS  read-only
	STATUS  mandatory
	DESCRIPTION "I Line 3 KVA C"
		::= { analog_values 199 }

I_Line_3_KVA_C_Alarm OBJECT-TYPE
	SYNTAX  AnalogAlarm
	ACCESS  read-only
	STATUS  mandatory
	DESCRIPTION "I Line 3 KVA C Alarm"
		::= { analog_alarms 199 }

I_Line_3_Total_KVA OBJECT-TYPE
	SYNTAX  INTEGER
	ACCESS  read-only
	STATUS  mandatory
	DESCRIPTION "I Line 3 Total KVA"
		::= { analog_values 200 }

I_Line_3_Total_KVA_Alarm OBJECT-TYPE
	SYNTAX  AnalogAlarm
	ACCESS  read-only
	STATUS  mandatory
	DESCRIPTION "I Line 3 Total KVA Alarm"
		::= { analog_alarms 200 }

I_Line_3_Total_%KVA OBJECT-TYPE
	SYNTAX  INTEGER
	ACCESS  read-only
	STATUS  mandatory
	DESCRIPTION "I Line 3 Total %KVA"
		::= { analog_values 201 }

I_Line_3_Total_%KVA_Alarm OBJECT-TYPE
	SYNTAX  AnalogAlarm
	ACCESS  read-only
	STATUS  mandatory
	DESCRIPTION "I Line 3 Total %KVA Alarm"
		::= { analog_alarms 201 }

I_Line_3_KW_A OBJECT-TYPE
	SYNTAX  INTEGER
	ACCESS  read-only
	STATUS  mandatory
	DESCRIPTION "I Line 3 KW A"
		::= { analog_values 202 }

I_Line_3_KW_A_Alarm OBJECT-TYPE
	SYNTAX  AnalogAlarm
	ACCESS  read-only
	STATUS  mandatory
	DESCRIPTION "I Line 3 KW A Alarm"
		::= { analog_alarms 202 }

I_Line_3_KW_B OBJECT-TYPE
	SYNTAX  INTEGER
	ACCESS  read-only
	STATUS  mandatory
	DESCRIPTION "I Line 3 KW B"
		::= { analog_values 203 }

I_Line_3_KW_B_Alarm OBJECT-TYPE
	SYNTAX  AnalogAlarm
	ACCESS  read-only
	STATUS  mandatory
	DESCRIPTION "I Line 3 KW B Alarm"
		::= { analog_alarms 203 }

I_Line_3_KW_C OBJECT-TYPE
	SYNTAX  INTEGER
	ACCESS  read-only
	STATUS  mandatory
	DESCRIPTION "I Line 3 KW C"
		::= { analog_values 204 }

I_Line_3_KW_C_Alarm OBJECT-TYPE
	SYNTAX  AnalogAlarm
	ACCESS  read-only
	STATUS  mandatory
	DESCRIPTION "I Line 3 KW C Alarm"
		::= { analog_alarms 204 }

I_Line_3_Total_KW OBJECT-TYPE
	SYNTAX  INTEGER
	ACCESS  read-only
	STATUS  mandatory
	DESCRIPTION "I Line 3 Total KW"
		::= { analog_values 205 }

I_Line_3_Total_KW_Alarm OBJECT-TYPE
	SYNTAX  AnalogAlarm
	ACCESS  read-only
	STATUS  mandatory
	DESCRIPTION "I Line 3 Total KW Alarm"
		::= { analog_alarms 205 }

I_Line_3_PF_A OBJECT-TYPE
	SYNTAX  AnalogHundredths
	ACCESS  read-only
	STATUS  mandatory
	DESCRIPTION "I Line 3 PF A"
		::= { analog_values 206 }

I_Line_3_PF_A_Alarm OBJECT-TYPE
	SYNTAX  AnalogAlarm
	ACCESS  read-only
	STATUS  mandatory
	DESCRIPTION "I Line 3 PF A Alarm"
		::= { analog_alarms 206 }

I_Line_3_PF_B OBJECT-TYPE
	SYNTAX  AnalogHundredths
	ACCESS  read-only
	STATUS  mandatory
	DESCRIPTION "I Line 3 PF B"
		::= { analog_values 207 }

I_Line_3_PF_B_Alarm OBJECT-TYPE
	SYNTAX  AnalogAlarm
	ACCESS  read-only
	STATUS  mandatory
	DESCRIPTION "I Line 3 PF B Alarm"
		::= { analog_alarms 207 }

I_Line_3_PF_C OBJECT-TYPE
	SYNTAX  AnalogHundredths
	ACCESS  read-only
	STATUS  mandatory
	DESCRIPTION "I Line 3 PF C"
		::= { analog_values 208 }

I_Line_3_PF_C_Alarm OBJECT-TYPE
	SYNTAX  AnalogAlarm
	ACCESS  read-only
	STATUS  mandatory
	DESCRIPTION "I Line 3 PF C Alarm"
		::= { analog_alarms 208 }

I_Line_4_Volts_AB OBJECT-TYPE
	SYNTAX  INTEGER
	ACCESS  read-only
	STATUS  mandatory
	DESCRIPTION "I Line 4 Volts AB"
		::= { analog_values 209 }

I_Line_4_Volts_AB_Alarm OBJECT-TYPE
	SYNTAX  AnalogAlarm
	ACCESS  read-only
	STATUS  mandatory
	DESCRIPTION "I Line 4 Volts AB Alarm"
		::= { analog_alarms 209 }

I_Line_4_Volts_BC OBJECT-TYPE
	SYNTAX  INTEGER
	ACCESS  read-only
	STATUS  mandatory
	DESCRIPTION "I Line 4 Volts BC"
		::= { analog_values 210 }

I_Line_4_Volts_BC_Alarm OBJECT-TYPE
	SYNTAX  AnalogAlarm
	ACCESS  read-only
	STATUS  mandatory
	DESCRIPTION "I Line 4 Volts BC Alarm"
		::= { analog_alarms 210 }

I_Line_4_Volts_CA OBJECT-TYPE
	SYNTAX  INTEGER
	ACCESS  read-only
	STATUS  mandatory
	DESCRIPTION "I Line 4 Volts CA"
		::= { analog_values 211 }

I_Line_4_Volts_CA_Alarm OBJECT-TYPE
	SYNTAX  AnalogAlarm
	ACCESS  read-only
	STATUS  mandatory
	DESCRIPTION "I Line 4 Volts CA Alarm"
		::= { analog_alarms 211 }

I_Line_4_Volts_AN OBJECT-TYPE
	SYNTAX  INTEGER
	ACCESS  read-only
	STATUS  mandatory
	DESCRIPTION "I Line 4 Volts AN"
		::= { analog_values 212 }

I_Line_4_Volts_AN_Alarm OBJECT-TYPE
	SYNTAX  AnalogAlarm
	ACCESS  read-only
	STATUS  mandatory
	DESCRIPTION "I Line 4 Volts AN Alarm"
		::= { analog_alarms 212 }

I_Line_4_Volts_BN OBJECT-TYPE
	SYNTAX  INTEGER
	ACCESS  read-only
	STATUS  mandatory
	DESCRIPTION "I Line 4 Volts BN"
		::= { analog_values 213 }

I_Line_4_Volts_BN_Alarm OBJECT-TYPE
	SYNTAX  AnalogAlarm
	ACCESS  read-only
	STATUS  mandatory
	DESCRIPTION "I Line 4 Volts BN Alarm"
		::= { analog_alarms 213 }

I_Line_4_Volts_CN OBJECT-TYPE
	SYNTAX  INTEGER
	ACCESS  read-only
	STATUS  mandatory
	DESCRIPTION "I Line 4 Volts CN"
		::= { analog_values 214 }

I_Line_4_Volts_CN_Alarm OBJECT-TYPE
	SYNTAX  AnalogAlarm
	ACCESS  read-only
	STATUS  mandatory
	DESCRIPTION "I Line 4 Volts CN Alarm"
		::= { analog_alarms 214 }

I_Line_4_Amps_A OBJECT-TYPE
	SYNTAX  INTEGER
	ACCESS  read-only
	STATUS  mandatory
	DESCRIPTION "I Line 4 Amps A"
		::= { analog_values 215 }

I_Line_4_Amps_A_Alarm OBJECT-TYPE
	SYNTAX  AnalogAlarm
	ACCESS  read-only
	STATUS  mandatory
	DESCRIPTION "I Line 4 Amps A Alarm"
		::= { analog_alarms 215 }

I_Line_4_Amps_B OBJECT-TYPE
	SYNTAX  INTEGER
	ACCESS  read-only
	STATUS  mandatory
	DESCRIPTION "I Line 4 Amps B"
		::= { analog_values 216 }

I_Line_4_Amps_B_Alarm OBJECT-TYPE
	SYNTAX  AnalogAlarm
	ACCESS  read-only
	STATUS  mandatory
	DESCRIPTION "I Line 4 Amps B Alarm"
		::= { analog_alarms 216 }

I_Line_4_Amps_C OBJECT-TYPE
	SYNTAX  INTEGER
	ACCESS  read-only
	STATUS  mandatory
	DESCRIPTION "I Line 4 Amps C"
		::= { analog_values 217 }

I_Line_4_Amps_C_Alarm OBJECT-TYPE
	SYNTAX  AnalogAlarm
	ACCESS  read-only
	STATUS  mandatory
	DESCRIPTION "I Line 4 Amps C Alarm"
		::= { analog_alarms 217 }

I_Line_4_KVA_A OBJECT-TYPE
	SYNTAX  INTEGER
	ACCESS  read-only
	STATUS  mandatory
	DESCRIPTION "I Line 4 KVA A"
		::= { analog_values 218 }

I_Line_4_KVA_A_Alarm OBJECT-TYPE
	SYNTAX  AnalogAlarm
	ACCESS  read-only
	STATUS  mandatory
	DESCRIPTION "I Line 4 KVA A Alarm"
		::= { analog_alarms 218 }

I_Line_4_KVA_B OBJECT-TYPE
	SYNTAX  INTEGER
	ACCESS  read-only
	STATUS  mandatory
	DESCRIPTION "I Line 4 KVA B"
		::= { analog_values 219 }

I_Line_4_KVA_B_Alarm OBJECT-TYPE
	SYNTAX  AnalogAlarm
	ACCESS  read-only
	STATUS  mandatory
	DESCRIPTION "I Line 4 KVA B Alarm"
		::= { analog_alarms 219 }

I_Line_4_KVA_C OBJECT-TYPE
	SYNTAX  INTEGER
	ACCESS  read-only
	STATUS  mandatory
	DESCRIPTION "I Line 4 KVA C"
		::= { analog_values 220 }

I_Line_4_KVA_C_Alarm OBJECT-TYPE
	SYNTAX  AnalogAlarm
	ACCESS  read-only
	STATUS  mandatory
	DESCRIPTION "I Line 4 KVA C Alarm"
		::= { analog_alarms 220 }

I_Line_4_Total_KVA OBJECT-TYPE
	SYNTAX  INTEGER
	ACCESS  read-only
	STATUS  mandatory
	DESCRIPTION "I Line 4 Total KVA"
		::= { analog_values 221 }

I_Line_4_Total_KVA_Alarm OBJECT-TYPE
	SYNTAX  AnalogAlarm
	ACCESS  read-only
	STATUS  mandatory
	DESCRIPTION "I Line 4 Total KVA Alarm"
		::= { analog_alarms 221 }

I_Line_4_Total_%KVA OBJECT-TYPE
	SYNTAX  INTEGER
	ACCESS  read-only
	STATUS  mandatory
	DESCRIPTION "I Line 4 Total %KVA"
		::= { analog_values 222 }

I_Line_4_Total_%KVA_Alarm OBJECT-TYPE
	SYNTAX  AnalogAlarm
	ACCESS  read-only
	STATUS  mandatory
	DESCRIPTION "I Line 4 Total %KVA Alarm"
		::= { analog_alarms 222 }

I_Line_4_KW_A OBJECT-TYPE
	SYNTAX  INTEGER
	ACCESS  read-only
	STATUS  mandatory
	DESCRIPTION "I Line 4 KW A"
		::= { analog_values 223 }

I_Line_4_KW_A_Alarm OBJECT-TYPE
	SYNTAX  AnalogAlarm
	ACCESS  read-only
	STATUS  mandatory
	DESCRIPTION "I Line 4 KW A Alarm"
		::= { analog_alarms 223 }

I_Line_4_KW_B OBJECT-TYPE
	SYNTAX  INTEGER
	ACCESS  read-only
	STATUS  mandatory
	DESCRIPTION "I Line 4 KW B"
		::= { analog_values 224 }

I_Line_4_KW_B_Alarm OBJECT-TYPE
	SYNTAX  AnalogAlarm
	ACCESS  read-only
	STATUS  mandatory
	DESCRIPTION "I Line 4 KW B Alarm"
		::= { analog_alarms 224 }

I_Line_4_KW_C OBJECT-TYPE
	SYNTAX  INTEGER
	ACCESS  read-only
	STATUS  mandatory
	DESCRIPTION "I Line 4 KW C"
		::= { analog_values 225 }

I_Line_4_KW_C_Alarm OBJECT-TYPE
	SYNTAX  AnalogAlarm
	ACCESS  read-only
	STATUS  mandatory
	DESCRIPTION "I Line 4 KW C Alarm"
		::= { analog_alarms 225 }

I_Line_4_Total_KW OBJECT-TYPE
	SYNTAX  INTEGER
	ACCESS  read-only
	STATUS  mandatory
	DESCRIPTION "I Line 4 Total KW"
		::= { analog_values 226 }

I_Line_4_Total_KW_Alarm OBJECT-TYPE
	SYNTAX  AnalogAlarm
	ACCESS  read-only
	STATUS  mandatory
	DESCRIPTION "I Line 4 Total KW Alarm"
		::= { analog_alarms 226 }

I_Line_4_PF_A OBJECT-TYPE
	SYNTAX  AnalogHundredths
	ACCESS  read-only
	STATUS  mandatory
	DESCRIPTION "I Line 4 PF A"
		::= { analog_values 227 }

I_Line_4_PF_A_Alarm OBJECT-TYPE
	SYNTAX  AnalogAlarm
	ACCESS  read-only
	STATUS  mandatory
	DESCRIPTION "I Line 4 PF A Alarm"
		::= { analog_alarms 227 }

I_Line_4_PF_B OBJECT-TYPE
	SYNTAX  AnalogHundredths
	ACCESS  read-only
	STATUS  mandatory
	DESCRIPTION "I Line 4 PF B"
		::= { analog_values 228 }

I_Line_4_PF_B_Alarm OBJECT-TYPE
	SYNTAX  AnalogAlarm
	ACCESS  read-only
	STATUS  mandatory
	DESCRIPTION "I Line 4 PF B Alarm"
		::= { analog_alarms 228 }

I_Line_4_PF_C OBJECT-TYPE
	SYNTAX  AnalogHundredths
	ACCESS  read-only
	STATUS  mandatory
	DESCRIPTION "I Line 4 PF C"
		::= { analog_values 229 }

I_Line_4_PF_C_Alarm OBJECT-TYPE
	SYNTAX  AnalogAlarm
	ACCESS  read-only
	STATUS  mandatory
	DESCRIPTION "I Line 4 PF C Alarm"
		::= { analog_alarms 229 }

I_Line_5_Volts_AB OBJECT-TYPE
	SYNTAX  INTEGER
	ACCESS  read-only
	STATUS  mandatory
	DESCRIPTION "I Line 5 Volts AB"
		::= { analog_values 230 }

I_Line_5_Volts_AB_Alarm OBJECT-TYPE
	SYNTAX  AnalogAlarm
	ACCESS  read-only
	STATUS  mandatory
	DESCRIPTION "I Line 5 Volts AB Alarm"
		::= { analog_alarms 230 }

I_Line_5_Volts_BC OBJECT-TYPE
	SYNTAX  INTEGER
	ACCESS  read-only
	STATUS  mandatory
	DESCRIPTION "I Line 5 Volts BC"
		::= { analog_values 231 }

I_Line_5_Volts_BC_Alarm OBJECT-TYPE
	SYNTAX  AnalogAlarm
	ACCESS  read-only
	STATUS  mandatory
	DESCRIPTION "I Line 5 Volts BC Alarm"
		::= { analog_alarms 231 }

I_Line_5_Volts_CA OBJECT-TYPE
	SYNTAX  INTEGER
	ACCESS  read-only
	STATUS  mandatory
	DESCRIPTION "I Line 5 Volts CA"
		::= { analog_values 232 }

I_Line_5_Volts_CA_Alarm OBJECT-TYPE
	SYNTAX  AnalogAlarm
	ACCESS  read-only
	STATUS  mandatory
	DESCRIPTION "I Line 5 Volts CA Alarm"
		::= { analog_alarms 232 }

I_Line_5_Volts_AN OBJECT-TYPE
	SYNTAX  INTEGER
	ACCESS  read-only
	STATUS  mandatory
	DESCRIPTION "I Line 5 Volts AN"
		::= { analog_values 233 }

I_Line_5_Volts_AN_Alarm OBJECT-TYPE
	SYNTAX  AnalogAlarm
	ACCESS  read-only
	STATUS  mandatory
	DESCRIPTION "I Line 5 Volts AN Alarm"
		::= { analog_alarms 233 }

I_Line_5_Volts_BN OBJECT-TYPE
	SYNTAX  INTEGER
	ACCESS  read-only
	STATUS  mandatory
	DESCRIPTION "I Line 5 Volts BN"
		::= { analog_values 234 }

I_Line_5_Volts_BN_Alarm OBJECT-TYPE
	SYNTAX  AnalogAlarm
	ACCESS  read-only
	STATUS  mandatory
	DESCRIPTION "I Line 5 Volts BN Alarm"
		::= { analog_alarms 234 }

I_Line_5_Volts_CN OBJECT-TYPE
	SYNTAX  INTEGER
	ACCESS  read-only
	STATUS  mandatory
	DESCRIPTION "I Line 5 Volts CN"
		::= { analog_values 235 }

I_Line_5_Volts_CN_Alarm OBJECT-TYPE
	SYNTAX  AnalogAlarm
	ACCESS  read-only
	STATUS  mandatory
	DESCRIPTION "I Line 5 Volts CN Alarm"
		::= { analog_alarms 235 }

I_Line_5_Amps_A OBJECT-TYPE
	SYNTAX  INTEGER
	ACCESS  read-only
	STATUS  mandatory
	DESCRIPTION "I Line 5 Amps A"
		::= { analog_values 236 }

I_Line_5_Amps_A_Alarm OBJECT-TYPE
	SYNTAX  AnalogAlarm
	ACCESS  read-only
	STATUS  mandatory
	DESCRIPTION "I Line 5 Amps A Alarm"
		::= { analog_alarms 236 }

I_Line_5_Amps_B OBJECT-TYPE
	SYNTAX  INTEGER
	ACCESS  read-only
	STATUS  mandatory
	DESCRIPTION "I Line 5 Amps B"
		::= { analog_values 237 }

I_Line_5_Amps_B_Alarm OBJECT-TYPE
	SYNTAX  AnalogAlarm
	ACCESS  read-only
	STATUS  mandatory
	DESCRIPTION "I Line 5 Amps B Alarm"
		::= { analog_alarms 237 }

I_Line_5_Amps_C OBJECT-TYPE
	SYNTAX  INTEGER
	ACCESS  read-only
	STATUS  mandatory
	DESCRIPTION "I Line 5 Amps C"
		::= { analog_values 238 }

I_Line_5_Amps_C_Alarm OBJECT-TYPE
	SYNTAX  AnalogAlarm
	ACCESS  read-only
	STATUS  mandatory
	DESCRIPTION "I Line 5 Amps C Alarm"
		::= { analog_alarms 238 }

I_Line_5_KVA_A OBJECT-TYPE
	SYNTAX  INTEGER
	ACCESS  read-only
	STATUS  mandatory
	DESCRIPTION "I Line 5 KVA A"
		::= { analog_values 239 }

I_Line_5_KVA_A_Alarm OBJECT-TYPE
	SYNTAX  AnalogAlarm
	ACCESS  read-only
	STATUS  mandatory
	DESCRIPTION "I Line 5 KVA A Alarm"
		::= { analog_alarms 239 }

I_Line_5_KVA_B OBJECT-TYPE
	SYNTAX  INTEGER
	ACCESS  read-only
	STATUS  mandatory
	DESCRIPTION "I Line 5 KVA B"
		::= { analog_values 240 }

I_Line_5_KVA_B_Alarm OBJECT-TYPE
	SYNTAX  AnalogAlarm
	ACCESS  read-only
	STATUS  mandatory
	DESCRIPTION "I Line 5 KVA B Alarm"
		::= { analog_alarms 240 }

I_Line_5_KVA_C OBJECT-TYPE
	SYNTAX  INTEGER
	ACCESS  read-only
	STATUS  mandatory
	DESCRIPTION "I Line 5 KVA C"
		::= { analog_values 241 }

I_Line_5_KVA_C_Alarm OBJECT-TYPE
	SYNTAX  AnalogAlarm
	ACCESS  read-only
	STATUS  mandatory
	DESCRIPTION "I Line 5 KVA C Alarm"
		::= { analog_alarms 241 }

I_Line_5_Total_KVA OBJECT-TYPE
	SYNTAX  INTEGER
	ACCESS  read-only
	STATUS  mandatory
	DESCRIPTION "I Line 5 Total KVA"
		::= { analog_values 242 }

I_Line_5_Total_KVA_Alarm OBJECT-TYPE
	SYNTAX  AnalogAlarm
	ACCESS  read-only
	STATUS  mandatory
	DESCRIPTION "I Line 5 Total KVA Alarm"
		::= { analog_alarms 242 }

I_Line_5_Total_%KVA OBJECT-TYPE
	SYNTAX  INTEGER
	ACCESS  read-only
	STATUS  mandatory
	DESCRIPTION "I Line 5 Total %KVA"
		::= { analog_values 243 }

I_Line_5_Total_%KVA_Alarm OBJECT-TYPE
	SYNTAX  AnalogAlarm
	ACCESS  read-only
	STATUS  mandatory
	DESCRIPTION "I Line 5 Total %KVA Alarm"
		::= { analog_alarms 243 }

I_Line_5_KW_A OBJECT-TYPE
	SYNTAX  INTEGER
	ACCESS  read-only
	STATUS  mandatory
	DESCRIPTION "I Line 5 KW A"
		::= { analog_values 244 }

I_Line_5_KW_A_Alarm OBJECT-TYPE
	SYNTAX  AnalogAlarm
	ACCESS  read-only
	STATUS  mandatory
	DESCRIPTION "I Line 5 KW A Alarm"
		::= { analog_alarms 244 }

I_Line_5_KW_B OBJECT-TYPE
	SYNTAX  INTEGER
	ACCESS  read-only
	STATUS  mandatory
	DESCRIPTION "I Line 5 KW B"
		::= { analog_values 245 }

I_Line_5_KW_B_Alarm OBJECT-TYPE
	SYNTAX  AnalogAlarm
	ACCESS  read-only
	STATUS  mandatory
	DESCRIPTION "I Line 5 KW B Alarm"
		::= { analog_alarms 245 }

I_Line_5_KW_C OBJECT-TYPE
	SYNTAX  INTEGER
	ACCESS  read-only
	STATUS  mandatory
	DESCRIPTION "I Line 5 KW C"
		::= { analog_values 246 }

I_Line_5_KW_C_Alarm OBJECT-TYPE
	SYNTAX  AnalogAlarm
	ACCESS  read-only
	STATUS  mandatory
	DESCRIPTION "I Line 5 KW C Alarm"
		::= { analog_alarms 246 }

I_Line_5_Total_KW OBJECT-TYPE
	SYNTAX  INTEGER
	ACCESS  read-only
	STATUS  mandatory
	DESCRIPTION "I Line 5 Total KW"
		::= { analog_values 247 }

I_Line_5_Total_KW_Alarm OBJECT-TYPE
	SYNTAX  AnalogAlarm
	ACCESS  read-only
	STATUS  mandatory
	DESCRIPTION "I Line 5 Total KW Alarm"
		::= { analog_alarms 247 }

I_Line_5_PF_A OBJECT-TYPE
	SYNTAX  AnalogHundredths
	ACCESS  read-only
	STATUS  mandatory
	DESCRIPTION "I Line 5 PF A"
		::= { analog_values 248 }

I_Line_5_PF_A_Alarm OBJECT-TYPE
	SYNTAX  AnalogAlarm
	ACCESS  read-only
	STATUS  mandatory
	DESCRIPTION "I Line 5 PF A Alarm"
		::= { analog_alarms 248 }

I_Line_5_PF_B OBJECT-TYPE
	SYNTAX  AnalogHundredths
	ACCESS  read-only
	STATUS  mandatory
	DESCRIPTION "I Line 5 PF B"
		::= { analog_values 249 }

I_Line_5_PF_B_Alarm OBJECT-TYPE
	SYNTAX  AnalogAlarm
	ACCESS  read-only
	STATUS  mandatory
	DESCRIPTION "I Line 5 PF B Alarm"
		::= { analog_alarms 249 }

I_Line_5_PF_C OBJECT-TYPE
	SYNTAX  AnalogHundredths
	ACCESS  read-only
	STATUS  mandatory
	DESCRIPTION "I Line 5 PF C"
		::= { analog_values 250 }

I_Line_5_PF_C_Alarm OBJECT-TYPE
	SYNTAX  AnalogAlarm
	ACCESS  read-only
	STATUS  mandatory
	DESCRIPTION "I Line 5 PF C Alarm"
		::= { analog_alarms 250 }

I_Line_6_Volts_AB OBJECT-TYPE
	SYNTAX  INTEGER
	ACCESS  read-only
	STATUS  mandatory
	DESCRIPTION "I Line 6 Volts AB"
		::= { analog_values 251 }

I_Line_6_Volts_AB_Alarm OBJECT-TYPE
	SYNTAX  AnalogAlarm
	ACCESS  read-only
	STATUS  mandatory
	DESCRIPTION "I Line 6 Volts AB Alarm"
		::= { analog_alarms 251 }

I_Line_6_Volts_BC OBJECT-TYPE
	SYNTAX  INTEGER
	ACCESS  read-only
	STATUS  mandatory
	DESCRIPTION "I Line 6 Volts BC"
		::= { analog_values 252 }

I_Line_6_Volts_BC_Alarm OBJECT-TYPE
	SYNTAX  AnalogAlarm
	ACCESS  read-only
	STATUS  mandatory
	DESCRIPTION "I Line 6 Volts BC Alarm"
		::= { analog_alarms 252 }

I_Line_6_Volts_CA OBJECT-TYPE
	SYNTAX  INTEGER
	ACCESS  read-only
	STATUS  mandatory
	DESCRIPTION "I Line 6 Volts CA"
		::= { analog_values 253 }

I_Line_6_Volts_CA_Alarm OBJECT-TYPE
	SYNTAX  AnalogAlarm
	ACCESS  read-only
	STATUS  mandatory
	DESCRIPTION "I Line 6 Volts CA Alarm"
		::= { analog_alarms 253 }

I_Line_6_Volts_AN OBJECT-TYPE
	SYNTAX  INTEGER
	ACCESS  read-only
	STATUS  mandatory
	DESCRIPTION "I Line 6 Volts AN"
		::= { analog_values 254 }

I_Line_6_Volts_AN_Alarm OBJECT-TYPE
	SYNTAX  AnalogAlarm
	ACCESS  read-only
	STATUS  mandatory
	DESCRIPTION "I Line 6 Volts AN Alarm"
		::= { analog_alarms 254 }

I_Line_6_Volts_BN OBJECT-TYPE
	SYNTAX  INTEGER
	ACCESS  read-only
	STATUS  mandatory
	DESCRIPTION "I Line 6 Volts BN"
		::= { analog_values 255 }

I_Line_6_Volts_BN_Alarm OBJECT-TYPE
	SYNTAX  AnalogAlarm
	ACCESS  read-only
	STATUS  mandatory
	DESCRIPTION "I Line 6 Volts BN Alarm"
		::= { analog_alarms 255 }

I_Line_6_Volts_CN OBJECT-TYPE
	SYNTAX  INTEGER
	ACCESS  read-only
	STATUS  mandatory
	DESCRIPTION "I Line 6 Volts CN"
		::= { analog_values 256 }

I_Line_6_Volts_CN_Alarm OBJECT-TYPE
	SYNTAX  AnalogAlarm
	ACCESS  read-only
	STATUS  mandatory
	DESCRIPTION "I Line 6 Volts CN Alarm"
		::= { analog_alarms 256 }

I_Line_6_Amps_A OBJECT-TYPE
	SYNTAX  INTEGER
	ACCESS  read-only
	STATUS  mandatory
	DESCRIPTION "I Line 6 Amps A"
		::= { analog_values 257 }

I_Line_6_Amps_A_Alarm OBJECT-TYPE
	SYNTAX  AnalogAlarm
	ACCESS  read-only
	STATUS  mandatory
	DESCRIPTION "I Line 6 Amps A Alarm"
		::= { analog_alarms 257 }

I_Line_6_Amps_B OBJECT-TYPE
	SYNTAX  INTEGER
	ACCESS  read-only
	STATUS  mandatory
	DESCRIPTION "I Line 6 Amps B"
		::= { analog_values 258 }

I_Line_6_Amps_B_Alarm OBJECT-TYPE
	SYNTAX  AnalogAlarm
	ACCESS  read-only
	STATUS  mandatory
	DESCRIPTION "I Line 6 Amps B Alarm"
		::= { analog_alarms 258 }

I_Line_6_Amps_C OBJECT-TYPE
	SYNTAX  INTEGER
	ACCESS  read-only
	STATUS  mandatory
	DESCRIPTION "I Line 6 Amps C"
		::= { analog_values 259 }

I_Line_6_Amps_C_Alarm OBJECT-TYPE
	SYNTAX  AnalogAlarm
	ACCESS  read-only
	STATUS  mandatory
	DESCRIPTION "I Line 6 Amps C Alarm"
		::= { analog_alarms 259 }

I_Line_6_KVA_A OBJECT-TYPE
	SYNTAX  INTEGER
	ACCESS  read-only
	STATUS  mandatory
	DESCRIPTION "I Line 6 KVA A"
		::= { analog_values 260 }

I_Line_6_KVA_A_Alarm OBJECT-TYPE
	SYNTAX  AnalogAlarm
	ACCESS  read-only
	STATUS  mandatory
	DESCRIPTION "I Line 6 KVA A Alarm"
		::= { analog_alarms 260 }

I_Line_6_KVA_B OBJECT-TYPE
	SYNTAX  INTEGER
	ACCESS  read-only
	STATUS  mandatory
	DESCRIPTION "I Line 6 KVA B"
		::= { analog_values 261 }

I_Line_6_KVA_B_Alarm OBJECT-TYPE
	SYNTAX  AnalogAlarm
	ACCESS  read-only
	STATUS  mandatory
	DESCRIPTION "I Line 6 KVA B Alarm"
		::= { analog_alarms 261 }

I_Line_6_KVA_C OBJECT-TYPE
	SYNTAX  INTEGER
	ACCESS  read-only
	STATUS  mandatory
	DESCRIPTION "I Line 6 KVA C"
		::= { analog_values 262 }

I_Line_6_KVA_C_Alarm OBJECT-TYPE
	SYNTAX  AnalogAlarm
	ACCESS  read-only
	STATUS  mandatory
	DESCRIPTION "I Line 6 KVA C Alarm"
		::= { analog_alarms 262 }

I_Line_6_Total_KVA OBJECT-TYPE
	SYNTAX  INTEGER
	ACCESS  read-only
	STATUS  mandatory
	DESCRIPTION "I Line 6 Total KVA"
		::= { analog_values 263 }

I_Line_6_Total_KVA_Alarm OBJECT-TYPE
	SYNTAX  AnalogAlarm
	ACCESS  read-only
	STATUS  mandatory
	DESCRIPTION "I Line 6 Total KVA Alarm"
		::= { analog_alarms 263 }

I_Line_6_Total_%KVA OBJECT-TYPE
	SYNTAX  INTEGER
	ACCESS  read-only
	STATUS  mandatory
	DESCRIPTION "I Line 6 Total %KVA"
		::= { analog_values 264 }

I_Line_6_Total_%KVA_Alarm OBJECT-TYPE
	SYNTAX  AnalogAlarm
	ACCESS  read-only
	STATUS  mandatory
	DESCRIPTION "I Line 6 Total %KVA Alarm"
		::= { analog_alarms 264 }

I_Line_6_KW_A OBJECT-TYPE
	SYNTAX  INTEGER
	ACCESS  read-only
	STATUS  mandatory
	DESCRIPTION "I Line 6 KW A"
		::= { analog_values 265 }

I_Line_6_KW_A_Alarm OBJECT-TYPE
	SYNTAX  AnalogAlarm
	ACCESS  read-only
	STATUS  mandatory
	DESCRIPTION "I Line 6 KW A Alarm"
		::= { analog_alarms 265 }

I_Line_6_KW_B OBJECT-TYPE
	SYNTAX  INTEGER
	ACCESS  read-only
	STATUS  mandatory
	DESCRIPTION "I Line 6 KW B"
		::= { analog_values 266 }

I_Line_6_KW_B_Alarm OBJECT-TYPE
	SYNTAX  AnalogAlarm
	ACCESS  read-only
	STATUS  mandatory
	DESCRIPTION "I Line 6 KW B Alarm"
		::= { analog_alarms 266 }

I_Line_6_KW_C OBJECT-TYPE
	SYNTAX  INTEGER
	ACCESS  read-only
	STATUS  mandatory
	DESCRIPTION "I Line 6 KW C"
		::= { analog_values 267 }

I_Line_6_KW_C_Alarm OBJECT-TYPE
	SYNTAX  AnalogAlarm
	ACCESS  read-only
	STATUS  mandatory
	DESCRIPTION "I Line 6 KW C Alarm"
		::= { analog_alarms 267 }

I_Line_6_Total_KW OBJECT-TYPE
	SYNTAX  INTEGER
	ACCESS  read-only
	STATUS  mandatory
	DESCRIPTION "I Line 6 Total KW"
		::= { analog_values 268 }

I_Line_6_Total_KW_Alarm OBJECT-TYPE
	SYNTAX  AnalogAlarm
	ACCESS  read-only
	STATUS  mandatory
	DESCRIPTION "I Line 6 Total KW Alarm"
		::= { analog_alarms 268 }

I_Line_6_PF_A OBJECT-TYPE
	SYNTAX  AnalogHundredths
	ACCESS  read-only
	STATUS  mandatory
	DESCRIPTION "I Line 6 PF A"
		::= { analog_values 269 }

I_Line_6_PF_A_Alarm OBJECT-TYPE
	SYNTAX  AnalogAlarm
	ACCESS  read-only
	STATUS  mandatory
	DESCRIPTION "I Line 6 PF A Alarm"
		::= { analog_alarms 269 }

I_Line_6_PF_B OBJECT-TYPE
	SYNTAX  AnalogHundredths
	ACCESS  read-only
	STATUS  mandatory
	DESCRIPTION "I Line 6 PF B"
		::= { analog_values 270 }

I_Line_6_PF_B_Alarm OBJECT-TYPE
	SYNTAX  AnalogAlarm
	ACCESS  read-only
	STATUS  mandatory
	DESCRIPTION "I Line 6 PF B Alarm"
		::= { analog_alarms 270 }

I_Line_6_PF_C OBJECT-TYPE
	SYNTAX  AnalogHundredths
	ACCESS  read-only
	STATUS  mandatory
	DESCRIPTION "I Line 6 PF C"
		::= { analog_values 271 }

I_Line_6_PF_C_Alarm OBJECT-TYPE
	SYNTAX  AnalogAlarm
	ACCESS  read-only
	STATUS  mandatory
	DESCRIPTION "I Line 6 PF C Alarm"
		::= { analog_alarms 271 }

I_Line_7_Volts_AB OBJECT-TYPE
	SYNTAX  INTEGER
	ACCESS  read-only
	STATUS  mandatory
	DESCRIPTION "I Line 7 Volts AB"
		::= { analog_values 272 }

I_Line_7_Volts_AB_Alarm OBJECT-TYPE
	SYNTAX  AnalogAlarm
	ACCESS  read-only
	STATUS  mandatory
	DESCRIPTION "I Line 7 Volts AB Alarm"
		::= { analog_alarms 272 }

I_Line_7_Volts_BC OBJECT-TYPE
	SYNTAX  INTEGER
	ACCESS  read-only
	STATUS  mandatory
	DESCRIPTION "I Line 7 Volts BC"
		::= { analog_values 273 }

I_Line_7_Volts_BC_Alarm OBJECT-TYPE
	SYNTAX  AnalogAlarm
	ACCESS  read-only
	STATUS  mandatory
	DESCRIPTION "I Line 7 Volts BC Alarm"
		::= { analog_alarms 273 }

I_Line_7_Volts_CA OBJECT-TYPE
	SYNTAX  INTEGER
	ACCESS  read-only
	STATUS  mandatory
	DESCRIPTION "I Line 7 Volts CA"
		::= { analog_values 274 }

I_Line_7_Volts_CA_Alarm OBJECT-TYPE
	SYNTAX  AnalogAlarm
	ACCESS  read-only
	STATUS  mandatory
	DESCRIPTION "I Line 7 Volts CA Alarm"
		::= { analog_alarms 274 }

I_Line_7_Volts_AN OBJECT-TYPE
	SYNTAX  INTEGER
	ACCESS  read-only
	STATUS  mandatory
	DESCRIPTION "I Line 7 Volts AN"
		::= { analog_values 275 }

I_Line_7_Volts_AN_Alarm OBJECT-TYPE
	SYNTAX  AnalogAlarm
	ACCESS  read-only
	STATUS  mandatory
	DESCRIPTION "I Line 7 Volts AN Alarm"
		::= { analog_alarms 275 }

I_Line_7_Volts_BN OBJECT-TYPE
	SYNTAX  INTEGER
	ACCESS  read-only
	STATUS  mandatory
	DESCRIPTION "I Line 7 Volts BN"
		::= { analog_values 276 }

I_Line_7_Volts_BN_Alarm OBJECT-TYPE
	SYNTAX  AnalogAlarm
	ACCESS  read-only
	STATUS  mandatory
	DESCRIPTION "I Line 7 Volts BN Alarm"
		::= { analog_alarms 276 }

I_Line_7_Volts_CN OBJECT-TYPE
	SYNTAX  INTEGER
	ACCESS  read-only
	STATUS  mandatory
	DESCRIPTION "I Line 7 Volts CN"
		::= { analog_values 277 }

I_Line_7_Volts_CN_Alarm OBJECT-TYPE
	SYNTAX  AnalogAlarm
	ACCESS  read-only
	STATUS  mandatory
	DESCRIPTION "I Line 7 Volts CN Alarm"
		::= { analog_alarms 277 }

I_Line_7_Amps_A OBJECT-TYPE
	SYNTAX  INTEGER
	ACCESS  read-only
	STATUS  mandatory
	DESCRIPTION "I Line 7 Amps A"
		::= { analog_values 278 }

I_Line_7_Amps_A_Alarm OBJECT-TYPE
	SYNTAX  AnalogAlarm
	ACCESS  read-only
	STATUS  mandatory
	DESCRIPTION "I Line 7 Amps A Alarm"
		::= { analog_alarms 278 }

I_Line_7_Amps_B OBJECT-TYPE
	SYNTAX  INTEGER
	ACCESS  read-only
	STATUS  mandatory
	DESCRIPTION "I Line 7 Amps B"
		::= { analog_values 279 }

I_Line_7_Amps_B_Alarm OBJECT-TYPE
	SYNTAX  AnalogAlarm
	ACCESS  read-only
	STATUS  mandatory
	DESCRIPTION "I Line 7 Amps B Alarm"
		::= { analog_alarms 279 }

I_Line_7_Amps_C OBJECT-TYPE
	SYNTAX  INTEGER
	ACCESS  read-only
	STATUS  mandatory
	DESCRIPTION "I Line 7 Amps C"
		::= { analog_values 280 }

I_Line_7_Amps_C_Alarm OBJECT-TYPE
	SYNTAX  AnalogAlarm
	ACCESS  read-only
	STATUS  mandatory
	DESCRIPTION "I Line 7 Amps C Alarm"
		::= { analog_alarms 280 }

I_Line_7_KVA_A OBJECT-TYPE
	SYNTAX  INTEGER
	ACCESS  read-only
	STATUS  mandatory
	DESCRIPTION "I Line 7 KVA A"
		::= { analog_values 281 }

I_Line_7_KVA_A_Alarm OBJECT-TYPE
	SYNTAX  AnalogAlarm
	ACCESS  read-only
	STATUS  mandatory
	DESCRIPTION "I Line 7 KVA A Alarm"
		::= { analog_alarms 281 }

I_Line_7_KVA_B OBJECT-TYPE
	SYNTAX  INTEGER
	ACCESS  read-only
	STATUS  mandatory
	DESCRIPTION "I Line 7 KVA B"
		::= { analog_values 282 }

I_Line_7_KVA_B_Alarm OBJECT-TYPE
	SYNTAX  AnalogAlarm
	ACCESS  read-only
	STATUS  mandatory
	DESCRIPTION "I Line 7 KVA B Alarm"
		::= { analog_alarms 282 }

I_Line_7_KVA_C OBJECT-TYPE
	SYNTAX  INTEGER
	ACCESS  read-only
	STATUS  mandatory
	DESCRIPTION "I Line 7 KVA C"
		::= { analog_values 283 }

I_Line_7_KVA_C_Alarm OBJECT-TYPE
	SYNTAX  AnalogAlarm
	ACCESS  read-only
	STATUS  mandatory
	DESCRIPTION "I Line 7 KVA C Alarm"
		::= { analog_alarms 283 }

I_Line_7_Total_KVA OBJECT-TYPE
	SYNTAX  INTEGER
	ACCESS  read-only
	STATUS  mandatory
	DESCRIPTION "I Line 7 Total KVA"
		::= { analog_values 284 }

I_Line_7_Total_KVA_Alarm OBJECT-TYPE
	SYNTAX  AnalogAlarm
	ACCESS  read-only
	STATUS  mandatory
	DESCRIPTION "I Line 7 Total KVA Alarm"
		::= { analog_alarms 284 }

I_Line_7_Total_%KVA OBJECT-TYPE
	SYNTAX  INTEGER
	ACCESS  read-only
	STATUS  mandatory
	DESCRIPTION "I Line 7 Total %KVA"
		::= { analog_values 285 }

I_Line_7_Total_%KVA_Alarm OBJECT-TYPE
	SYNTAX  AnalogAlarm
	ACCESS  read-only
	STATUS  mandatory
	DESCRIPTION "I Line 7 Total %KVA Alarm"
		::= { analog_alarms 285 }

I_Line_7_KW_A OBJECT-TYPE
	SYNTAX  INTEGER
	ACCESS  read-only
	STATUS  mandatory
	DESCRIPTION "I Line 7 KW A"
		::= { analog_values 286 }

I_Line_7_KW_A_Alarm OBJECT-TYPE
	SYNTAX  AnalogAlarm
	ACCESS  read-only
	STATUS  mandatory
	DESCRIPTION "I Line 7 KW A Alarm"
		::= { analog_alarms 286 }

I_Line_7_KW_B OBJECT-TYPE
	SYNTAX  INTEGER
	ACCESS  read-only
	STATUS  mandatory
	DESCRIPTION "I Line 7 KW B"
		::= { analog_values 287 }

I_Line_7_KW_B_Alarm OBJECT-TYPE
	SYNTAX  AnalogAlarm
	ACCESS  read-only
	STATUS  mandatory
	DESCRIPTION "I Line 7 KW B Alarm"
		::= { analog_alarms 287 }

I_Line_7_KW_C OBJECT-TYPE
	SYNTAX  INTEGER
	ACCESS  read-only
	STATUS  mandatory
	DESCRIPTION "I Line 7 KW C"
		::= { analog_values 288 }

I_Line_7_KW_C_Alarm OBJECT-TYPE
	SYNTAX  AnalogAlarm
	ACCESS  read-only
	STATUS  mandatory
	DESCRIPTION "I Line 7 KW C Alarm"
		::= { analog_alarms 288 }

I_Line_7_Total_KW OBJECT-TYPE
	SYNTAX  INTEGER
	ACCESS  read-only
	STATUS  mandatory
	DESCRIPTION "I Line 7 Total KW"
		::= { analog_values 289 }

I_Line_7_Total_KW_Alarm OBJECT-TYPE
	SYNTAX  AnalogAlarm
	ACCESS  read-only
	STATUS  mandatory
	DESCRIPTION "I Line 7 Total KW Alarm"
		::= { analog_alarms 289 }

I_Line_7_PF_A OBJECT-TYPE
	SYNTAX  AnalogHundredths
	ACCESS  read-only
	STATUS  mandatory
	DESCRIPTION "I Line 7 PF A"
		::= { analog_values 290 }

I_Line_7_PF_A_Alarm OBJECT-TYPE
	SYNTAX  AnalogAlarm
	ACCESS  read-only
	STATUS  mandatory
	DESCRIPTION "I Line 7 PF A Alarm"
		::= { analog_alarms 290 }

I_Line_7_PF_B OBJECT-TYPE
	SYNTAX  AnalogHundredths
	ACCESS  read-only
	STATUS  mandatory
	DESCRIPTION "I Line 7 PF B"
		::= { analog_values 291 }

I_Line_7_PF_B_Alarm OBJECT-TYPE
	SYNTAX  AnalogAlarm
	ACCESS  read-only
	STATUS  mandatory
	DESCRIPTION "I Line 7 PF B Alarm"
		::= { analog_alarms 291 }

I_Line_7_PF_C OBJECT-TYPE
	SYNTAX  AnalogHundredths
	ACCESS  read-only
	STATUS  mandatory
	DESCRIPTION "I Line 7 PF C"
		::= { analog_values 292 }

I_Line_7_PF_C_Alarm OBJECT-TYPE
	SYNTAX  AnalogAlarm
	ACCESS  read-only
	STATUS  mandatory
	DESCRIPTION "I Line 7 PF C Alarm"
		::= { analog_alarms 292 }

I_Line_8_Volts_AB OBJECT-TYPE
	SYNTAX  INTEGER
	ACCESS  read-only
	STATUS  mandatory
	DESCRIPTION "I Line 8 Volts AB"
		::= { analog_values 293 }

I_Line_8_Volts_AB_Alarm OBJECT-TYPE
	SYNTAX  AnalogAlarm
	ACCESS  read-only
	STATUS  mandatory
	DESCRIPTION "I Line 8 Volts AB Alarm"
		::= { analog_alarms 293 }

I_Line_8_Volts_BC OBJECT-TYPE
	SYNTAX  INTEGER
	ACCESS  read-only
	STATUS  mandatory
	DESCRIPTION "I Line 8 Volts BC"
		::= { analog_values 294 }

I_Line_8_Volts_BC_Alarm OBJECT-TYPE
	SYNTAX  AnalogAlarm
	ACCESS  read-only
	STATUS  mandatory
	DESCRIPTION "I Line 8 Volts BC Alarm"
		::= { analog_alarms 294 }

I_Line_8_Volts_CA OBJECT-TYPE
	SYNTAX  INTEGER
	ACCESS  read-only
	STATUS  mandatory
	DESCRIPTION "I Line 8 Volts CA"
		::= { analog_values 295 }

I_Line_8_Volts_CA_Alarm OBJECT-TYPE
	SYNTAX  AnalogAlarm
	ACCESS  read-only
	STATUS  mandatory
	DESCRIPTION "I Line 8 Volts CA Alarm"
		::= { analog_alarms 295 }

I_Line_8_Volts_AN OBJECT-TYPE
	SYNTAX  INTEGER
	ACCESS  read-only
	STATUS  mandatory
	DESCRIPTION "I Line 8 Volts AN"
		::= { analog_values 296 }

I_Line_8_Volts_AN_Alarm OBJECT-TYPE
	SYNTAX  AnalogAlarm
	ACCESS  read-only
	STATUS  mandatory
	DESCRIPTION "I Line 8 Volts AN Alarm"
		::= { analog_alarms 296 }

I_Line_8_Volts_BN OBJECT-TYPE
	SYNTAX  INTEGER
	ACCESS  read-only
	STATUS  mandatory
	DESCRIPTION "I Line 8 Volts BN"
		::= { analog_values 297 }

I_Line_8_Volts_BN_Alarm OBJECT-TYPE
	SYNTAX  AnalogAlarm
	ACCESS  read-only
	STATUS  mandatory
	DESCRIPTION "I Line 8 Volts BN Alarm"
		::= { analog_alarms 297 }

I_Line_8_Volts_CN OBJECT-TYPE
	SYNTAX  INTEGER
	ACCESS  read-only
	STATUS  mandatory
	DESCRIPTION "I Line 8 Volts CN"
		::= { analog_values 298 }

I_Line_8_Volts_CN_Alarm OBJECT-TYPE
	SYNTAX  AnalogAlarm
	ACCESS  read-only
	STATUS  mandatory
	DESCRIPTION "I Line 8 Volts CN Alarm"
		::= { analog_alarms 298 }

I_Line_8_Amps_A OBJECT-TYPE
	SYNTAX  INTEGER
	ACCESS  read-only
	STATUS  mandatory
	DESCRIPTION "I Line 8 Amps A"
		::= { analog_values 299 }

I_Line_8_Amps_A_Alarm OBJECT-TYPE
	SYNTAX  AnalogAlarm
	ACCESS  read-only
	STATUS  mandatory
	DESCRIPTION "I Line 8 Amps A Alarm"
		::= { analog_alarms 299 }

I_Line_8_Amps_B OBJECT-TYPE
	SYNTAX  INTEGER
	ACCESS  read-only
	STATUS  mandatory
	DESCRIPTION "I Line 8 Amps B"
		::= { analog_values 300 }

I_Line_8_Amps_B_Alarm OBJECT-TYPE
	SYNTAX  AnalogAlarm
	ACCESS  read-only
	STATUS  mandatory
	DESCRIPTION "I Line 8 Amps B Alarm"
		::= { analog_alarms 300 }

I_Line_8_Amps_C OBJECT-TYPE
	SYNTAX  INTEGER
	ACCESS  read-only
	STATUS  mandatory
	DESCRIPTION "I Line 8 Amps C"
		::= { analog_values 301 }

I_Line_8_Amps_C_Alarm OBJECT-TYPE
	SYNTAX  AnalogAlarm
	ACCESS  read-only
	STATUS  mandatory
	DESCRIPTION "I Line 8 Amps C Alarm"
		::= { analog_alarms 301 }

I_Line_8_KVA_A OBJECT-TYPE
	SYNTAX  INTEGER
	ACCESS  read-only
	STATUS  mandatory
	DESCRIPTION "I Line 8 KVA A"
		::= { analog_values 302 }

I_Line_8_KVA_A_Alarm OBJECT-TYPE
	SYNTAX  AnalogAlarm
	ACCESS  read-only
	STATUS  mandatory
	DESCRIPTION "I Line 8 KVA A Alarm"
		::= { analog_alarms 302 }

I_Line_8_KVA_B OBJECT-TYPE
	SYNTAX  INTEGER
	ACCESS  read-only
	STATUS  mandatory
	DESCRIPTION "I Line 8 KVA B"
		::= { analog_values 303 }

I_Line_8_KVA_B_Alarm OBJECT-TYPE
	SYNTAX  AnalogAlarm
	ACCESS  read-only
	STATUS  mandatory
	DESCRIPTION "I Line 8 KVA B Alarm"
		::= { analog_alarms 303 }

I_Line_8_KVA_C OBJECT-TYPE
	SYNTAX  INTEGER
	ACCESS  read-only
	STATUS  mandatory
	DESCRIPTION "I Line 8 KVA C"
		::= { analog_values 304 }

I_Line_8_KVA_C_Alarm OBJECT-TYPE
	SYNTAX  AnalogAlarm
	ACCESS  read-only
	STATUS  mandatory
	DESCRIPTION "I Line 8 KVA C Alarm"
		::= { analog_alarms 304 }

I_Line_8_Total_KVA OBJECT-TYPE
	SYNTAX  INTEGER
	ACCESS  read-only
	STATUS  mandatory
	DESCRIPTION "I Line 8 Total KVA"
		::= { analog_values 305 }

I_Line_8_Total_KVA_Alarm OBJECT-TYPE
	SYNTAX  AnalogAlarm
	ACCESS  read-only
	STATUS  mandatory
	DESCRIPTION "I Line 8 Total KVA Alarm"
		::= { analog_alarms 305 }

I_Line_8_Total_%KVA OBJECT-TYPE
	SYNTAX  INTEGER
	ACCESS  read-only
	STATUS  mandatory
	DESCRIPTION "I Line 8 Total %KVA"
		::= { analog_values 306 }

I_Line_8_Total_%KVA_Alarm OBJECT-TYPE
	SYNTAX  AnalogAlarm
	ACCESS  read-only
	STATUS  mandatory
	DESCRIPTION "I Line 8 Total %KVA Alarm"
		::= { analog_alarms 306 }

I_Line_8_KW_A OBJECT-TYPE
	SYNTAX  INTEGER
	ACCESS  read-only
	STATUS  mandatory
	DESCRIPTION "I Line 8 KW A"
		::= { analog_values 307 }

I_Line_8_KW_A_Alarm OBJECT-TYPE
	SYNTAX  AnalogAlarm
	ACCESS  read-only
	STATUS  mandatory
	DESCRIPTION "I Line 8 KW A Alarm"
		::= { analog_alarms 307 }

I_Line_8_KW_B OBJECT-TYPE
	SYNTAX  INTEGER
	ACCESS  read-only
	STATUS  mandatory
	DESCRIPTION "I Line 8 KW B"
		::= { analog_values 308 }

I_Line_8_KW_B_Alarm OBJECT-TYPE
	SYNTAX  AnalogAlarm
	ACCESS  read-only
	STATUS  mandatory
	DESCRIPTION "I Line 8 KW B Alarm"
		::= { analog_alarms 308 }

I_Line_8_KW_C OBJECT-TYPE
	SYNTAX  INTEGER
	ACCESS  read-only
	STATUS  mandatory
	DESCRIPTION "I Line 8 KW C"
		::= { analog_values 309 }

I_Line_8_KW_C_Alarm OBJECT-TYPE
	SYNTAX  AnalogAlarm
	ACCESS  read-only
	STATUS  mandatory
	DESCRIPTION "I Line 8 KW C Alarm"
		::= { analog_alarms 309 }

I_Line_8_Total_KW OBJECT-TYPE
	SYNTAX  INTEGER
	ACCESS  read-only
	STATUS  mandatory
	DESCRIPTION "I Line 8 Total KW"
		::= { analog_values 310 }

I_Line_8_Total_KW_Alarm OBJECT-TYPE
	SYNTAX  AnalogAlarm
	ACCESS  read-only
	STATUS  mandatory
	DESCRIPTION "I Line 8 Total KW Alarm"
		::= { analog_alarms 310 }

I_Line_8_PF_A OBJECT-TYPE
	SYNTAX  AnalogHundredths
	ACCESS  read-only
	STATUS  mandatory
	DESCRIPTION "I Line 8 PF A"
		::= { analog_values 311 }

I_Line_8_PF_A_Alarm OBJECT-TYPE
	SYNTAX  AnalogAlarm
	ACCESS  read-only
	STATUS  mandatory
	DESCRIPTION "I Line 8 PF A Alarm"
		::= { analog_alarms 311 }

I_Line_8_PF_B OBJECT-TYPE
	SYNTAX  AnalogHundredths
	ACCESS  read-only
	STATUS  mandatory
	DESCRIPTION "I Line 8 PF B"
		::= { analog_values 312 }

I_Line_8_PF_B_Alarm OBJECT-TYPE
	SYNTAX  AnalogAlarm
	ACCESS  read-only
	STATUS  mandatory
	DESCRIPTION "I Line 8 PF B Alarm"
		::= { analog_alarms 312 }

I_Line_8_PF_C OBJECT-TYPE
	SYNTAX  AnalogHundredths
	ACCESS  read-only
	STATUS  mandatory
	DESCRIPTION "I Line 8 PF C"
		::= { analog_values 313 }

I_Line_8_PF_C_Alarm OBJECT-TYPE
	SYNTAX  AnalogAlarm
	ACCESS  read-only
	STATUS  mandatory
	DESCRIPTION "I Line 8 PF C Alarm"
		::= { analog_alarms 313 }

Fan_1_Amps OBJECT-TYPE
	SYNTAX  INTEGER
	ACCESS  read-only
	STATUS  mandatory
	DESCRIPTION "Fan 1 Amps"
		::= { analog_values 314 }

Fan_1_Amps_Alarm OBJECT-TYPE
	SYNTAX  AnalogAlarm
	ACCESS  read-only
	STATUS  mandatory
	DESCRIPTION "Fan 1 Amps Alarm"
		::= { analog_alarms 314 }

Fan_2_Amps OBJECT-TYPE
	SYNTAX  INTEGER
	ACCESS  read-only
	STATUS  mandatory
	DESCRIPTION "Fan 2 Amps"
		::= { analog_values 315 }

Fan_2_Amps_Alarm OBJECT-TYPE
	SYNTAX  AnalogAlarm
	ACCESS  read-only
	STATUS  mandatory
	DESCRIPTION "Fan 2 Amps Alarm"
		::= { analog_alarms 315 }

Spare_1_Amps OBJECT-TYPE
	SYNTAX  INTEGER
	ACCESS  read-only
	STATUS  mandatory
	DESCRIPTION "Spare 1 Amps"
		::= { analog_values 316 }

Spare_1_Amps_Alarm OBJECT-TYPE
	SYNTAX  AnalogAlarm
	ACCESS  read-only
	STATUS  mandatory
	DESCRIPTION "Spare 1 Amps Alarm"
		::= { analog_alarms 316 }

Monitor_Power_S1 OBJECT-TYPE
	SYNTAX  INTEGER
	ACCESS  read-only
	STATUS  mandatory
	DESCRIPTION "Monitor Power S1"
		::= { analog_values 317 }

Monitor_Power_S1_Alarm OBJECT-TYPE
	SYNTAX  AnalogAlarm
	ACCESS  read-only
	STATUS  mandatory
	DESCRIPTION "Monitor Power S1 Alarm"
		::= { analog_alarms 317 }

Monitor_Power_S2 OBJECT-TYPE
	SYNTAX  INTEGER
	ACCESS  read-only
	STATUS  mandatory
	DESCRIPTION "Monitor Power S2"
		::= { analog_values 318 }

Monitor_Power_S2_Alarm OBJECT-TYPE
	SYNTAX  AnalogAlarm
	ACCESS  read-only
	STATUS  mandatory
	DESCRIPTION "Monitor Power S2 Alarm"
		::= { analog_alarms 318 }

Monitor_Power_Out1 OBJECT-TYPE
	SYNTAX  INTEGER
	ACCESS  read-only
	STATUS  mandatory
	DESCRIPTION "Monitor Power Out1"
		::= { analog_values 319 }

Monitor_Power_Out1_Alarm OBJECT-TYPE
	SYNTAX  AnalogAlarm
	ACCESS  read-only
	STATUS  mandatory
	DESCRIPTION "Monitor Power Out1 Alarm"
		::= { analog_alarms 319 }

Monitor_Power_Out2 OBJECT-TYPE
	SYNTAX  INTEGER
	ACCESS  read-only
	STATUS  mandatory
	DESCRIPTION "Monitor Power Out2"
		::= { analog_values 320 }

Monitor_Power_Out2_Alarm OBJECT-TYPE
	SYNTAX  AnalogAlarm
	ACCESS  read-only
	STATUS  mandatory
	DESCRIPTION "Monitor Power Out1 Alarm"
		::= { analog_alarms 320 }

Monitor_Power_Backup OBJECT-TYPE
	SYNTAX  INTEGER
	ACCESS  read-only
	STATUS  mandatory
	DESCRIPTION "Monitor Power Backup"
		::= { analog_values 321 }

Monitor_Power_Backup_Alarm OBJECT-TYPE
	SYNTAX  AnalogAlarm
	ACCESS  read-only
	STATUS  mandatory
	DESCRIPTION "Monitor Power Backup Alarm"
		::= { analog_alarms 321 }

-----------------------------------------------------
-- Digital Points
-----------------------------------------------------
Isolation_MCSW_1 OBJECT-TYPE
	SYNTAX  DigitalValueSwitch
	ACCESS  read-only
	STATUS  mandatory
	DESCRIPTION "Isolation switch 1"
		::= { digital_values 1 }

Isolation_MCSW_1_Alarm OBJECT-TYPE
	SYNTAX  DigitalAlarm
	ACCESS  read-only
	STATUS  mandatory
	DESCRIPTION "Isolation switch 1 alarm"
		::= { digital_alarms 1 }

Isolation_MCSW_2 OBJECT-TYPE
	SYNTAX  DigitalValueSwitch
	ACCESS  read-only
	STATUS  mandatory
	DESCRIPTION "Isolation switch 2"
		::= { digital_values 2 }

Isolation_MCSW_2_Alarm OBJECT-TYPE
	SYNTAX  DigitalAlarm
	ACCESS  read-only
	STATUS  mandatory
	DESCRIPTION "Isolation switch 2 alarm"
		::= { digital_alarms 2 }

Bypass_MCSW_1 OBJECT-TYPE
	SYNTAX  DigitalValueSwitch
	ACCESS  read-only
	STATUS  mandatory
	DESCRIPTION "Bypass switch 1"
		::= { digital_values 3 }

Bypass_MCSW_1_Alarm OBJECT-TYPE
	SYNTAX  DigitalAlarm
	ACCESS  read-only
	STATUS  mandatory
	DESCRIPTION "Bypass switch 1 alarm"
		::= { digital_alarms 3 }

Bypass_MCSW_2 OBJECT-TYPE
	SYNTAX  DigitalValueSwitch
	ACCESS  read-only
	STATUS  mandatory
	DESCRIPTION "Bypass switch 2"
		::= { digital_values 4 }

Bypass_MCSW_2_Alarm OBJECT-TYPE
	SYNTAX  DigitalAlarm
	ACCESS  read-only
	STATUS  mandatory
	DESCRIPTION "Bypass switch 2 alarm"
		::= { digital_alarms 4 }

Input_MCSW_1 OBJECT-TYPE
	SYNTAX  DigitalValueSwitch
	ACCESS  read-only
	STATUS  mandatory
	DESCRIPTION "Input switch 1"
		::= { digital_values 5 }

Input_MCSW_1_Alarm OBJECT-TYPE
	SYNTAX  DigitalAlarm
	ACCESS  read-only
	STATUS  mandatory
	DESCRIPTION "Input switch 1 alarm"
		::= { digital_alarms 5 }

Input_MCSW_2 OBJECT-TYPE
	SYNTAX  DigitalValueSwitch
	ACCESS  read-only
	STATUS  mandatory
	DESCRIPTION "Input switch 2"
		::= { digital_values 6 }

Input_MCSW_2_Alarm OBJECT-TYPE
	SYNTAX  DigitalAlarm
	ACCESS  read-only
	STATUS  mandatory
	DESCRIPTION "Input switch 2 alarm"
		::= { digital_alarms 6 }

Override OBJECT-TYPE
	SYNTAX  DigitalValueSwitch
	ACCESS  read-only
	STATUS  mandatory
	DESCRIPTION "Override"
		::= { digital_values 7 }

Override__Alarm OBJECT-TYPE
	SYNTAX  DigitalAlarm
	ACCESS  read-only
	STATUS  mandatory
	DESCRIPTION "Override alarm"
		::= { digital_alarms 7 }

Retransfer OBJECT-TYPE
	SYNTAX  DigitalValueSwitch
	ACCESS  read-only
	STATUS  mandatory
	DESCRIPTION "Retransfer"
		::= { digital_values 8 }

Retransfer__Alarm OBJECT-TYPE
	SYNTAX  DigitalAlarm
	ACCESS  read-only
	STATUS  mandatory
	DESCRIPTION "Retransfer alarm"
		::= { digital_alarms 8 }

ROI_IN_Control OBJECT-TYPE
	SYNTAX  DigitalValueSwitch
	ACCESS  read-only
	STATUS  mandatory
	DESCRIPTION "Mimic Control"
		::= { digital_values 9 }

RDI_IN_Control__Alarm OBJECT-TYPE
	SYNTAX  DigitalAlarm
	ACCESS  read-only
	STATUS  mandatory
	DESCRIPTION "Mimic Control alarm"
		::= { digital_alarms 9 }

Perfer_Source OBJECT-TYPE
	SYNTAX  DigitalValueSwitch
	ACCESS  read-only
	STATUS  mandatory
	DESCRIPTION "Perfer Source"
		::= { digital_values 10 }

Perfer_Source_Alarm OBJECT-TYPE
	SYNTAX  DigitalAlarm
	ACCESS  read-only
	STATUS  mandatory
	DESCRIPTION "Perfer Source Alarm"
		::= { digital_alarms 10 }

Main_1_Circuit_Breaker OBJECT-TYPE
	SYNTAX  DigitalValueSwitch
	ACCESS  read-only
	STATUS  mandatory
	DESCRIPTION "Main_1_Circuit_Breaker"
		::= { digital_values 11 }

Main_1_Circuit_Breaker_Alarm OBJECT-TYPE
	SYNTAX  DigitalAlarm
	ACCESS  read-only
	STATUS  mandatory
	DESCRIPTION "Main 1 Circuit Breaker Alarm"
		::= { digital_alarms 11 }

Main_2_Circuit_Breaker OBJECT-TYPE
	SYNTAX  DigitalValueSwitch
	ACCESS  read-only
	STATUS  mandatory
	DESCRIPTION "Main_2_Circuit_Breaker"
		::= { digital_values 12 }

Main_2_Circuit_Breaker_Alarm OBJECT-TYPE
	SYNTAX  DigitalAlarm
	ACCESS  read-only
	STATUS  mandatory
	DESCRIPTION "Main 2 Circuit Breaker Alarm"
		::= { digital_alarms 12 }
Building_8 OBJECT-TYPE
	SYNTAX  DigitalValueSwitch
	ACCESS  read-only
	STATUS  mandatory
	DESCRIPTION "Building 8"
		::= { digital_values 13 }
Building_8_Alarm OBJECT-TYPE
	SYNTAX  DigitalAlarm
	ACCESS  read-only
	STATUS  mandatory
	DESCRIPTION "Building 8 Alarm"
		::= { digital_alarms 13 }

Building_7 OBJECT-TYPE
	SYNTAX  DigitalValueSwitch
	ACCESS  read-only
	STATUS  mandatory
	DESCRIPTION "Building 7"
		::= { digital_values 14 }
Building_7_Alarm OBJECT-TYPE
	SYNTAX  DigitalAlarm
	ACCESS  read-only
	STATUS  mandatory
	DESCRIPTION "Building 7 Alarm"
		::= { digital_alarms 14 }

Building_6 OBJECT-TYPE
	SYNTAX  DigitalValueSwitch
	ACCESS  read-only
	STATUS  mandatory
	DESCRIPTION "Building 6"
		::= { digital_values 15 }
Building_6_Alarm OBJECT-TYPE
	SYNTAX  DigitalAlarm
	ACCESS  read-only
	STATUS  mandatory
	DESCRIPTION "Building 6 Alarm"
		::= { digital_alarms 15 }

Building_5 OBJECT-TYPE
	SYNTAX  DigitalValueSwitch
	ACCESS  read-only
	STATUS  mandatory
	DESCRIPTION "Building 5"
		::= { digital_values 16 }
Building_5_Alarm OBJECT-TYPE
	SYNTAX  DigitalAlarm
	ACCESS  read-only
	STATUS  mandatory
	DESCRIPTION "Building 5 Alarm"
		::= { digital_alarms 16 }

Building_4 OBJECT-TYPE
	SYNTAX  DigitalValueSwitch
	ACCESS  read-only
	STATUS  mandatory
	DESCRIPTION "Building 4"
		::= { digital_values 17 }
Building_4_Alarm OBJECT-TYPE
	SYNTAX  DigitalAlarm
	ACCESS  read-only
	STATUS  mandatory
	DESCRIPTION "Building 4 Alarm"
		::= { digital_alarms 17 }

Building_3 OBJECT-TYPE
	SYNTAX  DigitalValueSwitch
	ACCESS  read-only
	STATUS  mandatory
	DESCRIPTION "Building 3"
		::= { digital_values 18 }
Building_3_Alarm OBJECT-TYPE
	SYNTAX  DigitalAlarm
	ACCESS  read-only
	STATUS  mandatory
	DESCRIPTION "Building 3 Alarm"
		::= { digital_alarms 18 }

Building_2 OBJECT-TYPE
	SYNTAX  DigitalValueSwitch
	ACCESS  read-only
	STATUS  mandatory
	DESCRIPTION "Building 2"
		::= { digital_values 19 }
Building_2_Alarm OBJECT-TYPE
	SYNTAX  DigitalAlarm
	ACCESS  read-only
	STATUS  mandatory
	DESCRIPTION "Building 2 Alarm"
		::= { digital_alarms 19 }

Building_1 OBJECT-TYPE
	SYNTAX  DigitalValueSwitch
	ACCESS  read-only
	STATUS  mandatory
	DESCRIPTION "Building 1"
		::= { digital_values 20 }
Building_1_Alarm OBJECT-TYPE
	SYNTAX  DigitalAlarm
	ACCESS  read-only
	STATUS  mandatory
	DESCRIPTION "Building 1 Alarm"
		::= { digital_alarms 20 }

Output_Short OBJECT-TYPE
	SYNTAX  DigitalValueSwitch
	ACCESS  read-only
	STATUS  mandatory
	DESCRIPTION "Output Short"
		::= { digital_values 21 }
Output_Short_Alarm OBJECT-TYPE
	SYNTAX  DigitalAlarm
	ACCESS  read-only
	STATUS  mandatory
	DESCRIPTION "Output Short Alarm"
		::= { digital_alarms 21 }


Open_S1 OBJECT-TYPE
	SYNTAX  DigitalValueSwitch
	ACCESS  read-only
	STATUS  mandatory
	DESCRIPTION "Open S1"
		::= { digital_values 22 }
Open_S1_Alarm OBJECT-TYPE
	SYNTAX  DigitalAlarm
	ACCESS  read-only
	STATUS  mandatory
	DESCRIPTION "Open S1 Alarm"
		::= { digital_alarms 22 }

Open_S2 OBJECT-TYPE
	SYNTAX  DigitalValueSwitch
	ACCESS  read-only
	STATUS  mandatory
	DESCRIPTION "Open S2"
		::= { digital_values 23 }
Open_S2_Alarm OBJECT-TYPE
	SYNTAX  DigitalAlarm
	ACCESS  read-only
	STATUS  mandatory
	DESCRIPTION "Open S2 Alarm"
		::= { digital_alarms 23 }

EPO OBJECT-TYPE
	SYNTAX  DigitalValueSwitch
	ACCESS  read-only
	STATUS  mandatory
	DESCRIPTION "EPO"
		::= { digital_values 24 }
EPO_Alarm OBJECT-TYPE
	SYNTAX  DigitalAlarm
	ACCESS  read-only
	STATUS  mandatory
	DESCRIPTION "EPO Alarm"
		::= { digital_alarms 24 }

Remote_EPO OBJECT-TYPE
	SYNTAX  DigitalValueSwitch
	ACCESS  read-only
	STATUS  mandatory
	DESCRIPTION "Remote EPO"
		::= { digital_values 25 }
Remote_EPO_Alarm OBJECT-TYPE
	SYNTAX  DigitalAlarm
	ACCESS  read-only
	STATUS  mandatory
	DESCRIPTION "Remote EPO Alarm"
		::= { digital_alarms 25 }

XFMR_1_HT OBJECT-TYPE
	SYNTAX  DigitalValueSwitch
	ACCESS  read-only
	STATUS  mandatory
	DESCRIPTION "XFMR 1 HT"
		::= { digital_values 26 }
XFMR_1_HT_Alarm OBJECT-TYPE
	SYNTAX  DigitalAlarm
	ACCESS  read-only
	STATUS  mandatory
	DESCRIPTION "XFMR 1 HT Alarm"
		::= { digital_alarms 26 }

XFMR_1_OT OBJECT-TYPE
	SYNTAX  DigitalValueSwitch
	ACCESS  read-only
	STATUS  mandatory
	DESCRIPTION "XFMR 1 OT"
		::= { digital_values 27 }
XFMR_1_OT_Alarm OBJECT-TYPE
	SYNTAX  DigitalAlarm
	ACCESS  read-only
	STATUS  mandatory
	DESCRIPTION "XFMR 1 OT Alarm"
		::= { digital_alarms 27 }

XFMR_2_HT OBJECT-TYPE
	SYNTAX  DigitalValueSwitch
	ACCESS  read-only
	STATUS  mandatory
	DESCRIPTION "XFMR 2 HT"
		::= { digital_values 28 }
XFMR_2_HT_Alarm OBJECT-TYPE
	SYNTAX  DigitalAlarm
	ACCESS  read-only
	STATUS  mandatory
	DESCRIPTION "XFMR 2 HT Alarm"
		::= { digital_alarms 28 }

XFMR_2_OT OBJECT-TYPE
	SYNTAX  DigitalValueSwitch
	ACCESS  read-only
	STATUS  mandatory
	DESCRIPTION "XFMR 2 OT"
		::= { digital_values 29 }
XFMR_2_OT_Alarm OBJECT-TYPE
	SYNTAX  DigitalAlarm
	ACCESS  read-only
	STATUS  mandatory
	DESCRIPTION "XFMR 2 OT Alarm"
		::= { digital_alarms 29 }

SCR_High_Temp OBJECT-TYPE
	SYNTAX  DigitalValueSCR
	ACCESS  read-only
	STATUS  mandatory
	DESCRIPTION "SCR High Temp"
		::= { digital_values 30 }
SCR_High_Temp_Alarm OBJECT-TYPE
	SYNTAX  DigitalAlarm
	ACCESS  read-only
	STATUS  mandatory
	DESCRIPTION "SCR High Temp Alarm"
		::= { digital_alarms 30 }

SCR_Over_Temp OBJECT-TYPE
	SYNTAX  DigitalValueSCR
	ACCESS  read-only
	STATUS  mandatory
	DESCRIPTION "SCR Over Temp"
		::= { digital_values 31 }
SCR_Over_Temp_Alarm OBJECT-TYPE
	SYNTAX  DigitalAlarm
	ACCESS  read-only
	STATUS  mandatory
	DESCRIPTION "SCR Over Temp Alarm"
		::= { digital_alarms 31 }

Shunt_Trip_1 OBJECT-TYPE
	SYNTAX  DigitalValueSCR
	ACCESS  read-only
	STATUS  mandatory
	DESCRIPTION "Shunt Trip 1"
		::= { digital_values 32 }
Shunt_Trip_1_Alarm OBJECT-TYPE
	SYNTAX  DigitalAlarm
	ACCESS  read-only
	STATUS  mandatory
	DESCRIPTION "Shunt Trip 1 Alarm"
		::= { digital_alarms 32 }

Shunt_Trip_2 OBJECT-TYPE
	SYNTAX  DigitalValueSCR
	ACCESS  read-only
	STATUS  mandatory
	DESCRIPTION "Shunt Trip 2"
		::= { digital_values 33 }
Shunt_Trip_2_Alarm OBJECT-TYPE
	SYNTAX  DigitalAlarm
	ACCESS  read-only
	STATUS  mandatory
	DESCRIPTION "Shunt Trip 2 Alarm"
		::= { digital_alarms 33 }

DCPS_S1V OBJECT-TYPE
	SYNTAX  DigitalValueSwitch
	ACCESS  read-only
	STATUS  mandatory
	DESCRIPTION "DCPS S1V"
		::= { digital_values 34 }
DCPS_S1V_Alarm OBJECT-TYPE
	SYNTAX  DigitalAlarm
	ACCESS  read-only
	STATUS  mandatory
	DESCRIPTION "DCPS S1V Alarm"
		::= { digital_alarms 34 }

DCPS_S2V OBJECT-TYPE
	SYNTAX  DigitalValueSwitch
	ACCESS  read-only
	STATUS  mandatory
	DESCRIPTION "DCPS S2V"
		::= { digital_values 35 }
DCPS_S2V_Alarm OBJECT-TYPE
	SYNTAX  DigitalAlarm
	ACCESS  read-only
	STATUS  mandatory
	DESCRIPTION "DCPS S2V Alarm"
		::= { digital_alarms 35 }

DCPS_OV OBJECT-TYPE
	SYNTAX  DigitalValueSwitch
	ACCESS  read-only
	STATUS  mandatory
	DESCRIPTION "DCPS OV"
		::= { digital_values 36 }
DCPS_OV_Alarm OBJECT-TYPE
	SYNTAX  DigitalAlarm
	ACCESS  read-only
	STATUS  mandatory
	DESCRIPTION "DCPS OV Alarm"
		::= { digital_alarms 36 }

S1_Rotation OBJECT-TYPE
	SYNTAX  DigitalValueSwitch
	ACCESS  read-only
	STATUS  mandatory
	DESCRIPTION "S1 Rotation"
		::= { digital_values 37 }
S1_Rotation_Alarm OBJECT-TYPE
	SYNTAX  DigitalAlarm
	ACCESS  read-only
	STATUS  mandatory
	DESCRIPTION "S1 Rotation Alarm"
		::= { digital_alarms 37 }

S2_Rotation OBJECT-TYPE
	SYNTAX  DigitalValueSwitch
	ACCESS  read-only
	STATUS  mandatory
	DESCRIPTION "S2 Rotation"
		::= { digital_values 38 }
S2_Rotation_Alarm OBJECT-TYPE
	SYNTAX  DigitalAlarm
	ACCESS  read-only
	STATUS  mandatory
	DESCRIPTION "S2 Rotation Alarm"
		::= { digital_alarms 38 }
On_Source OBJECT-TYPE
	SYNTAX  DigitalValueSwitch
	ACCESS  read-only
	STATUS  mandatory
	DESCRIPTION "On Source"
		::= { digital_values 39 }

On_Source_Alarm OBJECT-TYPE
	SYNTAX  DigitalAlarm
	ACCESS  read-only
	STATUS  mandatory
	DESCRIPTION "On Source Alarm"
		::= { digital_alarms 39 }

Transfer OBJECT-TYPE
	SYNTAX  DigitalValueSwitch
	ACCESS  read-only
	STATUS  mandatory
	DESCRIPTION "Transfer"
		::= { digital_values 40 }

Transfer_Alarm OBJECT-TYPE
	SYNTAX  DigitalAlarm
	ACCESS  read-only
	STATUS  mandatory
	DESCRIPTION "Transfer Alarm"
		::= { digital_alarms 40 }

Shunt_Trip OBJECT-TYPE
	SYNTAX  DigitalValueSwitch
	ACCESS  read-only
	STATUS  mandatory
	DESCRIPTION "Shunt Trip"
		::= { digital_values 41 }

Shunt_Trip_Alarm OBJECT-TYPE
	SYNTAX  DigitalAlarm
	ACCESS  read-only
	STATUS  mandatory
	DESCRIPTION "Shunt Trip Alarm"
		::= { digital_alarms 41 }

EPO_Latched OBJECT-TYPE
	SYNTAX  DigitalValueSwitch
	ACCESS  read-only
	STATUS  mandatory
	DESCRIPTION "EPO Latched"
		::= { digital_values 42 }

EPO_Latched_Alarm OBJECT-TYPE
	SYNTAX  DigitalAlarm
	ACCESS  read-only
	STATUS  mandatory
	DESCRIPTION "EPO Latched Alarm"
		::= { digital_alarms 42 }

SAS_D_Open OBJECT-TYPE
	SYNTAX  DigitalValueSwitch
	ACCESS  read-only
	STATUS  mandatory
	DESCRIPTION "SAS D Open"
		::= { digital_values 43 }

SAS_D_Open_Alarm OBJECT-TYPE
	SYNTAX  DigitalAlarm
	ACCESS  read-only
	STATUS  mandatory
	DESCRIPTION "SAS D Open Alarm"
		::= { digital_alarms 43 }

SAS_D_DC OBJECT-TYPE
	SYNTAX  DigitalValueSwitch
	ACCESS  read-only
	STATUS  mandatory
	DESCRIPTION "SAS D DC"
		::= { digital_values 44 }

SAS_D_DC_Alarm OBJECT-TYPE
	SYNTAX  DigitalAlarm
	ACCESS  read-only
	STATUS  mandatory
	DESCRIPTION "SAS D DC Alarm"
		::= { digital_alarms 44 }

SAS_D_DC_1 OBJECT-TYPE
	SYNTAX  DigitalValueSwitch
	ACCESS  read-only
	STATUS  mandatory
	DESCRIPTION "SAS D DC 1"
		::= { digital_values 45 }

SAS_D_DC_1_Alarm OBJECT-TYPE
	SYNTAX  DigitalAlarm
	ACCESS  read-only
	STATUS  mandatory
	DESCRIPTION "SAS D DC 1 Alarm"
		::= { digital_alarms 45 }

SAS_D_DC_2 OBJECT-TYPE
	SYNTAX  DigitalValueSwitch
	ACCESS  read-only
	STATUS  mandatory
	DESCRIPTION "SAS D DC 2"
		::= { digital_values 46 }

SAS_D_DC_2_Alarm OBJECT-TYPE
	SYNTAX  DigitalAlarm
	ACCESS  read-only
	STATUS  mandatory
	DESCRIPTION "SAS D DC 2 Alarm"
		::= { digital_alarms 46 }

SAS_D_DC_Main OBJECT-TYPE
	SYNTAX  DigitalValueSwitch
	ACCESS  read-only
	STATUS  mandatory
	DESCRIPTION "SAS D DC Main"
		::= { digital_values 47 }

SAS_D_DC_Main_Alarm OBJECT-TYPE
	SYNTAX  DigitalAlarm
	ACCESS  read-only
	STATUS  mandatory
	DESCRIPTION "SAS D DC Main Alarm"
		::= { digital_alarms 47 }

SAS_D_Pulse_1 OBJECT-TYPE
	SYNTAX  DigitalValueSwitch
	ACCESS  read-only
	STATUS  mandatory
	DESCRIPTION "SAS D Pulse 1"
		::= { digital_values 48 }

SAS_D_Pulse_1_Alarm OBJECT-TYPE
	SYNTAX  DigitalAlarm
	ACCESS  read-only
	STATUS  mandatory
	DESCRIPTION "SAS D Pulse 1 Alarm"
		::= { digital_alarms 48 }

SAS_D_Pulse_2 OBJECT-TYPE
	SYNTAX  DigitalValueSwitch
	ACCESS  read-only
	STATUS  mandatory
	DESCRIPTION "SAS D Pulse 2"
		::= { digital_values 49 }

SAS_D_Pulse_2_Alarm OBJECT-TYPE
	SYNTAX  DigitalAlarm
	ACCESS  read-only
	STATUS  mandatory
	DESCRIPTION "SAS D Pulse 2 Alarm"
		::= { digital_alarms 49 }

SAS_D_Pulse_M OBJECT-TYPE
	SYNTAX  DigitalValueSwitch
	ACCESS  read-only
	STATUS  mandatory
	DESCRIPTION "SAS D Pulse M"
		::= { digital_values 50 }

SAS_D_Pulse_M_Alarm OBJECT-TYPE
	SYNTAX  DigitalAlarm
	ACCESS  read-only
	STATUS  mandatory
	DESCRIPTION "SAS D Pulse M Alarm"
		::= { digital_alarms 50 }

SAS_D_Voting OBJECT-TYPE
	SYNTAX  DigitalValueSwitch
	ACCESS  read-only
	STATUS  mandatory
	DESCRIPTION "SAS D Voting"
		::= { digital_values 51 }

SAS_D_Voting_Alarm OBJECT-TYPE
	SYNTAX  DigitalAlarm
	ACCESS  read-only
	STATUS  mandatory
	DESCRIPTION "SAS D Voting Alarm"
		::= { digital_alarms 51 }

SAS_D_SCR_1_DC OBJECT-TYPE
	SYNTAX  DigitalValueSwitch
	ACCESS  read-only
	STATUS  mandatory
	DESCRIPTION "SAS D 1 DC"
		::= { digital_values 52 }

SAS_D_SCR_1_DC_Alarm OBJECT-TYPE
	SYNTAX  DigitalAlarm
	ACCESS  read-only
	STATUS  mandatory
	DESCRIPTION "SAS D 1 DC Alarm"
		::= { digital_alarms 52 }

SAS_D_SCR_2_DC OBJECT-TYPE
	SYNTAX  DigitalValueSwitch
	ACCESS  read-only
	STATUS  mandatory
	DESCRIPTION "SAS D 1 DC"
		::= { digital_values 53 }

SAS_D_SCR_2_DC_Alarm OBJECT-TYPE
	SYNTAX  DigitalAlarm
	ACCESS  read-only
	STATUS  mandatory
	DESCRIPTION "SAS D 1 DC Alarm"
		::= { digital_alarms 53 }

SAS_D_Aux_3 OBJECT-TYPE
	SYNTAX  DigitalValueSwitch
	ACCESS  read-only
	STATUS  mandatory
	DESCRIPTION "SAS D Aux 3"
		::= { digital_values 54 }

SAS_D_Aux_3_Alarm OBJECT-TYPE
	SYNTAX  DigitalAlarm
	ACCESS  read-only
	STATUS  mandatory
	DESCRIPTION "SAS D Aux 3 Alarm"
		::= { digital_alarms 54 }

SAS_D_Aux_4 OBJECT-TYPE
	SYNTAX  DigitalValueSwitch
	ACCESS  read-only
	STATUS  mandatory
	DESCRIPTION "SAS D Aux 4"
		::= { digital_values 55 }

SAS_D_Aux_4_Alarm OBJECT-TYPE
	SYNTAX  DigitalAlarm
	ACCESS  read-only
	STATUS  mandatory
	DESCRIPTION "SAS D Aux 4 Alarm"
		::= { digital_alarms 55 }

SAS_D_Aux_5 OBJECT-TYPE
	SYNTAX  DigitalValueSwitch
	ACCESS  read-only
	STATUS  mandatory
	DESCRIPTION "SAS D Aux 5"
		::= { digital_values 56 }

SAS_D_Aux_5_Alarm OBJECT-TYPE
	SYNTAX  DigitalAlarm
	ACCESS  read-only
	STATUS  mandatory
	DESCRIPTION "SAS D Aux 5 Alarm"
		::= { digital_alarms 56 }

SAS_D_Aux_6 OBJECT-TYPE
	SYNTAX  DigitalValueSwitch
	ACCESS  read-only
	STATUS  mandatory
	DESCRIPTION "SAS D Aux 6"
		::= { digital_values 57 }

SAS_D_Aux_6_Alarm OBJECT-TYPE
	SYNTAX  DigitalAlarm
	ACCESS  read-only
	STATUS  mandatory
	DESCRIPTION "SAS D Aux 6 Alarm"
		::= { digital_alarms 57 }

SAS_D_Aux_7 OBJECT-TYPE
	SYNTAX  DigitalValueSwitch
	ACCESS  read-only
	STATUS  mandatory
	DESCRIPTION "SAS D Aux 7"
		::= { digital_values 58 }

SAS_D_Aux_7_Alarm OBJECT-TYPE
	SYNTAX  DigitalAlarm
	ACCESS  read-only
	STATUS  mandatory
	DESCRIPTION "SAS D Aux 7 Alarm"
		::= { digital_alarms 58 }


SAS_1_Fiber_RX OBJECT-TYPE
	SYNTAX  DigitalValueSwitch
	ACCESS  read-only
	STATUS  mandatory
	DESCRIPTION "SAS 1 Fiber"
		::= { digital_values 59 }

SAS_1_Fiber_RX_Alarm OBJECT-TYPE
	SYNTAX  DigitalAlarm
	ACCESS  read-only
	STATUS  mandatory
	DESCRIPTION "SAS 1 Fiber Alarm"
		::= { digital_alarms 59 }


SAS_2_Fiber_RX OBJECT-TYPE
	SYNTAX  DigitalValueSwitch
	ACCESS  read-only
	STATUS  mandatory
	DESCRIPTION "SAS 2 Fiber"
		::= { digital_values 60 }

SAS_2_Fiber_RX_Alarm OBJECT-TYPE
	SYNTAX  DigitalAlarm
	ACCESS  read-only
	STATUS  mandatory
	DESCRIPTION "SAS 2 Fiber Alarm"
		::= { digital_alarms 60 }

SAS_3_Fiber_RX OBJECT-TYPE
	SYNTAX  DigitalValueSwitch
	ACCESS  read-only
	STATUS  mandatory
	DESCRIPTION "SAS 3 Fiber"
		::= { digital_values 61 }

SAS_3_Fiber_RX_Alarm OBJECT-TYPE
	SYNTAX  DigitalAlarm
	ACCESS  read-only
	STATUS  mandatory
	DESCRIPTION "SAS 3 Fiber Alarm"
		::= { digital_alarms 61 }

SAS_1_Output OBJECT-TYPE
	SYNTAX  DigitalValueSwitch
	ACCESS  read-only
	STATUS  mandatory
	DESCRIPTION "SAS 1 Output"
		::= { digital_values 62 }

SAS_1_Output_Alarm OBJECT-TYPE
	SYNTAX  DigitalAlarm
	ACCESS  read-only
	STATUS  mandatory
	DESCRIPTION "SAS 1 Output Alarm"
		::= { digital_alarms 62 }

SAS_2_Output OBJECT-TYPE
	SYNTAX  DigitalValueSwitch
	ACCESS  read-only
	STATUS  mandatory
	DESCRIPTION "SAS 2 Output"
		::= { digital_values 63 }

SAS_2_Output_Alarm OBJECT-TYPE
	SYNTAX  DigitalAlarm
	ACCESS  read-only
	STATUS  mandatory
	DESCRIPTION "SAS 2 Output Alarm"
		::= { digital_alarms 63 }

SAS_3_Output OBJECT-TYPE
	SYNTAX  DigitalValueSwitch
	ACCESS  read-only
	STATUS  mandatory
	DESCRIPTION "SAS 3 Output"
		::= { digital_values 64 }

SAS_3_Output_Alarm OBJECT-TYPE
	SYNTAX  DigitalAlarm
	ACCESS  read-only
	STATUS  mandatory
	DESCRIPTION "SAS 3 Output Alarm"
		::= { digital_alarms 64 }

SAS_In_Control OBJECT-TYPE
	SYNTAX  DigitalValueSwitch
	ACCESS  read-only
	STATUS  mandatory
	DESCRIPTION "SAS In Control"
		::= { digital_values 65 }

SAS_In_Control_Alarm OBJECT-TYPE
	SYNTAX  DigitalAlarm
	ACCESS  read-only
	STATUS  mandatory
	DESCRIPTION "SAS In Control Alarm"
		::= { digital_alarms 65 }

SAS_1_SCR_1 OBJECT-TYPE
	SYNTAX  DigitalValueSCR
	ACCESS  read-only
	STATUS  mandatory
	DESCRIPTION "SAS 1 SCR 1"
		::= { digital_values 66 }

SAS_1_SCR_1_Alarm OBJECT-TYPE
	SYNTAX  DigitalAlarm
	ACCESS  read-only
	STATUS  mandatory
	DESCRIPTION "SAS 1 SCR 1 Alarm"
		::= { digital_alarms 66 }


SAS_2_SCR_1 OBJECT-TYPE
	SYNTAX  DigitalValueSCR
	ACCESS  read-only
	STATUS  mandatory
	DESCRIPTION "SAS 2 SCR 1"
		::= { digital_values 67 }

SAS_2_SCR_1_Alarm OBJECT-TYPE
	SYNTAX  DigitalAlarm
	ACCESS  read-only
	STATUS  mandatory
	DESCRIPTION "SAS 2 SCR 1 Alarm"
		::= { digital_alarms 67 }

SAS_3_SCR_1 OBJECT-TYPE
	SYNTAX  DigitalValueSCR
	ACCESS  read-only
	STATUS  mandatory
	DESCRIPTION "SAS 3 SCR 1"
		::= { digital_values 68 }

SAS_3_SCR_1_Alarm OBJECT-TYPE
	SYNTAX  DigitalAlarm
	ACCESS  read-only
	STATUS  mandatory
	DESCRIPTION "SAS 3 SCR 1 Alarm"
		::= { digital_alarms 68 }

SAS_1_SCR_2 OBJECT-TYPE
	SYNTAX  DigitalValueSCR
	ACCESS  read-only
	STATUS  mandatory
	DESCRIPTION "SAS 1 SCR 2"
		::= { digital_values 69 }

SAS_1_SCR_2_Alarm OBJECT-TYPE
	SYNTAX  DigitalAlarm
	ACCESS  read-only
	STATUS  mandatory
	DESCRIPTION "SAS 1 SCR 2 Alarm"
		::= { digital_alarms 69 }

SAS_2_SCR_2 OBJECT-TYPE
	SYNTAX  DigitalValueSCR
	ACCESS  read-only
	STATUS  mandatory
	DESCRIPTION "SAS 2 SCR 2"
		::= { digital_values 70 }

SAS_2_SCR_2_Alarm OBJECT-TYPE
	SYNTAX  DigitalAlarm
	ACCESS  read-only
	STATUS  mandatory
	DESCRIPTION "SAS 2 SCR 2 Alarm"
		::= { digital_alarms 70 }

SAS_3_SCR_2 OBJECT-TYPE
	SYNTAX  DigitalValueSCR
	ACCESS  read-only
	STATUS  mandatory
	DESCRIPTION "SAS 3 SCR 2"
		::= { digital_values 71 }

SAS_3_SCR_2_Alarm OBJECT-TYPE
	SYNTAX  DigitalAlarm
	ACCESS  read-only
	STATUS  mandatory
	DESCRIPTION "SAS 3 SCR 2 Alarm"
		::= { digital_alarms 71 }

SAS_SCR_1 OBJECT-TYPE
	SYNTAX  DigitalValueSCR
	ACCESS  read-only
	STATUS  mandatory
	DESCRIPTION "SAS SCR 1"
		::= { digital_values 72 }

SAS_SCR_1_Alarm OBJECT-TYPE
	SYNTAX  DigitalAlarm
	ACCESS  read-only
	STATUS  mandatory
	DESCRIPTION "SAS SCR 1  Alarm"
		::= { digital_alarms 72 }

SAS_SCR_2 OBJECT-TYPE
	SYNTAX  DigitalValueSCR
	ACCESS  read-only
	STATUS  mandatory
	DESCRIPTION "SAS SCR 2"
		::= { digital_values 73 }

SAS_SCR_2_Alarm OBJECT-TYPE
	SYNTAX  DigitalAlarm
	ACCESS  read-only
	STATUS  mandatory
	DESCRIPTION "SAS SCR 2  Alarm"
		::= { digital_alarms 73 }

SAS_1_S1_Gated OBJECT-TYPE
	SYNTAX  DigitalValueSCR
	ACCESS  read-only
	STATUS  mandatory
	DESCRIPTION "SAS 1 S1 Gated"
		::= { digital_values 74 }

SAS_1_S1_Gated_Alarm OBJECT-TYPE
	SYNTAX  DigitalAlarm
	ACCESS  read-only
	STATUS  mandatory
	DESCRIPTION "SAS 1 S1 Gated Alarm"
		::= { digital_alarms 74 }

SAS_2_S1_Gated OBJECT-TYPE
	SYNTAX  DigitalValueSwitch
	ACCESS  read-only
	STATUS  mandatory
	DESCRIPTION "SAS 2 S1 Gated"
		::= { digital_values 75 }

SAS_2_S1_Gated_Alarm OBJECT-TYPE
	SYNTAX  DigitalAlarm
	ACCESS  read-only
	STATUS  mandatory
	DESCRIPTION "SAS 2 S1 Gated Alarm"
		::= { digital_alarms 75 }

SAS_3_S1_Gated OBJECT-TYPE
	SYNTAX  DigitalValueSwitch
	ACCESS  read-only
	STATUS  mandatory
	DESCRIPTION "SAS 3 S1 Gated"
		::= { digital_values 76 }

SAS_3_S1_Gated_Alarm OBJECT-TYPE
	SYNTAX  DigitalAlarm
	ACCESS  read-only
	STATUS  mandatory
	DESCRIPTION "SAS 3 S1 Gated Alarm"
		::= { digital_alarms 76 }

SAS_1_S2_Gated OBJECT-TYPE
	SYNTAX  DigitalValueSwitch
	ACCESS  read-only
	STATUS  mandatory
	DESCRIPTION "SAS 1 S2 Gated"
		::= { digital_values 77 }

SAS_1_S2_Gated_Alarm OBJECT-TYPE
	SYNTAX  DigitalAlarm
	ACCESS  read-only
	STATUS  mandatory
	DESCRIPTION "SAS 1 S2 Gated Alarm"
		::= { digital_alarms 77 }

SAS_2_S2_Gated OBJECT-TYPE
	SYNTAX  DigitalValueSwitch
	ACCESS  read-only
	STATUS  mandatory
	DESCRIPTION "SAS 2 S2 Gated"
		::= { digital_values 78 }

SAS_2_S2_Gated_Alarm OBJECT-TYPE
	SYNTAX  DigitalAlarm
	ACCESS  read-only
	STATUS  mandatory
	DESCRIPTION "SAS 2 S2 Gated Alarm"
		::= { digital_alarms 78 }

SAS_3_S2_Gated OBJECT-TYPE
	SYNTAX  DigitalValueSwitch
	ACCESS  read-only
	STATUS  mandatory
	DESCRIPTION "SAS 3 S2 Gated"
		::= { digital_values 79 }

SAS_3_S2_Gated_Alarm OBJECT-TYPE
	SYNTAX  DigitalAlarm
	ACCESS  read-only
	STATUS  mandatory
	DESCRIPTION "SAS 3 S2 Gated Alarm"
		::= { digital_alarms 79 }

SAS_S1_Gated OBJECT-TYPE
	SYNTAX  DigitalValueSwitch
	ACCESS  read-only
	STATUS  mandatory
	DESCRIPTION "SAS S1 Gated"
		::= { digital_values 80 }

SAS_S1_Gated_Alarm OBJECT-TYPE
	SYNTAX  DigitalAlarm
	ACCESS  read-only
	STATUS  mandatory
	DESCRIPTION "SAS S1 Gated Alarm"
		::= { digital_alarms 80 }

SAS_S2_Gated OBJECT-TYPE
	SYNTAX  DigitalValueSwitch
	ACCESS  read-only
	STATUS  mandatory
	DESCRIPTION "SAS S2 Gated"
		::= { digital_values 81 }

SAS_S2_Gated_Alarm OBJECT-TYPE
	SYNTAX  DigitalAlarm
	ACCESS  read-only
	STATUS  mandatory
	DESCRIPTION "SAS S2 Gated Alarm"
		::= { digital_alarms 81 }

SAS_D_Timeout OBJECT-TYPE
	SYNTAX  DigitalValueSwitch
	ACCESS  read-only
	STATUS  mandatory
	DESCRIPTION "SAS D Timeout"
		::= { digital_values 82 }

SAS_D_Timeout_Alarm OBJECT-TYPE
	SYNTAX  DigitalAlarm
	ACCESS  read-only
	STATUS  mandatory
	DESCRIPTION "SAS D Timeout Alarm"
		::= { digital_alarms 82 }

SAS_1_Timeout OBJECT-TYPE
	SYNTAX  DigitalValueSwitch
	ACCESS  read-only
	STATUS  mandatory
	DESCRIPTION "SAS 1 Timeout"
		::= { digital_values 83 }

SAS_1_Timeout_Alarm OBJECT-TYPE
	SYNTAX  DigitalAlarm
	ACCESS  read-only
	STATUS  mandatory
	DESCRIPTION "SAS 1 Timeout Alarm"
		::= { digital_alarms 83 }

SAS_2_Timeout OBJECT-TYPE
	SYNTAX  DigitalValueSwitch
	ACCESS  read-only
	STATUS  mandatory
	DESCRIPTION "SAS 2 Timeout"
		::= { digital_values 84 }

SAS_2_Timeout_Alarm OBJECT-TYPE
	SYNTAX  DigitalAlarm
	ACCESS  read-only
	STATUS  mandatory
	DESCRIPTION "SAS 2 Timeout Alarm"
		::= { digital_alarms 84 }

SAS_3_Timeout OBJECT-TYPE
	SYNTAX  DigitalValueSwitch
	ACCESS  read-only
	STATUS  mandatory
	DESCRIPTION "SAS 3 Timeout"
		::= { digital_values 85 }

ROI_Timeout OBJECT-TYPE
	SYNTAX  DigitalValueSwitch
	ACCESS  read-only
	STATUS  mandatory
	DESCRIPTION "Mimic Timeout"
		::= { digital_values 86 }

ROI_Timeout_Alarm OBJECT-TYPE
	SYNTAX  DigitalAlarm
	ACCESS  read-only
	STATUS  mandatory
	DESCRIPTION "Mimic Timeout Alarm"
		::= { digital_alarms 86 }

JCPS_Timeout OBJECT-TYPE
	SYNTAX  DigitalValueSwitch
	ACCESS  read-only
	STATUS  mandatory
	DESCRIPTION "PS Timeout"
		::= { digital_values 87 }

JCPS_Timeout_Alarm OBJECT-TYPE
	SYNTAX  DigitalAlarm
	ACCESS  read-only
	STATUS  mandatory
	DESCRIPTION "PS Timeout Alarm"
		::= { digital_alarms 87 }

SAS_TX_1_Down OBJECT-TYPE
	SYNTAX  DigitalValueSwitch
	ACCESS  read-only
	STATUS  mandatory
	DESCRIPTION "SAS RX 1 Down"
		::= { digital_values 88 }

SAS_TX_1_Down_Alarm OBJECT-TYPE
	SYNTAX  DigitalAlarm
	ACCESS  read-only
	STATUS  mandatory
	DESCRIPTION "SAS RX 1 Down"
		::= { digital_alarms 88 }

SAS_TX_2_Down OBJECT-TYPE
	SYNTAX  DigitalValueSwitch
	ACCESS  read-only
	STATUS  mandatory
	DESCRIPTION "SAS RX 2 Down"
		::= { digital_values 89 }

SAS_TX_2_Down_Alarm OBJECT-TYPE
	SYNTAX  DigitalAlarm
	ACCESS  read-only
	STATUS  mandatory
	DESCRIPTION "SAS RX 2 Down"
		::= { digital_alarms 89 }

SAS_TX_3_Down OBJECT-TYPE
	SYNTAX  DigitalValueSwitch
	ACCESS  read-only
	STATUS  mandatory
	DESCRIPTION "SAS RX 3 Down"
		::= { digital_values 90 }

SAS_TX_3_Down_Alarm OBJECT-TYPE
	SYNTAX  DigitalAlarm
	ACCESS  read-only
	STATUS  mandatory
	DESCRIPTION "SAS RX 3 Down"
		::= { digital_alarms 90 }

SAS_Down OBJECT-TYPE
	SYNTAX  DigitalValueSwitch
	ACCESS  read-only
	STATUS  mandatory
	DESCRIPTION "SAS Down"
		::= { digital_values 91 }

SAS_Down_Alarm OBJECT-TYPE
	SYNTAX  DigitalAlarm
	ACCESS  read-only
	STATUS  mandatory
	DESCRIPTION "SAS Down Alarm"
		::= { digital_alarms 91 }

SAS_1_Fuse_A OBJECT-TYPE
	SYNTAX  DigitalValueSwitch
	ACCESS  read-only
	STATUS  mandatory
	DESCRIPTION "SAS 1 Fuse A"
		::= { digital_values 92 }

SAS_1_Fuse_A_Alarm OBJECT-TYPE
	SYNTAX  DigitalAlarm
	ACCESS  read-only
	STATUS  mandatory
	DESCRIPTION "SAS 1 Fuse A Alarm"
		::= { digital_alarms 92 }

SAS_1_Fuse_B OBJECT-TYPE
	SYNTAX  DigitalValueSwitch
	ACCESS  read-only
	STATUS  mandatory
	DESCRIPTION "SAS 1 Fuse B"
		::= { digital_values 93 }

SAS_1_Fuse_B_Alarm OBJECT-TYPE
	SYNTAX  DigitalAlarm
	ACCESS  read-only
	STATUS  mandatory
	DESCRIPTION "SAS 1 Fuse B Alarm"
		::= { digital_alarms 93 }

SAS_1_Fuse_C OBJECT-TYPE
	SYNTAX  DigitalValueSwitch
	ACCESS  read-only
	STATUS  mandatory
	DESCRIPTION "SAS 1 Fuse C"
		::= { digital_values 94 }

SAS_1_Fuse_C_Alarm OBJECT-TYPE
	SYNTAX  DigitalAlarm
	ACCESS  read-only
	STATUS  mandatory
	DESCRIPTION "SAS 1 Fuse C Alarm"
		::= { digital_alarms 94 }

SAS_1_Aux_3 OBJECT-TYPE
	SYNTAX  DigitalValueSwitch
	ACCESS  read-only
	STATUS  mandatory
	DESCRIPTION "SAS 1 Aux 3"
		::= { digital_values 95 }

SAS_1_Aux_3_Alarm OBJECT-TYPE
	SYNTAX  DigitalAlarm
	ACCESS  read-only
	STATUS  mandatory
	DESCRIPTION "SAS 1 Aux 3 Alarm"
		::= { digital_alarms 95 }

SAS_1_Aux_4 OBJECT-TYPE
	SYNTAX  DigitalValueSwitch
	ACCESS  read-only
	STATUS  mandatory
	DESCRIPTION "SAS 1 Aux 4"
		::= { digital_values 96 }

SAS_1_Aux_4_Alarm OBJECT-TYPE
	SYNTAX  DigitalAlarm
	ACCESS  read-only
	STATUS  mandatory
	DESCRIPTION "SAS 1 Aux 4 Alarm"
		::= { digital_alarms 96 }

SAS_1_Aux_5 OBJECT-TYPE
	SYNTAX  DigitalValueSwitch
	ACCESS  read-only
	STATUS  mandatory
	DESCRIPTION "SAS 1 Aux 5"
		::= { digital_values 97 }

SAS_1_Aux_5_Alarm OBJECT-TYPE
	SYNTAX  DigitalAlarm
	ACCESS  read-only
	STATUS  mandatory
	DESCRIPTION "SAS 1 Aux 5 Alarm"
		::= { digital_alarms 97 }

SAS_1_Aux_6 OBJECT-TYPE
	SYNTAX  DigitalValueSwitch
	ACCESS  read-only
	STATUS  mandatory
	DESCRIPTION "SAS 1 Aux 6"
		::= { digital_values 98 }

SAS_1_Aux_6_Alarm OBJECT-TYPE
	SYNTAX  DigitalAlarm
	ACCESS  read-only
	STATUS  mandatory
	DESCRIPTION "SAS 1 Aux 6 Alarm"
		::= { digital_alarms 98 }

SAS_1_Aux_7 OBJECT-TYPE
	SYNTAX  DigitalValueSwitch
	ACCESS  read-only
	STATUS  mandatory
	DESCRIPTION "SAS 1 Aux 7"
		::= { digital_values 99 }

SAS_1_Aux_7_Alarm OBJECT-TYPE
	SYNTAX  DigitalAlarm
	ACCESS  read-only
	STATUS  mandatory
	DESCRIPTION "SAS 1 Aux 7 Alarm"
		::= { digital_alarms 99 }

SAS_2_Fuse_A OBJECT-TYPE
	SYNTAX  DigitalValueSwitch
	ACCESS  read-only
	STATUS  mandatory
	DESCRIPTION "SAS 2 Fuse A"
		::= { digital_values 100 }

SAS_2_Fuse_A_Alarm OBJECT-TYPE
	SYNTAX  DigitalAlarm
	ACCESS  read-only
	STATUS  mandatory
	DESCRIPTION "SAS 2 Fuse A Alarm"
		::= { digital_alarms 100 }

SAS_2_Fuse_B OBJECT-TYPE
	SYNTAX  DigitalValueSwitch
	ACCESS  read-only
	STATUS  mandatory
	DESCRIPTION "SAS 2 Fuse B"
		::= { digital_values 101 }

SAS_2_Fuse_B_Alarm OBJECT-TYPE
	SYNTAX  DigitalAlarm
	ACCESS  read-only
	STATUS  mandatory
	DESCRIPTION "SAS 2 Fuse B Alarm"
		::= { digital_alarms 101 }

SAS_2_Fuse_C OBJECT-TYPE
	SYNTAX  DigitalValueSwitch
	ACCESS  read-only
	STATUS  mandatory
	DESCRIPTION "SAS 2 Fuse C"
		::= { digital_values 102 }

SAS_2_Fuse_C_Alarm OBJECT-TYPE
	SYNTAX  DigitalAlarm
	ACCESS  read-only
	STATUS  mandatory
	DESCRIPTION "SAS 2 Fuse C Alarm"
		::= { digital_alarms 102 }

SAS_2_Aux_3 OBJECT-TYPE
	SYNTAX  DigitalValueSwitch
	ACCESS  read-only
	STATUS  mandatory
	DESCRIPTION "SAS 2 Aux 3"
		::= { digital_values 103 }

SAS_2_Aux_3_Alarm OBJECT-TYPE
	SYNTAX  DigitalAlarm
	ACCESS  read-only
	STATUS  mandatory
	DESCRIPTION "SAS 2 Aux 3 Alarm"
		::= { digital_alarms 103 }

SAS_2_Aux_4 OBJECT-TYPE
	SYNTAX  DigitalValueSwitch
	ACCESS  read-only
	STATUS  mandatory
	DESCRIPTION "SAS 2 Aux 4"
		::= { digital_values 104 }

SAS_2_Aux_4_Alarm OBJECT-TYPE
	SYNTAX  DigitalAlarm
	ACCESS  read-only
	STATUS  mandatory
	DESCRIPTION "SAS 2 Aux 4 Alarm"
		::= { digital_alarms 104 }

SAS_2_Aux_5 OBJECT-TYPE
	SYNTAX  DigitalValueSwitch
	ACCESS  read-only
	STATUS  mandatory
	DESCRIPTION "SAS 2 Aux 5"
		::= { digital_values 105 }

SAS_2_Aux_5_Alarm OBJECT-TYPE
	SYNTAX  DigitalAlarm
	ACCESS  read-only
	STATUS  mandatory
	DESCRIPTION "SAS 2 Aux 5 Alarm"
		::= { digital_alarms 105 }

SAS_2_Aux_6 OBJECT-TYPE
	SYNTAX  DigitalValueSwitch
	ACCESS  read-only
	STATUS  mandatory
	DESCRIPTION "SAS 2 Aux 6"
		::= { digital_values 106 }

SAS_2_Aux_6_Alarm OBJECT-TYPE
	SYNTAX  DigitalAlarm
	ACCESS  read-only
	STATUS  mandatory
	DESCRIPTION "SAS 2 Aux 6 Alarm"
		::= { digital_alarms 106 }

SAS_2_Aux_7 OBJECT-TYPE
	SYNTAX  DigitalValueSwitch
	ACCESS  read-only
	STATUS  mandatory
	DESCRIPTION "SAS 2 Aux 7"
		::= { digital_values 107 }

SAS_2_Aux_7_Alarm OBJECT-TYPE
	SYNTAX  DigitalAlarm
	ACCESS  read-only
	STATUS  mandatory
	DESCRIPTION "SAS 2 Aux 7 Alarm"
		::= { digital_alarms 107 }

SAS_3_Fuse_A OBJECT-TYPE
	SYNTAX  DigitalValueSwitch
	ACCESS  read-only
	STATUS  mandatory
	DESCRIPTION "SAS 3 Fuse A"
		::= { digital_values 108 }

SAS_3_Fuse_A_Alarm OBJECT-TYPE
	SYNTAX  DigitalAlarm
	ACCESS  read-only
	STATUS  mandatory
	DESCRIPTION "SAS 3 Fuse A Alarm"
		::= { digital_alarms 108 }

SAS_3_Fuse_B OBJECT-TYPE
	SYNTAX  DigitalValueSwitch
	ACCESS  read-only
	STATUS  mandatory
	DESCRIPTION "SAS 3 Fuse B"
		::= { digital_values 109 }

SAS_3_Fuse_B_Alarm OBJECT-TYPE
	SYNTAX  DigitalAlarm
	ACCESS  read-only
	STATUS  mandatory
	DESCRIPTION "SAS 3 Fuse B Alarm"
		::= { digital_alarms 109 }

SAS_3_Fuse_C OBJECT-TYPE
	SYNTAX  DigitalValueSwitch
	ACCESS  read-only
	STATUS  mandatory
	DESCRIPTION "SAS 3 Fuse C"
		::= { digital_values 110 }

SAS_3_Fuse_C_Alarm OBJECT-TYPE
	SYNTAX  DigitalAlarm
	ACCESS  read-only
	STATUS  mandatory
	DESCRIPTION "SAS 3 Fuse C Alarm"
		::= { digital_alarms 110 }

SAS_3_Aux_3 OBJECT-TYPE
	SYNTAX  DigitalValueSwitch
	ACCESS  read-only
	STATUS  mandatory
	DESCRIPTION "SAS 3 Aux 3"
		::= { digital_values 111 }

SAS_3_Aux_3_Alarm OBJECT-TYPE
	SYNTAX  DigitalAlarm
	ACCESS  read-only
	STATUS  mandatory
	DESCRIPTION "SAS 3 Aux 3 Alarm"
		::= { digital_alarms 111 }

SAS_3_Aux_4 OBJECT-TYPE
	SYNTAX  DigitalValueSwitch
	ACCESS  read-only
	STATUS  mandatory
	DESCRIPTION "SAS 3 Aux 4"
		::= { digital_values 112 }

SAS_3_Aux_4_Alarm OBJECT-TYPE
	SYNTAX  DigitalAlarm
	ACCESS  read-only
	STATUS  mandatory
	DESCRIPTION "SAS 3 Aux 4 Alarm"
		::= { digital_alarms 112 }

SAS_3_Aux_5 OBJECT-TYPE
	SYNTAX  DigitalValueSwitch
	ACCESS  read-only
	STATUS  mandatory
	DESCRIPTION "SAS 3 Aux 5"
		::= { digital_values 113 }

SAS_3_Aux_5_Alarm OBJECT-TYPE
	SYNTAX  DigitalAlarm
	ACCESS  read-only
	STATUS  mandatory
	DESCRIPTION "SAS 3 Aux 5 Alarm"
		::= { digital_alarms 113 }

SAS_3_Aux_6 OBJECT-TYPE
	SYNTAX  DigitalValueSwitch
	ACCESS  read-only
	STATUS  mandatory
	DESCRIPTION "SAS 3 Aux 6"
		::= { digital_values 114 }

SAS_3_Aux_6_Alarm OBJECT-TYPE
	SYNTAX  DigitalAlarm
	ACCESS  read-only
	STATUS  mandatory
	DESCRIPTION "SAS 3 Aux 6 Alarm"
		::= { digital_alarms 114 }

SAS_3_Aux_7 OBJECT-TYPE
	SYNTAX  DigitalValueSwitch
	ACCESS  read-only
	STATUS  mandatory
	DESCRIPTION "SAS 3 Aux 7"
		::= { digital_values 115 }

SAS_3_Aux_7_Alarm OBJECT-TYPE
	SYNTAX  DigitalAlarm
	ACCESS  read-only
	STATUS  mandatory
	DESCRIPTION "SAS 3 Aux 7 Alarm"
		::= { digital_alarms 115 }

SAS_1_S1_Alarm OBJECT-TYPE
	SYNTAX  DigitalAlarm
	ACCESS  read-only
	STATUS  mandatory
	DESCRIPTION "SAS 1 S1 Alarm"
		::= { digital_alarms 116 }

SAS_2_S1_Alarm OBJECT-TYPE
	SYNTAX  DigitalAlarm
	ACCESS  read-only
	STATUS  mandatory
	DESCRIPTION "SAS 2 S1 Alarm"
		::= { digital_alarms 117 }
SAS_3_S1_Alarm OBJECT-TYPE
	SYNTAX  DigitalAlarm
	ACCESS  read-only
	STATUS  mandatory
	DESCRIPTION "SAS 3 S1 Alarm"
		::= { digital_alarms 118 }

SAS_1_S2_Alarm OBJECT-TYPE
	SYNTAX  DigitalAlarm
	ACCESS  read-only
	STATUS  mandatory
	DESCRIPTION "SAS 1 S2 Alarm"
		::= { digital_alarms 119 }

SAS_2_S2_Alarm OBJECT-TYPE
	SYNTAX  DigitalAlarm
	ACCESS  read-only
	STATUS  mandatory
	DESCRIPTION "SAS 2 S2 Alarm"
		::= { digital_alarms 120 }
SAS_3_S2_Alarm OBJECT-TYPE
	SYNTAX  DigitalAlarm
	ACCESS  read-only
	STATUS  mandatory
	DESCRIPTION "SAS 3 S2 Alarm"
		::= { digital_alarms 121 }

SAS_RIO_Alarm OBJECT-TYPE
	SYNTAX  DigitalAlarm
	ACCESS  read-only
	STATUS  mandatory
	DESCRIPTION "SAS ROI Alarm"
		::= { digital_alarms 122 }

I_Line_1_Aux OBJECT-TYPE
	SYNTAX  DigitalValueSwitch
	ACCESS  read-only
	STATUS  mandatory
	DESCRIPTION "I Line 1 Aux"
		::= { digital_values 123 }

I_Line_1_Aux_Alarm OBJECT-TYPE
	SYNTAX  DigitalAlarm
	ACCESS  read-only
	STATUS  mandatory
	DESCRIPTION "I Line 1 Aux Alarm"
		::= { digital_alarms 123 }

I_Line_1_Bell OBJECT-TYPE
	SYNTAX  DigitalValueSwitch
	ACCESS  read-only
	STATUS  mandatory
	DESCRIPTION "I Line 1 Bell"
		::= { digital_values 124 }

I_Line_1_Bell_Alarm OBJECT-TYPE
	SYNTAX  DigitalAlarm
	ACCESS  read-only
	STATUS  mandatory
	DESCRIPTION "I Line 1 Bell Alarm"
		::= { digital_alarms 124 }

I_Line_2_Aux OBJECT-TYPE
	SYNTAX  DigitalValueSwitch
	ACCESS  read-only
	STATUS  mandatory
	DESCRIPTION "I Line 2 Aux"
		::= { digital_values 125 }

I_Line_2_Aux_Alarm OBJECT-TYPE
	SYNTAX  DigitalAlarm
	ACCESS  read-only
	STATUS  mandatory
	DESCRIPTION "I Line 2 Aux Alarm"
		::= { digital_alarms 125 }

I_Line_2_Bell OBJECT-TYPE
	SYNTAX  DigitalValueSwitch
	ACCESS  read-only
	STATUS  mandatory
	DESCRIPTION "I Line 2 Bell"
		::= { digital_values 126 }

I_Line_2_Bell_Alarm OBJECT-TYPE
	SYNTAX  DigitalAlarm
	ACCESS  read-only
	STATUS  mandatory
	DESCRIPTION "I Line 2 Bell Alarm"
		::= { digital_alarms 126 }

I_Line_3_Aux OBJECT-TYPE
	SYNTAX  DigitalValueSwitch
	ACCESS  read-only
	STATUS  mandatory
	DESCRIPTION "I Line 3 Aux"
		::= { digital_values 127 }

I_Line_3_Aux_Alarm OBJECT-TYPE
	SYNTAX  DigitalAlarm
	ACCESS  read-only
	STATUS  mandatory
	DESCRIPTION "I Line 3 Aux Alarm"
		::= { digital_alarms 127 }

I_Line_3_Bell OBJECT-TYPE
	SYNTAX  DigitalValueSwitch
	ACCESS  read-only
	STATUS  mandatory
	DESCRIPTION "I Line 3 Bell"
		::= { digital_values 128 }

I_Line_3_Bell_Alarm OBJECT-TYPE
	SYNTAX  DigitalAlarm
	ACCESS  read-only
	STATUS  mandatory
	DESCRIPTION "I Line 3 Bell Alarm"
		::= { digital_alarms 128 }

I_Line_4_Aux OBJECT-TYPE
	SYNTAX  DigitalValueSwitch
	ACCESS  read-only
	STATUS  mandatory
	DESCRIPTION "I Line 4 Aux"
		::= { digital_values 129 }

I_Line_4_Aux_Alarm OBJECT-TYPE
	SYNTAX  DigitalAlarm
	ACCESS  read-only
	STATUS  mandatory
	DESCRIPTION "I Line 4 Aux Alarm"
		::= { digital_alarms 129 }

I_Line_4_Bell OBJECT-TYPE
	SYNTAX  DigitalValueSwitch
	ACCESS  read-only
	STATUS  mandatory
	DESCRIPTION "I Line 4 Bell"
		::= { digital_values 130 }

I_Line_4_Bell_Alarm OBJECT-TYPE
	SYNTAX  DigitalAlarm
	ACCESS  read-only
	STATUS  mandatory
	DESCRIPTION "I Line 4 Bell Alarm"
		::= { digital_alarms 130 }

I_Line_5_Aux OBJECT-TYPE
	SYNTAX  DigitalValueSwitch
	ACCESS  read-only
	STATUS  mandatory
	DESCRIPTION "I Line 5 Aux"
		::= { digital_values 131 }

I_Line_5_Aux_Alarm OBJECT-TYPE
	SYNTAX  DigitalAlarm
	ACCESS  read-only
	STATUS  mandatory
	DESCRIPTION "I Line 5 Aux Alarm"
		::= { digital_alarms 131 }

I_Line_5_Bell OBJECT-TYPE
	SYNTAX  DigitalValueSwitch
	ACCESS  read-only
	STATUS  mandatory
	DESCRIPTION "I Line 5 Bell"
		::= { digital_values 132 }

I_Line_5_Bell_Alarm OBJECT-TYPE
	SYNTAX  DigitalAlarm
	ACCESS  read-only
	STATUS  mandatory
	DESCRIPTION "I Line 5 Bell Alarm"
		::= { digital_alarms 132 }

I_Line_6_Aux OBJECT-TYPE
	SYNTAX  DigitalValueSwitch
	ACCESS  read-only
	STATUS  mandatory
	DESCRIPTION "I Line 6 Aux"
		::= { digital_values 133 }

I_Line_6_Aux_Alarm OBJECT-TYPE
	SYNTAX  DigitalAlarm
	ACCESS  read-only
	STATUS  mandatory
	DESCRIPTION "I Line 6 Aux Alarm"
		::= { digital_alarms 133 }

I_Line_6_Bell OBJECT-TYPE
	SYNTAX  DigitalValueSwitch
	ACCESS  read-only
	STATUS  mandatory
	DESCRIPTION "I Line 6 Bell"
		::= { digital_values 134 }

I_Line_6_Bell_Alarm OBJECT-TYPE
	SYNTAX  DigitalAlarm
	ACCESS  read-only
	STATUS  mandatory
	DESCRIPTION "I Line 6 Bell Alarm"
		::= { digital_alarms 134 }

I_Line_7_Aux OBJECT-TYPE
	SYNTAX  DigitalValueSwitch
	ACCESS  read-only
	STATUS  mandatory
	DESCRIPTION "I Line 7 Aux"
		::= { digital_values 135 }

I_Line_7_Aux_Alarm OBJECT-TYPE
	SYNTAX  DigitalAlarm
	ACCESS  read-only
	STATUS  mandatory
	DESCRIPTION "I Line 7 Aux Alarm"
		::= { digital_alarms 135 }

I_Line_7_Bell OBJECT-TYPE
	SYNTAX  DigitalValueSwitch
	ACCESS  read-only
	STATUS  mandatory
	DESCRIPTION "I Line 7 Bell"
		::= { digital_values 136 }

I_Line_7_Bell_Alarm OBJECT-TYPE
	SYNTAX  DigitalAlarm
	ACCESS  read-only
	STATUS  mandatory
	DESCRIPTION "I Line 7 Bell Alarm"
		::= { digital_alarms 136 }

I_Line_8_Aux OBJECT-TYPE
	SYNTAX  DigitalValueSwitch
	ACCESS  read-only
	STATUS  mandatory
	DESCRIPTION "I Line 8 Aux"
		::= { digital_values 137 }

I_Line_8_Aux_Alarm OBJECT-TYPE
	SYNTAX  DigitalAlarm
	ACCESS  read-only
	STATUS  mandatory
	DESCRIPTION "I Line 8 Aux Alarm"
		::= { digital_alarms 137 }

I_Line_8_Bell OBJECT-TYPE
	SYNTAX  DigitalValueSwitch
	ACCESS  read-only
	STATUS  mandatory
	DESCRIPTION "I Line 8 Bell"
		::= { digital_values 138 }

I_Line_8_Bell_Alarm OBJECT-TYPE
	SYNTAX  DigitalAlarm
	ACCESS  read-only
	STATUS  mandatory
	DESCRIPTION "I Line 8 Bell Alarm"
		::= { digital_alarms 138 }

Neutral_Wrong OBJECT-TYPE
	SYNTAX  DigitalValueSwitch
	ACCESS  read-only
	STATUS  mandatory
	DESCRIPTION "Neutral Wrong"
		::= { digital_values 139 }

Neutral_Wrong_Alarm OBJECT-TYPE
	SYNTAX  DigitalAlarm
	ACCESS  read-only
	STATUS  mandatory
	DESCRIPTION "Neutral Wrong Alarm"
		::= { digital_alarms 139 }

Neutral_Logic OBJECT-TYPE
	SYNTAX  DigitalValueSwitch
	ACCESS  read-only
	STATUS  mandatory
	DESCRIPTION "Neutral Logic"
		::= { digital_values 140 }

Neutral_Logic_Alarm OBJECT-TYPE
	SYNTAX  DigitalAlarm
	ACCESS  read-only
	STATUS  mandatory
	DESCRIPTION "Neutral Logic Alarm"
		::= { digital_alarms 140 }

Door OBJECT-TYPE
	SYNTAX  DigitalValueSwitch
	ACCESS  read-only
	STATUS  mandatory
	DESCRIPTION "Door"
		::= { digital_values 141 }

Door_Alarm OBJECT-TYPE
	SYNTAX  DigitalAlarm
	ACCESS  read-only
	STATUS  mandatory
	DESCRIPTION "Door Alarm"
		::= { digital_alarms 141 }

Crosscurrent_1 OBJECT-TYPE
	SYNTAX  DigitalValueSwitch
	ACCESS  read-only
	STATUS  mandatory
	DESCRIPTION "Crosscurrent 1"
		::= { digital_values 142 }

Crosscurrent_1_Alarm OBJECT-TYPE
	SYNTAX  DigitalAlarm
	ACCESS  read-only
	STATUS  mandatory
	DESCRIPTION "Crosscurrent 1 Alarm"
		::= { digital_alarms 142 }

Crosscurrent_2 OBJECT-TYPE
	SYNTAX  DigitalValueSwitch
	ACCESS  read-only
	STATUS  mandatory
	DESCRIPTION "Crosscurrent 2"
		::= { digital_values 143 }

Crosscurrent_2_Alarm OBJECT-TYPE
	SYNTAX  DigitalAlarm
	ACCESS  read-only
	STATUS  mandatory
	DESCRIPTION "Crosscurrent 2 Alarm"
		::= { digital_alarms 143 }

Switch_State OBJECT-TYPE
	SYNTAX  DigitalValueSwitch
	ACCESS  read-only
	STATUS  mandatory
	DESCRIPTION "Switch State"
		::= { digital_values 144 }

Switch_State_Alarm OBJECT-TYPE
	SYNTAX  DigitalAlarm
	ACCESS  read-only
	STATUS  mandatory
	DESCRIPTION "Switch State Alarm"
		::= { digital_alarms 144 }

Maintenance OBJECT-TYPE
	SYNTAX  DigitalValueSwitch
	ACCESS  read-only
	STATUS  mandatory
	DESCRIPTION "Maintenance"
		::= { digital_values 145 }

Maintenance_Alarm OBJECT-TYPE
	SYNTAX  DigitalAlarm
	ACCESS  read-only
	STATUS  mandatory
	DESCRIPTION "Maintenance Alarm"
		::= { digital_alarms 145 }

Contractor_Timeout OBJECT-TYPE
	SYNTAX  DigitalValueSwitch
	ACCESS  read-only
	STATUS  mandatory
	DESCRIPTION "Contractor Timeout"
		::= { digital_values 146 }

Contractor_Timeout_Alarm OBJECT-TYPE
	SYNTAX  DigitalAlarm
	ACCESS  read-only
	STATUS  mandatory
	DESCRIPTION "Contractor Timeout Alarm"
		::= { digital_alarms 146 }

Contractor_DC1 OBJECT-TYPE
	SYNTAX  DigitalValueSwitch
	ACCESS  read-only
	STATUS  mandatory
	DESCRIPTION "Contractor DC1"
		::= { digital_values 147 }

Contractor_DC1_Alarm OBJECT-TYPE
	SYNTAX  DigitalAlarm
	ACCESS  read-only
	STATUS  mandatory
	DESCRIPTION "Contractor DC1 Alarm"
		::= { digital_alarms 147 }

Contractor_DC2 OBJECT-TYPE
	SYNTAX  DigitalValueSwitch
	ACCESS  read-only
	STATUS  mandatory
	DESCRIPTION "Contractor DC2"
		::= { digital_values 148 }

Contractor_DC2_Alarm OBJECT-TYPE
	SYNTAX  DigitalAlarm
	ACCESS  read-only
	STATUS  mandatory
	DESCRIPTION "Contractor DC2 Alarm"
		::= { digital_alarms 148 }

Summary OBJECT-TYPE
	SYNTAX  DigitalValueSwitch
	ACCESS  read-only
	STATUS  mandatory
	DESCRIPTION "Summary"
		::= { digital_values 149 }

Summary_Alarm OBJECT-TYPE
	SYNTAX  DigitalAlarm
	ACCESS  read-only
	STATUS  mandatory
	DESCRIPTION "Summary Alarm"
		::= { digital_alarms 149 }

END
