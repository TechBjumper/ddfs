--
-- Alphacool V2.6.MIB
-- MIB generated by Airedale
-- Tuesday, 14 April 2009
-- Current to Alphacool software V2.5
--


    	CAREL-alphacool-MIB DEFINITIONS ::= BEGIN
 
		IMPORTS
			OBJECT-GROUP
				FROM SNMPv2-CONF			
			sysContact, sysName, sysLocation			
				FROM SNMPv2-MIB
			enterprises, MODULE-IDENTITY, OBJECT-TYPE, Integer32			
				FROM SNMPv2-SMI;		
		
        alphacoolMIB MODULE-IDENTITY
      		LAST-UPDATED  "200904141017Z"		-- April 14, 2009 at 10:17 GMT
      		ORGANIZATION  "Airedale International Air Conditioning"
      		CONTACT-INFO
                "
                        Airedale International Air Conditioning
                        Leeds Road,
                       	Rawdon, Leeds. LS19 6JY
                        Tel: +00 (44) 113 239 1000
                "
      		DESCRIPTION
                "This is the MIB module for the Alphacool device, using pCOWeb SNMP."
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
   			DESCRIPTION "Code of the Agent. 2=pCOWeb."
		::= { systm 2 }
		
		-- 1.3.6.1.4.1.9839.2
		instruments OBJECT IDENTIFIER ::= { carel 2 }
		
		-- 1.3.6.1.4.1.9839.2.0
 		pCOWebInfo OBJECT IDENTIFIER ::= { instruments 0 }
		

		-- 1.3.6.1.4.1.9839.2.0.10
		pCOStatusgroup OBJECT IDENTIFIER ::= { pCOWebInfo 10 }
		
		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }
		
		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.




	-- 1.3.6.1.4.1.9839.2.1.1
	digitalObjects OBJECT IDENTIFIER ::= { alphacoolMIB 1 }

	  -- 1.3.6.1.4.1.9839.2.1.1.1
       remote-on-off OBJECT-TYPE
                    SYNTAX Integer32 (0..1)
                    UNITS "N/A"
                    MAX-ACCESS read-only
                    STATUS current
                    DESCRIPTION "Remote On/Off digital input"
                    ::= { digitalObjects 1 }

        -- 1.3.6.1.4.1.9839.2.1.1.2
       	airflow-switch OBJECT-TYPE
                    SYNTAX Integer32 (0..1)
                    UNITS "N/A"
                    MAX-ACCESS read-only
                    STATUS current
                    DESCRIPTION "Airflow Switch digital input"
                    ::= { digitalObjects 2 } 
                    
         -- 1.3.6.1.4.1.9839.2.1.1.3
        filter-switch OBJECT-TYPE
                    SYNTAX Integer32 (0..1)
                    UNITS "N/A"
                    MAX-ACCESS read-only
                    STATUS current
                    DESCRIPTION "Filter Switch input"
                    ::= { digitalObjects 3 }

	-- 1.3.6.1.4.1.9839.2.1.1.4
        ohco OBJECT-TYPE
                    SYNTAX Integer32 (0..1)
                    UNITS "N/A"
                    MAX-ACCESS read-only
                    STATUS current
                    DESCRIPTION "Overheat-cut-out input"
                    ::= { digitalObjects 4 }

	-- 1.3.6.1.4.1.9839.2.1.1.5
        hum-water-level OBJECT-TYPE
                    SYNTAX Integer32 (0..1)
                    UNITS "N/A"
                    MAX-ACCESS read-only
                    STATUS current
                    DESCRIPTION "Humidifier water level"
                    ::= { digitalObjects 5 }


        -- 1.3.6.1.4.1.9839.2.1.1.7
        fire-smoke OBJECT-TYPE
                    SYNTAX Integer32 (0..1)
                    UNITS "N/A"
                    MAX-ACCESS read-only
                    STATUS current
                    DESCRIPTION "Fire/Smoke/Phase digital input"
                    ::= { digitalObjects 7 }

        -- 1.3.6.1.4.1.9839.2.1.1.8
        water-flood OBJECT-TYPE
                    SYNTAX Integer32 (0..1)
                    UNITS "N/A"
                    MAX-ACCESS read-only
                    STATUS current
                    DESCRIPTION "Water Leak digital input"
                    ::= { digitalObjects 8 }

	-- 1.3.6.1.4.1.9839.2.1.1.9
        lp-switch1 OBJECT-TYPE
                    SYNTAX Integer32 (0..1)
                    UNITS "N/A"
                    MAX-ACCESS read-only
                    STATUS current
                    DESCRIPTION "Low Pressure Switch Circuit 1"
                    ::= { digitalObjects 9 }

	
	-- 1.3.6.1.4.1.9839.2.1.1.10
        lp-switch2 OBJECT-TYPE
                    SYNTAX Integer32 (0..1)
                    UNITS "N/A"
                    MAX-ACCESS read-only
                    STATUS current
                    DESCRIPTION "Low Pressure Switch Circuit 2"
                    ::= { digitalObjects 10 }

	-- 1.3.6.1.4.1.9839.2.1.1.12
        comp1-contactor OBJECT-TYPE
                    SYNTAX Integer32 (0..1)
                    UNITS "N/A"
                    MAX-ACCESS read-only
                    STATUS current
                    DESCRIPTION "Compressor 1 Contactor Status"
                    ::= { digitalObjects 12 }

	-- 1.3.6.1.4.1.9839.2.1.1.13
        comp2-contactor OBJECT-TYPE
                    SYNTAX Integer32 (0..1)
                    UNITS "N/A"
                    MAX-ACCESS read-only
                    STATUS current
                    DESCRIPTION "Compressor 2 Contactor Status"
                    ::= { digitalObjects 13 }

	-- 1.3.6.1.4.1.9839.2.1.1.15
        comp-1 OBJECT-TYPE
                    SYNTAX Integer32 (0..1)
                    UNITS "N/A"
                    MAX-ACCESS read-only
                    STATUS current
                    DESCRIPTION "Compressor 1 Output"
                    ::= { digitalObjects 15 }


	-- 1.3.6.1.4.1.9839.2.1.1.16
        comp-2 OBJECT-TYPE
                    SYNTAX Integer32 (0..1)
                    UNITS "N/A"
                    MAX-ACCESS read-only
                    STATUS current
                    DESCRIPTION "Compressor 2 Output"
                    ::= { digitalObjects 16 }

	-- 1.3.6.1.4.1.9839.2.1.1.18
        heat-1 OBJECT-TYPE
                    SYNTAX Integer32 (0..1)
                    UNITS "N/A"
                    MAX-ACCESS read-only
                    STATUS current
                    DESCRIPTION "Heater 1 Output"
                    ::= { digitalObjects 18 }


        -- 1.3.6.1.4.1.9839.2.1.1.19
        heat-2 OBJECT-TYPE
                    SYNTAX Integer32 (0..1)
                    UNITS "N/A"
                    MAX-ACCESS read-only
                    STATUS current
                    DESCRIPTION "Heater 2 Output"
                    ::= { digitalObjects 19 }

        -- 1.3.6.1.4.1.9839.2.1.1.21
        supply-fan OBJECT-TYPE
                    SYNTAX Integer32 (0..1)
                    UNITS "N/A"
                    MAX-ACCESS read-only
                    STATUS current
                    DESCRIPTION "Supply Fan On"
                    ::= { digitalObjects 21 }

	-- 1.3.6.1.4.1.9839.2.1.1.23
        hum-status OBJECT-TYPE
                    SYNTAX Integer32 (0..1)
                    UNITS "N/A"
                    MAX-ACCESS read-only
                    STATUS current
                    DESCRIPTION "Humidifier Status"
                    ::= { digitalObjects 23 }

	-- 1.3.6.1.4.1.9839.2.1.1.24
        fill-valve OBJECT-TYPE
                    SYNTAX Integer32 (0..1)
                    UNITS "N/A"
                    MAX-ACCESS read-only
                    STATUS current
                    DESCRIPTION "Humidifer Fill Valve"
                    ::= { digitalObjects 24 }

	-- 1.3.6.1.4.1.9839.2.1.1.25
        drain-valve OBJECT-TYPE
                    SYNTAX Integer32 (0..1)
                    UNITS "N/A"
                    MAX-ACCESS read-only
                    STATUS current
                    DESCRIPTION "Humidifier Drain Valve"
                    ::= { digitalObjects 25 }


        -- 1.3.6.1.4.1.9839.2.1.1.26
        non-critical OBJECT-TYPE
                    SYNTAX Integer32 (0..1)
                    UNITS "N/A"
                    MAX-ACCESS read-only
                    STATUS current
                    DESCRIPTION "alarm: Non Critical"
                    ::= { digitalObjects 26 }

        -- 1.3.6.1.4.1.9839.2.1.1.27
       critical	 OBJECT-TYPE
                    SYNTAX Integer32 (0..1)
                    UNITS "N/A"
                    MAX-ACCESS read-only
                    STATUS current
                    DESCRIPTION "alarm: Critical"
                    ::= { digitalObjects 27 }

	
	-- 1.3.6.1.4.1.9839.2.1.1.31
        lp-1 OBJECT-TYPE
                    SYNTAX Integer32 (0..1)
                    UNITS "N/A"
                    MAX-ACCESS read-only
                    STATUS current
                    DESCRIPTION "Low Pressure Switch Circuit 1"
                    ::= { digitalObjects 31 }

	-- 1.3.6.1.4.1.9839.2.1.1.32
        lp-2 OBJECT-TYPE
                    SYNTAX Integer32 (0..1)
                    UNITS "N/A"
                    MAX-ACCESS read-only
                    STATUS current
                    DESCRIPTION "Low Pressure Switch Circuit 2"
                    ::= { digitalObjects 32 }


        -- 1.3.6.1.4.1.9839.2.1.1.34
       airflow-fail-Alarm OBJECT-TYPE
                    SYNTAX Integer32 (0..1)
                    UNITS "N/A"
                    MAX-ACCESS read-only
                    STATUS current
                    DESCRIPTION "alarm: Airflow Fail"
                    ::= { digitalObjects 34 }

	-- 1.3.6.1.4.1.9839.2.1.1.35
        ohco-alarm OBJECT-TYPE
                    SYNTAX Integer32 (0..1)
                    UNITS "N/A"
                    MAX-ACCESS read-only
                    STATUS current
                    DESCRIPTION "alarm: Overheat-cut-out"
                    ::= { digitalObjects 35 }

        -- 1.3.6.1.4.1.9839.2.1.1.36
        fire-smoke-alarm OBJECT-TYPE
                    SYNTAX Integer32 (0..1)
                    UNITS "N/A"
                    MAX-ACCESS read-only
                    STATUS current
                    DESCRIPTION "alarm: Fire or Smoke"
                    ::= { digitalObjects 36 }

        -- 1.3.6.1.4.1.9839.2.1.1.37
       filter-change-alarm OBJECT-TYPE
                    SYNTAX Integer32 (0..1)
                    UNITS "N/A"
                    MAX-ACCESS read-only
                    STATUS current
                    DESCRIPTION "alarm: Filter"
                    ::= { digitalObjects 37 }

        -- 1.3.6.1.4.1.9839.2.1.1.38
       high-room-temp-alarm OBJECT-TYPE
                    SYNTAX Integer32 (0..1)
                    UNITS "N/A"
                    MAX-ACCESS read-only
                    STATUS current
                    DESCRIPTION "alarm: Room Temp High"
                    ::= { digitalObjects 38 }

       -- 1.3.6.1.4.1.9839.2.1.1.39
       low-room-temp-alarm OBJECT-TYPE
                    SYNTAX Integer32 (0..1)
                    UNITS "N/A"
                    MAX-ACCESS read-only
                    STATUS current
                    DESCRIPTION "alarm: Room Temp Low"
                    ::= { digitalObjects 39 }
                    
        -- 1.3.6.1.4.1.9839.2.1.1.40
       high-hum-alarm OBJECT-TYPE
                    SYNTAX Integer32 (0..1)
                    UNITS "N/A"
                    MAX-ACCESS read-only
                    STATUS current
                    DESCRIPTION "alarm: High Humidity"
                    ::= { digitalObjects 40 }

        -- 1.3.6.1.4.1.9839.2.1.1.41
       low-hUm-alarm OBJECT-TYPE
                    SYNTAX Integer32 (0..1)
                    UNITS "N/A"
                    MAX-ACCESS read-only
                    STATUS current
                    DESCRIPTION "alarm: Low Humidity"
                    ::= { digitalObjects 41 }

	-- 1.3.6.1.4.1.9839.2.1.1.42
        comp-1-maint OBJECT-TYPE
                    SYNTAX Integer32 (0..1)
                    UNITS "N/A"
                    MAX-ACCESS read-only
                    STATUS current
                    DESCRIPTION "alarm: compressor 1 maintenance"
                    ::= { digitalObjects 42 }

	-- 1.3.6.1.4.1.9839.2.1.1.43
        comp-2-maint OBJECT-TYPE
                    SYNTAX Integer32 (0..1)
                    UNITS "N/A"
                    MAX-ACCESS read-only
                    STATUS current
                    DESCRIPTION "alarm: compressor 2 maintenance"
                    ::= { digitalObjects 43 }

	-- 1.3.6.1.4.1.9839.2.1.1.45
        fan-maint OBJECT-TYPE
                    SYNTAX Integer32 (0..1)
                    UNITS "N/A"
                    MAX-ACCESS read-only
                    STATUS current
                    DESCRIPTION "alarm: supply fan maintenance"
                    ::= { digitalObjects 45 }

	-- 1.3.6.1.4.1.9839.2.1.1.46
        room-sensor-fail OBJECT-TYPE
                    SYNTAX Integer32 (0..1)
                    UNITS "N/A"
                    MAX-ACCESS read-only
                    STATUS current
                    DESCRIPTION "alarm: room temp sensor failure"
                    ::= { digitalObjects 46 }

	-- 1.3.6.1.4.1.9839.2.1.1.47
        room-humidity-fail OBJECT-TYPE
                    SYNTAX Integer32 (0..1)
                    UNITS "N/A"
                    MAX-ACCESS read-only
                    STATUS current
                    DESCRIPTION "alarm: room humidity sensor failure"
                    ::= { digitalObjects 47 }

	-- 1.3.6.1.4.1.9839.2.1.1.48
        supply-fail OBJECT-TYPE
                    SYNTAX Integer32 (0..1)
                    UNITS "N/A"
                    MAX-ACCESS read-only
                    STATUS current
                    DESCRIPTION "alarm: supply sensor failure"
                    ::= { digitalObjects 48 }

	-- 1.3.6.1.4.1.9839.2.1.1.53
        hum-high-current OBJECT-TYPE
                    SYNTAX Integer32 (0..1)
                    UNITS "N/A"
                    MAX-ACCESS read-only
                    STATUS current
                    DESCRIPTION "alarm: Humidifier High Current"
                    ::= { digitalObjects 53 }

	-- 1.3.6.1.4.1.9839.2.1.1.54
        hum-lack-water OBJECT-TYPE
                    SYNTAX Integer32 (0..1)
                    UNITS "N/A"
                    MAX-ACCESS read-only
                    STATUS current
                    DESCRIPTION "alarm: Humidifier Lack of Water"
                    ::= { digitalObjects 54 }

	-- 1.3.6.1.4.1.9839.2.1.1.55
        hum-low-current OBJECT-TYPE
                    SYNTAX Integer32 (0..1)
                    UNITS "N/A"
                    MAX-ACCESS read-only
                    STATUS current
                    DESCRIPTION "alarm: Humidifier Low Current"
                    ::= { digitalObjects 55 }
	

 	-- 1.3.6.1.4.1.9839.2.1.1.56
       clock-fault-alarm OBJECT-TYPE
                    SYNTAX Integer32 (0..1)
                    UNITS "N/A"
                    MAX-ACCESS read-only
                    STATUS current
                    DESCRIPTION "alarm: Clock Fault"
                    ::= { digitalObjects 56 }


  	-- 1.3.6.1.4.1.9839.2.1.1.62
       comp1-status OBJECT-TYPE
                    SYNTAX Integer32 (0..1)
                    UNITS "N/A"
                    MAX-ACCESS read-only
                    STATUS current
                    DESCRIPTION "alarm: Compressor 1 Status"
                    ::= { digitalObjects 62 }	

	-- 1.3.6.1.4.1.9839.2.1.1.63
       comp2-status OBJECT-TYPE
                    SYNTAX Integer32 (0..1)
                    UNITS "N/A"
                    MAX-ACCESS read-only
                    STATUS current
                    DESCRIPTION "alarm: Compressor 2 Status"
                    ::= { digitalObjects 63 }	

	-- 1.3.6.1.4.1.9839.2.1.1.64
       fridge-leak OBJECT-TYPE
                    SYNTAX Integer32 (0..1)
                    UNITS "N/A"
                    MAX-ACCESS read-only
                    STATUS current
                    DESCRIPTION "alarm: Refrigerant Leak"
                    ::= { digitalObjects 64 }

	-- 1.3.6.1.4.1.9839.2.1.1.65
       hum-maint OBJECT-TYPE
                    SYNTAX Integer32 (0..1)
                    UNITS "N/A"
                    MAX-ACCESS read-only
                    STATUS current
                    DESCRIPTION "alarm: humidifier maintenance"
                    ::= { digitalObjects 65 }

	-- 1.3.6.1.4.1.9839.2.1.1.66
       hum-flow OBJECT-TYPE
                    SYNTAX Integer32 (0..1)
                    UNITS "N/A"
                    MAX-ACCESS read-only
                    STATUS current
                    DESCRIPTION "alarm: Humidifier Water Flow"
                    ::= { digitalObjects 66 }	

        -- 1.3.6.1.4.1.9839.2.1.1.67
       network-failure OBJECT-TYPE
                    SYNTAX Integer32 (0..1)
                    UNITS "N/A"
                    MAX-ACCESS read-only
                    STATUS current
                    DESCRIPTION "alarm: pLAN failure"
                    ::= { digitalObjects 67 }

	 -- 1.3.6.1.4.1.9839.2.1.1.97
       hum-high-conduct OBJECT-TYPE
                    SYNTAX Integer32 (0..1)
                    UNITS "N/A"
                    MAX-ACCESS read-only
                    STATUS current
                    DESCRIPTION "alarm: Humidifier High Conductivity"
                    ::= { digitalObjects 97 }

	-- 1.3.6.1.4.1.9839.2.1.1.98
       hum-high-conduct-w OBJECT-TYPE
                    SYNTAX Integer32 (0..1)
                    UNITS "N/A"
                    MAX-ACCESS read-only
                    STATUS current
                    DESCRIPTION "Warning: Humidifier High Conductivity"
                    ::= { digitalObjects 98 }
                                            
	-- 1.3.6.1.4.1.9839.2.1.1.99
       hum-low-prod OBJECT-TYPE
                    SYNTAX Integer32 (0..1)
                    UNITS "N/A"
                    MAX-ACCESS read-only
                    STATUS current
                    DESCRIPTION "alarm: Humidifier Low Production"
                    ::= { digitalObjects 99 }

	-- 1.3.6.1.4.1.9839.2.1.1.100
       hum-drain OBJECT-TYPE
                    SYNTAX Integer32 (0..1)
                    UNITS "N/A"
                    MAX-ACCESS read-only
                    STATUS current
                    DESCRIPTION "alarm: Humidifier Drain"
                    ::= { digitalObjects 100 }

	-- 1.3.6.1.4.1.9839.2.1.1.101
       hum-high-level OBJECT-TYPE
                    SYNTAX Integer32 (0..1)
                    UNITS "N/A"
                    MAX-ACCESS read-only
                    STATUS current
                    DESCRIPTION "alarm: Humidifier High Level"
                    ::= { digitalObjects 101 }

	-- 1.3.6.1.4.1.9839.2.1.1.102
       hum-pre-ex OBJECT-TYPE
                    SYNTAX Integer32 (0..1)
                    UNITS "N/A"
                    MAX-ACCESS read-only
                    STATUS current
                    DESCRIPTION "alarm: Humidifier Pre-Exhaustion Warning"
                    ::= { digitalObjects 102 }

	-- 1.3.6.1.4.1.9839.2.1.1.103
       hum-foam OBJECT-TYPE
                    SYNTAX Integer32 (0..1)
                    UNITS "N/A"
                    MAX-ACCESS read-only
                    STATUS current
                    DESCRIPTION "alarm: Humidifier Foam Warning"
                    ::= { digitalObjects 103 }

	-- 1.3.6.1.4.1.9839.2.1.1.104
       hum-ex OBJECT-TYPE
                    SYNTAX Integer32 (0..1)
                    UNITS "N/A"
                    MAX-ACCESS read-only
                    STATUS current
                    DESCRIPTION "alarm: Humidifier Exhausted Warning"
                    ::= { digitalObjects 104 }

	-- 1.3.6.1.4.1.9839.2.1.1.107
       comp1-trip OBJECT-TYPE
                    SYNTAX Integer32 (0..1)
                    UNITS "N/A"
                    MAX-ACCESS read-only
                    STATUS current
                    DESCRIPTION "alarm: Compressor 1 Trip"
                    ::= { digitalObjects 107 }

	-- 1.3.6.1.4.1.9839.2.1.1.108
       comp2-trip OBJECT-TYPE
                    SYNTAX Integer32 (0..1)
                    UNITS "N/A"
                    MAX-ACCESS read-only
                    STATUS current
                    DESCRIPTION "alarm: Compressor 2 Trip"
                    ::= { digitalObjects 108 }

        -- 1.3.6.1.4.1.9839.2.1.1.110
       high-supply-alarm OBJECT-TYPE
                    SYNTAX Integer32 (0..1)
                    UNITS "N/A"
                    MAX-ACCESS read-only
                    STATUS current
                    DESCRIPTION "alarm: High Supply Temperature"
                    ::= { digitalObjects 110 }    
                        
       -- 1.3.6.1.4.1.9839.2.1.1.111
       low-supply-alarm OBJECT-TYPE
                    SYNTAX Integer32 (0..1)
                    UNITS "N/A"
                    MAX-ACCESS read-only
                    STATUS current
                    DESCRIPTION "alarm: Low Supply"
                    ::= { digitalObjects 111 }  

	 -- 1.3.6.1.4.1.9839.2.1.1.113
       hum-maint-alarm OBJECT-TYPE
                    SYNTAX Integer32 (0..1)
                    UNITS "N/A"
                    MAX-ACCESS read-only
                    STATUS current
                    DESCRIPTION "alarm: Humidifier Maintenance"
                    ::= { digitalObjects 113 }    
                
  	-- 1.3.6.1.4.1.9839.2.1.1.114
        bms-on-off OBJECT-TYPE
                    SYNTAX Integer32 (0..1)
                    UNITS "N/A"
                    MAX-ACCESS read-write
                    STATUS current
                    DESCRIPTION "Enable Unit by SNMP/BMS"
                    ::= { digitalObjects 114 }                  
        
        -- 1.3.6.1.4.1.9839.2.1.1.115
       bms-alarm-reset OBJECT-TYPE
                    SYNTAX Integer32 (0..1)
                    UNITS "N/A"
                    MAX-ACCESS read-write
                    STATUS current
                    DESCRIPTION "Alarm Reset via SNMP/BMS"
                    ::= { digitalObjects 115 }

	
      

        -- 1.3.6.1.4.1.9839.2.1.2
        analogObjects OBJECT IDENTIFIER ::= { alphacoolMIB 2 }

       
        -- 1.3.6.1.4.1.9839.2.1.2.1
        room-humidity OBJECT-TYPE
                    SYNTAX Integer32 (-32767..32767)
                    UNITS "%RH x 10"
                    MAX-ACCESS read-only
                    STATUS current
                    DESCRIPTION "Room Humidity"
                    ::= { analogObjects 1 }

	  -- 1.3.6.1.4.1.9839.2.1.2.2
        hum-conductivity OBJECT-TYPE
                    SYNTAX Integer32 (-32767..32767)
                    UNITS "USM"
                    MAX-ACCESS read-only
                    STATUS current
                    DESCRIPTION "Humidifier Conductivity"
                    ::= { analogObjects 2 }

	 -- 1.3.6.1.4.1.9839.2.1.2.3
        hum-current OBJECT-TYPE
                    SYNTAX Integer32 (-32767..32767)
                    UNITS "USM"
                    MAX-ACCESS read-only
                    STATUS current
                    DESCRIPTION "HUmidifier Current"
                    ::= { analogObjects 3 }

        -- 1.3.6.1.4.1.9839.2.1.2.4
        room-temp OBJECT-TYPE
                    SYNTAX Integer32 (-32767..32767)
                    UNITS "deg C x10"
                    MAX-ACCESS read-only
                    STATUS current
                    DESCRIPTION "Room Air Temperature"
                    ::= { analogObjects 4 }

 	-- 1.3.6.1.4.1.9839.2.1.2.5
        supply-temp OBJECT-TYPE
                    SYNTAX Integer32 (-32767..32767)
                    UNITS "deg C x10"
                    MAX-ACCESS read-only
                    STATUS current
                    DESCRIPTION "Supply Air Temp"
                    ::= { analogObjects 5 } 
                               
                           
        -- 1.3.6.1.4.1.9839.2.1.2.12
        temp-setpoint OBJECT-TYPE
                    SYNTAX Integer32 (0..999)
                    UNITS "deg C x10"
                    MAX-ACCESS read-write
                    STATUS current
                    DESCRIPTION "Return Air Temperature Setpoint"
                    DEFVAL { 200 }
                    ::= { analogObjects 12 }

	                    
        -- 1.3.6.1.4.1.9839.2.1.2.13
        hum-setpoint OBJECT-TYPE
                    SYNTAX Integer32 (0..999)
                    UNITS "%RH x10"
                    MAX-ACCESS read-write
                    STATUS current
                    DESCRIPTION "Humidity Setpoint"
                    DEFVAL { 200 }
                    ::= { analogObjects 13 }

	-- 1.3.6.1.4.1.9839.2.1.2.29
        supply-fan-op OBJECT-TYPE
                    SYNTAX Integer32 (-32767..32767)
                    UNITS "% x10"
                    MAX-ACCESS read-only
                    STATUS current
                    DESCRIPTION "Supply Fan Output"
                    ::= { analogObjects 29 }

	-- 1.3.6.1.4.1.9839.2.1.2.30
        cct1-condenser OBJECT-TYPE
                    SYNTAX Integer32 (-32767..32767)
                    UNITS "% x10"
                    MAX-ACCESS read-only
                    STATUS current
                    DESCRIPTION "Circuit 1 Condenser Fan Output"
                    ::= { analogObjects 30 }

	-- 1.3.6.1.4.1.9839.2.1.2.31
        cct2-condenser OBJECT-TYPE
                    SYNTAX Integer32 (-32767..32767)
                    UNITS "% x10"
                    MAX-ACCESS read-only
                    STATUS current
                    DESCRIPTION "Circuit 2 Condenser Fan Output"
                    ::= { analogObjects 31 }
                      
        -- 1.3.6.1.4.1.9839.2.1.2.40
        fan-hours-high OBJECT-TYPE
                    SYNTAX Integer32 (-32767..32767)
                    UNITS "hours x10"
                    MAX-ACCESS read-only
                    STATUS current
                    DESCRIPTION "Main Fan Hours Run - High"
                    ::= { analogObjects 40 }

	-- 1.3.6.1.4.1.9839.2.1.2.41
        fan-hours-low OBJECT-TYPE
                    SYNTAX Integer32 (-32767..32767)
                    UNITS "hours x10"
                    MAX-ACCESS read-only
                    STATUS current
                    DESCRIPTION "Main Fan Hours Run - Low"
                    ::= { analogObjects 41 }

	-- 1.3.6.1.4.1.9839.2.1.2.42
        hum-hours-high OBJECT-TYPE
                    SYNTAX Integer32 (-32767..32767)
                    UNITS "hours x10"
                    MAX-ACCESS read-only
                    STATUS current
                    DESCRIPTION "Humidifier Hours Run - High"
                    ::= { analogObjects 42 }

	-- 1.3.6.1.4.1.9839.2.1.2.43
        hum-hours-low OBJECT-TYPE
                    SYNTAX Integer32 (-32767..32767)
                    UNITS "hours x10"
                    MAX-ACCESS read-only
                    STATUS current
                    DESCRIPTION "Humidifier Hours Run - Low"
                    ::= { analogObjects 43 }

	-- 1.3.6.1.4.1.9839.2.1.2.44
        cp1-hours-high OBJECT-TYPE
                    SYNTAX Integer32 (-32767..32767)
                    UNITS "hours x10"
                    MAX-ACCESS read-only
                    STATUS current
                    DESCRIPTION "Compressor 1 Hours Run - High"
                    ::= { analogObjects 44 }

	
	-- 1.3.6.1.4.1.9839.2.1.2.45
        cp1-hours-low OBJECT-TYPE
                    SYNTAX Integer32 (-32767..32767)
                    UNITS "hours x10"
                    MAX-ACCESS read-only
                    STATUS current
                    DESCRIPTION "Compressor 1 Hours Run - Low"
                    ::= { analogObjects 45 }

	
	-- 1.3.6.1.4.1.9839.2.1.2.46
        cp2-hours-high OBJECT-TYPE
                    SYNTAX Integer32 (-32767..32767)
                    UNITS "hours x10"
                    MAX-ACCESS read-only
                    STATUS current
                    DESCRIPTION "Compressor 2 Hours Run - High"
                    ::= { analogObjects 46 }

	
	-- 1.3.6.1.4.1.9839.2.1.2.47
        cp2-hours-low OBJECT-TYPE
                    SYNTAX Integer32 (-32767..32767)
                    UNITS "hours x10"
                    MAX-ACCESS read-only
                    STATUS current
                    DESCRIPTION "Compressor 2 Hours Run - Low"
                    ::= { analogObjects 47 }

	-- 1.3.6.1.4.1.9839.2.1.2.50
        fridge-leak-level OBJECT-TYPE
                    SYNTAX Integer32 (-32767..32767)
                    UNITS "ppm x10"
                    MAX-ACCESS read-only
                    STATUS current
                    DESCRIPTION "Refrigerant Leak Level"
                    ::= { analogObjects 50 }


	END
