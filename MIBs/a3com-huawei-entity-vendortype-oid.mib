-- =================================================================
-- Copyright (C) 2001,2002 by  Huawei-3Com TECHNOLOGIES. All rights reserved.
--
-- Description:the definition of Huawei-3Com Entity Vendortype OID
-- Reference:
-- Version: V3.1
-- History:
-- V1.0 2004.05.13  Created by lvzhenfeng, modified by gaolong.
-- V1.1 2004.05.22  Adjusted by gaolong and lvzhenfeng.
--   1. Adjust module name to h3cEntityVendorTypeOID and its location is set to { h3c 3 }.
--   2. Rename module name prefix from h3cevtModule to h3cevtModuleRt_ 
--   and h3cevtModuleSw_ for routers and switchs seperately.
--   3. Add h3cevtSubModuleRouter and h3cevtSubModuleSwitch under h3cevtModule.
--   4. Split port type into two groups, one for routers, another for switchs.
-- V1.11 2004.6.17 add h3cevtHotSwapFan node by limeng for garibaldi
-- V1.12 2004.7.19 add h3cevtModuleSwitchType {117-138}
-- V1.13 2004.7.29 add h3cevtPortSwitchType {50-58}
-- V1.14 2004.8.12 add h3cevtModuleSw_LSA1FP8U(h3cevtModuleSwitchType 139) 
-- V1.15 2004.8.25 change emunation name
--                     from h3cevtModuleSw_LS81SFCA(120) to h3cevtModuleSw_LS81SRPG0(120),
--                     from h3cevtModuleSw_LS81SFCB(121) to h3cevtModuleSw_LS81SRPG1(121),
--                     from h3cevtModuleSw_LS81SFCC(122) to h3cevtModuleSw_LS81SRPG2(122),
--                     from h3cevtModuleSw_LS81SFCD(123) to h3cevtModuleSw_LS81SRPG3(123).
--                    modify comments for these emunations as well.
-- V1.2  2004.8.26 add sub identifier of h3cevtPortSwitchType from 59 to 71.
-- V1.21  2004.09.08 add sub identifier of h3cevtModuleSwitchType from 140 to 148.
-- V1.3  2004-09-14 add subidentifier under h3cevtModuleSwitchType from 149 to 157 by wangyahui
--                  add subidentifier under h3cevtModuleSwitchType from 158 to 159 by kangyinan
--                  add subidentifier under h3cevtModuleSwitchType from 72 to 93 by wangyahui
--                  add subidentifier under h3cevtModuleSwitchType from 94 to 96 by kangyinan
--                  add type description for h3cevtModuleSw_SP4, h3cevtModuleSw_UP1, h3cevtModuleSw_XP4 by kangyinan
-- V2.0 2004-10-12 updated by gaolong
--      Change all underscore('_') characters to hyphen characters('-') because underscore character is not allowed in MIB module.
--      Remove some adjacent hyphens
-- V2.1  2004-10-19 add subidentifier under h3cevtModuleSwitchType from 160 to 162 by kangyinan
--                  add subidentifier under h3cevtPortSwitchType 97 by kangyinan
-- V2.2  2004-09-18 add sub identifier for h3cevtModuleRouterType from 111 to 117 by taotao
-- V2.3  2004-11-18 add sub identifier 2 under h3cevtFan by liyutao 
-- V2.4  2004-11-23 add subidentifier under h3cevtModuleSwitchType from 163 to 166 by zhangchengmei
-- V2.5  2004-12-04 add subidentifier 118 under h3cevtModuleRouterType by lizhiyong
-- V2.6  2004-12-23 add sub identifier 4 to 7 under h3cevtPowerSupply by Zhangjianfeng
--                  add sub identifier 167 to 169 under h3cevtModuleSwitchType by Zhangjianfeng 
-- V2.7  2004-12-26 add subidentifier 170 under h3cevtModuleSwitchType by wangyahui
-- v2.8  2004-12-23 add subidentifier under h3cevtModuleSwitchType from 171 to 172 and
--                  add sub identifier 98 to 99 under h3cevtPortSwitchType by liyue
-- V2.9  2004-12-26 add sub identifier 173 under h3cevtModuleSwitchType by Zhangjianfeng
--                  add sub identifier 100 for 24G cascade port under h3cevtPort by Zhangjianfeng
-- V3.0  2004-01-07 add subidentifier 174 and 175 under h3cevtModuleSwitchType by wangyahui
-- V3.1  2005-01-31 add subidentifier 176 under h3cevtModuleSwitchType by wangyahui
-- =================================================================
A3COM-HUAWEI-ENTITY-VENDORTYPE-OID-MIB DEFINITIONS ::= BEGIN

IMPORTS
	MODULE-IDENTITY
		FROM SNMPv2-SMI
	h3c
		FROM A3COM-HUAWEI-OID-MIB;
	

h3cEntityVendorTypeOID MODULE-IDENTITY
        
        LAST-UPDATED "200403280000Z"
        ORGANIZATION "Huawei-3Com Technologies co.,Ltd."
            CONTACT-INFO 
                " R&D BeiJing, Huawei Technologies co.,Ltd.
                Huawei Bld.,NO.3 Xinxi Rd., 
                Shang-Di Information Industry Base,
                    Hai-Dian District Beijing P.R. China
                Zip:100085 
                Http://www.huawei-3com.com                                       
                E-mail:support@huawei-3com.com "
            DESCRIPTION 
                "The private mib file includes the definiton of the object identifiers 
                on huawei-3com products, which are used by the entPhysicalTable of the ENTITY-MIB
		to uniquely identify the type of each physical entry."
        ::= { h3c 3 }


h3cEntityVendortypeObjects   OBJECT IDENTIFIER ::= { h3cEntityVendorTypeOID 1 }

-- This MIB assigns OIDs for use as the values of entPhysicalVendorType.
-- The subtrees in which the OID values are assigned, are structured
-- into a hierarchy based on the values of RFC 2037's PhysicalClass
-- textual convention.  For reference, the definition of PhysicalClass
-- is as follows:
--
--      PhysicalClass ::= TEXTUAL-CONVENTION
--    	STATUS          current
--    	DESCRIPTION
--             "An enumerated value which provides an indication of the
--            	general hardware type of a particular physical entity."
--      SYNTAX      INTEGER  {
--              other(1),
--              unknown(2),
--              chassis(3),
--              backplane(4),
--              container(5),    e.g. slot or daughter-card holder
--              powerSupply(6),
--              fan(7),
--              sensor(8),
--              module(9),       e.g. plug-in card or daughter-card
--              port(10),
--		stack(11)        e.g., stack of multiple chassis entities
--          }
--

h3cevtOther		OBJECT IDENTIFIER ::= { h3cEntityVendortypeObjects 1 }

-- May be defined detailed in future.

h3cevtOtherUnknownCard	OBJECT IDENTIFIER ::= { h3cevtOther 1 }

h3cevtUnknown 	OBJECT IDENTIFIER ::= { h3cEntityVendortypeObjects 2 }

h3cevtChassis 	OBJECT IDENTIFIER ::= { h3cEntityVendortypeObjects 3 }

-- chassis OID assignments
-- May be substituted by sysObjectID. So none is assigned at present.

--
--backplane    
--	 The enumeration 'backplane' is applicable if the physical
--            entity class is some sort of device for aggregating and
--            forwarding networking traffic, such as a shared backplane in
--            a modular ethernet switch.  Note that an agent may model a
--            backplane as a single physical entity, which is actually
--            implemented as multiple discrete physical components (within
--            a chassis or stack).
--

h3cevtBackplane		OBJECT IDENTIFIER ::= { h3cEntityVendortypeObjects 4 }

--
-- h3cevtContainer section:  
--
h3cevtContainer		OBJECT IDENTIFIER ::= { h3cEntityVendortypeObjects 5 }
--
-- h3cevtPowerSupply section:  
-- 

h3cevtPowerSupply	OBJECT IDENTIFIER ::= { h3cEntityVendortypeObjects 6 }
h3cevtPowerSupplyAC		OBJECT IDENTIFIER ::= { h3cevtPowerSupply 2 }
h3cevtPowerSupplyDC		OBJECT IDENTIFIER ::= { h3cevtPowerSupply 3 }	
h3cevtPowerSupplySTD130W	OBJECT IDENTIFIER ::= { h3cevtPowerSupply 4 }     -- Standard 130W PSU 
h3cevtPowerSupplySTD180W	OBJECT IDENTIFIER ::= { h3cevtPowerSupply 5 }     -- Standard 180W PSU 
h3cevtPowerSupplyPOE24Port	OBJECT IDENTIFIER ::= { h3cevtPowerSupply 6 }     -- 24 Port POE PSU 480W 
h3cevtPowerSupplyPOE48Port	OBJECT IDENTIFIER ::= { h3cevtPowerSupply 7 }     -- 48 Port POE PSU 480W

--
-- h3cevtFan section:  
-- 

h3cevtFan		OBJECT IDENTIFIER ::= { h3cEntityVendortypeObjects 7 }
h3cevtHotSwapFan 	OBJECT IDENTIFIER ::=  {h3cevtFan 1 }
h3cevtNonHotSwapFan 	OBJECT IDENTIFIER ::=  {h3cevtFan 2 }

--
-- h3cevtSensor section:  
-- 
h3cevtSensor		OBJECT IDENTIFIER ::= { h3cEntityVendortypeObjects 8 }
h3cevtSensorTemperature		OBJECT IDENTIFIER ::= { h3cevtSensor 1 }	
h3cevtSensorVoltage		OBJECT IDENTIFIER ::= { h3cevtSensor 2 }		
h3cevtSensorFanSpeed		OBJECT IDENTIFIER ::= { h3cevtSensor 3 }		


--
-- h3cevtModule section:
-- 

h3cevtModule		OBJECT IDENTIFIER ::= { h3cEntityVendortypeObjects 9 }

-- h3cevtModule is subdivided into sections like Router and Switch. These represent
-- cards used only on the router and switch.
-- h3cevtModuleCommonCards contains cards that can be used interchangeably
-- across more than one platform


-- Acronyms used in the h3cevtModule section:
--

h3cevtModuleUnknownCard		OBJECT IDENTIFIER ::= { h3cevtModule 1 }

-- h3cevtModuleCommonCards - cards and subcards common to more
-- than one platform

h3cevtModuleCommonCards 	OBJECT IDENTIFIER ::= { h3cevtModule 2 }

-- h3cevtModuleRouterType cards are slot-cards specific to the Router.
h3cevtModuleRouterType		OBJECT IDENTIFIER ::= { h3cevtModule 3 }

--h3cevtModuleRt-Unavailable               OBJECT IDENTIFIER ::= { h3cevtModuleRouterType 1 }    	     

h3cevtModuleRt-As                          OBJECT IDENTIFIER ::= { h3cevtModuleRouterType 2 } 	     

h3cevtModuleRt-Sa                          OBJECT IDENTIFIER ::= { h3cevtModuleRouterType 3 } 	     

h3cevtModuleRt-Bi                          OBJECT IDENTIFIER ::= { h3cevtModuleRouterType 4 } 	     

h3cevtModuleRt-E12                         OBJECT IDENTIFIER ::= { h3cevtModuleRouterType 5 } 	     

h3cevtModuleRt-E14                         OBJECT IDENTIFIER ::= { h3cevtModuleRouterType 6 } 	     

h3cevtModuleRt-Fe1                         OBJECT IDENTIFIER ::= { h3cevtModuleRouterType 7 } 	     

h3cevtModuleRt-E1                          OBJECT IDENTIFIER ::= { h3cevtModuleRouterType 8 } 	     

h3cevtModuleRt-Fe2                         OBJECT IDENTIFIER ::= { h3cevtModuleRouterType 9 } 	     

h3cevtModuleRt-Vi2                         OBJECT IDENTIFIER ::= { h3cevtModuleRouterType 11 }	     

h3cevtModuleRt-Vi4                         OBJECT IDENTIFIER ::= { h3cevtModuleRouterType 12 }	     

h3cevtModuleRt-Vi30                        OBJECT IDENTIFIER ::= { h3cevtModuleRouterType 13 }	     

h3cevtModuleRt-S1b                         OBJECT IDENTIFIER ::= { h3cevtModuleRouterType 14 }	     

h3cevtModuleRt-Sa2                         OBJECT IDENTIFIER ::= { h3cevtModuleRouterType 15 }	     

h3cevtModuleRt-As16                        OBJECT IDENTIFIER ::= { h3cevtModuleRouterType 16 }	     

h3cevtModuleRt-New8as                      OBJECT IDENTIFIER ::= { h3cevtModuleRouterType 17 }	     

h3cevtModuleRt-Sa1                         OBJECT IDENTIFIER ::= { h3cevtModuleRouterType 18 }	     

h3cevtModuleRt-Fxs2                        OBJECT IDENTIFIER ::= { h3cevtModuleRouterType 19 }	     

h3cevtModuleRt-Fxo2                        OBJECT IDENTIFIER ::= { h3cevtModuleRouterType 20 }	     

h3cevtModuleRt-Em2                         OBJECT IDENTIFIER ::= { h3cevtModuleRouterType 21 }	     

h3cevtModuleRt-Fxs4                        OBJECT IDENTIFIER ::= { h3cevtModuleRouterType 22 }	     

h3cevtModuleRt-Fxo4                        OBJECT IDENTIFIER ::= { h3cevtModuleRouterType 23 }	     

h3cevtModuleRt-Em4                         OBJECT IDENTIFIER ::= { h3cevtModuleRouterType 24 }	     

h3cevtModuleRt-Sab                         OBJECT IDENTIFIER ::= { h3cevtModuleRouterType 25 }	     

h3cevtModuleRt-E1vi                        OBJECT IDENTIFIER ::= { h3cevtModuleRouterType 26 }	     

h3cevtModuleRt-Am12                        OBJECT IDENTIFIER ::= { h3cevtModuleRouterType 27 }	     

h3cevtModuleRt-Am6                         OBJECT IDENTIFIER ::= { h3cevtModuleRouterType 28 }	     

h3cevtModuleRt-Ndec                        OBJECT IDENTIFIER ::= { h3cevtModuleRouterType 29 }	     

h3cevtModuleRt-Newsa2                      OBJECT IDENTIFIER ::= { h3cevtModuleRouterType 30 }	     

h3cevtModuleRt-Aux                         OBJECT IDENTIFIER ::= { h3cevtModuleRouterType 31 }	     

h3cevtModuleRt-Console                     OBJECT IDENTIFIER ::= { h3cevtModuleRouterType 32 }	     

h3cevtModuleRt-Sic-wan                     OBJECT IDENTIFIER ::= { h3cevtModuleRouterType 33 }	     

h3cevtModuleRt-Sic-1fe                     OBJECT IDENTIFIER ::= { h3cevtModuleRouterType 34 }	     

h3cevtModuleRt-Sic-1sa                     OBJECT IDENTIFIER ::= { h3cevtModuleRouterType 35 }	     

h3cevtModuleRt-Sic-3as                     OBJECT IDENTIFIER ::= { h3cevtModuleRouterType 36 }	     

h3cevtModuleRt-Sic-1e1                     OBJECT IDENTIFIER ::= { h3cevtModuleRouterType 37 }	     

h3cevtModuleRt-Sic-1t1                     OBJECT IDENTIFIER ::= { h3cevtModuleRouterType 38 }	     

h3cevtModuleRt-Sic-1bu                     OBJECT IDENTIFIER ::= { h3cevtModuleRouterType 39 }	     

h3cevtModuleRt-Sic-2bu                     OBJECT IDENTIFIER ::= { h3cevtModuleRouterType 40 }	     

h3cevtModuleRt-Sic-1bs                     OBJECT IDENTIFIER ::= { h3cevtModuleRouterType 41 }	     

h3cevtModuleRt-Sic-2bs                     OBJECT IDENTIFIER ::= { h3cevtModuleRouterType 42 }	     

h3cevtModuleRt-Sic-1am                     OBJECT IDENTIFIER ::= { h3cevtModuleRouterType 43 }	     

h3cevtModuleRt-Sic-2am                     OBJECT IDENTIFIER ::= { h3cevtModuleRouterType 44 }	     

h3cevtModuleRt-Sic-1em                     OBJECT IDENTIFIER ::= { h3cevtModuleRouterType 45 }	     

h3cevtModuleRt-Sic-2em                     OBJECT IDENTIFIER ::= { h3cevtModuleRouterType 46 }	     

h3cevtModuleRt-Sic-1fxs                     OBJECT IDENTIFIER ::= { h3cevtModuleRouterType 47 }

h3cevtModuleRt-Sic-2fxs                     OBJECT IDENTIFIER ::= { h3cevtModuleRouterType 48 }	     

h3cevtModuleRt-Sic-1fxo                     OBJECT IDENTIFIER ::= { h3cevtModuleRouterType 49 }	     

h3cevtModuleRt-Sic-2fxo                     OBJECT IDENTIFIER ::= { h3cevtModuleRouterType 50 }	     

h3cevtModuleRt-Fcm6                         OBJECT IDENTIFIER ::= { h3cevtModuleRouterType 51 }

h3cevtModuleRt-Sa8                          OBJECT IDENTIFIER ::= { h3cevtModuleRouterType 52 }

h3cevtModuleRt-T11                          OBJECT IDENTIFIER ::= { h3cevtModuleRouterType 53 }	     

h3cevtModuleRt-T12                          OBJECT IDENTIFIER ::= { h3cevtModuleRouterType 54 }	     

h3cevtModuleRt-T14                          OBJECT IDENTIFIER ::= { h3cevtModuleRouterType 55 }	     

h3cevtModuleRt-T1vi                         OBJECT IDENTIFIER ::= { h3cevtModuleRouterType 56 }

h3cevtModuleRt-Fcm4                         OBJECT IDENTIFIER ::= { h3cevtModuleRouterType 57 }	     

h3cevtModuleRt-Fcm2                         OBJECT IDENTIFIER ::= { h3cevtModuleRouterType 58 }	     

h3cevtModuleRt-Rtb21ce3                     OBJECT IDENTIFIER ::= { h3cevtModuleRouterType 59 }

h3cevtModuleRt-Ame6                         OBJECT IDENTIFIER ::= { h3cevtModuleRouterType 60 }

h3cevtModuleRt-Ame12                        OBJECT IDENTIFIER ::= { h3cevtModuleRouterType 61 }

h3cevtModuleRt-E11-f                        OBJECT IDENTIFIER ::= { h3cevtModuleRouterType 65 }	     

h3cevtModuleRt-E12-f                        OBJECT IDENTIFIER ::= { h3cevtModuleRouterType 66 }	     

h3cevtModuleRt-E14-f                        OBJECT IDENTIFIER ::= { h3cevtModuleRouterType 67 }	     

h3cevtModuleRt-T11-f                        OBJECT IDENTIFIER ::= { h3cevtModuleRouterType 68 }	     

h3cevtModuleRt-T12-f                        OBJECT IDENTIFIER ::= { h3cevtModuleRouterType 69 }	     

h3cevtModuleRt-T14-f                        OBJECT IDENTIFIER ::= { h3cevtModuleRouterType 70 }	     

h3cevtModuleRt-E11-f-17                     OBJECT IDENTIFIER ::= { h3cevtModuleRouterType 71 }

h3cevtModuleRt-T11-f-17                     OBJECT IDENTIFIER ::= { h3cevtModuleRouterType 72 }	     

h3cevtModuleRt-Rtb21ct3                     OBJECT IDENTIFIER ::= { h3cevtModuleRouterType 73 }	     

h3cevtModuleRt-Atmadsl1                     OBJECT IDENTIFIER ::= { h3cevtModuleRouterType 74 }	     

h3cevtModuleRt-Atmadsl2                     OBJECT IDENTIFIER ::= { h3cevtModuleRouterType 75 }	     

h3cevtModuleRt-Atm155m                     OBJECT IDENTIFIER ::= { h3cevtModuleRouterType 76 }

h3cevtModuleRt-Ase8                        OBJECT IDENTIFIER ::= { h3cevtModuleRouterType 77 }

h3cevtModuleRt-Ase16                       OBJECT IDENTIFIER ::= { h3cevtModuleRouterType 78 }

h3cevtModuleRt-Sae4                        OBJECT IDENTIFIER ::= { h3cevtModuleRouterType 79 }

h3cevtModuleRt-Sae2                        OBJECT IDENTIFIER ::= { h3cevtModuleRouterType 80 }	     

h3cevtModuleRt-Atmshdsl1                   OBJECT IDENTIFIER ::= { h3cevtModuleRouterType 90 } 

h3cevtModuleRt-Atmshdsl2                   OBJECT IDENTIFIER ::= { h3cevtModuleRouterType 91 }	      

h3cevtModuleRt-Atmshdsl4                   OBJECT IDENTIFIER ::= { h3cevtModuleRouterType 92 }	      

h3cevtModuleRt-Atm25m                      OBJECT IDENTIFIER ::= { h3cevtModuleRouterType 93 }	      

h3cevtModuleRt-Atme3                       OBJECT IDENTIFIER ::= { h3cevtModuleRouterType 94 }	     	

h3cevtModuleRt-Atmt3                       OBJECT IDENTIFIER ::= { h3cevtModuleRouterType 95 }	      

h3cevtModuleRt-Xdsl-fec                    OBJECT IDENTIFIER ::= { h3cevtModuleRouterType 96 }	      

h3cevtModuleRt-Xdsl-adsl                   OBJECT IDENTIFIER ::= { h3cevtModuleRouterType 97 }	      

h3cevtModuleRt-Xdsl-gshdsl                 OBJECT IDENTIFIER ::= { h3cevtModuleRouterType 98 }	      

h3cevtModuleRt-Xdsl-bri                    OBJECT IDENTIFIER ::= { h3cevtModuleRouterType 99 }	      

h3cevtModuleRt-Xdsl-scc                    OBJECT IDENTIFIER ::= { h3cevtModuleRouterType 100 }

h3cevtModuleRt-Ge1            	           OBJECT IDENTIFIER ::= { h3cevtModuleRouterType 101 }

h3cevtModuleRt-Pos155m                     OBJECT IDENTIFIER ::= { h3cevtModuleRouterType 102 }

h3cevtModuleRt-Cpos            	           OBJECT IDENTIFIER ::= { h3cevtModuleRouterType 103 }

h3cevtModuleRt-Fe1op                       OBJECT IDENTIFIER ::= { h3cevtModuleRouterType 104 }

h3cevtModuleRt-Sae8            	           OBJECT IDENTIFIER ::= { h3cevtModuleRouterType 105 }

h3cevtModuleRt-Atm155m-mm                  OBJECT IDENTIFIER ::= { h3cevtModuleRouterType 106 }

h3cevtModuleRt-Atm155m-sm            	   OBJECT IDENTIFIER ::= { h3cevtModuleRouterType 107 }

h3cevtModuleRt-Atm155m-sml                 OBJECT IDENTIFIER ::= { h3cevtModuleRouterType 108 }

h3cevtModuleRt-Fe1op-sfx       	           OBJECT IDENTIFIER ::= { h3cevtModuleRouterType 109 }

h3cevtModuleRt-Fe1op-mfx       	           OBJECT IDENTIFIER ::= { h3cevtModuleRouterType 110 }

h3cevtModuleRt-Cpos-t1       	           OBJECT IDENTIFIER ::= { h3cevtModuleRouterType 111 }

h3cevtModuleRt-Ge1op       	           OBJECT IDENTIFIER ::= { h3cevtModuleRouterType 112 }

h3cevtModuleRt-Ge2op       	           OBJECT IDENTIFIER ::= { h3cevtModuleRouterType 113 }

h3cevtModuleRt-Ge2       	           OBJECT IDENTIFIER ::= { h3cevtModuleRouterType 114 }

h3cevtModuleRt-Fix-1wan       	           OBJECT IDENTIFIER ::= { h3cevtModuleRouterType 115 }

h3cevtModuleRt-Fix-1sae       	           OBJECT IDENTIFIER ::= { h3cevtModuleRouterType 116 }

h3cevtModuleRt-Cavium       	           OBJECT IDENTIFIER ::= { h3cevtModuleRouterType 117 }
                       	                                                                            
h3cevtModuleRt-Sic1Eth       	           OBJECT IDENTIFIER ::= { h3cevtModuleRouterType 118 }
                       	                                                                            
-- h3cevtModuleSwitchType cards are slot-cards specific to the Switch.
h3cevtModuleSwitchType	OBJECT IDENTIFIER ::= { h3cevtModule 4 }

--h3cevtModuleNULL(0),				 
h3cevtModuleSw-10OR100M                    OBJECT IDENTIFIER ::= { h3cevtModuleSwitchType 1 }  

h3cevtModuleSw-1000BASE-LX-SM              OBJECT IDENTIFIER ::= { h3cevtModuleSwitchType 2 }  

h3cevtModuleSw-1000BASE-SX-MM              OBJECT IDENTIFIER ::= { h3cevtModuleSwitchType 3 }  

h3cevtModuleSw-1000BASE-TX                 OBJECT IDENTIFIER ::= { h3cevtModuleSwitchType 4 }  

h3cevtModuleSw-100M-SINGLEMODE-FX          OBJECT IDENTIFIER ::= { h3cevtModuleSwitchType 5 }  

h3cevtModuleSw-100M-MULTIMODE-FX           OBJECT IDENTIFIER ::= { h3cevtModuleSwitchType 6 }  

h3cevtModuleSw-100M-100BASE-TX             OBJECT IDENTIFIER ::= { h3cevtModuleSwitchType 7 }  

h3cevtModuleSw-100M-HUB                    OBJECT IDENTIFIER ::= { h3cevtModuleSwitchType 8 }  

h3cevtModuleSw-VDSL                        OBJECT IDENTIFIER ::= { h3cevtModuleSwitchType 9 }  

h3cevtModuleSw-STACK                       OBJECT IDENTIFIER ::= { h3cevtModuleSwitchType 10 } 

h3cevtModuleSw-1000BASE-ZENITH-FX          OBJECT IDENTIFIER ::= { h3cevtModuleSwitchType 11 } 

h3cevtModuleSw-1000BASE-LONG-FX            OBJECT IDENTIFIER ::= { h3cevtModuleSwitchType 12 } 

h3cevtModuleSw-ADSL                        OBJECT IDENTIFIER ::= { h3cevtModuleSwitchType 13 } 

h3cevtModuleSw-4T10OR100-4FX100SM          OBJECT IDENTIFIER ::= { h3cevtModuleSwitchType 14 } 

h3cevtModuleSw-4T10OR100-4FX100MM          OBJECT IDENTIFIER ::= { h3cevtModuleSwitchType 15 } 

h3cevtModuleSw-VSPL                        OBJECT IDENTIFIER ::= { h3cevtModuleSwitchType 16 } 

h3cevtModuleSw-ASPL                        OBJECT IDENTIFIER ::= { h3cevtModuleSwitchType 17 } 

h3cevtModuleSw-1000M-SFP                   OBJECT IDENTIFIER ::= { h3cevtModuleSwitchType 18 } 

h3cevtModuleSw-LS82O2CM                    OBJECT IDENTIFIER ::= { h3cevtModuleSwitchType 19 } 

h3cevtModuleSw-LS82P2CM                    OBJECT IDENTIFIER ::= { h3cevtModuleSwitchType 20 } 

h3cevtModuleSw-LS82O4GM                    OBJECT IDENTIFIER ::= { h3cevtModuleSwitchType 21 } 

h3cevtModuleSw-LS82GB4C                    OBJECT IDENTIFIER ::= { h3cevtModuleSwitchType 22 } 

h3cevtModuleSw-LS82GT4C                    OBJECT IDENTIFIER ::= { h3cevtModuleSwitchType 23 } 

h3cevtModuleSw-LS82ST4C                    OBJECT IDENTIFIER ::= { h3cevtModuleSwitchType 24 } 

h3cevtModuleSw-BOARD-LS82DSPU              OBJECT IDENTIFIER ::= { h3cevtModuleSwitchType 25 } 

h3cevtModuleSw-BOARD-LS81GP8U              OBJECT IDENTIFIER ::= { h3cevtModuleSwitchType 26 } 

h3cevtModuleSw-BOARD-LS82GT20              OBJECT IDENTIFIER ::= { h3cevtModuleSwitchType 27 } 

h3cevtModuleSw-BOARD-LS82FE48              OBJECT IDENTIFIER ::= { h3cevtModuleSwitchType 28 } 

h3cevtModuleSw-LS82T24B                    OBJECT IDENTIFIER ::= { h3cevtModuleSwitchType 29 } 

h3cevtModuleSw-LSB1SRPA                    OBJECT IDENTIFIER ::= { h3cevtModuleSwitchType 30 } 

h3cevtModuleSw-LSB1FT48A                   OBJECT IDENTIFIER ::= { h3cevtModuleSwitchType 31 } 

h3cevtModuleSw-LSB1FT48B                   OBJECT IDENTIFIER ::= { h3cevtModuleSwitchType 32 } 

h3cevtModuleSw-LSB1F48GA                   OBJECT IDENTIFIER ::= { h3cevtModuleSwitchType 33 } 

h3cevtModuleSw-LSB1F48GB                   OBJECT IDENTIFIER ::= { h3cevtModuleSwitchType 34 } 

h3cevtModuleSw-LSB1FP20A                   OBJECT IDENTIFIER ::= { h3cevtModuleSwitchType 35 } 

h3cevtModuleSw-LSB1FP20B                   OBJECT IDENTIFIER ::= { h3cevtModuleSwitchType 36 } 

h3cevtModuleSw-FT48A                       OBJECT IDENTIFIER ::= { h3cevtModuleSwitchType 37 } 

h3cevtModuleSw-GP4U                        OBJECT IDENTIFIER ::= { h3cevtModuleSwitchType 38 } 

h3cevtModuleSw-GP2U                        OBJECT IDENTIFIER ::= { h3cevtModuleSwitchType 39 } 

h3cevtModuleSw-TGX1A                       OBJECT IDENTIFIER ::= { h3cevtModuleSwitchType 40 } 

h3cevtModuleSw-1000BASE-LX-SM-IR-SC        OBJECT IDENTIFIER ::= { h3cevtModuleSwitchType 41 } 

h3cevtModuleSw-1000BASE-SX-MM-SR-SC        OBJECT IDENTIFIER ::= { h3cevtModuleSwitchType 42 } 

h3cevtModuleSw-1000BASE-T-RJ45             OBJECT IDENTIFIER ::= { h3cevtModuleSwitchType 43 } 

h3cevtModuleSw-100BASE-FX-SM-IR-SC         OBJECT IDENTIFIER ::= { h3cevtModuleSwitchType 44 } 

h3cevtModuleSw-100BASE-FX-MM-SR-SC         OBJECT IDENTIFIER ::= { h3cevtModuleSwitchType 45 }

h3cevtModuleSw-GIGA-STACK-1M-PC            OBJECT IDENTIFIER ::= { h3cevtModuleSwitchType 46 } 

h3cevtModuleSw-1000BASE-LX-SM-VLR-LC       OBJECT IDENTIFIER ::= { h3cevtModuleSwitchType 47 } 

h3cevtModuleSw-1000BASE-LX-SM-LR-LC        OBJECT IDENTIFIER ::= { h3cevtModuleSwitchType 48 } 

h3cevtModuleSw-100BASE-FX-SM-LR-SC         OBJECT IDENTIFIER ::= { h3cevtModuleSwitchType 49 }

h3cevtModuleSw-1000BASE-X-GBIC             OBJECT IDENTIFIER ::= { h3cevtModuleSwitchType 50 }

h3cevtModuleSw-100M-SINGLEMODE-FX-LC       OBJECT IDENTIFIER ::= { h3cevtModuleSwitchType 51 } 

h3cevtModuleSw-100M-MULTIMODE-FX-LC        OBJECT IDENTIFIER ::= { h3cevtModuleSwitchType 52 } 

h3cevtModuleSw-1000BASE-4SFP               OBJECT IDENTIFIER ::= { h3cevtModuleSwitchType 53 } 

h3cevtModuleSw-1000BASE-4GBIC              OBJECT IDENTIFIER ::= { h3cevtModuleSwitchType 54 }

h3cevtModuleSw-1000BASE-FIXED-4SFP         OBJECT IDENTIFIER ::= { h3cevtModuleSwitchType 55 } 

h3cevtModuleSw-1000BASE-FIXED-4GBIC        OBJECT IDENTIFIER ::= { h3cevtModuleSwitchType 56 }  

h3cevtModuleSw-LSB1GP12A                   OBJECT IDENTIFIER ::= { h3cevtModuleSwitchType 57 }

h3cevtModuleSw-LSB1GP12B                   OBJECT IDENTIFIER ::= { h3cevtModuleSwitchType 58 }

h3cevtModuleSw-LSB1TGX1A                   OBJECT IDENTIFIER ::= { h3cevtModuleSwitchType 59 }

h3cevtModuleSw-LSB1TGX1B                   OBJECT IDENTIFIER ::= { h3cevtModuleSwitchType 60 } 

h3cevtModuleSw-LSB1P4G8A                   OBJECT IDENTIFIER ::= { h3cevtModuleSwitchType 61 } 

h3cevtModuleSw-LSB1P4G8B                   OBJECT IDENTIFIER ::= { h3cevtModuleSwitchType 62 } 

h3cevtModuleSw-LSB1A4G8A                   OBJECT IDENTIFIER ::= { h3cevtModuleSwitchType 63 } 

h3cevtModuleSw-LSB1A4G8B                   OBJECT IDENTIFIER ::= { h3cevtModuleSwitchType 64 } 

h3cevtModuleSw-FT48C                       OBJECT IDENTIFIER ::= { h3cevtModuleSwitchType 65 } 

h3cevtModuleSw-FP20                        OBJECT IDENTIFIER ::= { h3cevtModuleSwitchType 66 }

h3cevtModuleSw-BOARD-LS81FT48              OBJECT IDENTIFIER ::= { h3cevtModuleSwitchType 67 } 

h3cevtModuleSw-BOARD-LS81GB8U              OBJECT IDENTIFIER ::= { h3cevtModuleSwitchType 68 } 

h3cevtModuleSw-BOARD-LS81GT8U              OBJECT IDENTIFIER ::= { h3cevtModuleSwitchType 69 } 

h3cevtModuleSw-BOARD-LS81FS24              OBJECT IDENTIFIER ::= { h3cevtModuleSwitchType 70 } 

h3cevtModuleSw-BOARD-LS81FM24              OBJECT IDENTIFIER ::= { h3cevtModuleSwitchType 71 }

h3cevtModuleSw-BOARD-LS82GP20              OBJECT IDENTIFIER ::= { h3cevtModuleSwitchType 72 }

h3cevtModuleSw-LSB1SRPB                    OBJECT IDENTIFIER ::= { h3cevtModuleSwitchType 73 }

h3cevtModuleSw-LSB1F32GA                   OBJECT IDENTIFIER ::= { h3cevtModuleSwitchType 74 }

h3cevtModuleSw-LSB1F32GB                   OBJECT IDENTIFIER ::= { h3cevtModuleSwitchType 75 } 

h3cevtModuleSw-LSB2FT48A	           OBJECT IDENTIFIER ::= { h3cevtModuleSwitchType 76 } 

h3cevtModuleSw-LSB2FT48B                   OBJECT IDENTIFIER ::= { h3cevtModuleSwitchType 77 } 

h3cevtModuleSw-LSB1GT12A                   OBJECT IDENTIFIER ::= { h3cevtModuleSwitchType 78 }

h3cevtModuleSw-LSB1GT12B                   OBJECT IDENTIFIER ::= { h3cevtModuleSwitchType 79 }

h3cevtModuleSw-PC4U                        OBJECT IDENTIFIER ::= { h3cevtModuleSwitchType 80 } 

h3cevtModuleSw-FT32A                	   OBJECT IDENTIFIER ::= { h3cevtModuleSwitchType 81 } 

h3cevtModuleSw-GT4U                 	   OBJECT IDENTIFIER ::= { h3cevtModuleSwitchType 82 } 

h3cevtModuleSw-BOARD-LS83FP20A      	   OBJECT IDENTIFIER ::= { h3cevtModuleSwitchType 83 }

h3cevtModuleSw-BOARD-LS82HGMU       	   OBJECT IDENTIFIER ::= { h3cevtModuleSwitchType 84 }

h3cevtModuleSw-LSB1GP8TB            	   OBJECT IDENTIFIER ::= { h3cevtModuleSwitchType 85 }

h3cevtModuleSw-LSB1GP8TC           	   OBJECT IDENTIFIER ::= { h3cevtModuleSwitchType 86 }

h3cevtModuleSw-LSB1GT8PB            	   OBJECT IDENTIFIER ::= { h3cevtModuleSwitchType 87 } 

h3cevtModuleSw-LSB1GT8PC            	   OBJECT IDENTIFIER ::= { h3cevtModuleSwitchType 88 }

h3cevtModuleSw-LSB1FT48C            	   OBJECT IDENTIFIER ::= { h3cevtModuleSwitchType 89 }

h3cevtModuleSw-LSB1FP20C            	   OBJECT IDENTIFIER ::= { h3cevtModuleSwitchType 90 }

h3cevtModuleSw-LSB1F32GC            	   OBJECT IDENTIFIER ::= { h3cevtModuleSwitchType 91 }

h3cevtModuleSw-LSB1GT12C            	   OBJECT IDENTIFIER ::= { h3cevtModuleSwitchType 92 }

h3cevtModuleSw-LSB1GP12C            	   OBJECT IDENTIFIER ::= { h3cevtModuleSwitchType 93 }

h3cevtModuleSw-LSB1P4G8C            	   OBJECT IDENTIFIER ::= { h3cevtModuleSwitchType 94 }

h3cevtModuleSw-LSB1TGX1C            	   OBJECT IDENTIFIER ::= { h3cevtModuleSwitchType 95 }

h3cevtModuleSw-LSB1GT24B            	   OBJECT IDENTIFIER ::= { h3cevtModuleSwitchType 96 }

h3cevtModuleSw-LSB1GT24C            	   OBJECT IDENTIFIER ::= { h3cevtModuleSwitchType 97 }

h3cevtModuleSw-LSB1GP24B            	   OBJECT IDENTIFIER ::= { h3cevtModuleSwitchType 98 }

h3cevtModuleSw-LSB1GP24C            	   OBJECT IDENTIFIER ::= { h3cevtModuleSwitchType 99 }

h3cevtModuleSw-LSB1XP2B            	   OBJECT IDENTIFIER ::= { h3cevtModuleSwitchType 100 }

h3cevtModuleSw-LSB1XP2C            	   OBJECT IDENTIFIER ::= { h3cevtModuleSwitchType 101 }

h3cevtModuleSw-LSB1GV48B            	   OBJECT IDENTIFIER ::= { h3cevtModuleSwitchType 102 }

h3cevtModuleSw-LSB1GV48C            	   OBJECT IDENTIFIER ::= { h3cevtModuleSwitchType 103 }

h3cevtModuleSw-LSB1SRPC            	   OBJECT IDENTIFIER ::= { h3cevtModuleSwitchType 104 }

h3cevtModuleSw-LSB1SRP1N0            	   OBJECT IDENTIFIER ::= { h3cevtModuleSwitchType 105 }

h3cevtModuleSw-LSB1SRP1N1            	   OBJECT IDENTIFIER ::= { h3cevtModuleSwitchType 106 }

h3cevtModuleSw-LSB1SRP1N2            	   OBJECT IDENTIFIER ::= { h3cevtModuleSwitchType 107 }

h3cevtModuleSw-GT24            	           OBJECT IDENTIFIER ::= { h3cevtModuleSwitchType 108 }

h3cevtModuleSw-GP24            	           OBJECT IDENTIFIER ::= { h3cevtModuleSwitchType 109 }

h3cevtModuleSw-XP2            	           OBJECT IDENTIFIER ::= { h3cevtModuleSwitchType 110 }

h3cevtModuleSw-GV48            	           OBJECT IDENTIFIER ::= { h3cevtModuleSwitchType 111 }

h3cevtModuleSw-LSG1GP8U            	   OBJECT IDENTIFIER ::= { h3cevtModuleSwitchType 112 }

h3cevtModuleSw-LSG1GT8U            	   OBJECT IDENTIFIER ::= { h3cevtModuleSwitchType 113 }

h3cevtModuleSw-LSG1TG1U            	   OBJECT IDENTIFIER ::= { h3cevtModuleSwitchType 114 }

h3cevtModuleSw-LSG1TD1U            	   OBJECT IDENTIFIER ::= { h3cevtModuleSwitchType 115 }

h3cevtModuleSw-LSB2FT48C            	   OBJECT IDENTIFIER ::= { h3cevtModuleSwitchType 116 } -- 48-Ports 100Base-TX Ethernet Interface module C

h3cevtModuleSw-LSB1GT48B            	   OBJECT IDENTIFIER ::= { h3cevtModuleSwitchType 117 } -- 48-Ports 10/100/1000Base-T Ethernet Interface Module B

h3cevtModuleSw-LSB1GT48C            	   OBJECT IDENTIFIER ::= { h3cevtModuleSwitchType 118 } -- 48-Ports 10/100/1000Base-T Ethernet Interface Module C

h3cevtModuleSw-LS81GT48            	   OBJECT IDENTIFIER ::= { h3cevtModuleSwitchType 119 } -- 48 Port Gigabit Ethernet Electric Interface Unit

h3cevtModuleSw-LS81SRPG0            	   OBJECT IDENTIFIER ::= { h3cevtModuleSwitchType 120 } -- Salience III, Switch and Route Processing Board

h3cevtModuleSw-LS81SRPG1            	   OBJECT IDENTIFIER ::= { h3cevtModuleSwitchType 121 } -- Salience III Plus

h3cevtModuleSw-LS81SRPG2            	   OBJECT IDENTIFIER ::= { h3cevtModuleSwitchType 122 } -- Salience III Lite

h3cevtModuleSw-LS81SRPG3            	   OBJECT IDENTIFIER ::= { h3cevtModuleSwitchType 123 } -- Salience III Edge

--h3cevtModuleSw-LS81SRPG            	   OBJECT IDENTIFIER ::= { h3cevtModuleSwitchType 124 } Switch And Route Processing Unit,Salience III. not used.

h3cevtModuleSw-SR01SRPUB            	   OBJECT IDENTIFIER ::= { h3cevtModuleSwitchType 125 } -- SR8812 Switching and Route Processing Unit

h3cevtModuleSw-SR01SRPUA            	   OBJECT IDENTIFIER ::= { h3cevtModuleSwitchType 126 } -- SR8805 Switching and Route Processing Unit

h3cevtModuleSw-SR01GP12L            	   OBJECT IDENTIFIER ::= { h3cevtModuleSwitchType 127 } -- 12-Port 1000Base-X Ethernet SFP Optical Interface Line Card(L)

h3cevtModuleSw-SR01GP12W            	   OBJECT IDENTIFIER ::= { h3cevtModuleSwitchType 128 } -- 12-Port 1000Base-X Ethernet SFP Optical Interface Line Card(W)

h3cevtModuleSw-SR01FT48L            	   OBJECT IDENTIFIER ::= { h3cevtModuleSwitchType 129 } -- 48-Port 10/100Base-TX Ethernet RJ45 Electrical Interface Line Card (L)

h3cevtModuleSw-SR01FT48W            	   OBJECT IDENTIFIER ::= { h3cevtModuleSwitchType 130 } -- 48-Port 10/100Base-TX Ethernet RJ45 Electrical Interface Line Card (W)

h3cevtModuleSw-SR01XK1W            	   OBJECT IDENTIFIER ::= { h3cevtModuleSwitchType 131 } -- 1-Port 10GBase-R Ethernet XENPAK Optical Interface Line Card (W)

h3cevtModuleSw-SR01FP20W            	   OBJECT IDENTIFIER ::= { h3cevtModuleSwitchType 132 } -- 20-Port 100Base-FX Ethernet SFP Optical Interface Line Card (W)

h3cevtModuleSw-SR01GT12W            	   OBJECT IDENTIFIER ::= { h3cevtModuleSwitchType 133 } -- 12-Port 10/100/1000Base-T Ethernet RJ45 Electrical Interface Line Card (W)

h3cevtModuleSw-SR01F32GL            	   OBJECT IDENTIFIER ::= { h3cevtModuleSwitchType 134 } -- 32-Port 10/100Base-TX Ethernet RJ45 Electrical Interface + 4-Port 1000Base-X Ethernet SFP Optical interface Line Card (L)

h3cevtModuleSw-SR01F32GW            	   OBJECT IDENTIFIER ::= { h3cevtModuleSwitchType 135 } -- 32-Port 10/100Base-TX Ethernet RJ45 Electrical Interface  + 4-Port 1000Base-X  Ethernet SFP Optical interface Line Card (W)

h3cevtModuleSw-SR01GT8PL            	   OBJECT IDENTIFIER ::= { h3cevtModuleSwitchType 136 } -- 8-Port 10/100/1000Base-T Ethernet RJ45 Electrical Interface + 4-Port 1000Base-X Ethernet SFP Optical Line Card (L)

h3cevtModuleSw-SR01GT8PW            	   OBJECT IDENTIFIER ::= { h3cevtModuleSwitchType 137 } -- 8-Port 10/100/1000Base-T Ethernet RJ45 Electrical Interface + 4-Port 1000Base-X Ethernet SFP Optical Line Card (W)

h3cevtModuleSw-SR01P4G8W            	   OBJECT IDENTIFIER ::= { h3cevtModuleSwitchType 138 } -- 4-Port 155M POS Optical Interface + 8-Port 1000Base-X Ethernet SFP Optical Interface Line Card (W)

h3cevtModuleSw-LSA1FP8U                    OBJECT IDENTIFIER ::= { h3cevtModuleSwitchType 139 } -- 8 Ports 100Base-FX Ethernet SFP Card

h3cevtModuleSw-LSB1SP4B                    OBJECT IDENTIFIER ::= { h3cevtModuleSwitchType 140 } -- 4-Port OC-48 POS SFP Optical Interface Board B
               
h3cevtModuleSw-LSB1SP4C                    OBJECT IDENTIFIER ::= { h3cevtModuleSwitchType 141} -- 4-Port OC-48 POS SFP Optical Interface Board C
               
h3cevtModuleSw-LSB1UP1B                    OBJECT IDENTIFIER ::= { h3cevtModuleSwitchType 142 } -- 1-Port OC-192 POS XFP Optical Interface Board B
               
h3cevtModuleSw-LSB1UP1C                    OBJECT IDENTIFIER ::= { h3cevtModuleSwitchType 143 } -- 1-Port OC-192 POS XFP Optical Interface Board C
               
h3cevtModuleSw-LSB1XP4B                    OBJECT IDENTIFIER ::= { h3cevtModuleSwitchType 144 } -- 4-Port 10GBase Ethernet XFP Optical Interface Board B
               
h3cevtModuleSw-LSB1XP4C                    OBJECT IDENTIFIER ::= { h3cevtModuleSwitchType 145 } -- 4-Port 10GBase Ethernet XFP Optical Interface Board C

h3cevtModuleSw-SP4                         OBJECT IDENTIFIER ::= { h3cevtModuleSwitchType 146 } -- 4-Port OC-48 POS SFP Optical Interface Module

h3cevtModuleSw-UP1                         OBJECT IDENTIFIER ::= { h3cevtModuleSwitchType 147 } -- 1-Port OC-192 POS XFP Optical Interface Module

h3cevtModuleSw-XP4                         OBJECT IDENTIFIER ::= { h3cevtModuleSwitchType 148 } -- 4-Port 10GBase Ethernet XFP Optical Interface Module

h3cevtModuleSw-LS81VSNP                    OBJECT IDENTIFIER ::= { h3cevtModuleSwitchType 149 } -- VerSatile Network Processing Board

h3cevtModuleSw-LS81T12P                    OBJECT IDENTIFIER ::= { h3cevtModuleSwitchType 150 } -- 12-Port 1000Base-T Gigabit Ethernet Interface(RJ45)+4-Port 1000BASE-X  Gigabit Ethernet Optical Interface Board(SFP,LC)

h3cevtModuleSw-LS81P12T                    OBJECT IDENTIFIER ::= { h3cevtModuleSwitchType 151 } -- 12-Port 1000BASE-X Gigabit Ethernet Optical Interface(SFP,LC)+4-Port 1000BASE-T Gigabit Ethernet Interface Board(RJ45)

h3cevtModuleSw-LS81GP8UB                   OBJECT IDENTIFIER ::= { h3cevtModuleSwitchType 152 } -- 8-Port 1000M Ethernet Optical Interface Board(SFP,LC),LC Connector

h3cevtModuleSw-LS81FT48E                   OBJECT IDENTIFIER ::= { h3cevtModuleSwitchType 153 } -- 48-Port 100M Ethernet Electrical Interface Switch Unit(RJ45)

h3cevtModuleSw-LS81GP4UB                   OBJECT IDENTIFIER ::= { h3cevtModuleSwitchType 154 } -- 4-Port 1000M Ethernet Optical Interface Board(SFP,LC)

h3cevtModuleSw-LS81GT8UE                   OBJECT IDENTIFIER ::= { h3cevtModuleSwitchType 155 } -- 8-Port 1000M Ethernet Electrical Interface Switch Unit (RJ45)

h3cevtModuleSw-LS81GT48A                   OBJECT IDENTIFIER ::= { h3cevtModuleSwitchType 156 } -- 48 Port Gigabit Ethernet Electric Interface Unit

h3cevtModuleSw-LS81FP48                    OBJECT IDENTIFIER ::= { h3cevtModuleSwitchType 157 } -- 48 Port 100M Ethernet Optical Interface Board(SFP,LC)

h3cevtModuleSw-LSB1XK1B                    OBJECT IDENTIFIER ::= { h3cevtModuleSwitchType 158 } -- 1-Port 10GBase-R Ethernet XENPAK Optical Interface Board B

h3cevtModuleSw-LSB1XK1C                    OBJECT IDENTIFIER ::= { h3cevtModuleSwitchType 159 } -- 1-Port 10GBase-R Ethernet XENPAK Optical Interface Board C

h3cevtModuleSw-SR01SRPUC                   OBJECT IDENTIFIER ::= { h3cevtModuleSwitchType 160 } -- Switching and Route Processing Unit C

h3cevtModuleSw-SR01SRPUD                   OBJECT IDENTIFIER ::= { h3cevtModuleSwitchType 161 } -- Switching and Route Processing Unit D

h3cevtModuleSw-SR01SRPUE                   OBJECT IDENTIFIER ::= { h3cevtModuleSwitchType 162 } -- Switching and Route Processing Unit E

h3cevtModuleSw-LSB1SRP1N3                  OBJECT IDENTIFIER ::= { h3cevtModuleSwitchType 163 } -- Switching and Route Process Unit,Clock Module

h3cevtModuleSw-LSB1VP2B                    OBJECT IDENTIFIER ::= { h3cevtModuleSwitchType 164 } -- 2*10G Resilient Packet Ring Interface Line Card

h3cevtModuleSw-LSB1NATB                    OBJECT IDENTIFIER ::= { h3cevtModuleSwitchType 165 } -- NAT Service Processing Card (B)

h3cevtModuleSw-LSB1VPNB                    OBJECT IDENTIFIER ::= { h3cevtModuleSwitchType 166 } -- VPN Service Processing Card (B)

h3cevtModuleSw-LSGP8P	                   OBJECT IDENTIFIER ::= { h3cevtModuleSwitchType 167 } -- 8-Port 1000M SFP Module 

h3cevtModuleSw-LSXK1P	                   OBJECT IDENTIFIER ::= { h3cevtModuleSwitchType 168 } -- 1-Port 10G Xenpak Module

h3cevtModuleSw-LSXP2P	                   OBJECT IDENTIFIER ::= { h3cevtModuleSwitchType 169 } -- 2-Port 10G XFP Module

h3cevtModuleSw-LS81FT48F                   OBJECT IDENTIFIER ::= { h3cevtModuleSwitchType 170 } -- 48-Port 100M Ethernet Electrical Interface Switch Unit(RJ45)

h3cevtModuleSw-LS81PT8G	                   OBJECT IDENTIFIER ::= { h3cevtModuleSwitchType 171 } -- 8 Port 1000BASE-X Gigabit Passive Optical Line Interface Board

h3cevtModuleSw-LS81PT4G	                   OBJECT IDENTIFIER ::= { h3cevtModuleSwitchType 172 } -- 4 Port 1000BASE-X Gigabit Passive Optical Line Interface Board

h3cevtModuleSw-LSSTK24G	                   OBJECT IDENTIFIER ::= { h3cevtModuleSwitchType 173 } -- 24G Stacking Ports Module

h3cevtModuleSw-LS82GT20A                   OBJECT IDENTIFIER ::= { h3cevtModuleSwitchType 174 } -- 20-Port 1000Base-T Gigabit Ethernet Electrical Interface Board(RJ45), BCM5697

h3cevtModuleSw-LS82GP20A                   OBJECT IDENTIFIER ::= { h3cevtModuleSwitchType 175 } -- 20-Port 1000BASE-X Gigabit Ethernet Optical Interface Board(SFP,LC), BCM5697

h3cevtModuleSw-LS81TGX1C                   OBJECT IDENTIFIER ::= { h3cevtModuleSwitchType 176 } -- 1-Port 10G Base-R Ethernet Board

h3cevtModuleSw-BOARD-LS82SRPB              OBJECT IDENTIFIER ::= { h3cevtModuleSwitchType 254 }

h3cevtModuleSw-BORAD-LS83SRPC              OBJECT IDENTIFIER ::= { h3cevtModuleSwitchType 255 }

h3cevtModuleSw-Main            	           OBJECT IDENTIFIER ::= { h3cevtModuleSwitchType 256 }



-- Here define submodule for routers
h3cevtSubModuleRouter		OBJECT IDENTIFIER ::= { h3cevtModule 5 }


-- Here define submodule for switchs
h3cevtSubModuleSwitch		OBJECT IDENTIFIER ::= { h3cevtModule 6 }


--h3cevtModuleCpuType 		OBJECT IDENTIFIER ::= { h3cevtModule 7 }  Reserved for future use.

--
-- h3cevtPort section:
-- 
 
h3cevtPort			OBJECT IDENTIFIER ::= { h3cEntityVendortypeObjects 10 }
h3cevtPortUnknownPorts		OBJECT IDENTIFIER ::= { h3cevtPort 1 }
h3cevtPortCommonPorts		OBJECT IDENTIFIER ::= { h3cevtPort 2 }
h3cevtPortRouterType		OBJECT IDENTIFIER ::= { h3cevtPort 3 }
h3cevtPortSwitchType		OBJECT IDENTIFIER ::= { h3cevtPort 4 }


-- Below are ports used to router
h3cevtPortRt-Async			OBJECT IDENTIFIER ::= { h3cevtPortRouterType 1 }	-- Async interface

h3cevtPortRt-Analogmodem		OBJECT IDENTIFIER ::= { h3cevtPortRouterType 2 }	-- Analog modem interface

h3cevtPortRt-Atm			OBJECT IDENTIFIER ::= { h3cevtPortRouterType 3 }	-- 

h3cevtPortRt-AtmAdsl			OBJECT IDENTIFIER ::= { h3cevtPortRouterType 4 }	-- 

h3cevtPortRt-AtmShdsl			OBJECT IDENTIFIER ::= { h3cevtPortRouterType 5 }	-- 

h3cevtPortRt-AtmE1			OBJECT IDENTIFIER ::= { h3cevtPortRouterType 6 }	-- 

h3cevtPortRt-AtmT1			OBJECT IDENTIFIER ::= { h3cevtPortRouterType 7 }	-- 

h3cevtPortRt-AtmE3			OBJECT IDENTIFIER ::= { h3cevtPortRouterType 8 }	-- 

h3cevtPortRt-AtmT3			OBJECT IDENTIFIER ::= { h3cevtPortRouterType 9 }	-- 

h3cevtPortRt-Atm622M			OBJECT IDENTIFIER ::= { h3cevtPortRouterType 10 }	-- 

h3cevtPortRt-AtmImaE1			OBJECT IDENTIFIER ::= { h3cevtPortRouterType 11 }	-- 

h3cevtPortRt-AtmImaT1			OBJECT IDENTIFIER ::= { h3cevtPortRouterType 12 }	-- 

h3cevtPortRt-Atm25M			OBJECT IDENTIFIER ::= { h3cevtPortRouterType 13 }	-- 

h3cevtPortRt-Bri			OBJECT IDENTIFIER ::= { h3cevtPortRouterType 14 }	-- 

h3cevtPortRt-Console			OBJECT IDENTIFIER ::= { h3cevtPortRouterType 15 }	-- 

h3cevtPortRt-E1				OBJECT IDENTIFIER ::= { h3cevtPortRouterType 16 }	-- 

h3cevtPortRt-E3				OBJECT IDENTIFIER ::= { h3cevtPortRouterType 17 }	-- 

h3cevtPortRt-T1				OBJECT IDENTIFIER ::= { h3cevtPortRouterType 18 }	-- 

h3cevtPortRt-T3				OBJECT IDENTIFIER ::= { h3cevtPortRouterType 19 }	-- 

h3cevtPortRt-Cpos			OBJECT IDENTIFIER ::= { h3cevtPortRouterType 20 }	-- 

h3cevtPortRt-Ethernet			OBJECT IDENTIFIER ::= { h3cevtPortRouterType 21 }	-- 

h3cevtPortRt-Serial			OBJECT IDENTIFIER ::= { h3cevtPortRouterType 22 }	-- 

h3cevtPortRt-E1f			OBJECT IDENTIFIER ::= { h3cevtPortRouterType 23 }	-- 

h3cevtPortRt-T1f			OBJECT IDENTIFIER ::= { h3cevtPortRouterType 24 }	-- 

h3cevtPortRt-Pos			OBJECT IDENTIFIER ::= { h3cevtPortRouterType 25 }	-- 

h3cevtPortRt-Ge				OBJECT IDENTIFIER ::= { h3cevtPortRouterType 26 }	-- 

h3cevtPortRt-Aux			OBJECT IDENTIFIER ::= { h3cevtPortRouterType 27 }	-- 

--h3cevtPortRt-Null			OBJECT IDENTIFIER ::= { h3cevtPortRouterType 28 }	-- 

--h3cevtPortRt-Max			OBJECT IDENTIFIER ::= { h3cevtPortRouterType 29 }	-- 

-- Below are ports used to switchs
--h3cevtPortSw-Unknown			OBJECT IDENTIFIER ::= { h3cevtPortSwitchType 0 }

h3cevtPortSw-10or100M			OBJECT IDENTIFIER ::= { h3cevtPortSwitchType 1 }	-- 

h3cevtPortSw-1000BaseLxSm		OBJECT IDENTIFIER ::= { h3cevtPortSwitchType 2 }	-- 

h3cevtPortSw-1000BaseSxMm		OBJECT IDENTIFIER ::= { h3cevtPortSwitchType 3 }	-- 

h3cevtPortSw-1000BaseTx			OBJECT IDENTIFIER ::= { h3cevtPortSwitchType 4 }	-- 

h3cevtPortSw-100MSinglemodeFx		OBJECT IDENTIFIER ::= { h3cevtPortSwitchType 5 }	-- 

h3cevtPortSw-100MMultimodeFx		OBJECT IDENTIFIER ::= { h3cevtPortSwitchType 6 }	-- 

h3cevtPortSw-100M100BaseTx		OBJECT IDENTIFIER ::= { h3cevtPortSwitchType 7 }	-- 

h3cevtPortSw-100MHub			OBJECT IDENTIFIER ::= { h3cevtPortSwitchType 8 }	-- 

h3cevtPortSw-Vdsl			OBJECT IDENTIFIER ::= { h3cevtPortSwitchType 9 }	-- 

h3cevtPortSw-Stack			OBJECT IDENTIFIER ::= { h3cevtPortSwitchType 10 }	-- 

h3cevtPortSw-1000BaseZenithFx		OBJECT IDENTIFIER ::= { h3cevtPortSwitchType 11 }	-- 

h3cevtPortSw-1000BaseLongFx		OBJECT IDENTIFIER ::= { h3cevtPortSwitchType 12 }	-- 

h3cevtPortSw-Adsl			OBJECT IDENTIFIER ::= { h3cevtPortSwitchType 13 }	-- 

h3cevtPortSw-10or100MDb			OBJECT IDENTIFIER ::= { h3cevtPortSwitchType 14 }	-- 

h3cevtPortSw-10GBaseLrSm		OBJECT IDENTIFIER ::= { h3cevtPortSwitchType 15 }	-- 

h3cevtPortSw-10GBaseLx4Mm		OBJECT IDENTIFIER ::= { h3cevtPortSwitchType 16 }	-- 

h3cevtPortSw-10GBaseLx4Sm		OBJECT IDENTIFIER ::= { h3cevtPortSwitchType 17 }	-- 

h3cevtPortSw-100MLongFx			OBJECT IDENTIFIER ::= { h3cevtPortSwitchType 18 }	-- 

h3cevtPortSw-1000BaseCx			OBJECT IDENTIFIER ::= { h3cevtPortSwitchType 19 }	-- 

h3cevtPortSw-1000BaseZenithFxLc		OBJECT IDENTIFIER ::= { h3cevtPortSwitchType 20 }	-- 

h3cevtPortSw-1000BaseLongFxLc		OBJECT IDENTIFIER ::= { h3cevtPortSwitchType 21 }	-- 

h3cevtPortSw-100MSmFxSc			OBJECT IDENTIFIER ::= { h3cevtPortSwitchType 22 }	-- 

h3cevtPortSw-100MMmFxSc			OBJECT IDENTIFIER ::= { h3cevtPortSwitchType 23 }	-- 

h3cevtPortSw-100MSmFxLc			OBJECT IDENTIFIER ::= { h3cevtPortSwitchType 24 }	-- 

h3cevtPortSw-100MMmFxLc			OBJECT IDENTIFIER ::= { h3cevtPortSwitchType 25 }	-- 

h3cevtPortSw-GbicNoConnector		OBJECT IDENTIFIER ::= { h3cevtPortSwitchType 26 }	-- 

h3cevtPortSw-Gbic1000BaseT		OBJECT IDENTIFIER ::= { h3cevtPortSwitchType 27 }	-- 

h3cevtPortSw-Gbic1000BaseLx		OBJECT IDENTIFIER ::= { h3cevtPortSwitchType 28 }	-- 

h3cevtPortSw-Gbic1000BaseSx		OBJECT IDENTIFIER ::= { h3cevtPortSwitchType 29 }	-- 

h3cevtPortSw-Gbic1000BaseZx		OBJECT IDENTIFIER ::= { h3cevtPortSwitchType 30 }	-- 

h3cevtPortSw-ComboNoConnector		OBJECT IDENTIFIER ::= { h3cevtPortSwitchType 31 }	-- 

h3cevtPortSw-Combo1000BaseLx		OBJECT IDENTIFIER ::= { h3cevtPortSwitchType 32 }	-- 

h3cevtPortSw-Combo1000BaseLxFiber	OBJECT IDENTIFIER ::= { h3cevtPortSwitchType 33 }	-- 

h3cevtPortSw-Combo1000BaseLxCopper	OBJECT IDENTIFIER ::= { h3cevtPortSwitchType 34 }	-- 

h3cevtPortSw-Combo1000BaseSx		OBJECT IDENTIFIER ::= { h3cevtPortSwitchType 35 }	-- 

h3cevtPortSw-Combo1000BaseSxFiber	OBJECT IDENTIFIER ::= { h3cevtPortSwitchType 36 }	-- 

h3cevtPortSw-Combo1000BaseSxCopper	OBJECT IDENTIFIER ::= { h3cevtPortSwitchType 37 }	-- 

h3cevtPortSw-Combo1000BaseZx		OBJECT IDENTIFIER ::= { h3cevtPortSwitchType 38 }	-- 

h3cevtPortSw-Combo1000BaseZxFiber	OBJECT IDENTIFIER ::= { h3cevtPortSwitchType 39 }	-- 

h3cevtPortSw-Combo1000BaseZxCopper	OBJECT IDENTIFIER ::= { h3cevtPortSwitchType 40 }	-- 

h3cevtPortSw-155PosSxMmf		OBJECT IDENTIFIER ::= { h3cevtPortSwitchType 41 }	-- 

h3cevtPortSw-155PosLxSmf		OBJECT IDENTIFIER ::= { h3cevtPortSwitchType 42 }	-- 

-- added by Garibaldi

h3cevtPortSw-1000BASE-T			OBJECT IDENTIFIER ::= { h3cevtPortSwitchType 43 }	-- 1000 Base-T Port

h3cevtPortSw-1000BASE-SX-SFP		OBJECT IDENTIFIER ::= { h3cevtPortSwitchType 44 }	-- 1000 Base-SX SFP Port

h3cevtPortSw-1000BASE-LX-SFP		OBJECT IDENTIFIER ::= { h3cevtPortSwitchType 45 }	-- 1000 Base-LX SFP Port

h3cevtPortSw-1000BASE-T-AN-SFP		OBJECT IDENTIFIER ::= { h3cevtPortSwitchType 46 }	-- 1000 Base-T AN SFP Port

h3cevtPortSw-10GBASE-LX4-XENPAK		OBJECT IDENTIFIER ::= { h3cevtPortSwitchType 47 }	-- 10G Base-LX4 XENPAK Port

h3cevtPortSw-10GBASE-LR-XENPAK		OBJECT IDENTIFIER ::= { h3cevtPortSwitchType 48 }	-- 10G Base-LR XENPAK Port

h3cevtPortSw-10GBASE-CX4		OBJECT IDENTIFIER ::= { h3cevtPortSwitchType 49 }	-- 10G Base-CX4 Port

h3cevtPortSw-1000BASE-ZX-SFP            OBJECT IDENTIFIER ::= { h3cevtPortSwitchType 50 }    -- 1000 Base-ZX SFP Port

h3cevtPortSw-1000BASE-MM-SFP            OBJECT IDENTIFIER ::= { h3cevtPortSwitchType 51 }    -- 1000 Base-MM SFP Port

h3cevtPortSw-100BASE-SX-SFP             OBJECT IDENTIFIER ::= { h3cevtPortSwitchType 52 }    -- 100 Base-SX SFP Port

h3cevtPortSw-100BASE-LX-SFP             OBJECT IDENTIFIER ::= { h3cevtPortSwitchType 53 }    -- 100 Base-LX SFP Port

h3cevtPortSw-100BASE-T-AN-SFP           OBJECT IDENTIFIER ::= { h3cevtPortSwitchType 54 }    -- 100 Base-T SFP Port

h3cevtPortSw-100BASE-ZX-SFP             OBJECT IDENTIFIER ::= { h3cevtPortSwitchType 55 }    -- 100 Base-ZX SFP Port

h3cevtPortSw-100BASE-MM-SFP             OBJECT IDENTIFIER ::= { h3cevtPortSwitchType 56 }    -- 100 Base-MM SFP Port

h3cevtPortSw-SFP-NO-CONNECTOR           OBJECT IDENTIFIER ::= { h3cevtPortSwitchType 57 }    -- No Connector SFP Port 

h3cevtPortSw-SFP-UNKNOWN-CONNECTOR      OBJECT IDENTIFIER ::= { h3cevtPortSwitchType 58 }    -- Unknown SFP Port

h3cevtPortSw-POS-NO-CONNECTOR      OBJECT IDENTIFIER ::= { h3cevtPortSwitchType 59 }    -- POS no connector

h3cevtPortSw-10G-BASE-SR      OBJECT IDENTIFIER ::= { h3cevtPortSwitchType 60 }    -- 10GBASE-SR Fiber Optic Transceivers with SC Connector
            
h3cevtPortSw-10G-BASE-ER      OBJECT IDENTIFIER ::= { h3cevtPortSwitchType 61 }    -- 10GBASE-ER Fiber Optic Transceivers with SC Connector

h3cevtPortSw-10G-BASE-LX4     OBJECT IDENTIFIER ::= { h3cevtPortSwitchType 62 }    -- 10GBASE-LX4 Fiber Optic Transceivers with SC Connector

h3cevtPortSw-10G-BASE-SW      OBJECT IDENTIFIER ::= { h3cevtPortSwitchType 63 }    -- 10GBASE-SW Fiber Optic Transceivers with SC Connector

h3cevtPortSw-10G-BASE-LW      OBJECT IDENTIFIER ::= { h3cevtPortSwitchType 64 }    -- 10GBASE-LW Fiber Optic Transceivers with SC Connector

h3cevtPortSw-10G-BASE-EW      OBJECT IDENTIFIER ::= { h3cevtPortSwitchType 65 }    -- 10GBASE-EW Fiber Optic Transceivers with SC Connector

h3cevtPortSw-10G-LR-SM-LC     OBJECT IDENTIFIER ::= { h3cevtPortSwitchType 66 }    -- 10GBASE-LR Single Mode Fiber Optic Transceivers with LC Connector

h3cevtPortSw-10G-SR-MM-LC     OBJECT IDENTIFIER ::= { h3cevtPortSwitchType 67 }    -- 10GBASE-SR Multi Mode Fiber Optic Transceivers with LC Connector

h3cevtPortSw-10G-ER-SM-LC     OBJECT IDENTIFIER ::= { h3cevtPortSwitchType 68 }    -- 10GBASE-ER Single Mode Fiber Optic Transceivers with LC Connector

h3cevtPortSw-10G-LW-SM-LC     OBJECT IDENTIFIER ::= { h3cevtPortSwitchType 69 }    -- 10GBASE-LW Single Mode Fiber Optic Transceivers with LC Connector

h3cevtPortSw-10G-SW-MM-LC     OBJECT IDENTIFIER ::= { h3cevtPortSwitchType 70 }    -- 10GBASE-SW Multi Mode Fiber Optic Transceivers with LC Connector 

h3cevtPortSw-10G-EW-SM-LC     OBJECT IDENTIFIER ::= { h3cevtPortSwitchType 71 }    -- 10GBASE-EW Single Mode Fiber Optic Transceivers with LC Connector

h3cevtPortSw-100BASE-SM-MTRJ     OBJECT IDENTIFIER ::= { h3cevtPortSwitchType 72 }    -- 100 Base-SM MTRJ Port

h3cevtPortSw-100BASE-MM-MTRJ     OBJECT IDENTIFIER ::= { h3cevtPortSwitchType 73 }    -- 100 Base-MM MTRJ Port

h3cevtPortSw-XFP-NO-CONNECTOR    OBJECT IDENTIFIER ::= { h3cevtPortSwitchType 74 }    -- XFP without Transceiver

h3cevtPortSw-XFP-10GBASE-SR      OBJECT IDENTIFIER ::= { h3cevtPortSwitchType 75 }    -- 10GBASE-SR XFP Transceiver

h3cevtPortSw-XFP-10GBASE-LR      OBJECT IDENTIFIER ::= { h3cevtPortSwitchType 76 }    -- 10GBASE-LR XFP Transceiver

h3cevtPortSw-XFP-10GBASE-ER      OBJECT IDENTIFIER ::= { h3cevtPortSwitchType 77 }    -- 10GBASE-ER XFP Transceiver

h3cevtPortSw-XFP-10GBASE-SW      OBJECT IDENTIFIER ::= { h3cevtPortSwitchType 78 }    -- 10GBASE-SW XFP Transceiver

h3cevtPortSw-XFP-10GBASE-LW      OBJECT IDENTIFIER ::= { h3cevtPortSwitchType 79 }    -- 10GBASE-LW XFP Transceiver

h3cevtPortSw-XFP-10GBASE-EW      OBJECT IDENTIFIER ::= { h3cevtPortSwitchType 80 }    -- 10GBASE-EW XFP Transceiver

h3cevtPortSw-XFP-10GBASE-CX4     OBJECT IDENTIFIER ::= { h3cevtPortSwitchType 81 }    -- 10GBASE-CX4 XFP Transceiver

h3cevtPortSw-XFP-10GBASE-LX4     OBJECT IDENTIFIER ::= { h3cevtPortSwitchType 82 }    -- 10GBASE-LX4 XFP Transceiver

h3cevtPortSw-XFP-UNKNOWN         OBJECT IDENTIFIER ::= { h3cevtPortSwitchType 83 }    -- Unknown  XFP Transceiver

h3cevtPortSw-XPK-NOCONNECTOR     OBJECT IDENTIFIER ::= { h3cevtPortSwitchType 84 }    -- Xenpak without Transceiver

h3cevtPortSw-XPK-10GBASE-SR      OBJECT IDENTIFIER ::= { h3cevtPortSwitchType 85 }    -- 10GBASE-SR Xenpak Transceiver

h3cevtPortSw-XPK-10GBASE-LR      OBJECT IDENTIFIER ::= { h3cevtPortSwitchType 86 }    -- 10GBASE-LR Xenpak Transceiver

h3cevtPortSw-XPK-10GBASE-ER      OBJECT IDENTIFIER ::= { h3cevtPortSwitchType 87 }    -- 10GBASE-ER Xenpak Transceiver

h3cevtPortSw-XPK-10GBASE-SW      OBJECT IDENTIFIER ::= { h3cevtPortSwitchType 88 }    -- 10GBASE-SW Xenpak Transceiver

h3cevtPortSw-XPK-10GBASE-LW      OBJECT IDENTIFIER ::= { h3cevtPortSwitchType 89 }    -- 10GBASE-LW Xenpak Transceiver

h3cevtPortSw-XPK-10GBASE-EW      OBJECT IDENTIFIER ::= { h3cevtPortSwitchType 90 }    -- 10GBASE-EW Xenpak Transceiver

h3cevtPortSw-XPK-10GBASE-CX4     OBJECT IDENTIFIER ::= { h3cevtPortSwitchType 91 }    -- 10GBASE-CX4 Xenpak Transceiver

h3cevtPortSw-XPK-10GBASE-LX4     OBJECT IDENTIFIER ::= { h3cevtPortSwitchType 92 }    -- 10GBASE-LX4 Xenpak Transceiver

h3cevtPortSw-XPK-UNKNOWN         OBJECT IDENTIFIER ::= { h3cevtPortSwitchType 93 }    -- Unknown Xenpak Transceiver

h3cevtPortSw-POS-OC48-SR-SM-LC   OBJECT IDENTIFIER ::= { h3cevtPortSwitchType 94 }    -- OC48-SR Single Mode Fiber Optic Transceivers with LC Connector

h3cevtPortSw-POS-OC48-IR-SM-LC   OBJECT IDENTIFIER ::= { h3cevtPortSwitchType 95 }    -- OC48-IR Single Mode Fiber Optic Transceivers with LC Connector

h3cevtPortSw-POS-OC48-LR-SM-LC   OBJECT IDENTIFIER ::= { h3cevtPortSwitchType 96 }    -- OC48-LR Single Mode Fiber Optic Transceivers with LC Connector

h3cevtPortSw-10G-BASE-CX4        OBJECT IDENTIFIER ::= { h3cevtPortSwitchType 97 }    -- 10G BASE-CX4 Electrical Interface

h3cevtPortSw-OLT-1000BASE-BX-SFF-SC  OBJECT IDENTIFIER ::= { h3cevtPortSwitchType 98 }    -- 1000 BASE-BX SFF SC OLT Interface

h3cevtPortSw-ONU-1000BASE-BX-SFF-SC  OBJECT IDENTIFIER ::= { h3cevtPortSwitchType 99 }    -- 1000 BASE-BX SFF SC ONU Interface

h3cevtPortSw-24G-CASCADE         OBJECT IDENTIFIER ::= { h3cevtPortSwitchType 100 }    -- 24G Cascade port

--
-- h3cevtStack section:
-- 
 
h3cevtStack	 	OBJECT IDENTIFIER ::= { h3cEntityVendortypeObjects 11 }


END
