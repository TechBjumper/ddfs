KAWAMURA-RP482LC-MIB DEFINITIONS ::= BEGIN

   IMPORTS
       MODULE-IDENTITY, OBJECT-TYPE, NOTIFICATION-TYPE,enterprises
           FROM SNMPv2-SMI
       DisplayString FROM SNMPv2-TC;

kawamura                OBJECT IDENTIFIER ::= { enterprises 14307 }

kwRp482lc MODULE-IDENTITY
       LAST-UPDATED "0310040000Z"
       ORGANIZATION "Kawamura Electric Inc."
       CONTACT-INFO
              "         Technical Support

               Postal: Kawamura Electric Inc.
                       3-36 Akatsuki-cho Seto-City
                       Aichi 489-0071 Japan

               Tel   : +81 561 86  8162
               Fax   : +81 561 86  8165

               E-mail: to-sato@kawamura.co.jp "
  
       DESCRIPTION       "A MIB module for RP482LC"

      ::= { kawamura 2 }

kwlcObjects          OBJECT IDENTIFIER ::= { kwRp482lc 1 }
kwlcTraps            OBJECT IDENTIFIER ::= { kwRp482lc 2 }

-- Digital Input Group
kwlcDigitalInputGroup  OBJECT IDENTIFIER ::= { kwlcObjects 1 }

  kwlcDigitalInputTable OBJECT-TYPE
       SYNTAX     SEQUENCE OF KwlcDigitalInputEntry
       MAX-ACCESS not-accessible
       STATUS     current
       DESCRIPTION
	       "The table of Digital Input Ports."
       ::= { kwlcDigitalInputGroup 1 }
   
  kwlcDigitalInputEntry OBJECT-TYPE
       SYNTAX     KwlcDigitalInputEntry
       MAX-ACCESS not-accessible
       STATUS     current
       DESCRIPTION
	       "The information about one Digital Input Port."
       INDEX { kwlcDIPortIndex }
       ::= { kwlcDigitalInputTable 1 }
   
   KwlcDigitalInputEntry ::= SEQUENCE {
       kwlcDIPortIndex    INTEGER(1..255),
       kwlcDIPortName     DisplayString(SIZE(0..24)),
       kwlcDIPortMode     INTEGER,
       kwlcDIPortOnName   DisplayString(SIZE(0..16)),
       kwlcDIPortOffName  DisplayString(SIZE(0..16)),
       kwlcDIPortAlarmMode INTEGER,
       kwlcDIPortOnDelay   INTEGER(0..600),
       kwlcDIPortPulseRate  Integer32,
       kwlcDIPortPulseUnit  DisplayString(SIZE(0..10)),
       kwlcDIPortPulseAlarm  Integer32,
       kwlcDIPortCurrentValue  Integer32,
       kwlcDIPortPulseValue  Integer32,
       kwlcDIPortAlarmState   INTEGER
   }
   
   kwlcDIPortIndex OBJECT-TYPE
       SYNTAX     INTEGER(1..255) 
       MAX-ACCESS read-only
       STATUS     current
       DESCRIPTION
	       "The index of the Digital Input Port."
       ::= { kwlcDigitalInputEntry 1 }
   
   kwlcDIPortName OBJECT-TYPE
       SYNTAX     DisplayString(SIZE(0..24))
       MAX-ACCESS read-only
       STATUS     current
       DESCRIPTION
	       "The name of the Digital Input Port."
       ::= { kwlcDigitalInputEntry 2 }

   kwlcDIPortMode OBJECT-TYPE
       SYNTAX     INTEGER{
                       notUsed(1),
                       diMode(2),
                       pulseMode(3),
                       keyMode(4),
                       unknown(5)
                   }
       MAX-ACCESS read-only
       STATUS     current
       DESCRIPTION
	       "The mode of the Digital Input Port."
       ::= { kwlcDigitalInputEntry 3 }

   kwlcDIPortOnName OBJECT-TYPE
       SYNTAX     DisplayString(SIZE(0..16))
       MAX-ACCESS read-only
       STATUS     current
       DESCRIPTION
	       "The name when the Digital Input Port is On."
       ::= { kwlcDigitalInputEntry 4 }

   kwlcDIPortOffName OBJECT-TYPE
       SYNTAX     DisplayString(SIZE(0..16))
       MAX-ACCESS read-only
       STATUS     current
       DESCRIPTION
	       "The name when  the Digital Input Port is off."
       ::= { kwlcDigitalInputEntry 5 }

   kwlcDIPortAlarmMode OBJECT-TYPE
       SYNTAX    INTEGER{
                  offAlarm(1),
                  onAlarm(2),
                  noAlarmA(3),
                  noAlarmB(4)
                 }
       MAX-ACCESS read-only
       STATUS     current
       DESCRIPTION
	       "The alarm mode of the Digital Input Port."
       ::= { kwlcDigitalInputEntry 6 }

   kwlcDIPortOnDelay OBJECT-TYPE
       SYNTAX     INTEGER(0..600)
       UNITS   "Sec"
       MAX-ACCESS read-only
       STATUS     current
       DESCRIPTION
	       "The On Delay  of the Digital Input Port."
       ::= { kwlcDigitalInputEntry 7 }

   kwlcDIPortPulseRate OBJECT-TYPE
       SYNTAX     Integer32
       UNITS    "(x 0.001)"
       MAX-ACCESS read-only
       STATUS     current
       DESCRIPTION
	       "The Pulse Input Rate of the Digital Input Port."
       ::= { kwlcDigitalInputEntry 8 }

   kwlcDIPortPulseUnit OBJECT-TYPE
       SYNTAX     DisplayString(SIZE(0..16))
       MAX-ACCESS read-only
       STATUS     current
       DESCRIPTION
	       "The Unit of the Digital Input Port for Pulse Input."
       ::= { kwlcDigitalInputEntry 9 }

   kwlcDIPortPulseAlarm OBJECT-TYPE
       SYNTAX   Integer32
       UNITS    "(x 0.001)"
       MAX-ACCESS read-only
       STATUS     current
       DESCRIPTION
	       "The threshold  value of the Digital Input Port for Pulse Input."
       ::= { kwlcDigitalInputEntry 10 }

   kwlcDIPortCurrentValue OBJECT-TYPE
       SYNTAX     INTEGER{
                    off(0),
                    on(1),
		    pulse(2)
                  }
       MAX-ACCESS read-only
       STATUS     current
       DESCRIPTION
	       "The current value  of the Digital Input Port."
       ::= { kwlcDigitalInputEntry 11 }

   kwlcDIPortPulseValue OBJECT-TYPE
       SYNTAX   Integer32
       UNITS    "(x 0.001)"
       MAX-ACCESS read-only
       STATUS     current
       DESCRIPTION
	       "The added value of the Pulse Input."
       ::= { kwlcDigitalInputEntry 12 }

   kwlcDIPortAlarmState OBJECT-TYPE
       SYNTAX     INTEGER{
                     normal(1),
                     alarm(2),
                     unknown(3)
                  }
       MAX-ACCESS read-only
       STATUS     current
       DESCRIPTION
	       "The alarm state of the Digital Input Port."
       ::= { kwlcDigitalInputEntry 13 }


-- Analog Input Group
kwlcAnalogInputGroup   OBJECT IDENTIFIER ::= { kwlcObjects 2 }

  kwlcAnalogInputTable OBJECT-TYPE
       SYNTAX     SEQUENCE OF KwlcAnalogInputEntry
       MAX-ACCESS not-accessible
       STATUS     current
       DESCRIPTION
	       "The table of Analog Input Ports."
       ::= { kwlcAnalogInputGroup 1 }
   
  kwlcAnalogInputEntry OBJECT-TYPE
       SYNTAX     KwlcAnalogInputEntry
       MAX-ACCESS not-accessible
       STATUS     current
       DESCRIPTION
	       "The information about one Analog Input Port."
       INDEX { kwlcAIPortIndex }
       ::= { kwlcAnalogInputTable 1 }
   
   KwlcAnalogInputEntry ::= SEQUENCE {
       kwlcAIPortIndex    INTEGER(1..255),
       kwlcAIPortName     DisplayString(SIZE(0..24)),
       kwlcAIPortMode     INTEGER,
       kwlcAIPortID     DisplayString(SIZE(0..32)),
       kwlcAIPortUnit     DisplayString(SIZE(0..10)),
       kwlcAIPortRangeMin Integer32,
       kwlcAIPortRangeMax Integer32,
       kwlcAIPortLowThreshold Integer32,
       kwlcAIPortLowWarning Integer32,
       kwlcAIPortHighWarning Integer32,
       kwlcAIPortHighThreshold Integer32,
       kwlcAIPortLowHyst Integer32,
       kwlcAIPortHighHyst Integer32,
       kwlcAIPortCurrentValue  Integer32,
       kwlcAIPortAlarmState   INTEGER
   }
   
   kwlcAIPortIndex OBJECT-TYPE
       SYNTAX     INTEGER(1..255) 
       MAX-ACCESS read-only
       STATUS     current
       DESCRIPTION
	       "The index of the Analog Input Port."
       ::= { kwlcAnalogInputEntry 1 }
   
   kwlcAIPortName OBJECT-TYPE
       SYNTAX     DisplayString(SIZE(0..24))
       MAX-ACCESS read-only
       STATUS     current
       DESCRIPTION
	       "The name of the Analog Input Port."
       ::= { kwlcAnalogInputEntry 2 }

   kwlcAIPortMode OBJECT-TYPE
       SYNTAX     INTEGER{
                         notUsed(1),
                         mA(2),
                         ct(3),
                         v(4),
                         unknown(5)
                 }
       MAX-ACCESS read-only
       STATUS     current
       DESCRIPTION
	       "The mode of the Analog Input Port."
       ::= { kwlcAnalogInputEntry 3 }

   kwlcAIPortID OBJECT-TYPE
       SYNTAX     DisplayString(SIZE(0..32))
       MAX-ACCESS read-only
       STATUS     current
       DESCRIPTION
	       "The ID of the Analog Input Port."
       ::= { kwlcAnalogInputEntry 4 }

   kwlcAIPortUnit OBJECT-TYPE
       SYNTAX     DisplayString(SIZE(0..10))
       MAX-ACCESS read-only
       STATUS     current
       DESCRIPTION
	       "The unit of the Analog Input Port."
       ::= { kwlcAnalogInputEntry 5 }

   kwlcAIPortRangeMin OBJECT-TYPE
       SYNTAX     Integer32
       UNITS    "(x 0.001)"
       MAX-ACCESS read-only
       STATUS     current
       DESCRIPTION
	       "The min value of the Analog Input Port range."
       ::= { kwlcAnalogInputEntry 6 }

   kwlcAIPortRangeMax OBJECT-TYPE
       SYNTAX     Integer32
       UNITS    "(x 0.001)"
       MAX-ACCESS read-only
       STATUS     current
       DESCRIPTION
	       "The max value of the Analog Input Port range."
       ::= { kwlcAnalogInputEntry 7 }

   kwlcAIPortLowThreshold OBJECT-TYPE
       SYNTAX     Integer32
       UNITS    "(x 0.001)"
       MAX-ACCESS read-only
       STATUS     current
       DESCRIPTION
	       "The lower threshold  value of the Analog Input Port."
       ::= { kwlcAnalogInputEntry 8 }

   kwlcAIPortLowWarning OBJECT-TYPE
       SYNTAX     Integer32
       UNITS    "(x 0.001)"
       MAX-ACCESS read-only
       STATUS     current
       DESCRIPTION
	       "The lower warning level value of the Analog Input Port."
       ::= { kwlcAnalogInputEntry 9 }

   kwlcAIPortHighWarning OBJECT-TYPE
       SYNTAX   Integer32
       UNITS    "(x 0.001)"
       MAX-ACCESS read-only
       STATUS     current
       DESCRIPTION
	       "The higher warning level value of the Analog Input Port."
       ::= { kwlcAnalogInputEntry 10 }

   kwlcAIPortHighThreshold OBJECT-TYPE
       SYNTAX   Integer32
       UNITS    "(x 0.001)"
       MAX-ACCESS read-only
       STATUS     current
       DESCRIPTION
	       "The higher threshold  value of the Analog Input Port."
       ::= { kwlcAnalogInputEntry 11 }

   kwlcAIPortLowHyst OBJECT-TYPE
       SYNTAX   Integer32
       UNITS    "(x 0.001)"
       MAX-ACCESS read-only
       STATUS     current
       DESCRIPTION
	       "The low histrysis  value of the Analog Input Port."
       ::= { kwlcAnalogInputEntry 12 }

   kwlcAIPortHighHyst OBJECT-TYPE
       SYNTAX   Integer32
       UNITS    "(x 0.001)"
       MAX-ACCESS read-only
       STATUS     current
       DESCRIPTION
	       "The high histrysis  value of the Analog Input Port."
       ::= { kwlcAnalogInputEntry 13 }


   kwlcAIPortCurrentValue OBJECT-TYPE
       SYNTAX   Integer32
       UNITS    "(x 0.001)"
       MAX-ACCESS read-only
       STATUS     current
       DESCRIPTION
	       "The current value  of the Analog Input Port."
       ::= { kwlcAnalogInputEntry 14 }


   kwlcAIPortAlarmState OBJECT-TYPE
       SYNTAX     INTEGER{
		      normal(1),
                      lowAlarm(2),
                      highAlarm(3),
                      lowWarning(4),
                      highWarning(5),
                      sensorAlarm(6),
                      unknown(7)
                   }
       MAX-ACCESS read-only
       STATUS     current
       DESCRIPTION
	       "The alarm state of the Analog Input Port."
       ::= { kwlcAnalogInputEntry 15 }


-- Thermo Input Group 
kwlcThermoInputGroup   OBJECT IDENTIFIER ::= { kwlcObjects 3 }

  kwlcThermoInputTable OBJECT-TYPE
       SYNTAX     SEQUENCE OF KwlcThermoInputEntry
       MAX-ACCESS not-accessible
       STATUS     current
       DESCRIPTION
	       "The table of Thermo Input Ports."
       ::= { kwlcThermoInputGroup 1 }
   
  kwlcThermoInputEntry OBJECT-TYPE
       SYNTAX     KwlcThermoInputEntry
       MAX-ACCESS not-accessible
       STATUS     current
       DESCRIPTION
	       "The information about one Thermo Input Port."
       INDEX { kwlcTIPortIndex }
       ::= { kwlcThermoInputTable 1 }
   
   KwlcThermoInputEntry ::= SEQUENCE {
       kwlcTIPortIndex    INTEGER(1..255),
       kwlcTIPortName     DisplayString(SIZE(0..24)),
       kwlcTIPortMode     INTEGER,
       kwlcTIPortID     DisplayString(SIZE(0..32)),
       kwlcTIPortLowThreshold Integer32,
       kwlcTIPortLowWarning Integer32,
       kwlcTIPortHighWarning Integer32,
       kwlcTIPortHighThreshold Integer32,
       kwlcTIPortLowHyst Integer32,
       kwlcTIPortHighHyst Integer32,
       kwlcTIPortCurrentValue  Integer32,
       kwlcTIPortAlarmState   INTEGER
   }
   
   kwlcTIPortIndex OBJECT-TYPE
       SYNTAX     INTEGER(1..255) 
       MAX-ACCESS read-only
       STATUS     current
       DESCRIPTION
	       "The index of the Thermo Input Port."
       ::= { kwlcThermoInputEntry 1 }
   
   kwlcTIPortName OBJECT-TYPE
       SYNTAX     DisplayString(SIZE(0..24))
       MAX-ACCESS read-only
       STATUS     current
       DESCRIPTION
	       "The name of the Thermo Input Port."
       ::= { kwlcThermoInputEntry 2 }

   kwlcTIPortMode OBJECT-TYPE
       SYNTAX     INTEGER{
                      notUsed(1),
                      used(2),
                      unknown(3)
                   }
       MAX-ACCESS read-only
       STATUS     current
       DESCRIPTION
	       "The mode of the Thermo Input Port."
       ::= { kwlcThermoInputEntry 3 }

   kwlcTIPortID OBJECT-TYPE
       SYNTAX     DisplayString(SIZE(0..32))
       MAX-ACCESS read-only
       STATUS     current
       DESCRIPTION
	       "The ID of the Thermo Input Port."
       ::= { kwlcThermoInputEntry 4 }

   kwlcTIPortLowThreshold OBJECT-TYPE
       SYNTAX     Integer32
       UNITS    "(x 0.1 'C)"
       MAX-ACCESS read-only
       STATUS     current
       DESCRIPTION
	       "The lower threshold  value of the Thermo Input Port."
       ::= { kwlcThermoInputEntry 5 }

   kwlcTIPortLowWarning OBJECT-TYPE
       SYNTAX     Integer32
       UNITS    "(x 0.1 'C)"
       MAX-ACCESS read-only
       STATUS     current
       DESCRIPTION
	       "The lower warning value of the Thermo Input Port."
       ::= { kwlcThermoInputEntry 6 }

   kwlcTIPortHighWarning OBJECT-TYPE
       SYNTAX   Integer32
       UNITS    "(x 0.1 'C)"
       MAX-ACCESS read-only
       STATUS     current
       DESCRIPTION
	       "The higher warning value of the Thermo Input Port."
       ::= { kwlcThermoInputEntry 7 }

   kwlcTIPortHighThreshold OBJECT-TYPE
       SYNTAX   Integer32
       UNITS    "(x 0.1 'C)"
       MAX-ACCESS read-only
       STATUS     current
       DESCRIPTION
	       "The higher threshold  value of the Thermo Input Port."
       ::= { kwlcThermoInputEntry 8 }

   kwlcTIPortLowHyst OBJECT-TYPE
       SYNTAX   Integer32
        UNITS    "(x 0.1 'C)"
       MAX-ACCESS read-only
       STATUS     current
       DESCRIPTION
	       "The low histrysis  value of the Thermo Input Port."
       ::= { kwlcThermoInputEntry 9 }

   kwlcTIPortHighHyst OBJECT-TYPE
       SYNTAX   Integer32
       UNITS    "(x 0.1 'C)"
       MAX-ACCESS read-only
       STATUS     current
       DESCRIPTION
	       "The high histrysis  value of the Thermo Input Port."
       ::= { kwlcThermoInputEntry 10 }

   kwlcTIPortCurrentValue OBJECT-TYPE
       SYNTAX   Integer32
       UNITS    "(x 0.1 'C)"
       MAX-ACCESS read-only
       STATUS     current
       DESCRIPTION
	       "The current value  of the Thermo Input Port."
       ::= { kwlcThermoInputEntry 11 }

   kwlcTIPortAlarmState OBJECT-TYPE
       SYNTAX     INTEGER{
		      normal(1),
                      lowAlarm(2),
                      highAlarm(3),
                      lowWarning(4),
                      highWarning(5),
                      sensorAlarm(6),
                      unknown(7)
                   }
       MAX-ACCESS read-only
       STATUS     current
       DESCRIPTION
	       "The alarm state of the Thermo Input Port."
       ::= { kwlcThermoInputEntry 12 }


-- Digital Output Group
kwlcDigitalOutputGroup OBJECT IDENTIFIER ::= { kwlcObjects 4 }

  kwlcDigitalOutputTable OBJECT-TYPE
       SYNTAX     SEQUENCE OF KwlcDigitalOutputEntry
       MAX-ACCESS not-accessible
       STATUS     current
       DESCRIPTION
	       "The table of Digital Output Ports."
       ::= { kwlcDigitalOutputGroup 1 }
   
  kwlcDigitalOutputEntry OBJECT-TYPE
       SYNTAX     KwlcDigitalOutputEntry
       MAX-ACCESS not-accessible
       STATUS     current
       DESCRIPTION
	       "The information about one Digital Output Port."
       INDEX { kwlcDOPortIndex }
       ::= { kwlcDigitalOutputTable 1 }
   
   KwlcDigitalOutputEntry ::= SEQUENCE {
       kwlcDOPortIndex    INTEGER(1..255),
       kwlcDOPortName     DisplayString(SIZE(0..24)),
       kwlcDOPortMode     INTEGER,
       kwlcDOPortOnName   DisplayString(SIZE(0..16)),
       kwlcDOPortOffName  DisplayString(SIZE(0..16)),
       kwlcDOPortDefValue INTEGER,
       kwlcDOPortControlCondition INTEGER,
       kwlcDOPortRelPort   DisplayString(SIZE(0..16)),
       kwlcDOPortControlMode INTEGER,
       kwlcDOPortCurrentValue  INTEGER
   }
   
   kwlcDOPortIndex OBJECT-TYPE
       SYNTAX     INTEGER(1..255) 
       MAX-ACCESS read-only
       STATUS     current
       DESCRIPTION
	       "The index of the Digital Output Port."
       ::= { kwlcDigitalOutputEntry 1 }
   
   kwlcDOPortName OBJECT-TYPE
       SYNTAX     DisplayString(SIZE(0..24))
       MAX-ACCESS read-only
       STATUS     current
       DESCRIPTION
	       "The name of the Digital Output Port."
       ::= { kwlcDigitalOutputEntry 2 }

   kwlcDOPortMode OBJECT-TYPE
       SYNTAX     INTEGER{
                       notUsed(1),
                       used(2),
                       unknown(3)
                   }
       MAX-ACCESS read-only
       STATUS     current
       DESCRIPTION
	       "The mode of the Digital Output Port."
       ::= { kwlcDigitalOutputEntry 3 }

   kwlcDOPortOnName OBJECT-TYPE
       SYNTAX     DisplayString(SIZE(0..16))
       MAX-ACCESS read-only
       STATUS     current
       DESCRIPTION
	       "The name when the Digital Output Port is On."
       ::= { kwlcDigitalOutputEntry 4 }

   kwlcDOPortOffName OBJECT-TYPE
       SYNTAX     DisplayString(SIZE(0..16))
       MAX-ACCESS read-only
       STATUS     current
       DESCRIPTION
	       "The name when  the Digital Output Port is off."
       ::= { kwlcDigitalOutputEntry 5 }

   kwlcDOPortDefValue OBJECT-TYPE
       SYNTAX     INTEGER{
                       off(0),
                       on(1)
                   }
       MAX-ACCESS read-only
       STATUS     current
       DESCRIPTION
	       "The default value of the Digital Output Port."
       ::= { kwlcDigitalOutputEntry 6 }


   kwlcDOPortControlCondition OBJECT-TYPE
       SYNTAX     INTEGER{
			manual(1),
			allalarm(2),
			allDIalarm(3),
			allAIalarm(4),
			allTIalarm(5),
			allWarning(6),
			allAIwarning(8),
			allTIwarning(9),
			diAlarm(11),
			aiAlarm(12),
			tiAlarm(13),
			aiWarning(14),
			tiWarning(15),
			unknown(16),
			manualPulse(99)
		  }
       MAX-ACCESS read-only
       STATUS     current
       DESCRIPTION
	       "The contorol condition  of the Digital Ouput Port."
       ::= { kwlcDigitalOutputEntry 7 }

   kwlcDOPortRelPort OBJECT-TYPE
       SYNTAX     DisplayString(SIZE(0..16))
       MAX-ACCESS read-only
       STATUS     current
       DESCRIPTION
	       "The contorol condition name of the Digital Ouput Port."
       ::= { kwlcDigitalOutputEntry 8 }

    kwlcDOPortControlMode OBJECT-TYPE
       SYNTAX    INTEGER{
                  autoReset(1),
                  selfKeep(2)
                 }
       MAX-ACCESS read-only
       STATUS     current
       DESCRIPTION
	       "The contorol mode of the Digital Output Port."
       ::= { kwlcDigitalOutputEntry 9 }

   kwlcDOPortCurrentValue OBJECT-TYPE
       SYNTAX     INTEGER{
                    off(0),
                    on(1)
                  }
       MAX-ACCESS read-write
       STATUS     current
       DESCRIPTION
	       "The current value  of the Digital Output Port."
       ::= { kwlcDigitalOutputEntry 10 }

-- RP482LC Traps

   kwlcDIAlarmOn  NOTIFICATION-TYPE
       OBJECTS { kwlcDIPortIndex }  
       STATUS  current
       DESCRIPTION
               "A Digital Input Alarm on
                trap which is sent when the Digital Input 
                Port Alarm is on."
       ::= { kwlcTraps 1 }

   kwlcDIAlarmOff  NOTIFICATION-TYPE
       OBJECTS { kwlcDIPortIndex }  
       STATUS  current
       DESCRIPTION
               "A Digital Input Alarm  off trap   
                which is sent when the Digital Input 
                Port Alarm is off."
       ::= { kwlcTraps 2 }

   kwlcAIHTAlarmOn  NOTIFICATION-TYPE
       OBJECTS { kwlcAIPortIndex }  
       STATUS  current
       DESCRIPTION
               "An Analog Input High Threshold Alarm on
                 trap which is sent when the Analog Input 
                Port High Threshold Alarm is off."
       ::= { kwlcTraps 3 }

   kwlcAIHTAlarmOff  NOTIFICATION-TYPE
       OBJECTS { kwlcAIPortIndex }  
       STATUS  current
       DESCRIPTION
               "An Analog Input High Threshold Alarm off
                 trap which is sent when the Analog Input 
                Port High Threshold Alarm is on."
       ::= { kwlcTraps 4 }

   kwlcAILTAlarmOn  NOTIFICATION-TYPE
       OBJECTS { kwlcAIPortIndex }  
       STATUS  current
       DESCRIPTION
               "An Analog Input  Low Threshold Alarm on
                 trap which is sent when the Analog Input 
                Port Low Threshold Alarm is off."
       ::= { kwlcTraps 5 }

   kwlcAILTAlarmOff  NOTIFICATION-TYPE
       OBJECTS { kwlcAIPortIndex }  
       STATUS  current
       DESCRIPTION
               "An Analog Input Low Threshold Alarm off
                 trap which is sent when the Analog Input 
                Port Low Threshold Alarm is on."
       ::= { kwlcTraps 6 }

   kwlcAIHTWarningOn  NOTIFICATION-TYPE
       OBJECTS { kwlcAIPortIndex }  
       STATUS  current
       DESCRIPTION
               "An Analog Input High Threshold Warning on
                 trap which is sent when the Analog Input 
                Port High Threshold Warning off."
       ::= { kwlcTraps 7 }

   kwlcAIHTWarningOff  NOTIFICATION-TYPE
       OBJECTS { kwlcAIPortIndex }  
       STATUS  current
       DESCRIPTION
               "An Analog Input High Threshold Warning off
                 trap which is sent when the Analog Input 
                Port High Threshold Warning is on."
       ::= { kwlcTraps 8 }

   kwlcAILTWarningOn  NOTIFICATION-TYPE
       OBJECTS { kwlcAIPortIndex }  
       STATUS  current
       DESCRIPTION
               "An Analog Input Low Threshold Warning on
                 trap which is sent when the Analog Input 
                Port Low Threshold Warning is off."
       ::= { kwlcTraps 9 }

   kwlcAILTWarningOff  NOTIFICATION-TYPE
       OBJECTS { kwlcAIPortIndex }  
       STATUS  current
       DESCRIPTION
               "An Analog Input Low Threshold Warning off
                 trap which is sent when the Analog Input 
                Port Low Threshold Warning is on."
       ::= { kwlcTraps 10 }

   kwlcAISensorAlarmOn  NOTIFICATION-TYPE
       OBJECTS { kwlcAIPortIndex }  
       STATUS  current
       DESCRIPTION
               "An Analog Input Sensor Alarm on
                 trap which is sent when the Analog Input 
                Port Sensor Alarm is off."
       ::= { kwlcTraps 11 }

   kwlcAISensorAlarmOff  NOTIFICATION-TYPE
       OBJECTS { kwlcAIPortIndex }  
       STATUS  current
       DESCRIPTION
               "An Analog Input Sensor Alarm off
                 trap which is sent when the Analog Input 
                Port Sensor Alarm is on."
       ::= { kwlcTraps 12 }


   kwlcTIHTAlarmOn  NOTIFICATION-TYPE
       OBJECTS { kwlcTIPortIndex }  
       STATUS  current
       DESCRIPTION
               "An Thermo Input High Threshold Alarm on
                 trap which is sent when the Thermo Input 
                Port High Threshold Alarm is off."
       ::= { kwlcTraps 13 }

   kwlcTIHTAlarmOff  NOTIFICATION-TYPE
       OBJECTS { kwlcTIPortIndex }  
       STATUS  current
       DESCRIPTION
               "An Thermo Input High Threshold Alarm off
                 trap which is sent when the Thermo Input 
                Port High Threshold Alarm is on."
       ::= { kwlcTraps 14 }

   kwlcTILTAlarmOn  NOTIFICATION-TYPE
       OBJECTS { kwlcTIPortIndex }  
       STATUS  current
       DESCRIPTION
               "An Thermo Input  Low Threshold Alarm on
                 trap which is sent when the Thermo Input 
                Port Low Threshold Alarm is off."
       ::= { kwlcTraps 15 }

   kwlcTILTAlarmOff  NOTIFICATION-TYPE
       OBJECTS { kwlcTIPortIndex }  
       STATUS  current
       DESCRIPTION
               "An Thermo Input Low Threshold Alarm off
                 trap which is sent when the Thermo Input 
                Port Low Threshold Alarm is on."
       ::= { kwlcTraps 16 }

   kwlcTIHTWarningOn  NOTIFICATION-TYPE
       OBJECTS { kwlcTIPortIndex }  
       STATUS  current
       DESCRIPTION
               "An Thermo Input High Threshold Warning on
                 trap which is sent when the Thermo Input 
                Port High Threshold Warning is off."
       ::= { kwlcTraps 17 }

   kwlcTIHTWarningOff  NOTIFICATION-TYPE
       OBJECTS { kwlcTIPortIndex }  
       STATUS  current
       DESCRIPTION
               "An Thermo Input High Threshold Warning off
                 trap which is sent when the Thermo Input 
                Port High Threshold Warning is on."
       ::= { kwlcTraps 18 }

   kwlcTILTWarningOn  NOTIFICATION-TYPE
       OBJECTS { kwlcTIPortIndex }  
       STATUS  current
       DESCRIPTION
               "An Thermo Input  Low Threshold Warning on
                 trap which is sent when the Thermo Input 
                Port Low Threshold Warning is off."
       ::= { kwlcTraps 19 }

   kwlcTILTWarningOff  NOTIFICATION-TYPE
       OBJECTS { kwlcTIPortIndex }  
       STATUS  current
       DESCRIPTION
               "An Thermo Input Low Threshold Warning off
                 trap which is sent when the Thermo Input 
                Port Low Threshold Warning is on."
       ::= { kwlcTraps 20 }

   kwlcTISensorAlarmOn  NOTIFICATION-TYPE
       STATUS  current
       DESCRIPTION
               "An Thermo Input Sensor Alarm on
                 trap which is sent when the Thermo Input 
                Port Sensor Alarm is off."
       ::= { kwlcTraps 21 }

   kwlcTISensorAlarmOff  NOTIFICATION-TYPE
       STATUS  current
       DESCRIPTION
               "An Thermo Input Sensor Alarm off
                 trap which is sent when the Thermo Input 
                Port Sensor Alarm is on."
       ::= { kwlcTraps 22 }


   kwlcAgentStop  NOTIFICATION-TYPE
       STATUS  current
       DESCRIPTION
               "RP482LC Agent Stopped."
       ::= { kwlcTraps 99 }


END
