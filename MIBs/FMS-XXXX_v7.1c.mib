--  Title:    FMS-XXXX.MIB
--  Version:  v7.1c	
--  Date:     06/17/04 09:02am
--
--  Copyright @ 2004 RLE Technologies.  All rights reserved worldwide.
--
--  This MIB defines objects for the RLE falcon SNMP Agent.
--

RLE-FALCON-EM-MIB DEFINITIONS ::= BEGIN

IMPORTS
        TruthValue
                FROM RFC1253-MIB
        DisplayString
                FROM RFC1213-MIB
        OBJECT-TYPE, Gauge
                FROM RFC1155-SMI
        TRAP-TYPE
                FROM RFC-1215
        Counter, enterprises
                FROM RFC1155-SMI;
   PositiveInteger ::= INTEGER (1..2147483647)

rle OBJECT IDENTIFIER ::= { enterprises  3184 }

products   OBJECT IDENTIFIER ::= { rle  1 }

falcon-em  OBJECT IDENTIFIER ::= { products  5 }

falcon-emMIB OBJECT IDENTIFIER ::= { falcon-em 1 }

falconIdent OBJECT IDENTIFIER ::= { falcon-emMIB 1 }

falconIdentManufacturer OBJECT-TYPE
    SYNTAX  DisplayString
    ACCESS  read-only
    STATUS  mandatory
    DESCRIPTION
           "The Monitor Control Unit manufacturer."
    ::= { falconIdent  1 }

falconIdentModel OBJECT-TYPE
    SYNTAX  DisplayString
    ACCESS  read-only
    STATUS  mandatory
    DESCRIPTION
           "The Monitor Control Unit Model designation."
    ::= { falconIdent  2 }

falconIdentSoftwareVersion OBJECT-TYPE
    SYNTAX  DisplayString
    ACCESS  read-only
    STATUS  mandatory
    DESCRIPTION
           "The falcon SNMP Agent software version."
    ::= { falconIdent  3 }

falconIdentSpecific OBJECT-TYPE
    SYNTAX  OBJECT IDENTIFIER
    ACCESS  read-only
    STATUS  mandatory
    DESCRIPTION
           "A reference to MIB definitions specific to the
            particular Monitor Unit being managed. This
            object is used to locate the product-specific MIB
            for this device.

            If this information is not present, its value
            should be the OBJECT IDENTIFIER { 0 0 },
            which is a syntactically valid object identifier,
            and any conformant implementation of ASN.1 and BER
            must be able to generate and recognize this value."
    ::= { falconIdent  4 }

falconOptionCards OBJECT IDENTIFIER ::= { falconIdent 5 }

falconOptionCard1 OBJECT-TYPE
    SYNTAX  INTEGER {
    notInstalled(0),
    analog12input12relay(1),
    digital12input12relay(2),
    digital24input(3)
}
    ACCESS  read-only
    STATUS  mandatory
    DESCRIPTION
           "Option slot #1."
    ::= { falconOptionCards  1 }

falconOptionCard2 OBJECT-TYPE
    SYNTAX  INTEGER {
    notInstalled(0),
    analog12input12relay(1),
    digital12input12relay(2),
    digital24input(3)
}
    ACCESS  read-only
    STATUS  mandatory
    DESCRIPTION
           "Option slot #2."
    ::= { falconOptionCards  2 }

falconOptionCard3 OBJECT-TYPE
    SYNTAX  INTEGER {
    notInstalled(0),
    analog12input12relay(1),
    digital12input12relay(2),
    digital24input(3)
}
    ACCESS  read-only
    STATUS  mandatory
    DESCRIPTION
           "Option slot #3."
    ::= { falconOptionCards  3 }

falconOptionCard4 OBJECT-TYPE
    SYNTAX  INTEGER {
    notInstalled(0),
    analog12input12relay(1),
    digital12input12relay(2),
    digital24input(3)
}
    ACCESS  read-only
    STATUS  mandatory
    DESCRIPTION
           "Option slot #4."
    ::= { falconOptionCards  4 }

falconSystem OBJECT IDENTIFIER ::= { falcon-emMIB 2 }

falconSystemSettings OBJECT IDENTIFIER ::= { falconSystem 1 }

falconClock OBJECT-TYPE
    SYNTAX  DisplayString
    ACCESS  read-write
    STATUS  mandatory
    DESCRIPTION
           "The falcon internal clock settings.
            Displayed as MM/DD/YY HH:MM:SS"
    ::= { falconSystemSettings  1 }

falconDoorAlarmBypass OBJECT-TYPE
    SYNTAX  INTEGER (-2147483648..2147483647)
    ACCESS  read-write
    STATUS  mandatory
    DESCRIPTION
           "The falcon door alarm bypass switch.
            This allows the alarm to be bypassed upon valid keypad access.
            Zero disables this, or use 1 thru 8 for the corresponding
            falcon input."
    ::= { falconSystemSettings  2 }

falconInputVoltage OBJECT-TYPE
    SYNTAX  INTEGER (-2147483648..2147483647)
    ACCESS  read-only
    STATUS  mandatory
    DESCRIPTION
           "The falcon input voltage (DC Power)."
    ::= { falconSystemSettings  3 }

falconLowBatteryThreshold OBJECT-TYPE
    SYNTAX  INTEGER (-2147483648..2147483647)
    ACCESS  read-write
    STATUS  mandatory
    DESCRIPTION
           "The low voltage trip point for the low battery alarm.
            When the input voltage goes below this voltage, the
            Low Battery alarm is set."
    ::= { falconSystemSettings  4 }

falconAnalogAverage OBJECT-TYPE
    SYNTAX  INTEGER (0..60)
    ACCESS  read-write
    STATUS  mandatory
    DESCRIPTION
           "This is the analog averaging duration in seconds.
            The analog input readings are averaged for this time
            period before updating. This value must be set to
            1,2,3,4,5,6,10,15,20,30 or 60 seconds."
    ::= { falconSystemSettings  5 }

falconPagerStatusString OBJECT-TYPE
    SYNTAX  DisplayString
    ACCESS  read-only
    STATUS  mandatory
    DESCRIPTION
           "The falcon last page status char string."
    ::= { falconSystemSettings  6 }

falconKeypad OBJECT IDENTIFIER ::= { falconSystem 2 }

falconKeypadUsers OBJECT-TYPE
    SYNTAX  INTEGER
    ACCESS  read-only
    STATUS  mandatory
    DESCRIPTION
           "The number of keypad users allowed on this system."
    ::= { falconKeypad 1 }

falconKeypadUsersTable OBJECT-TYPE
    SYNTAX  SEQUENCE OF FalconKeypadUserEntry
    ACCESS  not-accessible
    STATUS  mandatory
    DESCRIPTION
           "A table of the falcon keypad users.  The number of
            users is given by the value of falconKeypadUsers."
    ::= { falconKeypad 2 }

falconKeypadUserEntry OBJECT-TYPE
     SYNTAX  FalconKeypadUserEntry
     ACCESS  not-accessible
     STATUS  mandatory
     DESCRIPTION
            "An entry containing objects for the Falcon
             keypad user configuration."
     INDEX   { falconKeypadUserIndex }
     ::= { falconKeypadUsersTable 1 }


FalconKeypadUserEntry ::= SEQUENCE {
     falconKeypadUserIndex       INTEGER,
     falconKeypadCode            DisplayString,
     falconKeypadName            DisplayString
}

falconKeypadUserIndex OBJECT-TYPE
    SYNTAX  INTEGER
    ACCESS  read-only
    STATUS  mandatory
    DESCRIPTION
           "A unique value for each keypad user.  Its value
            ranges between 1 and the value of falconKeypadUsers."
     ::= { falconKeypadUserEntry 1 }

falconKeypadCode OBJECT-TYPE
    SYNTAX  DisplayString
    ACCESS  read-write
    STATUS  mandatory
    DESCRIPTION
           "The falcon keypad access code for user #X.
            This can be up to six numeric characters."
    ::= { falconKeypadUserEntry  2 }

falconKeypadName OBJECT-TYPE
    SYNTAX  DisplayString
    ACCESS  read-write
    STATUS  mandatory
    DESCRIPTION
           "The falcon keypad access name for user #X.
            This can be up to 20 characters."
    ::= { falconKeypadUserEntry  3 }

falconInputs OBJECT IDENTIFIER ::= { falcon-emMIB  3 }

falconInputPorts OBJECT IDENTIFIER ::= { falconInputs  1 }

falconNumberOfInputPorts OBJECT-TYPE
    SYNTAX  INTEGER
    ACCESS  read-only
    STATUS  mandatory
    DESCRIPTION
           "The number of input ports available on this system."
    ::= { falconInputPorts 1 }

falconInputTable OBJECT-TYPE
    SYNTAX  SEQUENCE OF FalconInputEntry
    ACCESS  not-accessible
    STATUS  mandatory
    DESCRIPTION
           "A table of the falcon input port status and configuration.
            The number of input ports is given by the value of 
            falconNumberOfInputPorts."
    ::= { falconInputPorts 2 }

falconInputEntry OBJECT-TYPE
     SYNTAX  FalconInputEntry
     ACCESS  not-accessible
     STATUS  mandatory
     DESCRIPTION
            "An entry containing objects for the Falcon
             input port data and configuration."
     INDEX   { falconInputIndex }
     ::= { falconInputTable 1 }

          
FalconInputEntry ::= SEQUENCE {
     falconInputIndex       INTEGER,
     falconInputType        INTEGER,
     falconInputState       INTEGER,
     falconInputReading     INTEGER,
     falconInputGain        INTEGER,
     falconInputOffset      INTEGER,
     falconInputLabel       DisplayString,
     falconInputUOM         DisplayString,
     falconInputHighLimit2  INTEGER,
     falconInputHighLimit   INTEGER,
     falconInputLowLimit    INTEGER,
     falconInputLowLimit2   INTEGER,
     falconInputDelay       INTEGER,
     falconInputHysteresis  INTEGER,
     falconInputSchedule    INTEGER,
     falconInputDigOffLabel DisplayString
}     

falconInputIndex OBJECT-TYPE
    SYNTAX  INTEGER
    ACCESS  read-only
    STATUS  mandatory
    DESCRIPTION
           "A unique value for each input port.  Its value
            ranges between 1 and the value of falconNumberOfInputPorts."
     ::= { falconInputEntry 1 }

falconInputType OBJECT-TYPE
    SYNTAX  INTEGER {
    notInstalled(0),
    analog(1),
    digital(2)
}
    ACCESS  read-only
    STATUS  mandatory
    DESCRIPTION
           "The installed hardware for Input Number X. If this value
            is notInstalled(0) then this input is not physically installed
            in the falcon."
    ::= { falconInputEntry  2 }

falconInputState OBJECT-TYPE
    SYNTAX  INTEGER {
    notInstalled(0),
    notConfigured(1),
    analog4to20Installed(2),
    digitalNOInstalled(3),
    digitalNCInstalled(4),
    digitalSTInstalled(5)
}
    ACCESS  read-write
    STATUS  mandatory
    DESCRIPTION
           "The state of use of Input Number X. When a sensor is
            connected to Input 1 set State to installed(2) to
            indicate that the value of falconReading1 is valid.
            When no sensor is connected to Input 1 set
            State to notConfigured(1) to indicate that the value of
            falconInputReading may not be valid."
    ::= { falconInputEntry  3 }

falconInputReading OBJECT-TYPE
    SYNTAX  INTEGER (-2147483648..2147483647)
    ACCESS  read-only
    STATUS  mandatory
    DESCRIPTION
           "The reading for sensor.
            If the input is digital, the reading will be 1 (active) or
            0 (inactive)"
    ::= { falconInputEntry  4 }

falconInputGain OBJECT-TYPE
    SYNTAX  INTEGER (-2147483648..2147483647)
    ACCESS  read-write
    STATUS  mandatory
    DESCRIPTION
           "A correction gain associated with the sensor variable.
            The value of gain is multiplied by the value from
            Input Sensor to obtain the value of the Input variable."
    ::= { falconInputEntry  5 }

falconInputOffset OBJECT-TYPE
    SYNTAX  INTEGER (-2147483648..2147483647)
    ACCESS  read-write
    STATUS  mandatory
    DESCRIPTION
           "A correction Offset associated with the sensor variable.
            The value of Offset is added to the value from
            the Input Sensor to obtain the value of the Input variable."
    ::= { falconInputEntry  6 }

falconInputLabel OBJECT-TYPE
    SYNTAX  DisplayString
    ACCESS  read-write
    STATUS  mandatory
    DESCRIPTION
           "A user-defined text string associated with the Input port."
    ::= { falconInputEntry  7 }

falconInputUOM OBJECT-TYPE
    SYNTAX  DisplayString
    ACCESS  read-write
    STATUS  mandatory
    DESCRIPTION
           "A user-defined text string associated with the Input port."
    ::= { falconInputEntry  8 }

falconInputHighLimit2 OBJECT-TYPE
    SYNTAX  INTEGER (-2147483648..2147483647)
    ACCESS  read-write
    STATUS  mandatory
    DESCRIPTION
           "When the input port reaches or exceeds this value a trap will
            be generated signifying a high alarm condition at this sensor."
    ::= { falconInputEntry  9 }

falconInputHighLimit OBJECT-TYPE
    SYNTAX  INTEGER (-2147483648..2147483647)
    ACCESS  read-write
    STATUS  mandatory
    DESCRIPTION
           "When the input port reaches or exceeds this value a trap will
            be generated signifying a high alarm condition at this sensor."
    ::= { falconInputEntry  10 }

falconInputLowLimit OBJECT-TYPE
    SYNTAX  INTEGER (-2147483648..2147483647)
    ACCESS  read-write
    STATUS  mandatory
    DESCRIPTION
           "When the input port reaches or goes below this value a trap will
            be generated signifying a low alarm condition at this sensor."
    ::= { falconInputEntry  11 }

falconInputLowLimit2 OBJECT-TYPE
    SYNTAX  INTEGER (-2147483648..2147483647)
    ACCESS  read-write
    STATUS  mandatory
    DESCRIPTION
           "When the input port reaches or goes below this value a trap will
            be generated signifying a low alarm condition at this sensor."
    ::= { falconInputEntry  12 }

falconInputDelay OBJECT-TYPE
    SYNTAX  INTEGER (0..600)
    ACCESS  read-write
    STATUS  mandatory
    DESCRIPTION
           "The number of seconds an alarm for this input must
            be present before annunication. The range of this
            setting is 0..600."
    ::= { falconInputEntry  13 }

falconInputHysteresis OBJECT-TYPE
    SYNTAX  INTEGER (0..2147483647)
    ACCESS  read-write
    STATUS  mandatory
    DESCRIPTION
           "The value of alarm hysteresis for this input.
            The input reading must decrease or increase by this
            value before the alarm will clear."
    ::= { falconInputEntry  14 }

falconInputSchedule OBJECT-TYPE
    SYNTAX  INTEGER {
    none(0),
    a(1),
    b(2)
}
    ACCESS  read-only
    STATUS  mandatory
    DESCRIPTION
           "The current alarm disable schedule for the input port."
    ::= { falconInputEntry  15 }

falconInputDigOffLabel OBJECT-TYPE
    SYNTAX  DisplayString
    ACCESS  read-write
    STATUS  mandatory
    DESCRIPTION
           "A user-defined text string associated with the input port.
            This string is used for digital off text."
    ::= { falconInputEntry  16 }

falconTHSensors OBJECT IDENTIFIER ::= { falconInputs 2 }

falconTempSensors OBJECT IDENTIFIER ::= { falconTHSensors 1 }

falconNumberOfTempSensors OBJECT-TYPE
    SYNTAX  INTEGER
    ACCESS  read-only
    STATUS  mandatory
    DESCRIPTION
           "The number of internal temperature sensors available on this system."
    ::= { falconTempSensors 1 }

falconTSTable OBJECT-TYPE
    SYNTAX  SEQUENCE OF FalconTSEntry
    ACCESS  not-accessible
    STATUS  mandatory
    DESCRIPTION
           "A table of the falcon internal temperature sensor
            status and configuration. The number of sensors is given
            by the value of falconNumberOfTempSensors."
    ::= { falconTempSensors 2 }

falconTSEntry OBJECT-TYPE
     SYNTAX  FalconTSEntry
     ACCESS  not-accessible
     STATUS  mandatory
     DESCRIPTION
            "An entry containing objects for the Falcon internal 
             temperature sensor data and configuration."
     INDEX   { falconTSIndex }
     ::= { falconTSTable 1 }

          
FalconTSEntry ::= SEQUENCE {
    falconTSIndex                       INTEGER,
    falconTemperatureSensorState        INTEGER,
    falconTemperatureSensorReading      INTEGER,
    falconTemperatureSensorOffset       INTEGER,
    falconTemperatureSensorLabel        DisplayString,
    falconTemperatureSensorUOM          DisplayString,
    falconTemperatureSensorHighLimit2   INTEGER,
    falconTemperatureSensorHighLimit    INTEGER,
    falconTemperatureSensorLowLimit     INTEGER,
    falconTemperatureSensorLowLimit2    INTEGER,
    falconTemperatureSensorDelay        INTEGER,
    falconTemperatureSensorHysteresis   INTEGER,
    falconTemperatureSensorSchedule     INTEGER
}     

falconTSIndex OBJECT-TYPE
    SYNTAX  INTEGER
    ACCESS  read-only
    STATUS  mandatory
    DESCRIPTION
           "A unique value for each internal temperature sensor.  Its value
            ranges between 1 and the value of falconNumberOfTempSensors."
     ::= { falconTSEntry 1 }

falconTemperatureSensorState OBJECT-TYPE
    SYNTAX  INTEGER {
    degF(0),
    degC(1)
}
    ACCESS  read-write
    STATUS  mandatory
    DESCRIPTION
           "The state of use of the internal temperature sensor."
    ::= { falconTSEntry  2 }

falconTemperatureSensorReading OBJECT-TYPE
    SYNTAX  INTEGER (-2147483648..2147483647)
    ACCESS  read-only
    STATUS  mandatory
    DESCRIPTION
           "The reading for internal temperature sensor."
    ::= { falconTSEntry  3 }

falconTemperatureSensorOffset OBJECT-TYPE
    SYNTAX  INTEGER (-2147483648..2147483647)
    ACCESS  read-write
    STATUS  mandatory
    DESCRIPTION
           "A correction Offset associated with the sensor variable.
            The value of Offset is added to the value from
            internal temperature sensor to obtain the value of
            the TemperatureSensor variable."
    ::= { falconTSEntry  4 }

falconTemperatureSensorLabel OBJECT-TYPE
    SYNTAX  DisplayString
    ACCESS  read-write
    STATUS  mandatory
    DESCRIPTION
           "A user-defined text string associated with internal temperature sensor."
    ::= { falconTSEntry  5 }

falconTemperatureSensorUOM OBJECT-TYPE
    SYNTAX  DisplayString
    ACCESS  read-write
    STATUS  mandatory
    DESCRIPTION
           "A user-defined text string associated with internal temperature sensor."
    ::= { falconTSEntry  6 }

falconTemperatureSensorHighLimit2 OBJECT-TYPE
    SYNTAX  INTEGER (-2147483648..2147483647)
    ACCESS  read-write
    STATUS  mandatory
    DESCRIPTION
           "When the internal temperature sensor reaches or exceeds this value a trap will
            be generated signifying a high alarm condition."
    ::= { falconTSEntry  7 }

falconTemperatureSensorHighLimit OBJECT-TYPE
    SYNTAX  INTEGER (-2147483648..2147483647)
    ACCESS  read-write
    STATUS  mandatory
    DESCRIPTION
           "When the internal temperature sensor reaches or exceeds this value a trap will
            be generated signifying a high alarm condition."
    ::= { falconTSEntry  8 }

falconTemperatureSensorLowLimit OBJECT-TYPE
    SYNTAX  INTEGER (-2147483648..2147483647)
    ACCESS  read-write
    STATUS  mandatory
    DESCRIPTION
           "When the internal temperature sensor reaches or goes below this value a trap will
            be generated signifying a low alarm condition."
    ::= { falconTSEntry  9 }

falconTemperatureSensorLowLimit2 OBJECT-TYPE
    SYNTAX  INTEGER (-2147483648..2147483647)
    ACCESS  read-write
    STATUS  mandatory
    DESCRIPTION
           "When the internal temperature sensor reaches or goes below this value a trap will
            be generated signifying a low alarm condition."
    ::= { falconTSEntry  10 }

falconTemperatureSensorDelay OBJECT-TYPE
    SYNTAX  INTEGER (0..600)
    ACCESS  read-write
    STATUS  mandatory
    DESCRIPTION
           "The number of seconds an alarm for this input must
            be present before annunication. The range of this
            setting is 0..600."
    ::= { falconTSEntry  11 }

falconTemperatureSensorHysteresis OBJECT-TYPE
    SYNTAX  INTEGER (0..2147483647)
    ACCESS  read-write
    STATUS  mandatory
    DESCRIPTION
           "The value of alarm hysteresis for this sensor.
            The reading must decrease or increase by this
            value before the alarm will clear."
    ::= { falconTSEntry  12 }

falconTemperatureSensorSchedule OBJECT-TYPE
    SYNTAX  INTEGER {
    none(0),
    a(1),
    b(2)
}
    ACCESS  read-only
    STATUS  mandatory
    DESCRIPTION
           "The current alarm disable schedule for this sensor."
    ::= { falconTSEntry  13 }

falconHumiditySensors OBJECT IDENTIFIER ::= { falconTHSensors 2 }

falconNumberOfHumiditySensors OBJECT-TYPE
    SYNTAX  INTEGER
    ACCESS  read-only
    STATUS  mandatory
    DESCRIPTION
           "The number of internal humidity sensors available on this system."
    ::= { falconHumiditySensors 1 }

falconHSTable OBJECT-TYPE
    SYNTAX  SEQUENCE OF FalconHSEntry
    ACCESS  not-accessible
    STATUS  mandatory
    DESCRIPTION
           "A table of the falcon internal humidity sensor
            status and configuration. The number of sensors is given
            by the value of falconNumberOfHumiditySensors."
    ::= { falconHumiditySensors 2 }

falconHSEntry OBJECT-TYPE
     SYNTAX  FalconHSEntry
     ACCESS  not-accessible
     STATUS  mandatory
     DESCRIPTION
            "An entry containing objects for the Falcon internal
             humidity sensor data and configuration."
     INDEX   { falconHSIndex }
     ::= { falconHSTable 1 }

FalconHSEntry ::= SEQUENCE {
    falconHSIndex                   INTEGER,
    falconHumiditySensorState       INTEGER,
    falconHumiditySensorReading     INTEGER,
    falconHumiditySensorOffset      INTEGER,
    falconHumiditySensorLabel       DisplayString,
    falconHumiditySensorUOM         DisplayString,
    falconHumiditySensorHighLimit2  INTEGER,
    falconHumiditySensorHighLimit   INTEGER,
    falconHumiditySensorLowLimit    INTEGER,
    falconHumiditySensorLowLimit2   INTEGER,
    falconHumiditySensorDelay       INTEGER,
    falconHumiditySensorHysteresis  INTEGER,
    falconHumiditySensorSchedule    INTEGER
}

falconHSIndex OBJECT-TYPE
    SYNTAX  INTEGER
    ACCESS  read-only
    STATUS  mandatory
    DESCRIPTION
           "A unique value for each internal humidity sensor.  Its value
            ranges between 1 and the value of falconNumberOfHumiditySensors."
     ::= { falconHSEntry 1 }

falconHumiditySensorState OBJECT-TYPE
    SYNTAX  INTEGER {
    %rh(0)
}
    ACCESS  read-write
    STATUS  mandatory
    DESCRIPTION
           "The state of use of the internal humidity sensor."
    ::= { falconHSEntry  2 }

falconHumiditySensorReading OBJECT-TYPE
    SYNTAX  INTEGER (-2147483648..2147483647)
    ACCESS  read-only
    STATUS  mandatory
    DESCRIPTION
           "The reading for internal humidity sensor."
    ::= { falconHSEntry  3 }

falconHumiditySensorOffset OBJECT-TYPE
    SYNTAX  INTEGER (-2147483648..2147483647)
    ACCESS  read-write
    STATUS  mandatory
    DESCRIPTION
           "A correction Offset associated with the sensor variable.
            The value of Offset is added to the value from
            internal humidity sensor to obtain the value of
            the HumiditySensor variable."
    ::= { falconHSEntry  4 }

falconHumiditySensorLabel OBJECT-TYPE
    SYNTAX  DisplayString
    ACCESS  read-write
    STATUS  mandatory
    DESCRIPTION
           "A user-defined text string associated with internal humidity sensor."
    ::= { falconHSEntry  5 }

falconHumiditySensorUOM OBJECT-TYPE
    SYNTAX  DisplayString
    ACCESS  read-write
    STATUS  mandatory
    DESCRIPTION
           "A user-defined text string associated with internal humidity sensor."
    ::= { falconHSEntry  6 }

falconHumiditySensorHighLimit2 OBJECT-TYPE
    SYNTAX  INTEGER (-2147483648..2147483647)
    ACCESS  read-write
    STATUS  mandatory
    DESCRIPTION
           "When the internal humidity sensor reaches or exceeds this value a trap will
            be generated signifying a high alarm condition."
    ::= { falconHSEntry  7 }

falconHumiditySensorHighLimit OBJECT-TYPE
    SYNTAX  INTEGER (-2147483648..2147483647)
    ACCESS  read-write
    STATUS  mandatory
    DESCRIPTION
           "When the internal humidity sensor reaches or exceeds this value a trap will
            be generated signifying a high alarm condition."
    ::= { falconHSEntry  8 }

falconHumiditySensorLowLimit OBJECT-TYPE
    SYNTAX  INTEGER (-2147483648..2147483647)
    ACCESS  read-write
    STATUS  mandatory
    DESCRIPTION
           "When the internal humidity sensor reaches or goes below this value a trap will
            be generated signifying a low alarm condition."
    ::= { falconHSEntry  9 }

falconHumiditySensorLowLimit2 OBJECT-TYPE
    SYNTAX  INTEGER (-2147483648..2147483647)
    ACCESS  read-write
    STATUS  mandatory
    DESCRIPTION
           "When the internal humidity sensor reaches or goes below this value a trap will
            be generated signifying a low alarm condition."
    ::= { falconHSEntry  10 }

falconHumiditySensorDelay OBJECT-TYPE
    SYNTAX  INTEGER (0..600)
    ACCESS  read-write
    STATUS  mandatory
    DESCRIPTION
           "The number of seconds an alarm for this sensor must
            be present before annunication. The range of this
            setting is 0..600."
    ::= { falconHSEntry  11 }

falconHumiditySensorHysteresis OBJECT-TYPE
    SYNTAX  INTEGER (0..2147483647)
    ACCESS  read-write
    STATUS  mandatory
    DESCRIPTION
           "The value of alarm hysteresis for this sensor.
            The sensor reading must decrease or increase by this
            value before the alarm will clear."
    ::= { falconHSEntry  12 }

falconHumiditySensorSchedule OBJECT-TYPE
    SYNTAX  INTEGER {
    none(0),
    a(1),
    b(2)
}
    ACCESS  read-only
    STATUS  mandatory
    DESCRIPTION
           "The current alarm disable schedule for the humidity sensor."
    ::= { falconHSEntry  13 }

falconOutputs OBJECT IDENTIFIER ::= { falcon-emMIB  4 }

falconRelays OBJECT IDENTIFIER ::= { falconOutputs 1 }

falconNumberOfRelays OBJECT-TYPE
    SYNTAX  INTEGER
    ACCESS  read-only
    STATUS  mandatory
    DESCRIPTION
           "The number of output relays available on this system."
    ::= { falconRelays 1 }

falconRelayTable OBJECT-TYPE
    SYNTAX  SEQUENCE OF FalconRelayEntry
    ACCESS  not-accessible
    STATUS  mandatory
    DESCRIPTION
           "A table of the falcon output relay status and configuration.
            The number of relays is given by the value of 
            falconNumberOfRelays."
    ::= { falconRelays 2 }

falconRelayEntry OBJECT-TYPE
     SYNTAX  FalconRelayEntry
     ACCESS  not-accessible
     STATUS  mandatory
     DESCRIPTION
            "An entry containing objects for the Falcon
             output relay data and configuration."
     INDEX   { falconRelayIndex }
     ::= { falconRelayTable 1 }
          
FalconRelayEntry ::= SEQUENCE {
     falconRelayIndex       INTEGER,
     falconRelayState       INTEGER,
     falconRelayStatus      INTEGER,
     falconRelayLabel       DisplayString,
     falconRelayTime        INTEGER,
     falconRelaySchedule    INTEGER
}     

falconRelayIndex OBJECT-TYPE
    SYNTAX  INTEGER
    ACCESS  read-only
    STATUS  mandatory
    DESCRIPTION
           "A unique value for each output relay.  Its value
            ranges between 1 and the value of falconNumberOfRelays."
     ::= { falconRelayEntry 1 }

falconRelayState OBJECT-TYPE
    SYNTAX  INTEGER {
    normallyOff(1),
    normallyOn(2),
    forceOn(3),
    forceOff(4),
    keypadControlled(5)
}
    ACCESS  read-write
    STATUS  mandatory
    DESCRIPTION
           "The state of use of this relay. The relay can be
            set for normally open or closed. The relay can be forced
            to an on or off condition, or controlled by the keypad."
    ::= { falconRelayEntry  2 }

falconRelayStatus OBJECT-TYPE
    SYNTAX  INTEGER {
    normalOff(1),
    normalOn(2),
    forcedOn(3),
    forcedOff(4),
    keycodeActive(5),
    alarmedActive(6),
    scheduledActive(7)
}
    ACCESS  read-only
    STATUS  mandatory
    DESCRIPTION
           "The current status for this relay."
    ::= { falconRelayEntry  3 }

falconRelayLabel OBJECT-TYPE
    SYNTAX  DisplayString
    ACCESS  read-write
    STATUS  mandatory
    DESCRIPTION
           "A user-defined text string associated with this relay."
    ::= { falconRelayEntry  4 }

falconRelayTime OBJECT-TYPE
    SYNTAX  INTEGER (-2147483648..2147483647)
    ACCESS read-write
    STATUS     mandatory
    DESCRIPTION
        "The number of seconds the relay will be activated.
         Set this to -1 for indefinitely."
    ::= { falconRelayEntry  5 }

falconRelaySchedule OBJECT-TYPE
    SYNTAX  INTEGER {
    none(0),
    a(1),
    b(2)
}
    ACCESS  read-only
    STATUS  mandatory
    DESCRIPTION
           "The current schedule for this relay."
    ::= { falconRelayEntry  6 }

falconAlarms OBJECT IDENTIFIER ::= { falcon-emMIB  5 }

falconAlarmsPresent OBJECT-TYPE
    SYNTAX     Gauge
    ACCESS     read-only
    STATUS     mandatory
    DESCRIPTION
        "The present number of active alarm conditions."
    ::= { falconAlarms 1 }

falconAlarmTable OBJECT-TYPE
    SYNTAX     SEQUENCE OF FalconAlarmEntry
    ACCESS     not-accessible
    STATUS     mandatory
    DESCRIPTION
       "A list of alarm table entries.  The table contains
        zero, one, or many rows at any moment, depending upon
        the number of alarm conditions in effect.  The table
        is initially empty at agent startup.  The agent
        creates a row in the table each time a condition is
        detected and deletes that row when that condition no
        longer pertains.  The agent creates the first row with
        falconAlarmId equal to 1, and increments the value of
        falconAlarmId each time a new row is created, wrapping to
        the first free value greater than or equal to 1 when
        the maximum value of falconAlarmId would otherwise be
        exceeded.  Consequently, after multiple operations,
        the table may become sparse, e.g., containing entries
        for rows 95, 100, 101, and 203 and the entries should
        not be assumed to be in chronological order because
        falconAlarmId might have wrapped.

        Alarms are named by an AutonomousType (OBJECT
        IDENTIFIER), falconAlarmDescr, to allow a single table to
        reflect well known alarms plus alarms defined by a
        particular implementation, i.e., as documented in the
        private enterprise MIB definition for the device.  No
        two rows will have the same value of falconAlarmDescr,
        since alarms define conditions.  In order to meet this
        requirement, care should be taken in the definition of
        alarm conditions to insure that a system cannot enter
        the same condition multiple times simultaneously.

        The number of rows in the table at any given time is
        reflected by the value of falconAlarmsPresent."
    ::= { falconAlarms 2 }

falconAlarmEntry OBJECT-TYPE
    SYNTAX     FalconAlarmEntry
    ACCESS     not-accessible
    STATUS     mandatory
    DESCRIPTION
         "An entry containing information applicable to a
         particular alarm."
   INDEX { falconAlarmId }
   ::= { falconAlarmTable 1 }

FalconAlarmEntry ::= SEQUENCE {
    falconAlarmId          PositiveInteger,
    falconAlarmDescr       OBJECT IDENTIFIER
}

falconAlarmId OBJECT-TYPE
    SYNTAX     PositiveInteger
    ACCESS     not-accessible
    STATUS     mandatory
    DESCRIPTION
         "A unique identifier for an alarm condition.  This
          value must remain constant."
    ::= { falconAlarmEntry 1 }

falconAlarmDescr OBJECT-TYPE
    SYNTAX     OBJECT IDENTIFIER
    ACCESS     read-only
    STATUS     mandatory
    DESCRIPTION
        "A reference to an alarm description object.  The
         object referenced should not be accessible, but rather
         be used to provide a unique description of the alarm
         condition."
    ::= { falconAlarmEntry 2 }

--
-- Well known alarm conditions.
--

falconWellKnownAlarms    OBJECT IDENTIFIER ::= { falconAlarms 3 }

falconInput1DigAlarm OBJECT-TYPE
    SYNTAX  OBJECT IDENTIFIER
    ACCESS  read-only
    STATUS  mandatory
    DESCRIPTION
        "The digital input 1 has been activated."
    ::= { falconWellKnownAlarms  10 }

falconInput1HighAlarm OBJECT-TYPE
    SYNTAX  OBJECT IDENTIFIER
    ACCESS  read-only
    STATUS  mandatory
    DESCRIPTION
        "The reading for sensor 1 has reached the high limit
        value."
    ::= { falconWellKnownAlarms  11 }

falconInput1LowAlarm OBJECT-TYPE
    SYNTAX  OBJECT IDENTIFIER
    ACCESS  read-only
    STATUS  mandatory
    DESCRIPTION
        "The reading for sensor 1 has reached the low limit
        value."
    ::= { falconWellKnownAlarms  12 }

falconInput1High2Alarm OBJECT-TYPE
    SYNTAX  OBJECT IDENTIFIER
    ACCESS  read-only
    STATUS  mandatory
    DESCRIPTION
        "The reading for sensor 1 has reached the high limit
        value."
    ::= { falconWellKnownAlarms  13 }

falconInput1Low2Alarm OBJECT-TYPE
    SYNTAX  OBJECT IDENTIFIER
    ACCESS  read-only
    STATUS  mandatory
    DESCRIPTION
        "The reading for sensor 1 has reached the low limit
        value."
    ::= { falconWellKnownAlarms  14 }

falconInput2DigAlarm OBJECT-TYPE
    SYNTAX  OBJECT IDENTIFIER
    ACCESS  read-only
    STATUS  mandatory
    DESCRIPTION
        "The digital input 2 has been activated."
    ::= { falconWellKnownAlarms  20 }

falconInput2HighAlarm OBJECT-TYPE
    SYNTAX  OBJECT IDENTIFIER
    ACCESS  read-only
    STATUS  mandatory
    DESCRIPTION
        "The reading for sensor 2 has reached the high limit
        value."
    ::= { falconWellKnownAlarms  21 }

falconInput2LowAlarm OBJECT-TYPE
    SYNTAX  OBJECT IDENTIFIER
    ACCESS  read-only
    STATUS  mandatory
    DESCRIPTION
        "The reading for sensor 2 has reached the low limit
        value."
    ::= { falconWellKnownAlarms  22 }

falconInput2High2Alarm OBJECT-TYPE
    SYNTAX  OBJECT IDENTIFIER
    ACCESS  read-only
    STATUS  mandatory
    DESCRIPTION
        "The reading for sensor 2 has reached the high limit
        value."
    ::= { falconWellKnownAlarms  23 }

falconInput2Low2Alarm OBJECT-TYPE
    SYNTAX  OBJECT IDENTIFIER
    ACCESS  read-only
    STATUS  mandatory
    DESCRIPTION
        "The reading for sensor 2 has reached the low limit
        value."
    ::= { falconWellKnownAlarms  24 }

falconInput3DigAlarm OBJECT-TYPE
    SYNTAX  OBJECT IDENTIFIER
    ACCESS  read-only
    STATUS  mandatory
    DESCRIPTION
        "The digital input 3 has been activated."
    ::= { falconWellKnownAlarms  30 }

falconInput3HighAlarm OBJECT-TYPE
    SYNTAX  OBJECT IDENTIFIER
    ACCESS  read-only
    STATUS  mandatory
    DESCRIPTION
        "The reading for sensor 3 has reached the high limit
        value."
    ::= { falconWellKnownAlarms  31 }

falconInput3LowAlarm OBJECT-TYPE
    SYNTAX  OBJECT IDENTIFIER
    ACCESS  read-only
    STATUS  mandatory
    DESCRIPTION
        "The reading for sensor 3 has reached the low limit
        value."
    ::= { falconWellKnownAlarms  32 }

falconInput3High2Alarm OBJECT-TYPE
    SYNTAX  OBJECT IDENTIFIER
    ACCESS  read-only
    STATUS  mandatory
    DESCRIPTION
        "The reading for sensor 3 has reached the high limit
        value."
    ::= { falconWellKnownAlarms  33 }

falconInput3Low2Alarm OBJECT-TYPE
    SYNTAX  OBJECT IDENTIFIER
    ACCESS  read-only
    STATUS  mandatory
    DESCRIPTION
        "The reading for sensor 3 has reached the low limit
        value."
    ::= { falconWellKnownAlarms  34 }

falconInput4DigAlarm OBJECT-TYPE
    SYNTAX  OBJECT IDENTIFIER
    ACCESS  read-only
    STATUS  mandatory
    DESCRIPTION
        "The digital input 4 has been activated."
    ::= { falconWellKnownAlarms  40 }

falconInput4HighAlarm OBJECT-TYPE
    SYNTAX  OBJECT IDENTIFIER
    ACCESS  read-only
    STATUS  mandatory
    DESCRIPTION
        "The reading for sensor 4 has reached the high limit
        value."
    ::= { falconWellKnownAlarms  41 }

falconInput4LowAlarm OBJECT-TYPE
    SYNTAX  OBJECT IDENTIFIER
    ACCESS  read-only
    STATUS  mandatory
    DESCRIPTION
        "The reading for sensor 4 has reached the low limit
        value."
    ::= { falconWellKnownAlarms  42 }

falconInput4High2Alarm OBJECT-TYPE
    SYNTAX  OBJECT IDENTIFIER
    ACCESS  read-only
    STATUS  mandatory
    DESCRIPTION
        "The reading for sensor 4 has reached the high limit
        value."
    ::= { falconWellKnownAlarms  43 }

falconInput4Low2Alarm OBJECT-TYPE
    SYNTAX  OBJECT IDENTIFIER
    ACCESS  read-only
    STATUS  mandatory
    DESCRIPTION
        "The reading for sensor 4 has reached the low limit
        value."
    ::= { falconWellKnownAlarms  44 }

falconInput5DigAlarm OBJECT-TYPE
    SYNTAX  OBJECT IDENTIFIER
    ACCESS  read-only
    STATUS  mandatory
    DESCRIPTION
        "The digital input 5 has been activated."
    ::= { falconWellKnownAlarms  50 }

falconInput5HighAlarm OBJECT-TYPE
    SYNTAX  OBJECT IDENTIFIER
    ACCESS  read-only
    STATUS  mandatory
    DESCRIPTION
        "The reading for sensor 5 has reached the high limit
        value."
    ::= { falconWellKnownAlarms  51 }

falconInput5LowAlarm OBJECT-TYPE
    SYNTAX  OBJECT IDENTIFIER
    ACCESS  read-only
    STATUS  mandatory
    DESCRIPTION
        "The reading for sensor 5 has reached the low limit
        value."
    ::= { falconWellKnownAlarms  52 }

falconInput5High2Alarm OBJECT-TYPE
    SYNTAX  OBJECT IDENTIFIER
    ACCESS  read-only
    STATUS  mandatory
    DESCRIPTION
        "The reading for sensor 5 has reached the high limit
        value."
    ::= { falconWellKnownAlarms  53 }

falconInput5Low2Alarm OBJECT-TYPE
    SYNTAX  OBJECT IDENTIFIER
    ACCESS  read-only
    STATUS  mandatory
    DESCRIPTION
        "The reading for sensor 5 has reached the low limit
        value."
    ::= { falconWellKnownAlarms  54 }

falconInput6DigAlarm OBJECT-TYPE
    SYNTAX  OBJECT IDENTIFIER
    ACCESS  read-only
    STATUS  mandatory
    DESCRIPTION
        "The digital input 6 has been activated."
    ::= { falconWellKnownAlarms  60 }

falconInput6HighAlarm OBJECT-TYPE
    SYNTAX  OBJECT IDENTIFIER
    ACCESS  read-only
    STATUS  mandatory
    DESCRIPTION
        "The reading for sensor 6 has reached the high limit
        value."
    ::= { falconWellKnownAlarms  61 }

falconInput6LowAlarm OBJECT-TYPE
    SYNTAX  OBJECT IDENTIFIER
    ACCESS  read-only
    STATUS  mandatory
    DESCRIPTION
        "The reading for sensor 6 has reached the low limit
        value."
    ::= { falconWellKnownAlarms  62 }

falconInput6High2Alarm OBJECT-TYPE
    SYNTAX  OBJECT IDENTIFIER
    ACCESS  read-only
    STATUS  mandatory
    DESCRIPTION
        "The reading for sensor 6 has reached the high limit
        value."
    ::= { falconWellKnownAlarms  63 }

falconInput6Low2Alarm OBJECT-TYPE
    SYNTAX  OBJECT IDENTIFIER
    ACCESS  read-only
    STATUS  mandatory
    DESCRIPTION
        "The reading for sensor 6 has reached the low limit
        value."
    ::= { falconWellKnownAlarms  64 }

falconInput7DigAlarm OBJECT-TYPE
    SYNTAX  OBJECT IDENTIFIER
    ACCESS  read-only
    STATUS  mandatory
    DESCRIPTION
        "The digital input 7 has been activated."
    ::= { falconWellKnownAlarms  70 }

falconInput7HighAlarm OBJECT-TYPE
    SYNTAX  OBJECT IDENTIFIER
    ACCESS  read-only
    STATUS  mandatory
    DESCRIPTION
        "The reading for sensor 7 has reached the high limit
        value."
    ::= { falconWellKnownAlarms  71 }

falconInput7LowAlarm OBJECT-TYPE
    SYNTAX  OBJECT IDENTIFIER
    ACCESS  read-only
    STATUS  mandatory
    DESCRIPTION
        "The reading for sensor 7 has reached the low limit
        value."
    ::= { falconWellKnownAlarms  72 }

falconInput7High2Alarm OBJECT-TYPE
    SYNTAX  OBJECT IDENTIFIER
    ACCESS  read-only
    STATUS  mandatory
    DESCRIPTION
        "The reading for sensor 7 has reached the high limit
        value."
    ::= { falconWellKnownAlarms  73 }

falconInput7Low2Alarm OBJECT-TYPE
    SYNTAX  OBJECT IDENTIFIER
    ACCESS  read-only
    STATUS  mandatory
    DESCRIPTION
        "The reading for sensor 7 has reached the low limit
        value."
    ::= { falconWellKnownAlarms  74 }

falconInput8DigAlarm OBJECT-TYPE
    SYNTAX  OBJECT IDENTIFIER
    ACCESS  read-only
    STATUS  mandatory
    DESCRIPTION
        "The digital input 8 has been activated."
    ::= { falconWellKnownAlarms  80 }

falconInput8HighAlarm OBJECT-TYPE
    SYNTAX  OBJECT IDENTIFIER
    ACCESS  read-only
    STATUS  mandatory
    DESCRIPTION
        "The reading for sensor 8 has reached the high limit
        value."
    ::= { falconWellKnownAlarms  81 }

falconInput8LowAlarm OBJECT-TYPE
    SYNTAX  OBJECT IDENTIFIER
    ACCESS  read-only
    STATUS  mandatory
    DESCRIPTION
        "The reading for sensor 8 has reached the low limit
        value."
    ::= { falconWellKnownAlarms  82 }

falconInput8High2Alarm OBJECT-TYPE
    SYNTAX  OBJECT IDENTIFIER
    ACCESS  read-only
    STATUS  mandatory
    DESCRIPTION
        "The reading for sensor 8 has reached the high limit
        value."
    ::= { falconWellKnownAlarms  83 }

falconInput8Low2Alarm OBJECT-TYPE
    SYNTAX  OBJECT IDENTIFIER
    ACCESS  read-only
    STATUS  mandatory
    DESCRIPTION
        "The reading for sensor 8 has reached the low limit
        value."
    ::= { falconWellKnownAlarms  84 }

falconInput9DigAlarm OBJECT-TYPE
    SYNTAX  OBJECT IDENTIFIER
    ACCESS  read-only
    STATUS  mandatory
    DESCRIPTION
        "The digital input 9 has been activated."
    ::= { falconWellKnownAlarms  1010 }

falconInput9HighAlarm OBJECT-TYPE
    SYNTAX  OBJECT IDENTIFIER
    ACCESS  read-only
    STATUS  mandatory
    DESCRIPTION
        "The reading for sensor 9 has reached the high limit
        value."
    ::= { falconWellKnownAlarms  1011 }

falconInput9LowAlarm OBJECT-TYPE
    SYNTAX  OBJECT IDENTIFIER
    ACCESS  read-only
    STATUS  mandatory
    DESCRIPTION
        "The reading for sensor 9 has reached the low limit
        value."
    ::= { falconWellKnownAlarms  1012 }

falconInput9High2Alarm OBJECT-TYPE
    SYNTAX  OBJECT IDENTIFIER
    ACCESS  read-only
    STATUS  mandatory
    DESCRIPTION
        "The reading for sensor 9 has reached the high limit
        value."
    ::= { falconWellKnownAlarms  1013 }

falconInput9Low2Alarm OBJECT-TYPE
    SYNTAX  OBJECT IDENTIFIER
    ACCESS  read-only
    STATUS  mandatory
    DESCRIPTION
        "The reading for sensor 9 has reached the low limit
        value."
    ::= { falconWellKnownAlarms  1014 }

falconInput10DigAlarm OBJECT-TYPE
    SYNTAX  OBJECT IDENTIFIER
    ACCESS  read-only
    STATUS  mandatory
    DESCRIPTION
        "The digital input 10 has been activated."
    ::= { falconWellKnownAlarms  1020 }

falconInput10HighAlarm OBJECT-TYPE
    SYNTAX  OBJECT IDENTIFIER
    ACCESS  read-only
    STATUS  mandatory
    DESCRIPTION
        "The reading for sensor 10 has reached the high limit
        value."
    ::= { falconWellKnownAlarms  1021 }

falconInput10LowAlarm OBJECT-TYPE
    SYNTAX  OBJECT IDENTIFIER
    ACCESS  read-only
    STATUS  mandatory
    DESCRIPTION
        "The reading for sensor 10 has reached the low limit
        value."
    ::= { falconWellKnownAlarms  1022 }

falconInput10High2Alarm OBJECT-TYPE
    SYNTAX  OBJECT IDENTIFIER
    ACCESS  read-only
    STATUS  mandatory
    DESCRIPTION
        "The reading for sensor 10 has reached the high limit
        value."
    ::= { falconWellKnownAlarms  1023 }

falconInput10Low2Alarm OBJECT-TYPE
    SYNTAX  OBJECT IDENTIFIER
    ACCESS  read-only
    STATUS  mandatory
    DESCRIPTION
        "The reading for sensor 10 has reached the low limit
        value."
    ::= { falconWellKnownAlarms  1024 }

falconInput11DigAlarm OBJECT-TYPE
    SYNTAX  OBJECT IDENTIFIER
    ACCESS  read-only
    STATUS  mandatory
    DESCRIPTION
        "The digital input 11 has been activated."
    ::= { falconWellKnownAlarms  1030 }

falconInput11HighAlarm OBJECT-TYPE
    SYNTAX  OBJECT IDENTIFIER
    ACCESS  read-only
    STATUS  mandatory
    DESCRIPTION
        "The reading for sensor 11 has reached the high limit
        value."
    ::= { falconWellKnownAlarms  1031 }

falconInput11LowAlarm OBJECT-TYPE
    SYNTAX  OBJECT IDENTIFIER
    ACCESS  read-only
    STATUS  mandatory
    DESCRIPTION
        "The reading for sensor 11 has reached the low limit
        value."
    ::= { falconWellKnownAlarms  1032 }

falconInput11High2Alarm OBJECT-TYPE
    SYNTAX  OBJECT IDENTIFIER
    ACCESS  read-only
    STATUS  mandatory
    DESCRIPTION
        "The reading for sensor 11 has reached the high limit
        value."
    ::= { falconWellKnownAlarms  1033 }

falconInput11Low2Alarm OBJECT-TYPE
    SYNTAX  OBJECT IDENTIFIER
    ACCESS  read-only
    STATUS  mandatory
    DESCRIPTION
        "The reading for sensor 11 has reached the low limit
        value."
    ::= { falconWellKnownAlarms  1034 }

falconInput12DigAlarm OBJECT-TYPE
    SYNTAX  OBJECT IDENTIFIER
    ACCESS  read-only
    STATUS  mandatory
    DESCRIPTION
        "The digital input 12 has been activated."
    ::= { falconWellKnownAlarms  1040 }

falconInput12HighAlarm OBJECT-TYPE
    SYNTAX  OBJECT IDENTIFIER
    ACCESS  read-only
    STATUS  mandatory
    DESCRIPTION
        "The reading for sensor 12 has reached the high limit
        value."
    ::= { falconWellKnownAlarms  1041 }

falconInput12LowAlarm OBJECT-TYPE
    SYNTAX  OBJECT IDENTIFIER
    ACCESS  read-only
    STATUS  mandatory
    DESCRIPTION
        "The reading for sensor 12 has reached the low limit
        value."
    ::= { falconWellKnownAlarms  1042 }

falconInput12High2Alarm OBJECT-TYPE
    SYNTAX  OBJECT IDENTIFIER
    ACCESS  read-only
    STATUS  mandatory
    DESCRIPTION
        "The reading for sensor 12 has reached the high limit
        value."
    ::= { falconWellKnownAlarms  1043 }

falconInput12Low2Alarm OBJECT-TYPE
    SYNTAX  OBJECT IDENTIFIER
    ACCESS  read-only
    STATUS  mandatory
    DESCRIPTION
        "The reading for sensor 12 has reached the low limit
        value."
    ::= { falconWellKnownAlarms  1044 }

falconInput13DigAlarm OBJECT-TYPE
    SYNTAX  OBJECT IDENTIFIER
    ACCESS  read-only
    STATUS  mandatory
    DESCRIPTION
        "The digital input 13 has been activated."
    ::= { falconWellKnownAlarms  1050 }

falconInput13HighAlarm OBJECT-TYPE
    SYNTAX  OBJECT IDENTIFIER
    ACCESS  read-only
    STATUS  mandatory
    DESCRIPTION
        "The reading for sensor 13 has reached the high limit
        value."
    ::= { falconWellKnownAlarms  1051 }

falconInput13LowAlarm OBJECT-TYPE
    SYNTAX  OBJECT IDENTIFIER
    ACCESS  read-only
    STATUS  mandatory
    DESCRIPTION
        "The reading for sensor 13 has reached the low limit
        value."
    ::= { falconWellKnownAlarms  1052 }

falconInput13High2Alarm OBJECT-TYPE
    SYNTAX  OBJECT IDENTIFIER
    ACCESS  read-only
    STATUS  mandatory
    DESCRIPTION
        "The reading for sensor 13 has reached the high limit
        value."
    ::= { falconWellKnownAlarms  1053 }

falconInput13Low2Alarm OBJECT-TYPE
    SYNTAX  OBJECT IDENTIFIER
    ACCESS  read-only
    STATUS  mandatory
    DESCRIPTION
        "The reading for sensor 13 has reached the low limit
        value."
    ::= { falconWellKnownAlarms  1054 }

falconInput14DigAlarm OBJECT-TYPE
    SYNTAX  OBJECT IDENTIFIER
    ACCESS  read-only
    STATUS  mandatory
    DESCRIPTION
        "The digital input 14 has been activated."
    ::= { falconWellKnownAlarms  1060 }

falconInput14HighAlarm OBJECT-TYPE
    SYNTAX  OBJECT IDENTIFIER
    ACCESS  read-only
    STATUS  mandatory
    DESCRIPTION
        "The reading for sensor 14 has reached the high limit
        value."
    ::= { falconWellKnownAlarms  1061 }

falconInput14LowAlarm OBJECT-TYPE
    SYNTAX  OBJECT IDENTIFIER
    ACCESS  read-only
    STATUS  mandatory
    DESCRIPTION
        "The reading for sensor 14 has reached the low limit
        value."
    ::= { falconWellKnownAlarms  1062 }

falconInput14High2Alarm OBJECT-TYPE
    SYNTAX  OBJECT IDENTIFIER
    ACCESS  read-only
    STATUS  mandatory
    DESCRIPTION
        "The reading for sensor 14 has reached the high limit
        value."
    ::= { falconWellKnownAlarms  1063 }

falconInput14Low2Alarm OBJECT-TYPE
    SYNTAX  OBJECT IDENTIFIER
    ACCESS  read-only
    STATUS  mandatory
    DESCRIPTION
        "The reading for sensor 14 has reached the low limit
        value."
    ::= { falconWellKnownAlarms  1064 }

falconInput15DigAlarm OBJECT-TYPE
    SYNTAX  OBJECT IDENTIFIER
    ACCESS  read-only
    STATUS  mandatory
    DESCRIPTION
        "The digital input 15 has been activated."
    ::= { falconWellKnownAlarms  1070 }

falconInput15HighAlarm OBJECT-TYPE
    SYNTAX  OBJECT IDENTIFIER
    ACCESS  read-only
    STATUS  mandatory
    DESCRIPTION
        "The reading for sensor 15 has reached the high limit
        value."
    ::= { falconWellKnownAlarms  1071 }

falconInput15LowAlarm OBJECT-TYPE
    SYNTAX  OBJECT IDENTIFIER
    ACCESS  read-only
    STATUS  mandatory
    DESCRIPTION
        "The reading for sensor 15 has reached the low limit
        value."
    ::= { falconWellKnownAlarms  1072 }

falconInput15High2Alarm OBJECT-TYPE
    SYNTAX  OBJECT IDENTIFIER
    ACCESS  read-only
    STATUS  mandatory
    DESCRIPTION
        "The reading for sensor 15 has reached the high limit
        value."
    ::= { falconWellKnownAlarms  1073 }

falconInput15Low2Alarm OBJECT-TYPE
    SYNTAX  OBJECT IDENTIFIER
    ACCESS  read-only
    STATUS  mandatory
    DESCRIPTION
        "The reading for sensor 15 has reached the low limit
        value."
    ::= { falconWellKnownAlarms  1074 }

falconInput16DigAlarm OBJECT-TYPE
    SYNTAX  OBJECT IDENTIFIER
    ACCESS  read-only
    STATUS  mandatory
    DESCRIPTION
        "The digital input 16 has been activated."
    ::= { falconWellKnownAlarms  1080 }

falconInput16HighAlarm OBJECT-TYPE
    SYNTAX  OBJECT IDENTIFIER
    ACCESS  read-only
    STATUS  mandatory
    DESCRIPTION
        "The reading for sensor 16 has reached the high limit
        value."
    ::= { falconWellKnownAlarms  1081 }

falconInput16LowAlarm OBJECT-TYPE
    SYNTAX  OBJECT IDENTIFIER
    ACCESS  read-only
    STATUS  mandatory
    DESCRIPTION
        "The reading for sensor 16 has reached the low limit
        value."
    ::= { falconWellKnownAlarms  1082 }

falconInput16High2Alarm OBJECT-TYPE
    SYNTAX  OBJECT IDENTIFIER
    ACCESS  read-only
    STATUS  mandatory
    DESCRIPTION
        "The reading for sensor 16 has reached the high limit
        value."
    ::= { falconWellKnownAlarms  1083 }

falconInput16Low2Alarm OBJECT-TYPE
    SYNTAX  OBJECT IDENTIFIER
    ACCESS  read-only
    STATUS  mandatory
    DESCRIPTION
        "The reading for sensor 16 has reached the low limit
        value."
    ::= { falconWellKnownAlarms  1084 }

falconInput17DigAlarm OBJECT-TYPE
    SYNTAX  OBJECT IDENTIFIER
    ACCESS  read-only
    STATUS  mandatory
    DESCRIPTION
        "The digital input 17 has been activated."
    ::= { falconWellKnownAlarms  1090 }

falconInput17HighAlarm OBJECT-TYPE
    SYNTAX  OBJECT IDENTIFIER
    ACCESS  read-only
    STATUS  mandatory
    DESCRIPTION
        "The reading for sensor 17 has reached the high limit
        value."
    ::= { falconWellKnownAlarms  1091 }

falconInput17LowAlarm OBJECT-TYPE
    SYNTAX  OBJECT IDENTIFIER
    ACCESS  read-only
    STATUS  mandatory
    DESCRIPTION
        "The reading for sensor 17 has reached the low limit
        value."
    ::= { falconWellKnownAlarms  1092 }

falconInput17High2Alarm OBJECT-TYPE
    SYNTAX  OBJECT IDENTIFIER
    ACCESS  read-only
    STATUS  mandatory
    DESCRIPTION
        "The reading for sensor 17 has reached the high limit
        value."
    ::= { falconWellKnownAlarms  1093 }

falconInput17Low2Alarm OBJECT-TYPE
    SYNTAX  OBJECT IDENTIFIER
    ACCESS  read-only
    STATUS  mandatory
    DESCRIPTION
        "The reading for sensor 17 has reached the low limit
        value."
    ::= { falconWellKnownAlarms  1094 }

falconInput18DigAlarm OBJECT-TYPE
    SYNTAX  OBJECT IDENTIFIER
    ACCESS  read-only
    STATUS  mandatory
    DESCRIPTION
        "The digital input 18 has been activated."
    ::= { falconWellKnownAlarms  1100 }

falconInput18HighAlarm OBJECT-TYPE
    SYNTAX  OBJECT IDENTIFIER
    ACCESS  read-only
    STATUS  mandatory
    DESCRIPTION
        "The reading for sensor 18 has reached the high limit
        value."
    ::= { falconWellKnownAlarms  1101 }

falconInput18LowAlarm OBJECT-TYPE
    SYNTAX  OBJECT IDENTIFIER
    ACCESS  read-only
    STATUS  mandatory
    DESCRIPTION
        "The reading for sensor 18 has reached the low limit
        value."
    ::= { falconWellKnownAlarms  1102 }

falconInput18High2Alarm OBJECT-TYPE
    SYNTAX  OBJECT IDENTIFIER
    ACCESS  read-only
    STATUS  mandatory
    DESCRIPTION
        "The reading for sensor 18 has reached the high limit
        value."
    ::= { falconWellKnownAlarms  1103 }

falconInput18Low2Alarm OBJECT-TYPE
    SYNTAX  OBJECT IDENTIFIER
    ACCESS  read-only
    STATUS  mandatory
    DESCRIPTION
        "The reading for sensor 18 has reached the low limit
        value."
    ::= { falconWellKnownAlarms  1104 }

falconInput19DigAlarm OBJECT-TYPE
    SYNTAX  OBJECT IDENTIFIER
    ACCESS  read-only
    STATUS  mandatory
    DESCRIPTION
        "The digital input 19 has been activated."
    ::= { falconWellKnownAlarms  1110 }

falconInput19HighAlarm OBJECT-TYPE
    SYNTAX  OBJECT IDENTIFIER
    ACCESS  read-only
    STATUS  mandatory
    DESCRIPTION
        "The reading for sensor 19 has reached the high limit
        value."
    ::= { falconWellKnownAlarms  1111 }

falconInput19LowAlarm OBJECT-TYPE
    SYNTAX  OBJECT IDENTIFIER
    ACCESS  read-only
    STATUS  mandatory
    DESCRIPTION
        "The reading for sensor 19 has reached the low limit
        value."
    ::= { falconWellKnownAlarms  1112 }

falconInput19High2Alarm OBJECT-TYPE
    SYNTAX  OBJECT IDENTIFIER
    ACCESS  read-only
    STATUS  mandatory
    DESCRIPTION
        "The reading for sensor 19 has reached the high limit
        value."
    ::= { falconWellKnownAlarms  1113 }

falconInput19Low2Alarm OBJECT-TYPE
    SYNTAX  OBJECT IDENTIFIER
    ACCESS  read-only
    STATUS  mandatory
    DESCRIPTION
        "The reading for sensor 19 has reached the low limit
        value."
    ::= { falconWellKnownAlarms  1114 }
    
falconInput20DigAlarm OBJECT-TYPE
    SYNTAX  OBJECT IDENTIFIER
    ACCESS  read-only
    STATUS  mandatory
    DESCRIPTION
        "The digital input 20 has been activated."
    ::= { falconWellKnownAlarms  1120 }

falconInput20HighAlarm OBJECT-TYPE
    SYNTAX  OBJECT IDENTIFIER
    ACCESS  read-only
    STATUS  mandatory
    DESCRIPTION
        "The reading for sensor 20 has reached the high limit
        value."
    ::= { falconWellKnownAlarms  1121 }

falconInput20LowAlarm OBJECT-TYPE
    SYNTAX  OBJECT IDENTIFIER
    ACCESS  read-only
    STATUS  mandatory
    DESCRIPTION
        "The reading for sensor 20 has reached the low limit
        value."
    ::= { falconWellKnownAlarms  1122 }

falconInput20High2Alarm OBJECT-TYPE
    SYNTAX  OBJECT IDENTIFIER
    ACCESS  read-only
    STATUS  mandatory
    DESCRIPTION
        "The reading for sensor 20 has reached the high limit
        value."
    ::= { falconWellKnownAlarms  1123 }

falconInput20Low2Alarm OBJECT-TYPE
    SYNTAX  OBJECT IDENTIFIER
    ACCESS  read-only
    STATUS  mandatory
    DESCRIPTION
        "The reading for sensor 20 has reached the low limit
        value."
    ::= { falconWellKnownAlarms  1124 }

falconInput21DigAlarm OBJECT-TYPE
    SYNTAX  OBJECT IDENTIFIER
    ACCESS  read-only
    STATUS  mandatory
    DESCRIPTION
        "The digital input 21 has been activated."
    ::= { falconWellKnownAlarms  1130 }

falconInput22DigAlarm OBJECT-TYPE
    SYNTAX  OBJECT IDENTIFIER
    ACCESS  read-only
    STATUS  mandatory
    DESCRIPTION
        "The digital input 22 has been activated."
    ::= { falconWellKnownAlarms  1140 }

falconInput23DigAlarm OBJECT-TYPE
    SYNTAX  OBJECT IDENTIFIER
    ACCESS  read-only
    STATUS  mandatory
    DESCRIPTION
        "The digital input 23 has been activated."
    ::= { falconWellKnownAlarms  1150 }

falconInput24DigAlarm OBJECT-TYPE
    SYNTAX  OBJECT IDENTIFIER
    ACCESS  read-only
    STATUS  mandatory
    DESCRIPTION
        "The digital input 24 has been activated."
    ::= { falconWellKnownAlarms  1160 }

falconInput25DigAlarm OBJECT-TYPE
    SYNTAX  OBJECT IDENTIFIER
    ACCESS  read-only
    STATUS  mandatory
    DESCRIPTION
        "The digital input 25 has been activated."
    ::= { falconWellKnownAlarms  1170 }

falconInput26DigAlarm OBJECT-TYPE
    SYNTAX  OBJECT IDENTIFIER
    ACCESS  read-only
    STATUS  mandatory
    DESCRIPTION
        "The digital input 26 has been activated."
    ::= { falconWellKnownAlarms  1180 }

falconInput27DigAlarm OBJECT-TYPE
    SYNTAX  OBJECT IDENTIFIER
    ACCESS  read-only
    STATUS  mandatory
    DESCRIPTION
        "The digital input 27 has been activated."
    ::= { falconWellKnownAlarms  1190 }

falconInput28DigAlarm OBJECT-TYPE
    SYNTAX  OBJECT IDENTIFIER
    ACCESS  read-only
    STATUS  mandatory
    DESCRIPTION
        "The digital input 28 has been activated."
    ::= { falconWellKnownAlarms  1200 }

falconInput29DigAlarm OBJECT-TYPE
    SYNTAX  OBJECT IDENTIFIER
    ACCESS  read-only
    STATUS  mandatory
    DESCRIPTION
        "The digital input 29 has been activated."
    ::= { falconWellKnownAlarms  1210 }

falconInput30DigAlarm OBJECT-TYPE
    SYNTAX  OBJECT IDENTIFIER
    ACCESS  read-only
    STATUS  mandatory
    DESCRIPTION
        "The digital input 30 has been activated."
    ::= { falconWellKnownAlarms  1220 }

falconInput31DigAlarm OBJECT-TYPE
    SYNTAX  OBJECT IDENTIFIER
    ACCESS  read-only
    STATUS  mandatory
    DESCRIPTION
        "The digital input 31 has been activated."
    ::= { falconWellKnownAlarms  1230 }

falconInput32DigAlarm OBJECT-TYPE
    SYNTAX  OBJECT IDENTIFIER
    ACCESS  read-only
    STATUS  mandatory
    DESCRIPTION
        "The digital input 32 has been activated."
    ::= { falconWellKnownAlarms  1240 }

falconInput33DigAlarm OBJECT-TYPE
    SYNTAX  OBJECT IDENTIFIER
    ACCESS  read-only
    STATUS  mandatory
    DESCRIPTION
        "The digital input 33 has been activated."
    ::= { falconWellKnownAlarms  2010 }

falconInput33HighAlarm OBJECT-TYPE
    SYNTAX  OBJECT IDENTIFIER
    ACCESS  read-only
    STATUS  mandatory
    DESCRIPTION
        "The reading for sensor 33 has reached the high limit
        value."
    ::= { falconWellKnownAlarms  2011 }

falconInput33LowAlarm OBJECT-TYPE
    SYNTAX  OBJECT IDENTIFIER
    ACCESS  read-only
    STATUS  mandatory
    DESCRIPTION
        "The reading for sensor 33 has reached the low limit
        value."
    ::= { falconWellKnownAlarms  2012 }

falconInput33High2Alarm OBJECT-TYPE
    SYNTAX  OBJECT IDENTIFIER
    ACCESS  read-only
    STATUS  mandatory
    DESCRIPTION
        "The reading for sensor 33 has reached the high limit
        value."
    ::= { falconWellKnownAlarms  2013 }

falconInput33Low2Alarm OBJECT-TYPE
    SYNTAX  OBJECT IDENTIFIER
    ACCESS  read-only
    STATUS  mandatory
    DESCRIPTION
        "The reading for sensor 33 has reached the low limit
        value."
    ::= { falconWellKnownAlarms  2014 }

falconInput34DigAlarm OBJECT-TYPE
    SYNTAX  OBJECT IDENTIFIER
    ACCESS  read-only
    STATUS  mandatory
    DESCRIPTION
        "The digital input 34 has been activated."
    ::= { falconWellKnownAlarms  2020 }

falconInput34HighAlarm OBJECT-TYPE
    SYNTAX  OBJECT IDENTIFIER
    ACCESS  read-only
    STATUS  mandatory
    DESCRIPTION
        "The reading for sensor 34 has reached the high limit
        value."
    ::= { falconWellKnownAlarms  2021 }

falconInput34LowAlarm OBJECT-TYPE
    SYNTAX  OBJECT IDENTIFIER
    ACCESS  read-only
    STATUS  mandatory
    DESCRIPTION
        "The reading for sensor 34 has reached the low limit
        value."
    ::= { falconWellKnownAlarms  2022 }

falconInput34High2Alarm OBJECT-TYPE
    SYNTAX  OBJECT IDENTIFIER
    ACCESS  read-only
    STATUS  mandatory
    DESCRIPTION
        "The reading for sensor 34 has reached the high limit
        value."
    ::= { falconWellKnownAlarms  2023 }

falconInput34Low2Alarm OBJECT-TYPE
    SYNTAX  OBJECT IDENTIFIER
    ACCESS  read-only
    STATUS  mandatory
    DESCRIPTION
        "The reading for sensor 34 has reached the low limit
        value."
    ::= { falconWellKnownAlarms  2024 }

falconInput35DigAlarm OBJECT-TYPE
    SYNTAX  OBJECT IDENTIFIER
    ACCESS  read-only
    STATUS  mandatory
    DESCRIPTION
        "The digital input 35 has been activated."
    ::= { falconWellKnownAlarms  2030 }

falconInput35HighAlarm OBJECT-TYPE
    SYNTAX  OBJECT IDENTIFIER
    ACCESS  read-only
    STATUS  mandatory
    DESCRIPTION
        "The reading for sensor 35 has reached the high limit
        value."
    ::= { falconWellKnownAlarms  2031 }

falconInput35LowAlarm OBJECT-TYPE
    SYNTAX  OBJECT IDENTIFIER
    ACCESS  read-only
    STATUS  mandatory
    DESCRIPTION
        "The reading for sensor 35 has reached the low limit
        value."
    ::= { falconWellKnownAlarms  2032 }

falconInput35High2Alarm OBJECT-TYPE
    SYNTAX  OBJECT IDENTIFIER
    ACCESS  read-only
    STATUS  mandatory
    DESCRIPTION
        "The reading for sensor 35 has reached the high limit
        value."
    ::= { falconWellKnownAlarms  2033 }

falconInput35Low2Alarm OBJECT-TYPE
    SYNTAX  OBJECT IDENTIFIER
    ACCESS  read-only
    STATUS  mandatory
    DESCRIPTION
        "The reading for sensor 35 has reached the low limit
        value."
    ::= { falconWellKnownAlarms  2034 }

falconInput36DigAlarm OBJECT-TYPE
    SYNTAX  OBJECT IDENTIFIER
    ACCESS  read-only
    STATUS  mandatory
    DESCRIPTION
        "The digital input 36 has been activated."
    ::= { falconWellKnownAlarms  2040 }

falconInput36HighAlarm OBJECT-TYPE
    SYNTAX  OBJECT IDENTIFIER
    ACCESS  read-only
    STATUS  mandatory
    DESCRIPTION
        "The reading for sensor 36 has reached the high limit
        value."
    ::= { falconWellKnownAlarms  2041 }

falconInput36LowAlarm OBJECT-TYPE
    SYNTAX  OBJECT IDENTIFIER
    ACCESS  read-only
    STATUS  mandatory
    DESCRIPTION
        "The reading for sensor 36 has reached the low limit
        value."
    ::= { falconWellKnownAlarms  2042 }

falconInput36High2Alarm OBJECT-TYPE
    SYNTAX  OBJECT IDENTIFIER
    ACCESS  read-only
    STATUS  mandatory
    DESCRIPTION
        "The reading for sensor 36 has reached the high limit
        value."
    ::= { falconWellKnownAlarms  2043 }

falconInput36Low2Alarm OBJECT-TYPE
    SYNTAX  OBJECT IDENTIFIER
    ACCESS  read-only
    STATUS  mandatory
    DESCRIPTION
        "The reading for sensor 36 has reached the low limit
        value."
    ::= { falconWellKnownAlarms  2044 }

falconInput37DigAlarm OBJECT-TYPE
    SYNTAX  OBJECT IDENTIFIER
    ACCESS  read-only
    STATUS  mandatory
    DESCRIPTION
        "The digital input 37 has been activated."
    ::= { falconWellKnownAlarms  2050 }

falconInput37HighAlarm OBJECT-TYPE
    SYNTAX  OBJECT IDENTIFIER
    ACCESS  read-only
    STATUS  mandatory
    DESCRIPTION
        "The reading for sensor 37 has reached the high limit
        value."
    ::= { falconWellKnownAlarms  2051 }

falconInput37LowAlarm OBJECT-TYPE
    SYNTAX  OBJECT IDENTIFIER
    ACCESS  read-only
    STATUS  mandatory
    DESCRIPTION
        "The reading for sensor 37 has reached the low limit
        value."
    ::= { falconWellKnownAlarms  2052 }

falconInput37High2Alarm OBJECT-TYPE
    SYNTAX  OBJECT IDENTIFIER
    ACCESS  read-only
    STATUS  mandatory
    DESCRIPTION
        "The reading for sensor 37 has reached the high limit
        value."
    ::= { falconWellKnownAlarms  2053 }

falconInput37Low2Alarm OBJECT-TYPE
    SYNTAX  OBJECT IDENTIFIER
    ACCESS  read-only
    STATUS  mandatory
    DESCRIPTION
        "The reading for sensor 37 has reached the low limit
        value."
    ::= { falconWellKnownAlarms  2054 }

falconInput38DigAlarm OBJECT-TYPE
    SYNTAX  OBJECT IDENTIFIER
    ACCESS  read-only
    STATUS  mandatory
    DESCRIPTION
        "The digital input 38 has been activated."
    ::= { falconWellKnownAlarms  2060 }

falconInput38HighAlarm OBJECT-TYPE
    SYNTAX  OBJECT IDENTIFIER
    ACCESS  read-only
    STATUS  mandatory
    DESCRIPTION
        "The reading for sensor 38 has reached the high limit
        value."
    ::= { falconWellKnownAlarms  2061 }

falconInput38LowAlarm OBJECT-TYPE
    SYNTAX  OBJECT IDENTIFIER
    ACCESS  read-only
    STATUS  mandatory
    DESCRIPTION
        "The reading for sensor 38 has reached the low limit
        value."
    ::= { falconWellKnownAlarms  2062 }

falconInput38High2Alarm OBJECT-TYPE
    SYNTAX  OBJECT IDENTIFIER
    ACCESS  read-only
    STATUS  mandatory
    DESCRIPTION
        "The reading for sensor 38 has reached the high limit
        value."
    ::= { falconWellKnownAlarms  2063 }

falconInput38Low2Alarm OBJECT-TYPE
    SYNTAX  OBJECT IDENTIFIER
    ACCESS  read-only
    STATUS  mandatory
    DESCRIPTION
        "The reading for sensor 38 has reached the low limit
        value."
    ::= { falconWellKnownAlarms  2064 }

falconInput39DigAlarm OBJECT-TYPE
    SYNTAX  OBJECT IDENTIFIER
    ACCESS  read-only
    STATUS  mandatory
    DESCRIPTION
        "The digital input 39 has been activated."
    ::= { falconWellKnownAlarms  2070 }

falconInput39HighAlarm OBJECT-TYPE
    SYNTAX  OBJECT IDENTIFIER
    ACCESS  read-only
    STATUS  mandatory
    DESCRIPTION
        "The reading for sensor 39 has reached the high limit
        value."
    ::= { falconWellKnownAlarms  2071 }

falconInput39LowAlarm OBJECT-TYPE
    SYNTAX  OBJECT IDENTIFIER
    ACCESS  read-only
    STATUS  mandatory
    DESCRIPTION
        "The reading for sensor 39 has reached the low limit
        value."
    ::= { falconWellKnownAlarms  2072 }

falconInput39High2Alarm OBJECT-TYPE
    SYNTAX  OBJECT IDENTIFIER
    ACCESS  read-only
    STATUS  mandatory
    DESCRIPTION
        "The reading for sensor 39 has reached the high limit
        value."
    ::= { falconWellKnownAlarms  2073 }

falconInput39Low2Alarm OBJECT-TYPE
    SYNTAX  OBJECT IDENTIFIER
    ACCESS  read-only
    STATUS  mandatory
    DESCRIPTION
        "The reading for sensor 39 has reached the low limit
        value."
    ::= { falconWellKnownAlarms  2074 }

falconInput40DigAlarm OBJECT-TYPE
    SYNTAX  OBJECT IDENTIFIER
    ACCESS  read-only
    STATUS  mandatory
    DESCRIPTION
        "The digital input 40 has been activated."
    ::= { falconWellKnownAlarms  2080 }

falconInput40HighAlarm OBJECT-TYPE
    SYNTAX  OBJECT IDENTIFIER
    ACCESS  read-only
    STATUS  mandatory
    DESCRIPTION
        "The reading for sensor 40 has reached the high limit
        value."
    ::= { falconWellKnownAlarms  2081 }

falconInput40LowAlarm OBJECT-TYPE
    SYNTAX  OBJECT IDENTIFIER
    ACCESS  read-only
    STATUS  mandatory
    DESCRIPTION
        "The reading for sensor 40 has reached the low limit
        value."
    ::= { falconWellKnownAlarms  2082 }

falconInput40High2Alarm OBJECT-TYPE
    SYNTAX  OBJECT IDENTIFIER
    ACCESS  read-only
    STATUS  mandatory
    DESCRIPTION
        "The reading for sensor 40 has reached the high limit
        value."
    ::= { falconWellKnownAlarms  2083 }

falconInput40Low2Alarm OBJECT-TYPE
    SYNTAX  OBJECT IDENTIFIER
    ACCESS  read-only
    STATUS  mandatory
    DESCRIPTION
        "The reading for sensor 40 has reached the low limit
        value."
    ::= { falconWellKnownAlarms  2084 }

falconInput41DigAlarm OBJECT-TYPE
    SYNTAX  OBJECT IDENTIFIER
    ACCESS  read-only
    STATUS  mandatory
    DESCRIPTION
        "The digital input 41 has been activated."
    ::= { falconWellKnownAlarms  2090 }

falconInput41HighAlarm OBJECT-TYPE
    SYNTAX  OBJECT IDENTIFIER
    ACCESS  read-only
    STATUS  mandatory
    DESCRIPTION
        "The reading for sensor 41 has reached the high limit
        value."
    ::= { falconWellKnownAlarms  2091 }

falconInput41LowAlarm OBJECT-TYPE
    SYNTAX  OBJECT IDENTIFIER
    ACCESS  read-only
    STATUS  mandatory
    DESCRIPTION
        "The reading for sensor 41 has reached the low limit
        value."
    ::= { falconWellKnownAlarms  2092 }

falconInput41High2Alarm OBJECT-TYPE
    SYNTAX  OBJECT IDENTIFIER
    ACCESS  read-only
    STATUS  mandatory
    DESCRIPTION
        "The reading for sensor 41 has reached the high limit
        value."
    ::= { falconWellKnownAlarms  2093 }

falconInput41Low2Alarm OBJECT-TYPE
    SYNTAX  OBJECT IDENTIFIER
    ACCESS  read-only
    STATUS  mandatory
    DESCRIPTION
        "The reading for sensor 41 has reached the low limit
        value."
    ::= { falconWellKnownAlarms  2094 }

falconInput42DigAlarm OBJECT-TYPE
    SYNTAX  OBJECT IDENTIFIER
    ACCESS  read-only
    STATUS  mandatory
    DESCRIPTION
        "The digital input 42 has been activated."
    ::= { falconWellKnownAlarms  2100 }

falconInput42HighAlarm OBJECT-TYPE
    SYNTAX  OBJECT IDENTIFIER
    ACCESS  read-only
    STATUS  mandatory
    DESCRIPTION
        "The reading for sensor 42 has reached the high limit
        value."
    ::= { falconWellKnownAlarms  2101 }

falconInput42LowAlarm OBJECT-TYPE
    SYNTAX  OBJECT IDENTIFIER
    ACCESS  read-only
    STATUS  mandatory
    DESCRIPTION
        "The reading for sensor 42 has reached the low limit
        value."
    ::= { falconWellKnownAlarms  2102 }

falconInput42High2Alarm OBJECT-TYPE
    SYNTAX  OBJECT IDENTIFIER
    ACCESS  read-only
    STATUS  mandatory
    DESCRIPTION
        "The reading for sensor 42 has reached the high limit
        value."
    ::= { falconWellKnownAlarms  2103 }

falconInput42Low2Alarm OBJECT-TYPE
    SYNTAX  OBJECT IDENTIFIER
    ACCESS  read-only
    STATUS  mandatory
    DESCRIPTION
        "The reading for sensor 42 has reached the low limit
        value."
    ::= { falconWellKnownAlarms  2104 }

falconInput43DigAlarm OBJECT-TYPE
    SYNTAX  OBJECT IDENTIFIER
    ACCESS  read-only
    STATUS  mandatory
    DESCRIPTION
        "The digital input 43 has been activated."
    ::= { falconWellKnownAlarms  2110 }

falconInput43HighAlarm OBJECT-TYPE
    SYNTAX  OBJECT IDENTIFIER
    ACCESS  read-only
    STATUS  mandatory
    DESCRIPTION
        "The reading for sensor 43 has reached the high limit
        value."
    ::= { falconWellKnownAlarms  2111 }

falconInput43LowAlarm OBJECT-TYPE
    SYNTAX  OBJECT IDENTIFIER
    ACCESS  read-only
    STATUS  mandatory
    DESCRIPTION
        "The reading for sensor 43 has reached the low limit
        value."
    ::= { falconWellKnownAlarms  2112 }

falconInput43High2Alarm OBJECT-TYPE
    SYNTAX  OBJECT IDENTIFIER
    ACCESS  read-only
    STATUS  mandatory
    DESCRIPTION
        "The reading for sensor 43 has reached the high limit
        value."
    ::= { falconWellKnownAlarms  2113 }

falconInput43Low2Alarm OBJECT-TYPE
    SYNTAX  OBJECT IDENTIFIER
    ACCESS  read-only
    STATUS  mandatory
    DESCRIPTION
        "The reading for sensor 43 has reached the low limit
        value."
    ::= { falconWellKnownAlarms  2114 }

falconInput44DigAlarm OBJECT-TYPE
    SYNTAX  OBJECT IDENTIFIER
    ACCESS  read-only
    STATUS  mandatory
    DESCRIPTION
        "The digital input 44 has been activated."
    ::= { falconWellKnownAlarms  2120 }

falconInput44HighAlarm OBJECT-TYPE
    SYNTAX  OBJECT IDENTIFIER
    ACCESS  read-only
    STATUS  mandatory
    DESCRIPTION
        "The reading for sensor 44 has reached the high limit
        value."
    ::= { falconWellKnownAlarms  2121 }

falconInput44LowAlarm OBJECT-TYPE
    SYNTAX  OBJECT IDENTIFIER
    ACCESS  read-only
    STATUS  mandatory
    DESCRIPTION
        "The reading for sensor 44 has reached the low limit
        value."
    ::= { falconWellKnownAlarms  2122 }

falconInput44High2Alarm OBJECT-TYPE
    SYNTAX  OBJECT IDENTIFIER
    ACCESS  read-only
    STATUS  mandatory
    DESCRIPTION
        "The reading for sensor 44 has reached the high limit
        value."
    ::= { falconWellKnownAlarms  2123 }

falconInput44Low2Alarm OBJECT-TYPE
    SYNTAX  OBJECT IDENTIFIER
    ACCESS  read-only
    STATUS  mandatory
    DESCRIPTION
        "The reading for sensor 44 has reached the low limit
        value."
    ::= { falconWellKnownAlarms  2124 }

falconInput45DigAlarm OBJECT-TYPE
    SYNTAX  OBJECT IDENTIFIER
    ACCESS  read-only
    STATUS  mandatory
    DESCRIPTION
        "The digital input 45 has been activated."
    ::= { falconWellKnownAlarms  2130 }

falconInput46DigAlarm OBJECT-TYPE
    SYNTAX  OBJECT IDENTIFIER
    ACCESS  read-only
    STATUS  mandatory
    DESCRIPTION
        "The digital input 46 has been activated."
    ::= { falconWellKnownAlarms  2140 }

falconInput47DigAlarm OBJECT-TYPE
    SYNTAX  OBJECT IDENTIFIER
    ACCESS  read-only
    STATUS  mandatory
    DESCRIPTION
        "The digital input 47 has been activated."
    ::= { falconWellKnownAlarms  2150 }

falconInput48DigAlarm OBJECT-TYPE
    SYNTAX  OBJECT IDENTIFIER
    ACCESS  read-only
    STATUS  mandatory
    DESCRIPTION
        "The digital input 48 has been activated."
    ::= { falconWellKnownAlarms  2160 }

falconInput49DigAlarm OBJECT-TYPE
    SYNTAX  OBJECT IDENTIFIER
    ACCESS  read-only
    STATUS  mandatory
    DESCRIPTION
        "The digital input 49 has been activated."
    ::= { falconWellKnownAlarms  2170 }

falconInput50DigAlarm OBJECT-TYPE
    SYNTAX  OBJECT IDENTIFIER
    ACCESS  read-only
    STATUS  mandatory
    DESCRIPTION
        "The digital input 50 has been activated."
    ::= { falconWellKnownAlarms  2180 }

falconInput51DigAlarm OBJECT-TYPE
    SYNTAX  OBJECT IDENTIFIER
    ACCESS  read-only
    STATUS  mandatory
    DESCRIPTION
        "The digital input 51 has been activated."
    ::= { falconWellKnownAlarms  2190 }

falconInput52DigAlarm OBJECT-TYPE
    SYNTAX  OBJECT IDENTIFIER
    ACCESS  read-only
    STATUS  mandatory
    DESCRIPTION
        "The digital input 52 has been activated."
    ::= { falconWellKnownAlarms  2200 }

falconInput53DigAlarm OBJECT-TYPE
    SYNTAX  OBJECT IDENTIFIER
    ACCESS  read-only
    STATUS  mandatory
    DESCRIPTION
        "The digital input 53 has been activated."
    ::= { falconWellKnownAlarms  2210 }

falconInput54DigAlarm OBJECT-TYPE
    SYNTAX  OBJECT IDENTIFIER
    ACCESS  read-only
    STATUS  mandatory
    DESCRIPTION
        "The digital input 54 has been activated."
    ::= { falconWellKnownAlarms  2220 }

falconInput55DigAlarm OBJECT-TYPE
    SYNTAX  OBJECT IDENTIFIER
    ACCESS  read-only
    STATUS  mandatory
    DESCRIPTION
        "The digital input 55 has been activated."
    ::= { falconWellKnownAlarms  2230 }

falconInput56DigAlarm OBJECT-TYPE
    SYNTAX  OBJECT IDENTIFIER
    ACCESS  read-only
    STATUS  mandatory
    DESCRIPTION
        "The digital input 56 has been activated."
    ::= { falconWellKnownAlarms  2240 }

falconInput57DigAlarm OBJECT-TYPE
    SYNTAX  OBJECT IDENTIFIER
    ACCESS  read-only
    STATUS  mandatory
    DESCRIPTION
        "The digital input 57 has been activated."
    ::= { falconWellKnownAlarms  3010 }

falconInput57HighAlarm OBJECT-TYPE
    SYNTAX  OBJECT IDENTIFIER
    ACCESS  read-only
    STATUS  mandatory
    DESCRIPTION
        "The reading for sensor 57 has reached the high limit
        value."
    ::= { falconWellKnownAlarms  3011 }

falconInput57LowAlarm OBJECT-TYPE
    SYNTAX  OBJECT IDENTIFIER
    ACCESS  read-only
    STATUS  mandatory
    DESCRIPTION
        "The reading for sensor 57 has reached the low limit
        value."
    ::= { falconWellKnownAlarms  3012 }

falconInput57High2Alarm OBJECT-TYPE
    SYNTAX  OBJECT IDENTIFIER
    ACCESS  read-only
    STATUS  mandatory
    DESCRIPTION
        "The reading for sensor 57 has reached the high limit
        value."
    ::= { falconWellKnownAlarms  3013 }

falconInput57Low2Alarm OBJECT-TYPE
    SYNTAX  OBJECT IDENTIFIER
    ACCESS  read-only
    STATUS  mandatory
    DESCRIPTION
        "The reading for sensor 57 has reached the low limit
        value."
    ::= { falconWellKnownAlarms  3014 }

falconInput58DigAlarm OBJECT-TYPE
    SYNTAX  OBJECT IDENTIFIER
    ACCESS  read-only
    STATUS  mandatory
    DESCRIPTION
        "The digital input 58 has been activated."
    ::= { falconWellKnownAlarms  3020 }

falconInput58HighAlarm OBJECT-TYPE
    SYNTAX  OBJECT IDENTIFIER
    ACCESS  read-only
    STATUS  mandatory
    DESCRIPTION
        "The reading for sensor 58 has reached the high limit
        value."
    ::= { falconWellKnownAlarms  3021 }

falconInput58LowAlarm OBJECT-TYPE
    SYNTAX  OBJECT IDENTIFIER
    ACCESS  read-only
    STATUS  mandatory
    DESCRIPTION
        "The reading for sensor 58 has reached the low limit
        value."
    ::= { falconWellKnownAlarms  3022 }

falconInput58High2Alarm OBJECT-TYPE
    SYNTAX  OBJECT IDENTIFIER
    ACCESS  read-only
    STATUS  mandatory
    DESCRIPTION
        "The reading for sensor 58 has reached the high limit
        value."
    ::= { falconWellKnownAlarms  3023 }

falconInput58Low2Alarm OBJECT-TYPE
    SYNTAX  OBJECT IDENTIFIER
    ACCESS  read-only
    STATUS  mandatory
    DESCRIPTION
        "The reading for sensor 58 has reached the low limit
        value."
    ::= { falconWellKnownAlarms  3024 }

falconInput59DigAlarm OBJECT-TYPE
    SYNTAX  OBJECT IDENTIFIER
    ACCESS  read-only
    STATUS  mandatory
    DESCRIPTION
        "The digital input 59 has been activated."
    ::= { falconWellKnownAlarms  3030 }

falconInput59HighAlarm OBJECT-TYPE
    SYNTAX  OBJECT IDENTIFIER
    ACCESS  read-only
    STATUS  mandatory
    DESCRIPTION
        "The reading for sensor 59 has reached the high limit
        value."
    ::= { falconWellKnownAlarms  3031 }

falconInput59LowAlarm OBJECT-TYPE
    SYNTAX  OBJECT IDENTIFIER
    ACCESS  read-only
    STATUS  mandatory
    DESCRIPTION
        "The reading for sensor 59 has reached the low limit
        value."
    ::= { falconWellKnownAlarms  3032 }

falconInput59High2Alarm OBJECT-TYPE
    SYNTAX  OBJECT IDENTIFIER
    ACCESS  read-only
    STATUS  mandatory
    DESCRIPTION
        "The reading for sensor 59 has reached the high limit
        value."
    ::= { falconWellKnownAlarms  3033 }

falconInput59Low2Alarm OBJECT-TYPE
    SYNTAX  OBJECT IDENTIFIER
    ACCESS  read-only
    STATUS  mandatory
    DESCRIPTION
        "The reading for sensor 59 has reached the low limit
        value."
    ::= { falconWellKnownAlarms  3034 }

falconInput60DigAlarm OBJECT-TYPE
    SYNTAX  OBJECT IDENTIFIER
    ACCESS  read-only
    STATUS  mandatory
    DESCRIPTION
        "The digital input 60 has been activated."
    ::= { falconWellKnownAlarms  3040 }

falconInput60HighAlarm OBJECT-TYPE
    SYNTAX  OBJECT IDENTIFIER
    ACCESS  read-only
    STATUS  mandatory
    DESCRIPTION
        "The reading for sensor 60 has reached the high limit
        value."
    ::= { falconWellKnownAlarms  3041 }

falconInput60LowAlarm OBJECT-TYPE
    SYNTAX  OBJECT IDENTIFIER
    ACCESS  read-only
    STATUS  mandatory
    DESCRIPTION
        "The reading for sensor 60 has reached the low limit
        value."
    ::= { falconWellKnownAlarms  3042 }

falconInput60High2Alarm OBJECT-TYPE
    SYNTAX  OBJECT IDENTIFIER
    ACCESS  read-only
    STATUS  mandatory
    DESCRIPTION
        "The reading for sensor 60 has reached the high limit
        value."
    ::= { falconWellKnownAlarms  3043 }

falconInput60Low2Alarm OBJECT-TYPE
    SYNTAX  OBJECT IDENTIFIER
    ACCESS  read-only
    STATUS  mandatory
    DESCRIPTION
        "The reading for sensor 60 has reached the low limit
        value."
    ::= { falconWellKnownAlarms  3044 }

falconInput61DigAlarm OBJECT-TYPE
    SYNTAX  OBJECT IDENTIFIER
    ACCESS  read-only
    STATUS  mandatory
    DESCRIPTION
        "The digital input 61 has been activated."
    ::= { falconWellKnownAlarms  3050 }

falconInput61HighAlarm OBJECT-TYPE
    SYNTAX  OBJECT IDENTIFIER
    ACCESS  read-only
    STATUS  mandatory
    DESCRIPTION
        "The reading for sensor 61 has reached the high limit
        value."
    ::= { falconWellKnownAlarms  3051 }

falconInput61LowAlarm OBJECT-TYPE
    SYNTAX  OBJECT IDENTIFIER
    ACCESS  read-only
    STATUS  mandatory
    DESCRIPTION
        "The reading for sensor 61 has reached the low limit
        value."
    ::= { falconWellKnownAlarms  3052 }

falconInput61High2Alarm OBJECT-TYPE
    SYNTAX  OBJECT IDENTIFIER
    ACCESS  read-only
    STATUS  mandatory
    DESCRIPTION
        "The reading for sensor 61 has reached the high limit
        value."
    ::= { falconWellKnownAlarms  3053 }

falconInput61Low2Alarm OBJECT-TYPE
    SYNTAX  OBJECT IDENTIFIER
    ACCESS  read-only
    STATUS  mandatory
    DESCRIPTION
        "The reading for sensor 61 has reached the low limit
        value."
    ::= { falconWellKnownAlarms  3054 }

falconInput62DigAlarm OBJECT-TYPE
    SYNTAX  OBJECT IDENTIFIER
    ACCESS  read-only
    STATUS  mandatory
    DESCRIPTION
        "The digital input 62 has been activated."
    ::= { falconWellKnownAlarms  3060 }

falconInput62HighAlarm OBJECT-TYPE
    SYNTAX  OBJECT IDENTIFIER
    ACCESS  read-only
    STATUS  mandatory
    DESCRIPTION
        "The reading for sensor 62 has reached the high limit
        value."
    ::= { falconWellKnownAlarms  3061 }

falconInput62LowAlarm OBJECT-TYPE
    SYNTAX  OBJECT IDENTIFIER
    ACCESS  read-only
    STATUS  mandatory
    DESCRIPTION
        "The reading for sensor 62 has reached the low limit
        value."
    ::= { falconWellKnownAlarms  3062 }

falconInput62High2Alarm OBJECT-TYPE
    SYNTAX  OBJECT IDENTIFIER
    ACCESS  read-only
    STATUS  mandatory
    DESCRIPTION
        "The reading for sensor 62 has reached the high limit
        value."
    ::= { falconWellKnownAlarms  3063 }

falconInput62Low2Alarm OBJECT-TYPE
    SYNTAX  OBJECT IDENTIFIER
    ACCESS  read-only
    STATUS  mandatory
    DESCRIPTION
        "The reading for sensor 62 has reached the low limit
        value."
    ::= { falconWellKnownAlarms  3064 }

falconInput63DigAlarm OBJECT-TYPE
    SYNTAX  OBJECT IDENTIFIER
    ACCESS  read-only
    STATUS  mandatory
    DESCRIPTION
        "The digital input 63 has been activated."
    ::= { falconWellKnownAlarms  3070 }

falconInput63HighAlarm OBJECT-TYPE
    SYNTAX  OBJECT IDENTIFIER
    ACCESS  read-only
    STATUS  mandatory
    DESCRIPTION
        "The reading for sensor 63 has reached the high limit
        value."
    ::= { falconWellKnownAlarms  3071 }

falconInput63LowAlarm OBJECT-TYPE
    SYNTAX  OBJECT IDENTIFIER
    ACCESS  read-only
    STATUS  mandatory
    DESCRIPTION
        "The reading for sensor 63 has reached the low limit
        value."
    ::= { falconWellKnownAlarms  3072 }

falconInput63High2Alarm OBJECT-TYPE
    SYNTAX  OBJECT IDENTIFIER
    ACCESS  read-only
    STATUS  mandatory
    DESCRIPTION
        "The reading for sensor 63 has reached the high limit
        value."
    ::= { falconWellKnownAlarms  3073 }

falconInput63Low2Alarm OBJECT-TYPE
    SYNTAX  OBJECT IDENTIFIER
    ACCESS  read-only
    STATUS  mandatory
    DESCRIPTION
        "The reading for sensor 63 has reached the low limit
        value."
    ::= { falconWellKnownAlarms  3074 }

falconInput64DigAlarm OBJECT-TYPE
    SYNTAX  OBJECT IDENTIFIER
    ACCESS  read-only
    STATUS  mandatory
    DESCRIPTION
        "The digital input 64 has been activated."
    ::= { falconWellKnownAlarms  3080 }

falconInput64HighAlarm OBJECT-TYPE
    SYNTAX  OBJECT IDENTIFIER
    ACCESS  read-only
    STATUS  mandatory
    DESCRIPTION
        "The reading for sensor 64 has reached the high limit
        value."
    ::= { falconWellKnownAlarms  3081 }

falconInput64LowAlarm OBJECT-TYPE
    SYNTAX  OBJECT IDENTIFIER
    ACCESS  read-only
    STATUS  mandatory
    DESCRIPTION
        "The reading for sensor 64 has reached the low limit
        value."
    ::= { falconWellKnownAlarms  3082 }

falconInput64High2Alarm OBJECT-TYPE
    SYNTAX  OBJECT IDENTIFIER
    ACCESS  read-only
    STATUS  mandatory
    DESCRIPTION
        "The reading for sensor 64 has reached the high limit
        value."
    ::= { falconWellKnownAlarms  3083 }

falconInput64Low2Alarm OBJECT-TYPE
    SYNTAX  OBJECT IDENTIFIER
    ACCESS  read-only
    STATUS  mandatory
    DESCRIPTION
        "The reading for sensor 64 has reached the low limit
        value."
    ::= { falconWellKnownAlarms  3084 }

falconInput65DigAlarm OBJECT-TYPE
    SYNTAX  OBJECT IDENTIFIER
    ACCESS  read-only
    STATUS  mandatory
    DESCRIPTION
        "The digital input 65 has been activated."
    ::= { falconWellKnownAlarms  3090 }

falconInput65HighAlarm OBJECT-TYPE
    SYNTAX  OBJECT IDENTIFIER
    ACCESS  read-only
    STATUS  mandatory
    DESCRIPTION
        "The reading for sensor 65 has reached the high limit
        value."
    ::= { falconWellKnownAlarms  3091 }

falconInput65LowAlarm OBJECT-TYPE
    SYNTAX  OBJECT IDENTIFIER
    ACCESS  read-only
    STATUS  mandatory
    DESCRIPTION
        "The reading for sensor 65 has reached the low limit
        value."
    ::= { falconWellKnownAlarms  3092 }

falconInput65High2Alarm OBJECT-TYPE
    SYNTAX  OBJECT IDENTIFIER
    ACCESS  read-only
    STATUS  mandatory
    DESCRIPTION
        "The reading for sensor 65 has reached the high limit
        value."
    ::= { falconWellKnownAlarms  3093 }

falconInput65Low2Alarm OBJECT-TYPE
    SYNTAX  OBJECT IDENTIFIER
    ACCESS  read-only
    STATUS  mandatory
    DESCRIPTION
        "The reading for sensor 65 has reached the low limit
        value."
    ::= { falconWellKnownAlarms  3094 }

falconInput66DigAlarm OBJECT-TYPE
    SYNTAX  OBJECT IDENTIFIER
    ACCESS  read-only
    STATUS  mandatory
    DESCRIPTION
        "The digital input 66 has been activated."
    ::= { falconWellKnownAlarms  3100 }

falconInput66HighAlarm OBJECT-TYPE
    SYNTAX  OBJECT IDENTIFIER
    ACCESS  read-only
    STATUS  mandatory
    DESCRIPTION
        "The reading for sensor 66 has reached the high limit
        value."
    ::= { falconWellKnownAlarms  3101 }

falconInput66LowAlarm OBJECT-TYPE
    SYNTAX  OBJECT IDENTIFIER
    ACCESS  read-only
    STATUS  mandatory
    DESCRIPTION
        "The reading for sensor 66 has reached the low limit
        value."
    ::= { falconWellKnownAlarms  3102 }

falconInput66High2Alarm OBJECT-TYPE
    SYNTAX  OBJECT IDENTIFIER
    ACCESS  read-only
    STATUS  mandatory
    DESCRIPTION
        "The reading for sensor 66 has reached the high limit
        value."
    ::= { falconWellKnownAlarms  3103 }

falconInput66Low2Alarm OBJECT-TYPE
    SYNTAX  OBJECT IDENTIFIER
    ACCESS  read-only
    STATUS  mandatory
    DESCRIPTION
        "The reading for sensor 66 has reached the low limit
        value."
    ::= { falconWellKnownAlarms  3104 }

falconInput67DigAlarm OBJECT-TYPE
    SYNTAX  OBJECT IDENTIFIER
    ACCESS  read-only
    STATUS  mandatory
    DESCRIPTION
        "The digital input 67 has been activated."
    ::= { falconWellKnownAlarms  3110 }

falconInput67HighAlarm OBJECT-TYPE
    SYNTAX  OBJECT IDENTIFIER
    ACCESS  read-only
    STATUS  mandatory
    DESCRIPTION
        "The reading for sensor 67 has reached the high limit
        value."
    ::= { falconWellKnownAlarms  3111 }

falconInput67LowAlarm OBJECT-TYPE
    SYNTAX  OBJECT IDENTIFIER
    ACCESS  read-only
    STATUS  mandatory
    DESCRIPTION
        "The reading for sensor 67 has reached the low limit
        value."
    ::= { falconWellKnownAlarms  3112 }

falconInput67High2Alarm OBJECT-TYPE
    SYNTAX  OBJECT IDENTIFIER
    ACCESS  read-only
    STATUS  mandatory
    DESCRIPTION
        "The reading for sensor 67 has reached the high limit
        value."
    ::= { falconWellKnownAlarms  3113 }

falconInput67Low2Alarm OBJECT-TYPE
    SYNTAX  OBJECT IDENTIFIER
    ACCESS  read-only
    STATUS  mandatory
    DESCRIPTION
        "The reading for sensor 67 has reached the low limit
        value."
    ::= { falconWellKnownAlarms  3114 }

falconInput68DigAlarm OBJECT-TYPE
    SYNTAX  OBJECT IDENTIFIER
    ACCESS  read-only
    STATUS  mandatory
    DESCRIPTION
        "The digital input 68 has been activated."
    ::= { falconWellKnownAlarms  3120 }

falconInput68HighAlarm OBJECT-TYPE
    SYNTAX  OBJECT IDENTIFIER
    ACCESS  read-only
    STATUS  mandatory
    DESCRIPTION
        "The reading for sensor 68 has reached the high limit
        value."
    ::= { falconWellKnownAlarms  3121 }

falconInput68LowAlarm OBJECT-TYPE
    SYNTAX  OBJECT IDENTIFIER
    ACCESS  read-only
    STATUS  mandatory
    DESCRIPTION
        "The reading for sensor 68 has reached the low limit
        value."
    ::= { falconWellKnownAlarms  3122 }

falconInput68High2Alarm OBJECT-TYPE
    SYNTAX  OBJECT IDENTIFIER
    ACCESS  read-only
    STATUS  mandatory
    DESCRIPTION
        "The reading for sensor 68 has reached the high limit
        value."
    ::= { falconWellKnownAlarms  3123 }

falconInput68Low2Alarm OBJECT-TYPE
    SYNTAX  OBJECT IDENTIFIER
    ACCESS  read-only
    STATUS  mandatory
    DESCRIPTION
        "The reading for sensor 68 has reached the low limit
        value."
    ::= { falconWellKnownAlarms  3124 }

falconInput69DigAlarm OBJECT-TYPE
    SYNTAX  OBJECT IDENTIFIER
    ACCESS  read-only
    STATUS  mandatory
    DESCRIPTION
        "The digital input 69 has been activated."
    ::= { falconWellKnownAlarms  3130 }

falconInput70DigAlarm OBJECT-TYPE
    SYNTAX  OBJECT IDENTIFIER
    ACCESS  read-only
    STATUS  mandatory
    DESCRIPTION
        "The digital input 70 has been activated."
    ::= { falconWellKnownAlarms  3140 }

falconInput71DigAlarm OBJECT-TYPE
    SYNTAX  OBJECT IDENTIFIER
    ACCESS  read-only
    STATUS  mandatory
    DESCRIPTION
        "The digital input 71 has been activated."
    ::= { falconWellKnownAlarms  3150 }

falconInput72DigAlarm OBJECT-TYPE
    SYNTAX  OBJECT IDENTIFIER
    ACCESS  read-only
    STATUS  mandatory
    DESCRIPTION
        "The digital input 72 has been activated."
    ::= { falconWellKnownAlarms  3160 }

falconInput73DigAlarm OBJECT-TYPE
    SYNTAX  OBJECT IDENTIFIER
    ACCESS  read-only
    STATUS  mandatory
    DESCRIPTION
        "The digital input 73 has been activated."
    ::= { falconWellKnownAlarms  3170 }

falconInput74DigAlarm OBJECT-TYPE
    SYNTAX  OBJECT IDENTIFIER
    ACCESS  read-only
    STATUS  mandatory
    DESCRIPTION
        "The digital input 74 has been activated."
    ::= { falconWellKnownAlarms  3180 }

falconInput75DigAlarm OBJECT-TYPE
    SYNTAX  OBJECT IDENTIFIER
    ACCESS  read-only
    STATUS  mandatory
    DESCRIPTION
        "The digital input 75 has been activated."
    ::= { falconWellKnownAlarms  3190 }

falconInput76DigAlarm OBJECT-TYPE
    SYNTAX  OBJECT IDENTIFIER
    ACCESS  read-only
    STATUS  mandatory
    DESCRIPTION
        "The digital input 76 has been activated."
    ::= { falconWellKnownAlarms  3200 }

falconInput77DigAlarm OBJECT-TYPE
    SYNTAX  OBJECT IDENTIFIER
    ACCESS  read-only
    STATUS  mandatory
    DESCRIPTION
        "The digital input 77 has been activated."
    ::= { falconWellKnownAlarms  3210 }

falconInput78DigAlarm OBJECT-TYPE
    SYNTAX  OBJECT IDENTIFIER
    ACCESS  read-only
    STATUS  mandatory
    DESCRIPTION
        "The digital input 78 has been activated."
    ::= { falconWellKnownAlarms  3220 }

falconInput79DigAlarm OBJECT-TYPE
    SYNTAX  OBJECT IDENTIFIER
    ACCESS  read-only
    STATUS  mandatory
    DESCRIPTION
        "The digital input 79 has been activated."
    ::= { falconWellKnownAlarms  3230 }

falconInput80DigAlarm OBJECT-TYPE
    SYNTAX  OBJECT IDENTIFIER
    ACCESS  read-only
    STATUS  mandatory
    DESCRIPTION
        "The digital input 80 has been activated."
    ::= { falconWellKnownAlarms  3240 }

falconInput81DigAlarm OBJECT-TYPE
    SYNTAX  OBJECT IDENTIFIER
    ACCESS  read-only
    STATUS  mandatory
    DESCRIPTION
        "The digital input 81 has been activated."
    ::= { falconWellKnownAlarms  4010 }

falconInput81HighAlarm OBJECT-TYPE
    SYNTAX  OBJECT IDENTIFIER
    ACCESS  read-only
    STATUS  mandatory
    DESCRIPTION
        "The reading for sensor 81 has reached the high limit
        value."
    ::= { falconWellKnownAlarms  4011 }

falconInput81LowAlarm OBJECT-TYPE
    SYNTAX  OBJECT IDENTIFIER
    ACCESS  read-only
    STATUS  mandatory
    DESCRIPTION
        "The reading for sensor 81 has reached the low limit
        value."
    ::= { falconWellKnownAlarms  4012 }

falconInput81High2Alarm OBJECT-TYPE
    SYNTAX  OBJECT IDENTIFIER
    ACCESS  read-only
    STATUS  mandatory
    DESCRIPTION
        "The reading for sensor 81 has reached the high limit
        value."
    ::= { falconWellKnownAlarms  4013 }

falconInput81Low2Alarm OBJECT-TYPE
    SYNTAX  OBJECT IDENTIFIER
    ACCESS  read-only
    STATUS  mandatory
    DESCRIPTION
        "The reading for sensor 81 has reached the low limit
        value."
    ::= { falconWellKnownAlarms  4014 }

falconInput82DigAlarm OBJECT-TYPE
    SYNTAX  OBJECT IDENTIFIER
    ACCESS  read-only
    STATUS  mandatory
    DESCRIPTION
        "The digital input 82 has been activated."
    ::= { falconWellKnownAlarms  4020 }

falconInput82HighAlarm OBJECT-TYPE
    SYNTAX  OBJECT IDENTIFIER
    ACCESS  read-only
    STATUS  mandatory
    DESCRIPTION
        "The reading for sensor 82 has reached the high limit
        value."
    ::= { falconWellKnownAlarms  4021 }

falconInput82LowAlarm OBJECT-TYPE
    SYNTAX  OBJECT IDENTIFIER
    ACCESS  read-only
    STATUS  mandatory
    DESCRIPTION
        "The reading for sensor 82 has reached the low limit
        value."
    ::= { falconWellKnownAlarms  4022 }

falconInput82High2Alarm OBJECT-TYPE
    SYNTAX  OBJECT IDENTIFIER
    ACCESS  read-only
    STATUS  mandatory
    DESCRIPTION
        "The reading for sensor 82 has reached the high limit
        value."
    ::= { falconWellKnownAlarms  4023 }

falconInput82Low2Alarm OBJECT-TYPE
    SYNTAX  OBJECT IDENTIFIER
    ACCESS  read-only
    STATUS  mandatory
    DESCRIPTION
        "The reading for sensor 82 has reached the low limit
        value."
    ::= { falconWellKnownAlarms  4024 }

falconInput83DigAlarm OBJECT-TYPE
    SYNTAX  OBJECT IDENTIFIER
    ACCESS  read-only
    STATUS  mandatory
    DESCRIPTION
        "The digital input 83 has been activated."
    ::= { falconWellKnownAlarms  4030 }

falconInput83HighAlarm OBJECT-TYPE
    SYNTAX  OBJECT IDENTIFIER
    ACCESS  read-only
    STATUS  mandatory
    DESCRIPTION
        "The reading for sensor 83 has reached the high limit
        value."
    ::= { falconWellKnownAlarms  4031 }

falconInput83LowAlarm OBJECT-TYPE
    SYNTAX  OBJECT IDENTIFIER
    ACCESS  read-only
    STATUS  mandatory
    DESCRIPTION
        "The reading for sensor 83 has reached the low limit
        value."
    ::= { falconWellKnownAlarms  4032 }

falconInput83High2Alarm OBJECT-TYPE
    SYNTAX  OBJECT IDENTIFIER
    ACCESS  read-only
    STATUS  mandatory
    DESCRIPTION
        "The reading for sensor 83 has reached the high limit
        value."
    ::= { falconWellKnownAlarms  4033 }

falconInput83Low2Alarm OBJECT-TYPE
    SYNTAX  OBJECT IDENTIFIER
    ACCESS  read-only
    STATUS  mandatory
    DESCRIPTION
        "The reading for sensor 83 has reached the low limit
        value."
    ::= { falconWellKnownAlarms  4034 }

falconInput84DigAlarm OBJECT-TYPE
    SYNTAX  OBJECT IDENTIFIER
    ACCESS  read-only
    STATUS  mandatory
    DESCRIPTION
        "The digital input 84 has been activated."
    ::= { falconWellKnownAlarms  4040 }

falconInput84HighAlarm OBJECT-TYPE
    SYNTAX  OBJECT IDENTIFIER
    ACCESS  read-only
    STATUS  mandatory
    DESCRIPTION
        "The reading for sensor 84 has reached the high limit
        value."
    ::= { falconWellKnownAlarms  4041 }

falconInput84LowAlarm OBJECT-TYPE
    SYNTAX  OBJECT IDENTIFIER
    ACCESS  read-only
    STATUS  mandatory
    DESCRIPTION
        "The reading for sensor 84 has reached the low limit
        value."
    ::= { falconWellKnownAlarms  4042 }

falconInput84High2Alarm OBJECT-TYPE
    SYNTAX  OBJECT IDENTIFIER
    ACCESS  read-only
    STATUS  mandatory
    DESCRIPTION
        "The reading for sensor 84 has reached the high limit
        value."
    ::= { falconWellKnownAlarms  4043 }

falconInput84Low2Alarm OBJECT-TYPE
    SYNTAX  OBJECT IDENTIFIER
    ACCESS  read-only
    STATUS  mandatory
    DESCRIPTION
        "The reading for sensor 84 has reached the low limit
        value."
    ::= { falconWellKnownAlarms  4044 }

falconInput85DigAlarm OBJECT-TYPE
    SYNTAX  OBJECT IDENTIFIER
    ACCESS  read-only
    STATUS  mandatory
    DESCRIPTION
        "The digital input 85 has been activated."
    ::= { falconWellKnownAlarms  4050 }

falconInput85HighAlarm OBJECT-TYPE
    SYNTAX  OBJECT IDENTIFIER
    ACCESS  read-only
    STATUS  mandatory
    DESCRIPTION
        "The reading for sensor 85 has reached the high limit
        value."
    ::= { falconWellKnownAlarms  4051 }

falconInput85LowAlarm OBJECT-TYPE
    SYNTAX  OBJECT IDENTIFIER
    ACCESS  read-only
    STATUS  mandatory
    DESCRIPTION
        "The reading for sensor 85 has reached the low limit
        value."
    ::= { falconWellKnownAlarms  4052 }

falconInput85High2Alarm OBJECT-TYPE
    SYNTAX  OBJECT IDENTIFIER
    ACCESS  read-only
    STATUS  mandatory
    DESCRIPTION
        "The reading for sensor 85 has reached the high limit
        value."
    ::= { falconWellKnownAlarms  4053 }

falconInput85Low2Alarm OBJECT-TYPE
    SYNTAX  OBJECT IDENTIFIER
    ACCESS  read-only
    STATUS  mandatory
    DESCRIPTION
        "The reading for sensor 85 has reached the low limit
        value."
    ::= { falconWellKnownAlarms  4054 }

falconInput86DigAlarm OBJECT-TYPE
    SYNTAX  OBJECT IDENTIFIER
    ACCESS  read-only
    STATUS  mandatory
    DESCRIPTION
        "The digital input 86 has been activated."
    ::= { falconWellKnownAlarms  4060 }

falconInput86HighAlarm OBJECT-TYPE
    SYNTAX  OBJECT IDENTIFIER
    ACCESS  read-only
    STATUS  mandatory
    DESCRIPTION
        "The reading for sensor 86 has reached the high limit
        value."
    ::= { falconWellKnownAlarms  4061 }

falconInput86LowAlarm OBJECT-TYPE
    SYNTAX  OBJECT IDENTIFIER
    ACCESS  read-only
    STATUS  mandatory
    DESCRIPTION
        "The reading for sensor 86 has reached the low limit
        value."
    ::= { falconWellKnownAlarms  4062 }

falconInput86High2Alarm OBJECT-TYPE
    SYNTAX  OBJECT IDENTIFIER
    ACCESS  read-only
    STATUS  mandatory
    DESCRIPTION
        "The reading for sensor 86 has reached the high limit
        value."
    ::= { falconWellKnownAlarms  4063 }

falconInput86Low2Alarm OBJECT-TYPE
    SYNTAX  OBJECT IDENTIFIER
    ACCESS  read-only
    STATUS  mandatory
    DESCRIPTION
        "The reading for sensor 86 has reached the low limit
        value."
    ::= { falconWellKnownAlarms  4064 }

falconInput87DigAlarm OBJECT-TYPE
    SYNTAX  OBJECT IDENTIFIER
    ACCESS  read-only
    STATUS  mandatory
    DESCRIPTION
        "The digital input 87 has been activated."
    ::= { falconWellKnownAlarms  4070 }

falconInput87HighAlarm OBJECT-TYPE
    SYNTAX  OBJECT IDENTIFIER
    ACCESS  read-only
    STATUS  mandatory
    DESCRIPTION
        "The reading for sensor 87 has reached the high limit
        value."
    ::= { falconWellKnownAlarms  4071 }

falconInput87LowAlarm OBJECT-TYPE
    SYNTAX  OBJECT IDENTIFIER
    ACCESS  read-only
    STATUS  mandatory
    DESCRIPTION
        "The reading for sensor 87 has reached the low limit
        value."
    ::= { falconWellKnownAlarms  4072 }

falconInput87High2Alarm OBJECT-TYPE
    SYNTAX  OBJECT IDENTIFIER
    ACCESS  read-only
    STATUS  mandatory
    DESCRIPTION
        "The reading for sensor 87 has reached the high limit
        value."
    ::= { falconWellKnownAlarms  4073 }

falconInput87Low2Alarm OBJECT-TYPE
    SYNTAX  OBJECT IDENTIFIER
    ACCESS  read-only
    STATUS  mandatory
    DESCRIPTION
        "The reading for sensor 87 has reached the low limit
        value."
    ::= { falconWellKnownAlarms  4074 }

falconInput88DigAlarm OBJECT-TYPE
    SYNTAX  OBJECT IDENTIFIER
    ACCESS  read-only
    STATUS  mandatory
    DESCRIPTION
        "The digital input 88 has been activated."
    ::= { falconWellKnownAlarms  4080 }

falconInput88HighAlarm OBJECT-TYPE
    SYNTAX  OBJECT IDENTIFIER
    ACCESS  read-only
    STATUS  mandatory
    DESCRIPTION
        "The reading for sensor 88 has reached the high limit
        value."
    ::= { falconWellKnownAlarms  4081 }

falconInput88LowAlarm OBJECT-TYPE
    SYNTAX  OBJECT IDENTIFIER
    ACCESS  read-only
    STATUS  mandatory
    DESCRIPTION
        "The reading for sensor 88 has reached the low limit
        value."
    ::= { falconWellKnownAlarms  4082 }

falconInput88High2Alarm OBJECT-TYPE
    SYNTAX  OBJECT IDENTIFIER
    ACCESS  read-only
    STATUS  mandatory
    DESCRIPTION
        "The reading for sensor 88 has reached the high limit
        value."
    ::= { falconWellKnownAlarms  4083 }

falconInput88Low2Alarm OBJECT-TYPE
    SYNTAX  OBJECT IDENTIFIER
    ACCESS  read-only
    STATUS  mandatory
    DESCRIPTION
        "The reading for sensor 88 has reached the low limit
        value."
    ::= { falconWellKnownAlarms  4084 }

falconInput89DigAlarm OBJECT-TYPE
    SYNTAX  OBJECT IDENTIFIER
    ACCESS  read-only
    STATUS  mandatory
    DESCRIPTION
        "The digital input 89 has been activated."
    ::= { falconWellKnownAlarms  4090 }

falconInput89HighAlarm OBJECT-TYPE
    SYNTAX  OBJECT IDENTIFIER
    ACCESS  read-only
    STATUS  mandatory
    DESCRIPTION
        "The reading for sensor 89 has reached the high limit
        value."
    ::= { falconWellKnownAlarms  4091 }

falconInput89LowAlarm OBJECT-TYPE
    SYNTAX  OBJECT IDENTIFIER
    ACCESS  read-only
    STATUS  mandatory
    DESCRIPTION
        "The reading for sensor 89 has reached the low limit
        value."
    ::= { falconWellKnownAlarms  4092 }

falconInput89High2Alarm OBJECT-TYPE
    SYNTAX  OBJECT IDENTIFIER
    ACCESS  read-only
    STATUS  mandatory
    DESCRIPTION
        "The reading for sensor 89 has reached the high limit
        value."
    ::= { falconWellKnownAlarms  4093 }

falconInput89Low2Alarm OBJECT-TYPE
    SYNTAX  OBJECT IDENTIFIER
    ACCESS  read-only
    STATUS  mandatory
    DESCRIPTION
        "The reading for sensor 89 has reached the low limit
        value."
    ::= { falconWellKnownAlarms  4094 }

falconInput90DigAlarm OBJECT-TYPE
    SYNTAX  OBJECT IDENTIFIER
    ACCESS  read-only
    STATUS  mandatory
    DESCRIPTION
        "The digital input 90 has been activated."
    ::= { falconWellKnownAlarms  4100 }

falconInput90HighAlarm OBJECT-TYPE
    SYNTAX  OBJECT IDENTIFIER
    ACCESS  read-only
    STATUS  mandatory
    DESCRIPTION
        "The reading for sensor 90 has reached the high limit
        value."
    ::= { falconWellKnownAlarms  4101 }

falconInput90LowAlarm OBJECT-TYPE
    SYNTAX  OBJECT IDENTIFIER
    ACCESS  read-only
    STATUS  mandatory
    DESCRIPTION
        "The reading for sensor 90 has reached the low limit
        value."
    ::= { falconWellKnownAlarms  4102 }

falconInput90High2Alarm OBJECT-TYPE
    SYNTAX  OBJECT IDENTIFIER
    ACCESS  read-only
    STATUS  mandatory
    DESCRIPTION
        "The reading for sensor 90 has reached the high limit
        value."
    ::= { falconWellKnownAlarms  4103 }

falconInput90Low2Alarm OBJECT-TYPE
    SYNTAX  OBJECT IDENTIFIER
    ACCESS  read-only
    STATUS  mandatory
    DESCRIPTION
        "The reading for sensor 90 has reached the low limit
        value."
    ::= { falconWellKnownAlarms  4104 }

falconInput91DigAlarm OBJECT-TYPE
    SYNTAX  OBJECT IDENTIFIER
    ACCESS  read-only
    STATUS  mandatory
    DESCRIPTION
        "The digital input 91 has been activated."
    ::= { falconWellKnownAlarms  4110 }

falconInput91HighAlarm OBJECT-TYPE
    SYNTAX  OBJECT IDENTIFIER
    ACCESS  read-only
    STATUS  mandatory
    DESCRIPTION
        "The reading for sensor 91 has reached the high limit
        value."
    ::= { falconWellKnownAlarms  4111 }

falconInput91LowAlarm OBJECT-TYPE
    SYNTAX  OBJECT IDENTIFIER
    ACCESS  read-only
    STATUS  mandatory
    DESCRIPTION
        "The reading for sensor 91 has reached the low limit
        value."
    ::= { falconWellKnownAlarms  4112 }

falconInput91High2Alarm OBJECT-TYPE
    SYNTAX  OBJECT IDENTIFIER
    ACCESS  read-only
    STATUS  mandatory
    DESCRIPTION
        "The reading for sensor 91 has reached the high limit
        value."
    ::= { falconWellKnownAlarms  4113 }

falconInput91Low2Alarm OBJECT-TYPE
    SYNTAX  OBJECT IDENTIFIER
    ACCESS  read-only
    STATUS  mandatory
    DESCRIPTION
        "The reading for sensor 91 has reached the low limit
        value."
    ::= { falconWellKnownAlarms  4114 }

falconInput92DigAlarm OBJECT-TYPE
    SYNTAX  OBJECT IDENTIFIER
    ACCESS  read-only
    STATUS  mandatory
    DESCRIPTION
        "The digital input 92 has been activated."
    ::= { falconWellKnownAlarms  4120 }

falconInput92HighAlarm OBJECT-TYPE
    SYNTAX  OBJECT IDENTIFIER
    ACCESS  read-only
    STATUS  mandatory
    DESCRIPTION
        "The reading for sensor 92 has reached the high limit
        value."
    ::= { falconWellKnownAlarms  4121 }

falconInput92LowAlarm OBJECT-TYPE
    SYNTAX  OBJECT IDENTIFIER
    ACCESS  read-only
    STATUS  mandatory
    DESCRIPTION
        "The reading for sensor 92 has reached the low limit
        value."
    ::= { falconWellKnownAlarms  4122 }

falconInput92High2Alarm OBJECT-TYPE
    SYNTAX  OBJECT IDENTIFIER
    ACCESS  read-only
    STATUS  mandatory
    DESCRIPTION
        "The reading for sensor 92 has reached the high limit
        value."
    ::= { falconWellKnownAlarms  4123 }

falconInput92Low2Alarm OBJECT-TYPE
    SYNTAX  OBJECT IDENTIFIER
    ACCESS  read-only
    STATUS  mandatory
    DESCRIPTION
        "The reading for sensor 92 has reached the low limit
        value."
    ::= { falconWellKnownAlarms  4124 }

falconInput93DigAlarm OBJECT-TYPE
    SYNTAX  OBJECT IDENTIFIER
    ACCESS  read-only
    STATUS  mandatory
    DESCRIPTION
        "The digital input 93 has been activated."
    ::= { falconWellKnownAlarms  4130 }

falconInput94DigAlarm OBJECT-TYPE
    SYNTAX  OBJECT IDENTIFIER
    ACCESS  read-only
    STATUS  mandatory
    DESCRIPTION
        "The digital input 94 has been activated."
    ::= { falconWellKnownAlarms  4140 }

falconInput95DigAlarm OBJECT-TYPE
    SYNTAX  OBJECT IDENTIFIER
    ACCESS  read-only
    STATUS  mandatory
    DESCRIPTION
        "The digital input 95 has been activated."
    ::= { falconWellKnownAlarms  4150 }

falconInput96DigAlarm OBJECT-TYPE
    SYNTAX  OBJECT IDENTIFIER
    ACCESS  read-only
    STATUS  mandatory
    DESCRIPTION
        "The digital input 96 has been activated."
    ::= { falconWellKnownAlarms  4160 }

falconInput97DigAlarm OBJECT-TYPE
    SYNTAX  OBJECT IDENTIFIER
    ACCESS  read-only
    STATUS  mandatory
    DESCRIPTION
        "The digital input 97 has been activated."
    ::= { falconWellKnownAlarms  4170 }

falconInput98DigAlarm OBJECT-TYPE
    SYNTAX  OBJECT IDENTIFIER
    ACCESS  read-only
    STATUS  mandatory
    DESCRIPTION
        "The digital input 98 has been activated."
    ::= { falconWellKnownAlarms  4180 }

falconInput99DigAlarm OBJECT-TYPE
    SYNTAX  OBJECT IDENTIFIER
    ACCESS  read-only
    STATUS  mandatory
    DESCRIPTION
        "The digital input 99 has been activated."
    ::= { falconWellKnownAlarms  4190 }

falconInput100DigAlarm OBJECT-TYPE
    SYNTAX  OBJECT IDENTIFIER
    ACCESS  read-only
    STATUS  mandatory
    DESCRIPTION
        "The digital input 100 has been activated."
    ::= { falconWellKnownAlarms  4200 }

falconInput101DigAlarm OBJECT-TYPE
    SYNTAX  OBJECT IDENTIFIER
    ACCESS  read-only
    STATUS  mandatory
    DESCRIPTION
        "The digital input 101 has been activated."
    ::= { falconWellKnownAlarms  4210 }

falconInput102DigAlarm OBJECT-TYPE
    SYNTAX  OBJECT IDENTIFIER
    ACCESS  read-only
    STATUS  mandatory
    DESCRIPTION
        "The digital input 102 has been activated."
    ::= { falconWellKnownAlarms  4220 }

falconInput103DigAlarm OBJECT-TYPE
    SYNTAX  OBJECT IDENTIFIER
    ACCESS  read-only
    STATUS  mandatory
    DESCRIPTION
        "The digital input 103 has been activated."
    ::= { falconWellKnownAlarms  4230 }

falconInput104DigAlarm OBJECT-TYPE
    SYNTAX  OBJECT IDENTIFIER
    ACCESS  read-only
    STATUS  mandatory
    DESCRIPTION
        "The digital input 104 has been activated."
    ::= { falconWellKnownAlarms  4240 }

falconTemperatureSensorHighAlarm OBJECT-TYPE
    SYNTAX  OBJECT IDENTIFIER
    ACCESS  read-only
    STATUS  mandatory
    DESCRIPTION
        "The reading for internal temperature sensor has reached the high limit
        value."
    ::= { falconWellKnownAlarms  5011 }

falconTemperatureSensorLowAlarm OBJECT-TYPE
    SYNTAX  OBJECT IDENTIFIER
    ACCESS  read-only
    STATUS  mandatory
    DESCRIPTION
        "The reading for internal temperature sensor has reached the low limit
        value."
    ::= { falconWellKnownAlarms  5012 }

falconTemperatureSensorHigh2Alarm OBJECT-TYPE
    SYNTAX  OBJECT IDENTIFIER
    ACCESS  read-only
    STATUS  mandatory
    DESCRIPTION
        "The reading for internal temperature sensor has reached the high limit
        value."
    ::= { falconWellKnownAlarms  5013 }

falconTemperatureSensorLow2Alarm OBJECT-TYPE
    SYNTAX  OBJECT IDENTIFIER
    ACCESS  read-only
    STATUS  mandatory
    DESCRIPTION
        "The reading for internal temperature sensor has reached the low limit
        value."
    ::= { falconWellKnownAlarms  5014 }

falconHumiditySensorHighAlarm OBJECT-TYPE
    SYNTAX  OBJECT IDENTIFIER
    ACCESS  read-only
    STATUS  mandatory
    DESCRIPTION
        "The reading for internal humidity sensor has reached the high limit
        value."
    ::= { falconWellKnownAlarms  5021 }

falconHumiditySensorLowAlarm OBJECT-TYPE
    SYNTAX  OBJECT IDENTIFIER
    ACCESS  read-only
    STATUS  mandatory
    DESCRIPTION
        "The reading for internal humidity sensor has reached the low limit
        value."
    ::= { falconWellKnownAlarms  5022 }

falconHumiditySensorHigh2Alarm OBJECT-TYPE
    SYNTAX  OBJECT IDENTIFIER
    ACCESS  read-only
    STATUS  mandatory
    DESCRIPTION
        "The reading for internal humidity sensor has reached the high limit
        value."
    ::= { falconWellKnownAlarms  5023 }

falconHumiditySensorLow2Alarm OBJECT-TYPE
    SYNTAX  OBJECT IDENTIFIER
    ACCESS  read-only
    STATUS  mandatory
    DESCRIPTION
        "The reading for internal humidity sensor has reached the low limit
        value."
    ::= { falconWellKnownAlarms  5024 }

falconLowBatteryAlarm OBJECT-TYPE
    SYNTAX  OBJECT IDENTIFIER
    ACCESS  read-only
    STATUS  mandatory
    DESCRIPTION
        "The Faclon has detected a low battery condition."
    ::= { falconWellKnownAlarms  6010 }

falconTraps OBJECT IDENTIFIER ::= { falcon-emMIB  6 }

falconAlarmEntryAdded TRAP-TYPE
    ENTERPRISE   falconTraps 
    DESCRIPTION
           "An AlarmEntryAdded Trap signifies that the a sensor
            reading has reached a high or low limit value."
    ::= 1

falconAlarmEntryRemoved TRAP-TYPE
    ENTERPRISE   falconTraps 
    DESCRIPTION
           "An AlarmEntryAdded Trap signifies that the a sensor
            reading has gone below the high limit value or above
            the low limit value."
    ::= 2

falconAccessGranted TRAP-TYPE
    ENTERPRISE   falconTraps 
    DESCRIPTION
           "An falconAccessGranted Trap signifies that a valid
            key code sequence was processed by the falcon."
    ::= 3

falconAccessDenied TRAP-TYPE
    ENTERPRISE   falconTraps 
    DESCRIPTION
           "An falconAccessedDenied Trap signifies that an invalid
            key code sequence was processed by the falcon."
    ::= 4

falconPageUnsuccessful TRAP-TYPE
    ENTERPRISE   falconTraps 
    DESCRIPTION
           "An falconPageUnsuccessful Trap signifies that an alpha
            numeric page could not be sent to the service."
    ::= 5

falconAlarmHistory OBJECT IDENTIFIER ::= { falcon-emMIB  7 }

falconAlarmHistoryEntries OBJECT-TYPE
    SYNTAX     Gauge
    ACCESS read-only
    STATUS     mandatory
    DESCRIPTION
        "The present number of entries in the alarm history."
    ::= { falconAlarmHistory 1 }

falconAlarmHistoryClear OBJECT-TYPE
    SYNTAX  INTEGER {
    clearBuffer(1)
}
    ACCESS  read-write
    STATUS  mandatory
    DESCRIPTION
           "Setting this value to ClearBuffer(1) will clear the
            alarm history buffer. "
    ::= { falconAlarmHistory 2 }

falconAlarmHistoryTable OBJECT-TYPE
    SYNTAX     SEQUENCE OF FalconAlarmHistoryEntry
    ACCESS not-accessible
    STATUS     mandatory
    DESCRIPTION
       "A list of alarm history table entries stored in the
        in the non-volatile memory.  The table contains zero,
        one, or many rows at any moment, depending upon the
        number of alarm conditions in effect. The falcon creates
        a row in the table each time a new alarm is detected.
        The falcon creates the first row with falconAlarmHistoryId
        equal to 1, and increments the value of falconAlarmHistoryId
        each time a new row is created, up to a maximum of 100.
        After 100 entries are created, the falcon will overwrite
        the earliest entry with the latest alarm.
        The number of rows in the table at any given time is
        reflected by the value of falconAlarmHistoryEntries."
    ::= { falconAlarmHistory 3 }

falconAlarmHistoryEntry OBJECT-TYPE
    SYNTAX     FalconAlarmHistoryEntry
    ACCESS     not-accessible
    STATUS     mandatory
    DESCRIPTION
         "An entry containing information applicable to a
         particular alarm history entry."
   INDEX { falconAlarmHistoryId }
   ::= { falconAlarmHistoryTable 1 }

FalconAlarmHistoryEntry ::= SEQUENCE {
    falconAlarmHistoryId     PositiveInteger,
    falconAlarmHistoryText   DisplayString
}

falconAlarmHistoryId OBJECT-TYPE
    SYNTAX     PositiveInteger
    ACCESS not-accessible
    STATUS     mandatory
    DESCRIPTION
         "A unique identifier for an alarm condition.  This
          value must remain constant."
    ::= { falconAlarmHistoryEntry 1 }

falconAlarmHistoryText OBJECT-TYPE
    SYNTAX     DisplayString
    ACCESS read-only
    STATUS     mandatory
    DESCRIPTION
        "A text desciption of the alarm history entry.
         Each of the strings will have the following format,
         AHxxx-id-type-timestamp label
         xxx  = number entry in the table
         id   = Alarm ID
         type = HIGH, LOW, ALM or RTN
         timestamp = MM/DD/YY HH:MM:SS
         Label = The label associated with the input channel"
    ::= { falconAlarmHistoryEntry 2 }

falconTrapSettings OBJECT IDENTIFIER ::= { falcon-emMIB  8 }

falconPersistantTraps OBJECT-TYPE
    SYNTAX  INTEGER (0..2147483647)
    ACCESS read-write
    STATUS     mandatory
    DESCRIPTION
        "The number of minutes between persistant traps.
         Set this to 0 to turn off persistant traps."
    ::= { falconTrapSettings 1 }

falconAlarmAcknowledge OBJECT-TYPE
    SYNTAX  INTEGER {
    acknowledgeAlarms(1)
}
    ACCESS  read-write
    STATUS  mandatory
    DESCRIPTION
           "Setting this value to AcknowledgeAlarms(1) will
            stop the falcon from sending persistant traps
            and dial out sequences."
    ::= { falconTrapSettings 2 }

falconSchedules OBJECT IDENTIFIER ::= { falcon-emMIB  9 }

falconScheduleABeginDOW OBJECT-TYPE
    SYNTAX  INTEGER {
    sunday(1),
    monday(2),
    tuesday(3),
    wednesday(4),
    thursday(5),
    friday(6),
    saturday(7)
}
    ACCESS  read-write
    STATUS  mandatory
    DESCRIPTION
           "The beginning day of the week for schedule A."
    ::= { falconSchedules  1 }

falconScheduleAEndDOW OBJECT-TYPE
    SYNTAX  INTEGER {
    sunday(1),
    monday(2),
    tuesday(3),
    wednesday(4),
    thursday(5),
    friday(6),
    saturday(7)
}
    ACCESS  read-write
    STATUS  mandatory
    DESCRIPTION
           "The ending day of the week for schedule A."
    ::= { falconSchedules  2 }

falconScheduleABeginTime OBJECT-TYPE
    SYNTAX  DisplayString
    ACCESS  read-write
    STATUS  mandatory
    DESCRIPTION
           "The schedule A beginning time of day.
            Displayed as HH:MM"
    ::= { falconSchedules  3 }

falconScheduleAEndTime OBJECT-TYPE
    SYNTAX  DisplayString
    ACCESS  read-write
    STATUS  mandatory
    DESCRIPTION
           "The schedule A ending time of day.
            Displayed as HH:MM"
    ::= { falconSchedules  4 }

falconScheduleBBeginDOW OBJECT-TYPE
    SYNTAX  INTEGER {
    sunday(1),
    monday(2),
    tuesday(3),
    wednesday(4),
    thursday(5),
    friday(6),
    saturday(7)
}
    ACCESS  read-write
    STATUS  mandatory
    DESCRIPTION
           "The beginning day of the week for schedule B."
    ::= { falconSchedules  5 }

falconScheduleBEndDOW OBJECT-TYPE
    SYNTAX  INTEGER {
    sunday(1),
    monday(2),
    tuesday(3),
    wednesday(4),
    thursday(5),
    friday(6),
    saturday(7)
}
    ACCESS  read-write
    STATUS  mandatory
    DESCRIPTION
           "The ending day of the week for schedule B."
    ::= { falconSchedules  6 }

falconScheduleBBeginTime OBJECT-TYPE
    SYNTAX  DisplayString
    ACCESS  read-write
    STATUS  mandatory
    DESCRIPTION
           "The schedule B beginning time of day.
            Displayed as HH:MM"
    ::= { falconSchedules  7 }

falconScheduleBEndTime OBJECT-TYPE
    SYNTAX  DisplayString
    ACCESS  read-write
    STATUS  mandatory
    DESCRIPTION
           "The schedule B ending time of day.
            Displayed as HH:MM"
    ::= { falconSchedules  8 }

falconPortTrap OBJECT IDENTIFIER ::= { falcon-emMIB  10 }

falconPort01Trap TRAP-TYPE
    ENTERPRISE   falconPortTrap 
    VARIABLES {
        falconAlarmId,
        falconAlarmDescr,
        falconInputLabel,
        falconInputReading,
        falconInputUOM
    }
    DESCRIPTION
        "The sensor on port #01 has reached an alarm state."
    ::= 1

falconPort02Trap TRAP-TYPE
    ENTERPRISE   falconPortTrap 
    VARIABLES {
        falconAlarmId,
        falconAlarmDescr,
        falconInputLabel,
        falconInputReading,
        falconInputUOM
    }
    DESCRIPTION
        "The sensor on port #02 has reached an alarm state."
    ::= 2

falconPort03Trap TRAP-TYPE
    ENTERPRISE   falconPortTrap 
    VARIABLES {
        falconAlarmId,
        falconAlarmDescr,
        falconInputLabel,
        falconInputReading,
        falconInputUOM
    }
    DESCRIPTION
        "The sensor on port #03 has reached an alarm state."
    ::= 3

falconPort04Trap TRAP-TYPE
    ENTERPRISE   falconPortTrap 
    VARIABLES {
        falconAlarmId,
        falconAlarmDescr,
        falconInputLabel,
        falconInputReading,
        falconInputUOM
    }
    DESCRIPTION
        "The sensor on port #04 has reached an alarm state."
    ::= 4

falconPort05Trap TRAP-TYPE
    ENTERPRISE   falconPortTrap 
    VARIABLES {
        falconAlarmId,
        falconAlarmDescr,
        falconInputLabel,
        falconInputReading,
        falconInputUOM
    }
    DESCRIPTION
        "The sensor on port #05 has reached an alarm state."
    ::= 5

falconPort06Trap TRAP-TYPE
    ENTERPRISE   falconPortTrap 
    VARIABLES {
        falconAlarmId,
        falconAlarmDescr,
        falconInputLabel,
        falconInputReading,
        falconInputUOM
    }
    DESCRIPTION
        "The sensor on port #06 has reached an alarm state."
    ::= 6

falconPort07Trap TRAP-TYPE
    ENTERPRISE   falconPortTrap 
    VARIABLES {
        falconAlarmId,
        falconAlarmDescr,
        falconInputLabel,
        falconInputReading,
        falconInputUOM
    }
    DESCRIPTION
        "The sensor on port #07 has reached an alarm state."
    ::= 7

falconPort08Trap TRAP-TYPE
    ENTERPRISE   falconPortTrap 
    VARIABLES {
        falconAlarmId,
        falconAlarmDescr,
        falconInputLabel,
        falconInputReading,
        falconInputUOM
    }
    DESCRIPTION
        "The sensor on port #08 has reached an alarm state."
    ::= 8

falconPort09Trap TRAP-TYPE
    ENTERPRISE   falconPortTrap 
    VARIABLES {
        falconAlarmId,
        falconAlarmDescr,
        falconInputLabel,
        falconInputReading,
        falconInputUOM
    }
    DESCRIPTION
        "The sensor on port #09 has reached an alarm state."
    ::= 9

falconPort10Trap TRAP-TYPE
    ENTERPRISE   falconPortTrap 
    VARIABLES {
        falconAlarmId,
        falconAlarmDescr,
        falconInputLabel,
        falconInputReading,
        falconInputUOM
    }
    DESCRIPTION
        "The sensor on port #10 has reached an alarm state."
    ::= 10

falconPort11Trap TRAP-TYPE
    ENTERPRISE   falconPortTrap 
    VARIABLES {
        falconAlarmId,
        falconAlarmDescr,
        falconInputLabel,
        falconInputReading,
        falconInputUOM
    }
    DESCRIPTION
        "The sensor on port #11 has reached an alarm state."
    ::= 11

falconPort12Trap TRAP-TYPE
    ENTERPRISE   falconPortTrap 
    VARIABLES {
        falconAlarmId,
        falconAlarmDescr,
        falconInputLabel,
        falconInputReading,
        falconInputUOM
    }
    DESCRIPTION
        "The sensor on port #12 has reached an alarm state."
    ::= 12

falconPort13Trap TRAP-TYPE
    ENTERPRISE   falconPortTrap 
    VARIABLES {
        falconAlarmId,
        falconAlarmDescr,
        falconInputLabel,
        falconInputReading,
        falconInputUOM
    }
    DESCRIPTION
        "The sensor on port #13 has reached an alarm state."
    ::= 13

falconPort14Trap TRAP-TYPE
    ENTERPRISE   falconPortTrap 
    VARIABLES {
        falconAlarmId,
        falconAlarmDescr,
        falconInputLabel,
        falconInputReading,
        falconInputUOM
    }
    DESCRIPTION
        "The sensor on port #14 has reached an alarm state."
    ::= 14

falconPort15Trap TRAP-TYPE
    ENTERPRISE   falconPortTrap 
    VARIABLES {
        falconAlarmId,
        falconAlarmDescr,
        falconInputLabel,
        falconInputReading,
        falconInputUOM
    }
    DESCRIPTION
        "The sensor on port #15 has reached an alarm state."
    ::= 15

falconPort16Trap TRAP-TYPE
    ENTERPRISE   falconPortTrap 
    VARIABLES {
        falconAlarmId,
        falconAlarmDescr,
        falconInputLabel,
        falconInputReading,
        falconInputUOM
    }
    DESCRIPTION
        "The sensor on port #16 has reached an alarm state."
    ::= 16

falconPort17Trap TRAP-TYPE
    ENTERPRISE   falconPortTrap 
    VARIABLES {
        falconAlarmId,
        falconAlarmDescr,
        falconInputLabel,
        falconInputReading,
        falconInputUOM
    }
    DESCRIPTION
        "The sensor on port #17 has reached an alarm state."
    ::= 17

falconPort18Trap TRAP-TYPE
    ENTERPRISE   falconPortTrap 
    VARIABLES {
        falconAlarmId,
        falconAlarmDescr,
        falconInputLabel,
        falconInputReading,
        falconInputUOM
    }
    DESCRIPTION
        "The sensor on port #18 has reached an alarm state."
    ::= 18

falconPort19Trap TRAP-TYPE
    ENTERPRISE   falconPortTrap 
    VARIABLES {
        falconAlarmId,
        falconAlarmDescr,
        falconInputLabel,
        falconInputReading,
        falconInputUOM
    }
    DESCRIPTION
        "The sensor on port #19 has reached an alarm state."
    ::= 19

falconPort20Trap TRAP-TYPE
    ENTERPRISE   falconPortTrap 
    VARIABLES {
        falconAlarmId,
        falconAlarmDescr,
        falconInputLabel,
        falconInputReading,
        falconInputUOM
    }
    DESCRIPTION
        "The sensor on port #20 has reached an alarm state."
    ::= 20

falconPort21Trap TRAP-TYPE
    ENTERPRISE   falconPortTrap 
    VARIABLES {
        falconAlarmId,
        falconAlarmDescr,
        falconInputLabel,
        falconInputReading,
        falconInputUOM
    }
    DESCRIPTION
        "The sensor on port #21 has reached an alarm state."
    ::= 21

falconPort22Trap TRAP-TYPE
    ENTERPRISE   falconPortTrap 
    VARIABLES {
        falconAlarmId,
        falconAlarmDescr,
        falconInputLabel,
        falconInputReading,
        falconInputUOM
    }
    DESCRIPTION
        "The sensor on port #22 has reached an alarm state."
    ::= 22

falconPort23Trap TRAP-TYPE
    ENTERPRISE   falconPortTrap 
    VARIABLES {
        falconAlarmId,
        falconAlarmDescr,
        falconInputLabel,
        falconInputReading,
        falconInputUOM
    }
    DESCRIPTION
        "The sensor on port #23 has reached an alarm state."
    ::= 23

falconPort24Trap TRAP-TYPE
    ENTERPRISE   falconPortTrap 
    VARIABLES {
        falconAlarmId,
        falconAlarmDescr,
        falconInputLabel,
        falconInputReading,
        falconInputUOM
    }
    DESCRIPTION
        "The sensor on port #24 has reached an alarm state."
    ::= 24

falconPort25Trap TRAP-TYPE
    ENTERPRISE   falconPortTrap 
    VARIABLES {
        falconAlarmId,
        falconAlarmDescr,
        falconInputLabel,
        falconInputReading,
        falconInputUOM
    }
    DESCRIPTION
        "The sensor on port #25 has reached an alarm state."
    ::= 25

falconPort26Trap TRAP-TYPE
    ENTERPRISE   falconPortTrap 
    VARIABLES {
        falconAlarmId,
        falconAlarmDescr,
        falconInputLabel,
        falconInputReading,
        falconInputUOM
    }
    DESCRIPTION
        "The sensor on port #26 has reached an alarm state."
    ::= 26

falconPort27Trap TRAP-TYPE
    ENTERPRISE   falconPortTrap 
    VARIABLES {
        falconAlarmId,
        falconAlarmDescr,
        falconInputLabel,
        falconInputReading,
        falconInputUOM
    }
    DESCRIPTION
        "The sensor on port #27 has reached an alarm state."
    ::= 27

falconPort28Trap TRAP-TYPE
    ENTERPRISE   falconPortTrap 
    VARIABLES {
        falconAlarmId,
        falconAlarmDescr,
        falconInputLabel,
        falconInputReading,
        falconInputUOM
    }
    DESCRIPTION
        "The sensor on port #28 has reached an alarm state."
    ::= 28

falconPort29Trap TRAP-TYPE
    ENTERPRISE   falconPortTrap 
    VARIABLES {
        falconAlarmId,
        falconAlarmDescr,
        falconInputLabel,
        falconInputReading,
        falconInputUOM
    }
    DESCRIPTION
        "The sensor on port #29 has reached an alarm state."
    ::= 29

falconPort30Trap TRAP-TYPE
    ENTERPRISE   falconPortTrap 
    VARIABLES {
        falconAlarmId,
        falconAlarmDescr,
        falconInputLabel,
        falconInputReading,
        falconInputUOM
    }
    DESCRIPTION
        "The sensor on port #30 has reached an alarm state."
    ::= 30

falconPort31Trap TRAP-TYPE
    ENTERPRISE   falconPortTrap 
    VARIABLES {
        falconAlarmId,
        falconAlarmDescr,
        falconInputLabel,
        falconInputReading,
        falconInputUOM
    }
    DESCRIPTION
        "The sensor on port #31 has reached an alarm state."
    ::= 31

falconPort32Trap TRAP-TYPE
    ENTERPRISE   falconPortTrap 
    VARIABLES {
        falconAlarmId,
        falconAlarmDescr,
        falconInputLabel,
        falconInputReading,
        falconInputUOM
    }
    DESCRIPTION
        "The sensor on port #32 has reached an alarm state."
    ::= 32

falconPort33Trap TRAP-TYPE
    ENTERPRISE   falconPortTrap 
    VARIABLES {
        falconAlarmId,
        falconAlarmDescr,
        falconInputLabel,
        falconInputReading,
        falconInputUOM
    }
    DESCRIPTION
        "The sensor on port #33 has reached an alarm state."
    ::= 33

falconPort34Trap TRAP-TYPE
    ENTERPRISE   falconPortTrap 
    VARIABLES {
        falconAlarmId,
        falconAlarmDescr,
        falconInputLabel,
        falconInputReading,
        falconInputUOM
    }
    DESCRIPTION
        "The sensor on port #34 has reached an alarm state."
    ::= 34

falconPort35Trap TRAP-TYPE
    ENTERPRISE   falconPortTrap 
    VARIABLES {
        falconAlarmId,
        falconAlarmDescr,
        falconInputLabel,
        falconInputReading,
        falconInputUOM
    }
    DESCRIPTION
        "The sensor on port #35 has reached an alarm state."
    ::= 35

falconPort36Trap TRAP-TYPE
    ENTERPRISE   falconPortTrap 
    VARIABLES {
        falconAlarmId,
        falconAlarmDescr,
        falconInputLabel,
        falconInputReading,
        falconInputUOM
    }
    DESCRIPTION
        "The sensor on port #36 has reached an alarm state."
    ::= 36

falconPort37Trap TRAP-TYPE
    ENTERPRISE   falconPortTrap 
    VARIABLES {
        falconAlarmId,
        falconAlarmDescr,
        falconInputLabel,
        falconInputReading,
        falconInputUOM
    }
    DESCRIPTION
        "The sensor on port #37 has reached an alarm state."
    ::= 37

falconPort38Trap TRAP-TYPE
    ENTERPRISE   falconPortTrap 
    VARIABLES {
        falconAlarmId,
        falconAlarmDescr,
        falconInputLabel,
        falconInputReading,
        falconInputUOM
    }
    DESCRIPTION
        "The sensor on port #38 has reached an alarm state."
    ::= 38

falconPort39Trap TRAP-TYPE
    ENTERPRISE   falconPortTrap 
    VARIABLES {
        falconAlarmId,
        falconAlarmDescr,
        falconInputLabel,
        falconInputReading,
        falconInputUOM
    }
    DESCRIPTION
        "The sensor on port #39 has reached an alarm state."
    ::= 39

falconPort40Trap TRAP-TYPE
    ENTERPRISE   falconPortTrap 
    VARIABLES {
        falconAlarmId,
        falconAlarmDescr,
        falconInputLabel,
        falconInputReading,
        falconInputUOM
    }
    DESCRIPTION
        "The sensor on port #40 has reached an alarm state."
    ::= 40

falconPort41Trap TRAP-TYPE
    ENTERPRISE   falconPortTrap 
    VARIABLES {
        falconAlarmId,
        falconAlarmDescr,
        falconInputLabel,
        falconInputReading,
        falconInputUOM
    }
    DESCRIPTION
        "The sensor on port #41 has reached an alarm state."
    ::= 41

falconPort42Trap TRAP-TYPE
    ENTERPRISE   falconPortTrap 
    VARIABLES {
        falconAlarmId,
        falconAlarmDescr,
        falconInputLabel,
        falconInputReading,
        falconInputUOM
    }
    DESCRIPTION
        "The sensor on port #42 has reached an alarm state."
    ::= 42

falconPort43Trap TRAP-TYPE
    ENTERPRISE   falconPortTrap 
    VARIABLES {
        falconAlarmId,
        falconAlarmDescr,
        falconInputLabel,
        falconInputReading,
        falconInputUOM
    }
    DESCRIPTION
        "The sensor on port #43 has reached an alarm state."
    ::= 43

falconPort44Trap TRAP-TYPE
    ENTERPRISE   falconPortTrap 
    VARIABLES {
        falconAlarmId,
        falconAlarmDescr,
        falconInputLabel,
        falconInputReading,
        falconInputUOM
    }
    DESCRIPTION
        "The sensor on port #44 has reached an alarm state."
    ::= 44

falconPort45Trap TRAP-TYPE
    ENTERPRISE   falconPortTrap 
    VARIABLES {
        falconAlarmId,
        falconAlarmDescr,
        falconInputLabel,
        falconInputReading,
        falconInputUOM
    }
    DESCRIPTION
        "The sensor on port #45 has reached an alarm state."
    ::= 45

falconPort46Trap TRAP-TYPE
    ENTERPRISE   falconPortTrap 
    VARIABLES {
        falconAlarmId,
        falconAlarmDescr,
        falconInputLabel,
        falconInputReading,
        falconInputUOM
    }
    DESCRIPTION
        "The sensor on port #46 has reached an alarm state."
    ::= 46

falconPort47Trap TRAP-TYPE
    ENTERPRISE   falconPortTrap 
    VARIABLES {
        falconAlarmId,
        falconAlarmDescr,
        falconInputLabel,
        falconInputReading,
        falconInputUOM
    }
    DESCRIPTION
        "The sensor on port #47 has reached an alarm state."
    ::= 47

falconPort48Trap TRAP-TYPE
    ENTERPRISE   falconPortTrap 
    VARIABLES {
        falconAlarmId,
        falconAlarmDescr,
        falconInputLabel,
        falconInputReading,
        falconInputUOM
    }
    DESCRIPTION
        "The sensor on port #48 has reached an alarm state."
    ::= 48

falconPort49Trap TRAP-TYPE
    ENTERPRISE   falconPortTrap 
    VARIABLES {
        falconAlarmId,
        falconAlarmDescr,
        falconInputLabel,
        falconInputReading,
        falconInputUOM
    }
    DESCRIPTION
        "The sensor on port #49 has reached an alarm state."
    ::= 49

falconPort50Trap TRAP-TYPE
    ENTERPRISE   falconPortTrap 
    VARIABLES {
        falconAlarmId,
        falconAlarmDescr,
        falconInputLabel,
        falconInputReading,
        falconInputUOM
    }
    DESCRIPTION
        "The sensor on port #50 has reached an alarm state."
    ::= 50

falconPort51Trap TRAP-TYPE
    ENTERPRISE   falconPortTrap 
    VARIABLES {
        falconAlarmId,
        falconAlarmDescr,
        falconInputLabel,
        falconInputReading,
        falconInputUOM
    }
    DESCRIPTION
        "The sensor on port #51 has reached an alarm state."
    ::= 51

falconPort52Trap TRAP-TYPE
    ENTERPRISE   falconPortTrap 
    VARIABLES {
        falconAlarmId,
        falconAlarmDescr,
        falconInputLabel,
        falconInputReading,
        falconInputUOM
    }
    DESCRIPTION
        "The sensor on port #52 has reached an alarm state."
    ::= 52

falconPort53Trap TRAP-TYPE
    ENTERPRISE   falconPortTrap 
    VARIABLES {
        falconAlarmId,
        falconAlarmDescr,
        falconInputLabel,
        falconInputReading,
        falconInputUOM
    }
    DESCRIPTION
        "The sensor on port #53 has reached an alarm state."
    ::= 53

falconPort54Trap TRAP-TYPE
    ENTERPRISE   falconPortTrap 
    VARIABLES {
        falconAlarmId,
        falconAlarmDescr,
        falconInputLabel,
        falconInputReading,
        falconInputUOM
    }
    DESCRIPTION
        "The sensor on port #54 has reached an alarm state."
    ::= 54

falconPort55Trap TRAP-TYPE
    ENTERPRISE   falconPortTrap 
    VARIABLES {
        falconAlarmId,
        falconAlarmDescr,
        falconInputLabel,
        falconInputReading,
        falconInputUOM
    }
    DESCRIPTION
        "The sensor on port #55 has reached an alarm state."
    ::= 55

falconPort56Trap TRAP-TYPE
    ENTERPRISE   falconPortTrap 
    VARIABLES {
        falconAlarmId,
        falconAlarmDescr,
        falconInputLabel,
        falconInputReading,
        falconInputUOM
    }
    DESCRIPTION
        "The sensor on port #56 has reached an alarm state."
    ::= 56

falconPort57Trap TRAP-TYPE
    ENTERPRISE   falconPortTrap 
    VARIABLES {
        falconAlarmId,
        falconAlarmDescr,
        falconInputLabel,
        falconInputReading,
        falconInputUOM
    }
    DESCRIPTION
        "The sensor on port #57 has reached an alarm state."
    ::= 57

falconPort58Trap TRAP-TYPE
    ENTERPRISE   falconPortTrap 
    VARIABLES {
        falconAlarmId,
        falconAlarmDescr,
        falconInputLabel,
        falconInputReading,
        falconInputUOM
    }
    DESCRIPTION
        "The sensor on port #58 has reached an alarm state."
    ::= 58

falconPort59Trap TRAP-TYPE
    ENTERPRISE   falconPortTrap 
    VARIABLES {
        falconAlarmId,
        falconAlarmDescr,
        falconInputLabel,
        falconInputReading,
        falconInputUOM
    }
    DESCRIPTION
        "The sensor on port #59 has reached an alarm state."
    ::= 59

falconPort60Trap TRAP-TYPE
    ENTERPRISE   falconPortTrap 
    VARIABLES {
        falconAlarmId,
        falconAlarmDescr,
        falconInputLabel,
        falconInputReading,
        falconInputUOM
    }
    DESCRIPTION
        "The sensor on port #60 has reached an alarm state."
    ::= 60

falconPort61Trap TRAP-TYPE
    ENTERPRISE   falconPortTrap 
    VARIABLES {
        falconAlarmId,
        falconAlarmDescr,
        falconInputLabel,
        falconInputReading,
        falconInputUOM
    }
    DESCRIPTION
        "The sensor on port #61 has reached an alarm state."
    ::= 61

falconPort62Trap TRAP-TYPE
    ENTERPRISE   falconPortTrap 
    VARIABLES {
        falconAlarmId,
        falconAlarmDescr,
        falconInputLabel,
        falconInputReading,
        falconInputUOM
    }
    DESCRIPTION
        "The sensor on port #62 has reached an alarm state."
    ::= 62

falconPort63Trap TRAP-TYPE
    ENTERPRISE   falconPortTrap 
    VARIABLES {
        falconAlarmId,
        falconAlarmDescr,
        falconInputLabel,
        falconInputReading,
        falconInputUOM
    }
    DESCRIPTION
        "The sensor on port #63 has reached an alarm state."
    ::= 63

falconPort64Trap TRAP-TYPE
    ENTERPRISE   falconPortTrap 
    VARIABLES {
        falconAlarmId,
        falconAlarmDescr,
        falconInputLabel,
        falconInputReading,
        falconInputUOM
    }
    DESCRIPTION
        "The sensor on port #64 has reached an alarm state."
    ::= 64

falconPort65Trap TRAP-TYPE
    ENTERPRISE   falconPortTrap 
    VARIABLES {
        falconAlarmId,
        falconAlarmDescr,
        falconInputLabel,
        falconInputReading,
        falconInputUOM
    }
    DESCRIPTION
        "The sensor on port #65 has reached an alarm state."
    ::= 65

falconPort66Trap TRAP-TYPE
    ENTERPRISE   falconPortTrap 
    VARIABLES {
        falconAlarmId,
        falconAlarmDescr,
        falconInputLabel,
        falconInputReading,
        falconInputUOM
    }
    DESCRIPTION
        "The sensor on port #66 has reached an alarm state."
    ::= 66

falconPort67Trap TRAP-TYPE
    ENTERPRISE   falconPortTrap 
    VARIABLES {
        falconAlarmId,
        falconAlarmDescr,
        falconInputLabel,
        falconInputReading,
        falconInputUOM
    }
    DESCRIPTION
        "The sensor on port #67 has reached an alarm state."
    ::= 67

falconPort68Trap TRAP-TYPE
    ENTERPRISE   falconPortTrap 
    VARIABLES {
        falconAlarmId,
        falconAlarmDescr,
        falconInputLabel,
        falconInputReading,
        falconInputUOM
    }
    DESCRIPTION
        "The sensor on port #68 has reached an alarm state."
    ::= 68

falconPort69Trap TRAP-TYPE
    ENTERPRISE   falconPortTrap 
    VARIABLES {
        falconAlarmId,
        falconAlarmDescr,
        falconInputLabel,
        falconInputReading,
        falconInputUOM
    }
    DESCRIPTION
        "The sensor on port #69 has reached an alarm state."
    ::= 69

falconPort70Trap TRAP-TYPE
    ENTERPRISE   falconPortTrap 
    VARIABLES {
        falconAlarmId,
        falconAlarmDescr,
        falconInputLabel,
        falconInputReading,
        falconInputUOM
    }
    DESCRIPTION
        "The sensor on port #70 has reached an alarm state."
    ::= 70

falconPort71Trap TRAP-TYPE
    ENTERPRISE   falconPortTrap 
    VARIABLES {
        falconAlarmId,
        falconAlarmDescr,
        falconInputLabel,
        falconInputReading,
        falconInputUOM
    }
    DESCRIPTION
        "The sensor on port #71 has reached an alarm state."
    ::= 71

falconPort72Trap TRAP-TYPE
    ENTERPRISE   falconPortTrap 
    VARIABLES {
        falconAlarmId,
        falconAlarmDescr,
        falconInputLabel,
        falconInputReading,
        falconInputUOM
    }
    DESCRIPTION
        "The sensor on port #72 has reached an alarm state."
    ::= 72

falconPort73Trap TRAP-TYPE
    ENTERPRISE   falconPortTrap 
    VARIABLES {
        falconAlarmId,
        falconAlarmDescr,
        falconInputLabel,
        falconInputReading,
        falconInputUOM
    }
    DESCRIPTION
        "The sensor on port #73 has reached an alarm state."
    ::= 73

falconPort74Trap TRAP-TYPE
    ENTERPRISE   falconPortTrap 
    VARIABLES {
        falconAlarmId,
        falconAlarmDescr,
        falconInputLabel,
        falconInputReading,
        falconInputUOM
    }
    DESCRIPTION
        "The sensor on port #74 has reached an alarm state."
    ::= 74

falconPort75Trap TRAP-TYPE
    ENTERPRISE   falconPortTrap 
    VARIABLES {
        falconAlarmId,
        falconAlarmDescr,
        falconInputLabel,
        falconInputReading,
        falconInputUOM
    }
    DESCRIPTION
        "The sensor on port #75 has reached an alarm state."
    ::= 75

falconPort76Trap TRAP-TYPE
    ENTERPRISE   falconPortTrap 
    VARIABLES {
        falconAlarmId,
        falconAlarmDescr,
        falconInputLabel,
        falconInputReading,
        falconInputUOM
    }
    DESCRIPTION
        "The sensor on port #76 has reached an alarm state."
    ::= 76

falconPort77Trap TRAP-TYPE
    ENTERPRISE   falconPortTrap 
    VARIABLES {
        falconAlarmId,
        falconAlarmDescr,
        falconInputLabel,
        falconInputReading,
        falconInputUOM
    }
    DESCRIPTION
        "The sensor on port #77 has reached an alarm state."
    ::= 77

falconPort78Trap TRAP-TYPE
    ENTERPRISE   falconPortTrap 
    VARIABLES {
        falconAlarmId,
        falconAlarmDescr,
        falconInputLabel,
        falconInputReading,
        falconInputUOM
    }
    DESCRIPTION
        "The sensor on port #78 has reached an alarm state."
    ::= 78

falconPort79Trap TRAP-TYPE
    ENTERPRISE   falconPortTrap 
    VARIABLES {
        falconAlarmId,
        falconAlarmDescr,
        falconInputLabel,
        falconInputReading,
        falconInputUOM
    }
    DESCRIPTION
        "The sensor on port #79 has reached an alarm state."
    ::= 79

falconPort80Trap TRAP-TYPE
    ENTERPRISE   falconPortTrap 
    VARIABLES {
        falconAlarmId,
        falconAlarmDescr,
        falconInputLabel,
        falconInputReading,
        falconInputUOM
    }
    DESCRIPTION
        "The sensor on port #80 has reached an alarm state."
    ::= 80

falconPort81Trap TRAP-TYPE
    ENTERPRISE   falconPortTrap 
    VARIABLES {
        falconAlarmId,
        falconAlarmDescr,
        falconInputLabel,
        falconInputReading,
        falconInputUOM
    }
    DESCRIPTION
        "The sensor on port #81 has reached an alarm state."
    ::= 81

falconPort82Trap TRAP-TYPE
    ENTERPRISE   falconPortTrap 
    VARIABLES {
        falconAlarmId,
        falconAlarmDescr,
        falconInputLabel,
        falconInputReading,
        falconInputUOM
    }
    DESCRIPTION
        "The sensor on port #82 has reached an alarm state."
    ::= 82

falconPort83Trap TRAP-TYPE
    ENTERPRISE   falconPortTrap 
    VARIABLES {
        falconAlarmId,
        falconAlarmDescr,
        falconInputLabel,
        falconInputReading,
        falconInputUOM
    }
    DESCRIPTION
        "The sensor on port #83 has reached an alarm state."
    ::= 83

falconPort84Trap TRAP-TYPE
    ENTERPRISE   falconPortTrap 
    VARIABLES {
        falconAlarmId,
        falconAlarmDescr,
        falconInputLabel,
        falconInputReading,
        falconInputUOM
    }
    DESCRIPTION
        "The sensor on port #84 has reached an alarm state."
    ::= 84

falconPort85Trap TRAP-TYPE
    ENTERPRISE   falconPortTrap 
    VARIABLES {
        falconAlarmId,
        falconAlarmDescr,
        falconInputLabel,
        falconInputReading,
        falconInputUOM
    }
    DESCRIPTION
        "The sensor on port #85 has reached an alarm state."
    ::= 85

falconPort86Trap TRAP-TYPE
    ENTERPRISE   falconPortTrap 
    VARIABLES {
        falconAlarmId,
        falconAlarmDescr,
        falconInputLabel,
        falconInputReading,
        falconInputUOM
    }
    DESCRIPTION
        "The sensor on port #86 has reached an alarm state."
    ::= 86

falconPort87Trap TRAP-TYPE
    ENTERPRISE   falconPortTrap 
    VARIABLES {
        falconAlarmId,
        falconAlarmDescr,
        falconInputLabel,
        falconInputReading,
        falconInputUOM
    }
    DESCRIPTION
        "The sensor on port #87 has reached an alarm state."
    ::= 87

falconPort88Trap TRAP-TYPE
    ENTERPRISE   falconPortTrap 
    VARIABLES {
        falconAlarmId,
        falconAlarmDescr,
        falconInputLabel,
        falconInputReading,
        falconInputUOM
    }
    DESCRIPTION
        "The sensor on port #88 has reached an alarm state."
    ::= 88

falconPort89Trap TRAP-TYPE
    ENTERPRISE   falconPortTrap 
    VARIABLES {
        falconAlarmId,
        falconAlarmDescr,
        falconInputLabel,
        falconInputReading,
        falconInputUOM
    }
    DESCRIPTION
        "The sensor on port #89 has reached an alarm state."
    ::= 89

falconPort90Trap TRAP-TYPE
    ENTERPRISE   falconPortTrap 
    VARIABLES {
        falconAlarmId,
        falconAlarmDescr,
        falconInputLabel,
        falconInputReading,
        falconInputUOM
    }
    DESCRIPTION
        "The sensor on port #90 has reached an alarm state."
    ::= 90

falconPort91Trap TRAP-TYPE
    ENTERPRISE   falconPortTrap 
    VARIABLES {
        falconAlarmId,
        falconAlarmDescr,
        falconInputLabel,
        falconInputReading,
        falconInputUOM
   }
    DESCRIPTION
        "The sensor on port #91 has reached an alarm state."
    ::= 91

falconPort92Trap TRAP-TYPE
    ENTERPRISE   falconPortTrap 
    VARIABLES {
        falconAlarmId,
        falconAlarmDescr,
        falconInputLabel,
        falconInputReading,
        falconInputUOM
    }
    DESCRIPTION
        "The sensor on port #92 has reached an alarm state."
    ::= 92

falconPort93Trap TRAP-TYPE
    ENTERPRISE   falconPortTrap 
    VARIABLES {
        falconAlarmId,
        falconAlarmDescr,
        falconInputLabel,
        falconInputReading,
        falconInputUOM
    }
    DESCRIPTION
        "The sensor on port #93 has reached an alarm state."
    ::= 93

falconPort94Trap TRAP-TYPE
    ENTERPRISE   falconPortTrap 
    VARIABLES {
        falconAlarmId,
        falconAlarmDescr,
        falconInputLabel,
        falconInputReading,
        falconInputUOM
    }
    DESCRIPTION
        "The sensor on port #94 has reached an alarm state."
    ::= 94

falconPort95Trap TRAP-TYPE
    ENTERPRISE   falconPortTrap 
    VARIABLES {
        falconAlarmId,
        falconAlarmDescr,
        falconInputLabel,
        falconInputReading,
        falconInputUOM
    }
    DESCRIPTION
        "The sensor on port #95 has reached an alarm state."
    ::= 95

falconPort96Trap TRAP-TYPE
    ENTERPRISE   falconPortTrap 
    VARIABLES {
        falconAlarmId,
        falconAlarmDescr,
        falconInputLabel,
        falconInputReading,
        falconInputUOM
    }
    DESCRIPTION
        "The sensor on port #96 has reached an alarm state."
    ::= 96

falconPort97Trap TRAP-TYPE
    ENTERPRISE   falconPortTrap 
    VARIABLES {
        falconAlarmId,
        falconAlarmDescr,
        falconInputLabel,
        falconInputReading,
        falconInputUOM
    }
    DESCRIPTION
        "The sensor on port #97 has reached an alarm state."
    ::= 97

falconPort98Trap TRAP-TYPE
    ENTERPRISE   falconPortTrap 
    VARIABLES {
        falconAlarmId,
        falconAlarmDescr,
        falconInputLabel,
        falconInputReading,
        falconInputUOM
    }
    DESCRIPTION
        "The sensor on port #98 has reached an alarm state."
    ::= 98

falconPort99Trap TRAP-TYPE
    ENTERPRISE   falconPortTrap 
    VARIABLES {
        falconAlarmId,
        falconAlarmDescr,
        falconInputLabel,
        falconInputReading,
        falconInputUOM
    }
    DESCRIPTION
        "The sensor on port #99 has reached an alarm state."
    ::= 99

falconPort100Trap TRAP-TYPE
    ENTERPRISE   falconPortTrap 
    VARIABLES {
        falconAlarmId,
        falconAlarmDescr,
        falconInputLabel,
        falconInputReading,
        falconInputUOM
    }
    DESCRIPTION
        "The sensor on port #100 has reached an alarm state."
    ::= 100

falconPort101Trap TRAP-TYPE
    ENTERPRISE   falconPortTrap 
    VARIABLES {
        falconAlarmId,
        falconAlarmDescr,
        falconInputLabel,
        falconInputReading,
        falconInputUOM
    }
    DESCRIPTION
        "The sensor on port #101 has reached an alarm state."
    ::= 101

falconPort102Trap TRAP-TYPE
    ENTERPRISE   falconPortTrap 
    VARIABLES {
        falconAlarmId,
        falconAlarmDescr,
        falconInputLabel,
        falconInputReading,
        falconInputUOM
    }
    DESCRIPTION
        "The sensor on port #102 has reached an alarm state."
    ::= 102

falconPort103Trap TRAP-TYPE
    ENTERPRISE   falconPortTrap 
    VARIABLES {
        falconAlarmId,
        falconAlarmDescr,
        falconInputLabel,
        falconInputReading,
        falconInputUOM
    }
    DESCRIPTION
        "The sensor on port #103 has reached an alarm state."
    ::= 103

falconPort104Trap TRAP-TYPE
    ENTERPRISE   falconPortTrap 
    VARIABLES {
        falconAlarmId,
        falconAlarmDescr,
        falconInputLabel,
        falconInputReading,
        falconInputUOM
    }
    DESCRIPTION
        "The sensor on port #104 has reached an alarm state."
    ::= 104

falconTemperatureSensorTrap TRAP-TYPE
    ENTERPRISE   falconPortTrap 
    VARIABLES {
        falconAlarmId,
        falconAlarmDescr,
        falconTemperatureSensorLabel,
        falconTemperatureSensorReading,
        falconTemperatureSensorUOM
    }
    DESCRIPTION
        "The internal temperature sensor has reached an alarm state."
    ::= 105

falconHumiditySensorTrap TRAP-TYPE
    ENTERPRISE   falconPortTrap 
    VARIABLES {
        falconAlarmId,
        falconAlarmDescr,
        falconHumiditySensorLabel,
        falconHumiditySensorReading,
        falconHumiditySensorUOM
    }
    DESCRIPTION
        "The internal Humidity sensor has reached an alarm state."
    ::= 106
    

falconPortTrapClear OBJECT IDENTIFIER ::= { falcon-emMIB  11 }

falconPort01TrapClear TRAP-TYPE
    ENTERPRISE   falconPortTrapClear 
    VARIABLES {
        falconAlarmId,
        falconAlarmDescr,
        falconInputLabel,
        falconInputReading,
        falconInputUOM
    }
    DESCRIPTION
        "The sensor on port #01 has returned to normal."
    ::= 1

falconPort02TrapClear TRAP-TYPE
    ENTERPRISE   falconPortTrapClear 
    VARIABLES {
        falconAlarmId,
        falconAlarmDescr,
        falconInputLabel,
        falconInputReading,
        falconInputUOM
    }
    DESCRIPTION
        "The sensor on port #02 has returned to normal."
    ::= 2

falconPort03TrapClear TRAP-TYPE
    ENTERPRISE   falconPortTrapClear 
    VARIABLES {
        falconAlarmId,
        falconAlarmDescr,
        falconInputLabel,
        falconInputReading,
        falconInputUOM
    }
    DESCRIPTION
        "The sensor on port #03 has returned to normal."
    ::= 3

falconPort04TrapClear TRAP-TYPE
    ENTERPRISE   falconPortTrapClear 
    VARIABLES {
        falconAlarmId,
        falconAlarmDescr,
        falconInputLabel,
        falconInputReading,
        falconInputUOM
    }
    DESCRIPTION
        "The sensor on port #04 has returned to normal."
    ::= 4

falconPort05TrapClear TRAP-TYPE
    ENTERPRISE   falconPortTrapClear 
    VARIABLES {
        falconAlarmId,
        falconAlarmDescr,
        falconInputLabel,
        falconInputReading,
        falconInputUOM
    }
    DESCRIPTION
        "The sensor on port #05 has returned to normal."
    ::= 5

falconPort06TrapClear TRAP-TYPE
    ENTERPRISE   falconPortTrapClear 
    VARIABLES {
        falconAlarmId,
        falconAlarmDescr,
        falconInputLabel,
        falconInputReading,
        falconInputUOM
    }
    DESCRIPTION
        "The sensor on port #06 has returned to normal."
    ::= 6

falconPort07TrapClear TRAP-TYPE
    ENTERPRISE   falconPortTrapClear 
    VARIABLES {
        falconAlarmId,
        falconAlarmDescr,
        falconInputLabel,
        falconInputReading,
        falconInputUOM
    }
    DESCRIPTION
        "The sensor on port #07 has returned to normal."
    ::= 7

falconPort08TrapClear TRAP-TYPE
    ENTERPRISE   falconPortTrapClear 
    VARIABLES {
        falconAlarmId,
        falconAlarmDescr,
        falconInputLabel,
        falconInputReading,
        falconInputUOM
    }
    DESCRIPTION
        "The sensor on port #08 has returned to normal."
    ::= 8
    
falconPort09TrapClear TRAP-TYPE
    ENTERPRISE   falconPortTrapClear 
    VARIABLES {
        falconAlarmId,
        falconAlarmDescr,
        falconInputLabel,
        falconInputReading,
        falconInputUOM
    }
    DESCRIPTION
        "The sensor on port #09 has returned to normal."
    ::= 9

falconPort10TrapClear TRAP-TYPE
    ENTERPRISE   falconPortTrapClear 
    VARIABLES {
        falconAlarmId,
        falconAlarmDescr,
        falconInputLabel,
        falconInputReading,
        falconInputUOM
    }
    DESCRIPTION
        "The sensor on port #10 has returned to normal."
    ::= 10

falconPort11TrapClear TRAP-TYPE
    ENTERPRISE   falconPortTrapClear 
    VARIABLES {
        falconAlarmId,
        falconAlarmDescr,
        falconInputLabel,
        falconInputReading,
        falconInputUOM
    }
    DESCRIPTION
        "The sensor on port #11 has returned to normal."
    ::= 11

falconPort12TrapClear TRAP-TYPE
    ENTERPRISE   falconPortTrapClear 
    VARIABLES {
        falconAlarmId,
        falconAlarmDescr,
        falconInputLabel,
        falconInputReading,
        falconInputUOM
    }
    DESCRIPTION
        "The sensor on port #12 has returned to normal."
    ::= 12

falconPort13TrapClear TRAP-TYPE
    ENTERPRISE   falconPortTrapClear 
    VARIABLES {
        falconAlarmId,
        falconAlarmDescr,
        falconInputLabel,
        falconInputReading,
        falconInputUOM
    }
    DESCRIPTION
        "The sensor on port #13 has returned to normal."
    ::= 13

falconPort14TrapClear TRAP-TYPE
    ENTERPRISE   falconPortTrapClear 
    VARIABLES {
        falconAlarmId,
        falconAlarmDescr,
        falconInputLabel,
        falconInputReading,
        falconInputUOM
    }
    DESCRIPTION
        "The sensor on port #14 has returned to normal."
    ::= 14

falconPort15TrapClear TRAP-TYPE
    ENTERPRISE   falconPortTrapClear 
    VARIABLES {
        falconAlarmId,
        falconAlarmDescr,
        falconInputLabel,
        falconInputReading,
        falconInputUOM
    }
    DESCRIPTION
        "The sensor on port #15 has returned to normal."
    ::= 15

falconPort16TrapClear TRAP-TYPE
    ENTERPRISE   falconPortTrapClear 
    VARIABLES {
        falconAlarmId,
        falconAlarmDescr,
        falconInputLabel,
        falconInputReading,
        falconInputUOM
    }
    DESCRIPTION
        "The sensor on port #16 has returned to normal."
    ::= 16

falconPort17TrapClear TRAP-TYPE
    ENTERPRISE   falconPortTrapClear 
    VARIABLES {
        falconAlarmId,
        falconAlarmDescr,
        falconInputLabel,
        falconInputReading,
        falconInputUOM
    }
    DESCRIPTION
        "The sensor on port #17 has returned to normal."
    ::= 17

falconPort18TrapClear TRAP-TYPE
    ENTERPRISE   falconPortTrapClear 
    VARIABLES {
        falconAlarmId,
        falconAlarmDescr,
        falconInputLabel,
        falconInputReading,
        falconInputUOM
    }
    DESCRIPTION
        "The sensor on port #18 has returned to normal."
    ::= 18

falconPort19TrapClear TRAP-TYPE
    ENTERPRISE   falconPortTrapClear 
    VARIABLES {
        falconAlarmId,
        falconAlarmDescr,
        falconInputLabel,
        falconInputReading,
        falconInputUOM
    }
    DESCRIPTION
        "The sensor on port #19 has returned to normal."
    ::= 19

falconPort20TrapClear TRAP-TYPE
    ENTERPRISE   falconPortTrapClear 
    VARIABLES {
        falconAlarmId,
        falconAlarmDescr,
        falconInputLabel,
        falconInputReading,
        falconInputUOM
    }
    DESCRIPTION
        "The sensor on port #20 has returned to normal."
    ::= 20

falconPort21TrapClear TRAP-TYPE
    ENTERPRISE   falconPortTrapClear 
    VARIABLES {
        falconAlarmId,
        falconAlarmDescr,
        falconInputLabel,
        falconInputReading,
        falconInputUOM
    }
    DESCRIPTION
        "The sensor on port #21 has returned to normal."
    ::= 21

falconPort22TrapClear TRAP-TYPE
    ENTERPRISE   falconPortTrapClear 
    VARIABLES {
        falconAlarmId,
        falconAlarmDescr,
        falconInputLabel,
        falconInputReading,
        falconInputUOM
    }
    DESCRIPTION
        "The sensor on port #22 has returned to normal."
    ::= 22

falconPort23TrapClear TRAP-TYPE
    ENTERPRISE   falconPortTrapClear 
    VARIABLES {
        falconAlarmId,
        falconAlarmDescr,
        falconInputLabel,
        falconInputReading,
        falconInputUOM
    }
    DESCRIPTION
        "The sensor on port #23 has returned to normal."
    ::= 23

falconPort24TrapClear TRAP-TYPE
    ENTERPRISE   falconPortTrapClear 
    VARIABLES {
        falconAlarmId,
        falconAlarmDescr,
        falconInputLabel,
        falconInputReading,
        falconInputUOM
    }
    DESCRIPTION
        "The sensor on port #24 has returned to normal."
    ::= 24

falconPort25TrapClear TRAP-TYPE
    ENTERPRISE   falconPortTrapClear 
    VARIABLES {
        falconAlarmId,
        falconAlarmDescr,
        falconInputLabel,
        falconInputReading,
        falconInputUOM
    }
    DESCRIPTION
        "The sensor on port #25 has returned to normal."
    ::= 25

falconPort26TrapClear TRAP-TYPE
    ENTERPRISE   falconPortTrapClear 
    VARIABLES {
        falconAlarmId,
        falconAlarmDescr,
        falconInputLabel,
        falconInputReading,
        falconInputUOM
    }
    DESCRIPTION
        "The sensor on port #26 has returned to normal."
    ::= 26

falconPort27TrapClear TRAP-TYPE
    ENTERPRISE   falconPortTrapClear 
    VARIABLES {
        falconAlarmId,
        falconAlarmDescr,
        falconInputLabel,
        falconInputReading,
        falconInputUOM
    }
    DESCRIPTION
        "The sensor on port #27 has returned to normal."
    ::= 27

falconPort28TrapClear TRAP-TYPE
    ENTERPRISE   falconPortTrapClear 
    VARIABLES {
        falconAlarmId,
        falconAlarmDescr,
        falconInputLabel,
        falconInputReading,
        falconInputUOM
    }
    DESCRIPTION
        "The sensor on port #28 has returned to normal."
    ::= 28

falconPort29TrapClear TRAP-TYPE
    ENTERPRISE   falconPortTrapClear 
    VARIABLES {
        falconAlarmId,
        falconAlarmDescr,
        falconInputLabel,
        falconInputReading,
        falconInputUOM
    }
    DESCRIPTION
        "The sensor on port #29 has returned to normal."
    ::= 29

falconPort30TrapClear TRAP-TYPE
    ENTERPRISE   falconPortTrapClear 
    VARIABLES {
        falconAlarmId,
        falconAlarmDescr,
        falconInputLabel,
        falconInputReading,
        falconInputUOM
    }
    DESCRIPTION
        "The sensor on port #30 has returned to normal."
    ::= 30

falconPort31TrapClear TRAP-TYPE
    ENTERPRISE   falconPortTrapClear 
    VARIABLES {
        falconAlarmId,
        falconAlarmDescr,
        falconInputLabel,
        falconInputReading,
        falconInputUOM
    }
    DESCRIPTION
        "The sensor on port #31 has returned to normal."
    ::= 31

falconPort32TrapClear TRAP-TYPE
    ENTERPRISE   falconPortTrapClear 
    VARIABLES {
        falconAlarmId,
        falconAlarmDescr,
        falconInputLabel,
        falconInputReading,
        falconInputUOM
    }
    DESCRIPTION
        "The sensor on port #32 has returned to normal."
    ::= 32


falconPort33TrapClear TRAP-TYPE
    ENTERPRISE   falconPortTrapClear 
    VARIABLES {
        falconAlarmId,
        falconAlarmDescr,
        falconInputLabel,
        falconInputReading,
        falconInputUOM
    }
    DESCRIPTION
        "The sensor on port #33 has returned to normal."
    ::= 33

falconPort34TrapClear TRAP-TYPE
    ENTERPRISE   falconPortTrapClear 
    VARIABLES {
        falconAlarmId,
        falconAlarmDescr,
        falconInputLabel,
        falconInputReading,
        falconInputUOM
    }
    DESCRIPTION
        "The sensor on port #34 has returned to normal."
    ::= 34

falconPort35TrapClear TRAP-TYPE
    ENTERPRISE   falconPortTrapClear 
    VARIABLES {
        falconAlarmId,
        falconAlarmDescr,
        falconInputLabel,
        falconInputReading,
        falconInputUOM
    }
    DESCRIPTION
        "The sensor on port #35 has returned to normal."
    ::= 35

falconPort36TrapClear TRAP-TYPE
    ENTERPRISE   falconPortTrapClear 
    VARIABLES {
        falconAlarmId,
        falconAlarmDescr,
        falconInputLabel,
        falconInputReading,
        falconInputUOM
    }
    DESCRIPTION
        "The sensor on port #36 has returned to normal."
    ::= 36

falconPort37TrapClear TRAP-TYPE
    ENTERPRISE   falconPortTrapClear 
    VARIABLES {
        falconAlarmId,
        falconAlarmDescr,
        falconInputLabel,
        falconInputReading,
        falconInputUOM
    }
    DESCRIPTION
        "The sensor on port #37 has returned to normal."
    ::= 37

falconPort38TrapClear TRAP-TYPE
    ENTERPRISE   falconPortTrapClear 
    VARIABLES {
        falconAlarmId,
        falconAlarmDescr,
        falconInputLabel,
        falconInputReading,
        falconInputUOM
    }
    DESCRIPTION
        "The sensor on port #38 has returned to normal."
    ::= 38

falconPort39TrapClear TRAP-TYPE
    ENTERPRISE   falconPortTrapClear 
    VARIABLES {
        falconAlarmId,
        falconAlarmDescr,
        falconInputLabel,
        falconInputReading,
        falconInputUOM
    }
    DESCRIPTION
        "The sensor on port #39 has returned to normal."
    ::= 39

falconPort40TrapClear TRAP-TYPE
    ENTERPRISE   falconPortTrapClear 
    VARIABLES {
        falconAlarmId,
        falconAlarmDescr,
        falconInputLabel,
        falconInputReading,
        falconInputUOM
    }
    DESCRIPTION
        "The sensor on port #40 has returned to normal."
    ::= 40

falconPort41TrapClear TRAP-TYPE
    ENTERPRISE   falconPortTrapClear 
    VARIABLES {
        falconAlarmId,
        falconAlarmDescr,
        falconInputLabel,
        falconInputReading,
        falconInputUOM
    }
    DESCRIPTION
        "The sensor on port #41 has returned to normal."
    ::= 41

falconPort42TrapClear TRAP-TYPE
    ENTERPRISE   falconPortTrapClear 
    VARIABLES {
        falconAlarmId,
        falconAlarmDescr,
        falconInputLabel,
        falconInputReading,
        falconInputUOM
    }
    DESCRIPTION
        "The sensor on port #42 has returned to normal."
    ::= 42


falconPort43TrapClear TRAP-TYPE
    ENTERPRISE   falconPortTrapClear 
    VARIABLES {
        falconAlarmId,
        falconAlarmDescr,
        falconInputLabel,
        falconInputReading,
        falconInputUOM
    }
    DESCRIPTION
        "The sensor on port #43 has returned to normal."
    ::= 43

falconPort44TrapClear TRAP-TYPE
    ENTERPRISE   falconPortTrapClear 
    VARIABLES {
        falconAlarmId,
        falconAlarmDescr,
        falconInputLabel,
        falconInputReading,
        falconInputUOM
    }
    DESCRIPTION
        "The sensor on port #44 has returned to normal."
    ::= 44

falconPort45TrapClear TRAP-TYPE
    ENTERPRISE   falconPortTrapClear 
    VARIABLES {
        falconAlarmId,
        falconAlarmDescr,
        falconInputLabel,
        falconInputReading,
        falconInputUOM
    }
    DESCRIPTION
        "The sensor on port #45 has returned to normal."
    ::= 45

falconPort46TrapClear TRAP-TYPE
    ENTERPRISE   falconPortTrapClear 
    VARIABLES {
        falconAlarmId,
        falconAlarmDescr,
        falconInputLabel,
        falconInputReading,
        falconInputUOM
    }
    DESCRIPTION
        "The sensor on port #46 has returned to normal."
    ::= 46

falconPort47TrapClear TRAP-TYPE
    ENTERPRISE   falconPortTrapClear 
    VARIABLES {
        falconAlarmId,
        falconAlarmDescr,
        falconInputLabel,
        falconInputReading,
        falconInputUOM
    }
    DESCRIPTION
        "The sensor on port #47 has returned to normal."
    ::= 47

falconPort48TrapClear TRAP-TYPE
    ENTERPRISE   falconPortTrapClear 
    VARIABLES {
        falconAlarmId,
        falconAlarmDescr,
        falconInputLabel,
        falconInputReading,
        falconInputUOM
    }
    DESCRIPTION
        "The sensor on port #48 has returned to normal."
    ::= 48

falconPort49TrapClear TRAP-TYPE
    ENTERPRISE   falconPortTrapClear 
    VARIABLES {
        falconAlarmId,
        falconAlarmDescr,
        falconInputLabel,
        falconInputReading,
        falconInputUOM
    }
    DESCRIPTION
        "The sensor on port #49 has returned to normal."
    ::= 49

falconPort50TrapClear TRAP-TYPE
    ENTERPRISE   falconPortTrapClear 
    VARIABLES {
        falconAlarmId,
        falconAlarmDescr,
        falconInputLabel,
        falconInputReading,
        falconInputUOM
    }
    DESCRIPTION
        "The sensor on port #50 has returned to normal."
    ::= 50

falconPort51TrapClear TRAP-TYPE
    ENTERPRISE   falconPortTrapClear 
    VARIABLES {
        falconAlarmId,
        falconAlarmDescr,
        falconInputLabel,
        falconInputReading,
        falconInputUOM
    }
    DESCRIPTION
        "The sensor on port #51 has returned to normal."
    ::= 51

falconPort52TrapClear TRAP-TYPE
    ENTERPRISE   falconPortTrapClear 
    VARIABLES {
        falconAlarmId,
        falconAlarmDescr,
        falconInputLabel,
        falconInputReading,
        falconInputUOM
    }
    DESCRIPTION
        "The sensor on port #52 has returned to normal."
    ::= 52


falconPort53TrapClear TRAP-TYPE
    ENTERPRISE   falconPortTrapClear 
    VARIABLES {
        falconAlarmId,
        falconAlarmDescr,
        falconInputLabel,
        falconInputReading,
        falconInputUOM
    }
    DESCRIPTION
        "The sensor on port #53 has returned to normal."
    ::= 53

falconPort54TrapClear TRAP-TYPE
    ENTERPRISE   falconPortTrapClear 
    VARIABLES {
        falconAlarmId,
        falconAlarmDescr,
        falconInputLabel,
        falconInputReading,
        falconInputUOM
    }
    DESCRIPTION
        "The sensor on port #54 has returned to normal."
    ::= 54

falconPort55TrapClear TRAP-TYPE
    ENTERPRISE   falconPortTrapClear 
    VARIABLES {
        falconAlarmId,
        falconAlarmDescr,
        falconInputLabel,
        falconInputReading,
        falconInputUOM
    }
    DESCRIPTION
        "The sensor on port #55 has returned to normal."
    ::= 55

falconPort56TrapClear TRAP-TYPE
    ENTERPRISE   falconPortTrapClear 
    VARIABLES {
        falconAlarmId,
        falconAlarmDescr,
        falconInputLabel,
        falconInputReading,
        falconInputUOM
    }
    DESCRIPTION
        "The sensor on port #56 has returned to normal."
    ::= 56

falconPort57TrapClear TRAP-TYPE
    ENTERPRISE   falconPortTrapClear 
    VARIABLES {
        falconAlarmId,
        falconAlarmDescr,
        falconInputLabel,
        falconInputReading,
        falconInputUOM
    }
    DESCRIPTION
        "The sensor on port #57 has returned to normal."
    ::= 57

falconPort58TrapClear TRAP-TYPE
    ENTERPRISE   falconPortTrapClear 
    VARIABLES {
        falconAlarmId,
        falconAlarmDescr,
        falconInputLabel,
        falconInputReading,
        falconInputUOM
    }
    DESCRIPTION
        "The sensor on port #58 has returned to normal."
    ::= 58

falconPort59TrapClear TRAP-TYPE
    ENTERPRISE   falconPortTrapClear 
    VARIABLES {
        falconAlarmId,
        falconAlarmDescr,
        falconInputLabel,
        falconInputReading,
        falconInputUOM
    }
    DESCRIPTION
        "The sensor on port #59 has returned to normal."
    ::= 59

falconPort60TrapClear TRAP-TYPE
    ENTERPRISE   falconPortTrapClear 
    VARIABLES {
        falconAlarmId,
        falconAlarmDescr,
        falconInputLabel,
        falconInputReading,
        falconInputUOM
    }
    DESCRIPTION
        "The sensor on port #60 has returned to normal."
    ::= 60

falconPort61TrapClear TRAP-TYPE
    ENTERPRISE   falconPortTrapClear 
    VARIABLES {
        falconAlarmId,
        falconAlarmDescr,
        falconInputLabel,
        falconInputReading,
        falconInputUOM
    }
    DESCRIPTION
        "The sensor on port #61 has returned to normal."
    ::= 61

falconPort62TrapClear TRAP-TYPE
    ENTERPRISE   falconPortTrapClear 
    VARIABLES {
        falconAlarmId,
        falconAlarmDescr,
        falconInputLabel,
        falconInputReading,
        falconInputUOM
    }
    DESCRIPTION
        "The sensor on port #62 has returned to normal."
    ::= 62

falconPort63TrapClear TRAP-TYPE
    ENTERPRISE   falconPortTrapClear 
    VARIABLES {
        falconAlarmId,
        falconAlarmDescr,
        falconInputLabel,
        falconInputReading,
        falconInputUOM
    }
    DESCRIPTION
        "The sensor on port #63 has returned to normal."
    ::= 63

falconPort64TrapClear TRAP-TYPE
    ENTERPRISE   falconPortTrapClear 
    VARIABLES {
        falconAlarmId,
        falconAlarmDescr,
        falconInputLabel,
        falconInputReading,
        falconInputUOM
    }
    DESCRIPTION
        "The sensor on port #64 has returned to normal."
    ::= 64

falconPort65TrapClear TRAP-TYPE
    ENTERPRISE   falconPortTrapClear 
    VARIABLES {
        falconAlarmId,
        falconAlarmDescr,
        falconInputLabel,
        falconInputReading,
        falconInputUOM
    }
    DESCRIPTION
        "The sensor on port #65 has returned to normal."
    ::= 65

falconPort66TrapClear TRAP-TYPE
    ENTERPRISE   falconPortTrapClear 
    VARIABLES {
        falconAlarmId,
        falconAlarmDescr,
        falconInputLabel,
        falconInputReading,
        falconInputUOM
    }
    DESCRIPTION
        "The sensor on port #66 has returned to normal."
    ::= 66

falconPort67TrapClear TRAP-TYPE
    ENTERPRISE   falconPortTrapClear 
    VARIABLES {
        falconAlarmId,
        falconAlarmDescr,
        falconInputLabel,
        falconInputReading,
        falconInputUOM
    }
    DESCRIPTION
        "The sensor on port #67 has returned to normal."
    ::= 67

falconPort68TrapClear TRAP-TYPE
    ENTERPRISE   falconPortTrapClear 
    VARIABLES {
        falconAlarmId,
        falconAlarmDescr,
        falconInputLabel,
        falconInputReading,
        falconInputUOM
    }
    DESCRIPTION
        "The sensor on port #68 has returned to normal."
    ::= 68

falconPort69TrapClear TRAP-TYPE
    ENTERPRISE   falconPortTrapClear 
    VARIABLES {
        falconAlarmId,
        falconAlarmDescr,
        falconInputLabel,
        falconInputReading,
        falconInputUOM
    }
    DESCRIPTION
        "The sensor on port #69 has returned to normal."
    ::= 69

falconPort70TrapClear TRAP-TYPE
    ENTERPRISE   falconPortTrapClear 
    VARIABLES {
        falconAlarmId,
        falconAlarmDescr,
        falconInputLabel,
        falconInputReading,
        falconInputUOM
    }
    DESCRIPTION
        "The sensor on port #70 has returned to normal."
    ::= 70

falconPort71TrapClear TRAP-TYPE
    ENTERPRISE   falconPortTrapClear 
    VARIABLES {
        falconAlarmId,
        falconAlarmDescr,
        falconInputLabel,
        falconInputReading,
        falconInputUOM
    }
    DESCRIPTION
        "The sensor on port #71 has returned to normal."
    ::= 71

falconPort72TrapClear TRAP-TYPE
    ENTERPRISE   falconPortTrapClear 
    VARIABLES {
        falconAlarmId,
        falconAlarmDescr,
        falconInputLabel,
        falconInputReading,
        falconInputUOM
    }
    DESCRIPTION
        "The sensor on port #72 has returned to normal."
    ::= 72

falconPort73TrapClear TRAP-TYPE
    ENTERPRISE   falconPortTrapClear 
    VARIABLES {
        falconAlarmId,
        falconAlarmDescr,
        falconInputLabel,
        falconInputReading,
        falconInputUOM
    }
    DESCRIPTION
        "The sensor on port #73 has returned to normal."
    ::= 73

falconPort74TrapClear TRAP-TYPE
    ENTERPRISE   falconPortTrapClear 
    VARIABLES {
        falconAlarmId,
        falconAlarmDescr,
        falconInputLabel,
        falconInputReading,
        falconInputUOM
    }
    DESCRIPTION
        "The sensor on port #74 has returned to normal."
    ::= 74

falconPort75TrapClear TRAP-TYPE
    ENTERPRISE   falconPortTrapClear 
    VARIABLES {
        falconAlarmId,
        falconAlarmDescr,
        falconInputLabel,
        falconInputReading,
        falconInputUOM
    }
    DESCRIPTION
        "The sensor on port #75 has returned to normal."
    ::= 75

falconPort76TrapClear TRAP-TYPE
    ENTERPRISE   falconPortTrapClear 
    VARIABLES {
        falconAlarmId,
        falconAlarmDescr,
        falconInputLabel,
        falconInputReading,
        falconInputUOM
    }
    DESCRIPTION
        "The sensor on port #76 has returned to normal."
    ::= 76

falconPort77TrapClear TRAP-TYPE
    ENTERPRISE   falconPortTrapClear 
    VARIABLES {
        falconAlarmId,
        falconAlarmDescr,
        falconInputLabel,
        falconInputReading,
        falconInputUOM
    }
    DESCRIPTION
        "The sensor on port #77 has returned to normal."
    ::= 77

falconPort78TrapClear TRAP-TYPE
    ENTERPRISE   falconPortTrapClear 
    VARIABLES {
        falconAlarmId,
        falconAlarmDescr,
        falconInputLabel,
        falconInputReading,
        falconInputUOM
    }
    DESCRIPTION
        "The sensor on port #78 has returned to normal."
    ::= 78

falconPort79TrapClear TRAP-TYPE
    ENTERPRISE   falconPortTrapClear 
    VARIABLES {
        falconAlarmId,
        falconAlarmDescr,
        falconInputLabel,
        falconInputReading,
        falconInputUOM
    }
    DESCRIPTION
        "The sensor on port #79 has returned to normal."
    ::= 79

falconPort80TrapClear TRAP-TYPE
    ENTERPRISE   falconPortTrapClear 
    VARIABLES {
        falconAlarmId,
        falconAlarmDescr,
        falconInputLabel,
        falconInputReading,
        falconInputUOM
    }
    DESCRIPTION
        "The sensor on port #80 has returned to normal."
    ::= 80

falconPort81TrapClear TRAP-TYPE
    ENTERPRISE   falconPortTrapClear 
    VARIABLES {
        falconAlarmId,
        falconAlarmDescr,
        falconInputLabel,
        falconInputReading,
        falconInputUOM
    }
    DESCRIPTION
        "The sensor on port #81 has returned to normal."
    ::= 81

falconPort82TrapClear TRAP-TYPE
    ENTERPRISE   falconPortTrapClear 
    VARIABLES {
        falconAlarmId,
        falconAlarmDescr,
        falconInputLabel,
        falconInputReading,
        falconInputUOM
    }
    DESCRIPTION
        "The sensor on port #82 has returned to normal."
    ::= 82

falconPort83TrapClear TRAP-TYPE
    ENTERPRISE   falconPortTrapClear 
    VARIABLES {
        falconAlarmId,
        falconAlarmDescr,
        falconInputLabel,
        falconInputReading,
        falconInputUOM
    }
    DESCRIPTION
        "The sensor on port #83 has returned to normal."
    ::= 83

falconPort84TrapClear TRAP-TYPE
    ENTERPRISE   falconPortTrapClear 
    VARIABLES {
        falconAlarmId,
        falconAlarmDescr,
        falconInputLabel,
        falconInputReading,
        falconInputUOM
    }
    DESCRIPTION
        "The sensor on port #84 has returned to normal."
    ::= 84

falconPort85TrapClear TRAP-TYPE
    ENTERPRISE   falconPortTrapClear 
    VARIABLES {
        falconAlarmId,
        falconAlarmDescr,
        falconInputLabel,
        falconInputReading,
        falconInputUOM
    }
    DESCRIPTION
        "The sensor on port #85 has returned to normal."
    ::= 85

falconPort86TrapClear TRAP-TYPE
    ENTERPRISE   falconPortTrapClear 
    VARIABLES {
        falconAlarmId,
        falconAlarmDescr,
        falconInputLabel,
        falconInputReading,
        falconInputUOM
    }
    DESCRIPTION
        "The sensor on port #86 has returned to normal."
    ::= 86

falconPort87TrapClear TRAP-TYPE
    ENTERPRISE   falconPortTrapClear 
    VARIABLES {
        falconAlarmId,
        falconAlarmDescr,
        falconInputLabel,
        falconInputReading,
        falconInputUOM
    }
    DESCRIPTION
        "The sensor on port #87 has returned to normal."
    ::= 87

falconPort88TrapClear TRAP-TYPE
    ENTERPRISE   falconPortTrapClear 
    VARIABLES {
        falconAlarmId,
        falconAlarmDescr,
        falconInputLabel,
        falconInputReading,
        falconInputUOM
    }
    DESCRIPTION
        "The sensor on port #88 has returned to normal."
    ::= 88

falconPort89TrapClear TRAP-TYPE
    ENTERPRISE   falconPortTrapClear 
    VARIABLES {
        falconAlarmId,
        falconAlarmDescr,
        falconInputLabel,
        falconInputReading,
        falconInputUOM
    }
    DESCRIPTION
        "The sensor on port #89 has returned to normal."
    ::= 89

falconPort90TrapClear TRAP-TYPE
    ENTERPRISE   falconPortTrapClear 
    VARIABLES {
        falconAlarmId,
        falconAlarmDescr,
        falconInputLabel,
        falconInputReading,
        falconInputUOM
    }
    DESCRIPTION
        "The sensor on port #90 has returned to normal."
    ::= 90

falconPort91TrapClear TRAP-TYPE
    ENTERPRISE   falconPortTrapClear 
    VARIABLES {
        falconAlarmId,
        falconAlarmDescr,
        falconInputLabel,
        falconInputReading,
        falconInputUOM
    }
    DESCRIPTION
        "The sensor on port #91 has returned to normal."
    ::= 91

falconPort92TrapClear TRAP-TYPE
    ENTERPRISE   falconPortTrapClear 
    VARIABLES {
        falconAlarmId,
        falconAlarmDescr,
        falconInputLabel,
        falconInputReading,
        falconInputUOM
    }
    DESCRIPTION
        "The sensor on port #92 has returned to normal."
    ::= 92

falconPort93TrapClear TRAP-TYPE
    ENTERPRISE   falconPortTrapClear 
    VARIABLES {
        falconAlarmId,
        falconAlarmDescr,
        falconInputLabel,
        falconInputReading,
        falconInputUOM
    }
    DESCRIPTION
        "The sensor on port #93 has returned to normal."
    ::= 93

falconPort94TrapClear TRAP-TYPE
    ENTERPRISE   falconPortTrapClear 
    VARIABLES {
        falconAlarmId,
        falconAlarmDescr,
        falconInputLabel,
        falconInputReading,
        falconInputUOM
    }
    DESCRIPTION
        "The sensor on port #94 has returned to normal."
    ::= 94

falconPort95TrapClear TRAP-TYPE
    ENTERPRISE   falconPortTrapClear 
    VARIABLES {
        falconAlarmId,
        falconAlarmDescr,
        falconInputLabel,
        falconInputReading,
        falconInputUOM
    }
    DESCRIPTION
        "The sensor on port #95 has returned to normal."
    ::= 95

falconPort96TrapClear TRAP-TYPE
    ENTERPRISE   falconPortTrapClear 
    VARIABLES {
        falconAlarmId,
        falconAlarmDescr,
        falconInputLabel,
        falconInputReading,
        falconInputUOM
    }
    DESCRIPTION
        "The sensor on port #96 has returned to normal."
    ::= 96

falconPort97TrapClear TRAP-TYPE
    ENTERPRISE   falconPortTrapClear 
    VARIABLES {
        falconAlarmId,
        falconAlarmDescr,
        falconInputLabel,
        falconInputReading,
        falconInputUOM
    }
    DESCRIPTION
        "The sensor on port #97 has returned to normal."
    ::= 97

falconPort98TrapClear TRAP-TYPE
    ENTERPRISE   falconPortTrapClear 
    VARIABLES {
        falconAlarmId,
        falconAlarmDescr,
        falconInputLabel,
        falconInputReading,
        falconInputUOM
    }
    DESCRIPTION
        "The sensor on port #98 has returned to normal."
    ::= 98

falconPort99TrapClear TRAP-TYPE
    ENTERPRISE   falconPortTrapClear 
    VARIABLES {
        falconAlarmId,
        falconAlarmDescr,
        falconInputLabel,
        falconInputReading,
        falconInputUOM
    }
    DESCRIPTION
        "The sensor on port #99 has returned to normal."
    ::= 99

falconPort100TrapClear TRAP-TYPE
    ENTERPRISE   falconPortTrapClear 
    VARIABLES {
        falconAlarmId,
        falconAlarmDescr,
        falconInputLabel,
        falconInputReading,
        falconInputUOM
    }
    DESCRIPTION
        "The sensor on port #100 has returned to normal."
    ::= 100

falconPort101TrapClear TRAP-TYPE
    ENTERPRISE   falconPortTrapClear 
    VARIABLES {
        falconAlarmId,
        falconAlarmDescr,
        falconInputLabel,
        falconInputReading,
        falconInputUOM
    }
    DESCRIPTION
        "The sensor on port #101 has returned to normal."
    ::= 101

falconPort102TrapClear TRAP-TYPE
    ENTERPRISE   falconPortTrapClear 
    VARIABLES {
        falconAlarmId,
        falconAlarmDescr,
        falconInputLabel,
        falconInputReading,
        falconInputUOM
    }
    DESCRIPTION
        "The sensor on port #102 has returned to normal."
    ::= 102


falconPort103TrapClear TRAP-TYPE
    ENTERPRISE   falconPortTrapClear 
    VARIABLES {
        falconAlarmId,
        falconAlarmDescr,
        falconInputLabel,
        falconInputReading,
        falconInputUOM
    }
    DESCRIPTION
        "The sensor on port #103 has returned to normal."
    ::= 103

falconPort104TrapClear TRAP-TYPE
    ENTERPRISE   falconPortTrapClear 
    VARIABLES {
        falconAlarmId,
        falconAlarmDescr,
        falconInputLabel,
        falconInputReading,
        falconInputUOM
    }
    DESCRIPTION
        "The sensor on port #104 has returned to normal."
    ::= 104

falconTemperatureSensorTrapClear TRAP-TYPE
    ENTERPRISE   falconPortTrapClear 
    VARIABLES {
        falconAlarmId,
        falconAlarmDescr,
        falconTemperatureSensorLabel,
        falconTemperatureSensorReading,
        falconTemperatureSensorUOM
    }
    DESCRIPTION
        "The internal temperature sensor has returned to normal."
    ::= 105

falconHumiditySensorTrapClear TRAP-TYPE
    ENTERPRISE   falconPortTrapClear 
    VARIABLES {
        falconAlarmId,
        falconAlarmDescr,
        falconHumiditySensorLabel,
        falconHumiditySensorReading,
        falconHumiditySensorUOM
    }
    DESCRIPTION
        "The internal Humidity sensor has returned to normal."
    ::= 106


--
-- The falcon Extension
--
        fms-X OBJECT IDENTIFIER ::= { falcon-em 2 }
        fms-A OBJECT IDENTIFIER ::= { falcon-em 3 }
        fms-B OBJECT IDENTIFIER ::= { falcon-em 4 }
        fms-C OBJECT IDENTIFIER ::= { falcon-em 5 }
        fms-AAxx OBJECT IDENTIFIER ::= { falcon-em 3300 }
        fms-AAAx OBJECT IDENTIFIER ::= { falcon-em 3330 }
        fms-AAAA OBJECT IDENTIFIER ::= { falcon-em 3333 }
        fms-AAAC OBJECT IDENTIFIER ::= { falcon-em 3335 }
        fms-AABx OBJECT IDENTIFIER ::= { falcon-em 3340 }
        fms-AABB OBJECT IDENTIFIER ::= { falcon-em 3344 }
        fms-AACx OBJECT IDENTIFIER ::= { falcon-em 3350 }
        fms-AACC OBJECT IDENTIFIER ::= { falcon-em 3355 }
        fms-ABxx OBJECT IDENTIFIER ::= { falcon-em 3400 }
        fms-ABBx OBJECT IDENTIFIER ::= { falcon-em 3440 }
        fms-ABBB OBJECT IDENTIFIER ::= { falcon-em 3444 }
        fms-ABBC OBJECT IDENTIFIER ::= { falcon-em 3445 }
        fms-ABCx OBJECT IDENTIFIER ::= { falcon-em 3450 }
        fms-ABCC OBJECT IDENTIFIER ::= { falcon-em 3455 }
        fms-ACxx OBJECT IDENTIFIER ::= { falcon-em 3500 }
        fms-ACCx OBJECT IDENTIFIER ::= { falcon-em 3550 }
        fms-ACCC OBJECT IDENTIFIER ::= { falcon-em 3555 }
        fms-BBxx OBJECT IDENTIFIER ::= { falcon-em 4400 }
        fms-BBBx OBJECT IDENTIFIER ::= { falcon-em 4440 }
        fms-BBBB OBJECT IDENTIFIER ::= { falcon-em 4444 }
        fms-BBBC OBJECT IDENTIFIER ::= { falcon-em 4445 }
        fms-BBCx OBJECT IDENTIFIER ::= { falcon-em 4450 }
        fms-BBCC OBJECT IDENTIFIER ::= { falcon-em 4455 }
        fms-BCxx OBJECT IDENTIFIER ::= { falcon-em 4500 }
        fms-BCCx OBJECT IDENTIFIER ::= { falcon-em 4550 }
        fms-BCCC OBJECT IDENTIFIER ::= { falcon-em 4555 }
        fms-CCxx OBJECT IDENTIFIER ::= { falcon-em 5500 }
        fms-CxCC OBJECT IDENTIFIER ::= { falcon-em 5055 }
        fms-CCxC OBJECT IDENTIFIER ::= { falcon-em 5505 }
        fms-CCCx OBJECT IDENTIFIER ::= { falcon-em 5550 }
        fms-CCCC OBJECT IDENTIFIER ::= { falcon-em 5555 } 
END
