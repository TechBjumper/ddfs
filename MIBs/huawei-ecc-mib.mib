HUAWEI-ECC-MIB DEFINITIONS ::= BEGIN
                                 IMPORTS
huaweiUtility
FROM HUAWEI-MIB
                                             OBJECT-GROUP, NOTIFICATION-GROUP
                                                 FROM SNMPv2-CONF
                                             Integer32, Unsigned32, OBJECT-TYPE, MODULE-IDENTITY, NOTIFICATION-TYPE
                                                 FROM SNMPv2-SMI
                                             TEXTUAL-CONVENTION
                                                 FROM SNMPv2-TC;
hwIDCMonitorMIB MODULE-IDENTITY
LAST-UPDATED "201210240000Z"
ORGANIZATION 
                                             "Huawei Technologies Co.,Ltd."
CONTACT-INFO 
                                             "Floor 5, Block 4, R&D Building,
                                             Huawei Longgang Production Base,
                                             Shenzhen,   P.R.C.
                                             http://www.huawei.com
                                             Zip: 518129."
DESCRIPTION 
                                             "EMAP MIB defines MIB objects which provides load and backup management, patch management NMS interfaces.
                                             The current version is v1.01"
REVISION "201210240000Z"
                                             DESCRIPTION 
                                             "Huawei emap mib v1.00"
::= { huaweiUtility 178 }

DisplayString ::= TEXTUAL-CONVENTION
                                             STATUS current
                                             DESCRIPTION 
                                             "Description."
                                             SYNTAX OCTET STRING (SIZE (1..64))
                                             
                                             RowStatus ::= TEXTUAL-CONVENTION
                                             STATUS current
                                             DESCRIPTION 
                                             "Description."
                                             SYNTAX INTEGER
                                             {
                                                     active(1),
                                                     notInService(2),
                                                     notReady(3),
                                                     createAndGo(4),
                                                     createAndWait(5),
                                                     destroy(6)
                                             }
                                             
                                             DateAndTime ::= TEXTUAL-CONVENTION
                                             STATUS current
                                             DESCRIPTION 
                                             "Description."
                                             SYNTAX OCTET STRING (SIZE (8..11))
                                             
                                             RunStatus ::= TEXTUAL-CONVENTION
                                             STATUS current
                                             DESCRIPTION 
                                                     "This integer value represents running status of the system. 
                                                     Depending on situation there may be limits on allowed values.
                                                     Operational values:
                                                     (1) unknown - status has not yet been defined
                                                     (2) normal - there are no activated alarms
                                                     (3) alarm - alarm status
                                             "
                                             SYNTAX INTEGER
                                             {
                                                     unknow(1),
                                                     normal(2),
                                                     alarm(3)
                                             }
                                             
                                             MeasuresRange ::= TEXTUAL-CONVENTION
                                             STATUS current
                                             DESCRIPTION 
                                             "Description."
                                             SYNTAX Integer32
                                             
                                             TruthValue ::= TEXTUAL-CONVENTION
                                             STATUS current
                                             DESCRIPTION 
                                             "Description."
                                             SYNTAX INTEGER
                                             {
                                                     true(1),
                                                     false(2)
                                             }
        hwMonitor OBJECT IDENTIFIER ::= { hwIDCMonitorMIB 1 }

        hwIDCMonitorMIBObjects OBJECT IDENTIFIER ::= { hwMonitor 1 }

        hwMonitorInfo OBJECT IDENTIFIER ::= { hwIDCMonitorMIBObjects 1 }

        hwMonitorAlarms OBJECT IDENTIFIER ::= { hwMonitorInfo 2 }

        hwAlarmTrapOrdinalNumber OBJECT-TYPE
            SYNTAX Unsigned32
            MAX-ACCESS read-write
            STATUS current
            DESCRIPTION
                "Monitor alarm serial number (SN) is the unique ID of the alarm Trap. It is used to resend and synchronize alarms. Its value range is 0 to 4294967296. When the value exceeds the maximum value, the system automatically clears the value and numbers the alarm from 0 to 4294967296.  
                  If the network management system (NMS) recieve the alarm number is not consequential, in such case that it notifies the SNMP agent the alarm number required.  So the monitor send the 100 alarm messages in maximum, after consequencial number required by NMS again. Specially, if NMS set the value to 0, the agent would clear the alarm queue automatically."
            ::= { hwMonitorAlarms 1 }

        hwAlarmQuantity OBJECT-TYPE
            SYNTAX Unsigned32 (0..65535)
            MAX-ACCESS read-only
            STATUS current
            DESCRIPTION
                "Alarm number in monitor alarm list which are support. It is used for alarm list management by NMS, and value range is 0 to 65535. "
            ::= { hwMonitorAlarms 2 }

        hwMonitorAlarmTable OBJECT-TYPE
            SYNTAX SEQUENCE OF HwMonitorAlarmEntry
            MAX-ACCESS not-accessible
             STATUS current
             DESCRIPTION
                "The table of monitor alarm."
            ::= { hwMonitorAlarms 3 }

        hwMonitorAlarmEntry OBJECT-TYPE
                        SYNTAX HwMonitorAlarmEntry
            MAX-ACCESS not-accessible
             STATUS current
             DESCRIPTION
                "The table of monitor alarm."
            INDEX { hwAlarmIndex }
            ::= { hwMonitorAlarmTable 1 }

        HwMonitorAlarmEntry            ::= SEQUENCE {
                hwAlarmIndex
                    Integer32,
                hwAlarmText
                    OCTET STRING,
                hwAlarmLevel
                    INTEGER,
                hwAlarmSigDesc
                    OCTET STRING,
                hwAlarmRowStatus
                    RowStatus
            }

        hwAlarmIndex OBJECT-TYPE
            SYNTAX Integer32 (1..65535)
            MAX-ACCESS read-only
            STATUS current
            DESCRIPTION
                "Monitor alarm table index. It is the unique ID of the monitor alarm."
            ::= { hwMonitorAlarmEntry 1 }

        hwAlarmText OBJECT-TYPE
            SYNTAX OCTET STRING (SIZE (0..63))
            MAX-ACCESS read-only
            STATUS current
            DESCRIPTION
                "Alarm name. It is of the character string type, and used to specify the content of a specific alarm.  "
            ::= { hwMonitorAlarmEntry 2 }

        hwAlarmLevel OBJECT-TYPE
            SYNTAX INTEGER
                {
                critical(1),
                major(2),
                minor(3),
                warning(4),
                unknown(255)
                }
            MAX-ACCESS read-write
            STATUS current
            DESCRIPTION
                "Alarm level, which users can configure the alarm severity, is an enumeration type:
                  If the enumeration value is 1, it indicates a critical alarm;
                  If the enumeration value is 2, it indicates a major alarm;
                  If the enumeration value is 3, it indicates a minor alarm;
                  If the enumeration value is 4, it indicates a warning; "
            ::= { hwMonitorAlarmEntry 3 }

        hwAlarmSigDesc OBJECT-TYPE
            SYNTAX OCTET STRING (SIZE (0..127))
            MAX-ACCESS read-only
            STATUS current
            DESCRIPTION
                "Alarm signal description. It is used to add and describe alarm content. Users can define the description of the alarm. Otherwise, the configured character can not be any other languages except English."
            ::= { hwMonitorAlarmEntry 4 }

        hwAlarmRowStatus OBJECT-TYPE
            SYNTAX RowStatus
            MAX-ACCESS read-create
            STATUS current
            DESCRIPTION
                "RowStatus of monitor alarms table."
            ::= { hwMonitorAlarmEntry 100 }

        hwNetPointTable OBJECT-TYPE
            SYNTAX SEQUENCE OF HwNetPointEntry
            MAX-ACCESS not-accessible
             STATUS current
             DESCRIPTION
                "The Table of Net Point."
            ::= { hwMonitorInfo 3 }

        hwNetPointEntry OBJECT-TYPE
                        SYNTAX HwNetPointEntry
            MAX-ACCESS not-accessible
             STATUS current
             DESCRIPTION
                "The Table of Net Point."
            INDEX { hwNetPointIndex }
            ::= { hwNetPointTable 1 }

        HwNetPointEntry            ::= SEQUENCE {
                hwNetPointIndex
                    Unsigned32,
                hwNetPointName
                    OCTET STRING,
                hwNetPointCheckEnable
                    INTEGER,
                hwNetPointState
                    INTEGER,
                hwNetPointIp
                    IpAddress
            }

        hwNetPointIndex OBJECT-TYPE
            SYNTAX Unsigned32
            MAX-ACCESS read-only
            STATUS current
            DESCRIPTION
                "Index of Net Point 1 to 16."
            ::= { hwNetPointEntry 1 }

        hwNetPointName OBJECT-TYPE
            SYNTAX OCTET STRING (SIZE (1..50))
            MAX-ACCESS read-only
            STATUS current
            DESCRIPTION
                "The Name of Net Point."
            ::= { hwNetPointEntry 2 }

        hwNetPointCheckEnable OBJECT-TYPE
            SYNTAX INTEGER
                {
                Disable(1),
                EnableAlarm(2),
                NoAlarm(3),
                Unknown(255)
                }
            MAX-ACCESS read-write
            STATUS current
            DESCRIPTION
                "Set the status of testing.
                  1 : Do not check the netpoint.
                  2 : Check netpoint, and alarm when disconnect.
                  3 : Check netpoint, but don't alarm when disconnect."
            ::= { hwNetPointEntry 3 }

        hwNetPointState OBJECT-TYPE
            SYNTAX INTEGER
                {
                Disconneted(1),
                OnLine(2),
                Unkown(255)
                }
            MAX-ACCESS read-only
            STATUS current
            DESCRIPTION
                "the connect status of NetPoint.
                  1 : the NetPoint can not connected.
                  2 : the NetPoint is reachable."
            ::= { hwNetPointEntry 4 }

        hwNetPointIp OBJECT-TYPE
            SYNTAX IpAddress (8..16)
            MAX-ACCESS read-write
            STATUS current
            DESCRIPTION
                "the IP address of NoetPoint."
            ::= { hwNetPointEntry 5 }

        hwNetPointExtendTable OBJECT IDENTIFIER ::= { hwMonitorInfo 4 }

        hwNetPointExtend1Table OBJECT-TYPE
            SYNTAX SEQUENCE OF HwNetPointExtend1Entry
            MAX-ACCESS not-accessible
             STATUS current
             DESCRIPTION
                "The Extended 1 Table of Net Point."
            ::= { hwNetPointExtendTable 1 }

        hwNetPointExtend1Entry OBJECT-TYPE
                        SYNTAX HwNetPointExtend1Entry
            MAX-ACCESS not-accessible
             STATUS current
             DESCRIPTION
                "The Extended 1 Table of Net Point."
            INDEX { hwNetPointIndex }
            ::= { hwNetPointExtend1Table 1 }

        HwNetPointExtend1Entry            ::= SEQUENCE {
                hwNetPointIndex
                    Unsigned32,
                hwNetPointExtend1Name
                    OCTET STRING,
                hwNetPointCheckEnable
                    INTEGER,
                hwNetPointState
                    INTEGER,
                hwNetPointIp
                    IpAddress
            }

        hwNetPointIndex OBJECT-TYPE
            SYNTAX Unsigned32
            MAX-ACCESS read-only
            STATUS current
            DESCRIPTION
                "Index of Net Point 17 to 47."
            ::= { hwNetPointExtend1Entry 1 }

        hwNetPointExtend1Name OBJECT-TYPE
            SYNTAX OCTET STRING (SIZE (1..50))
            MAX-ACCESS read-only
            STATUS current
            DESCRIPTION
                "The Name of Net Point Extend1."
            ::= { hwNetPointExtend1Entry 2 }

        hwNetPointCheckEnable OBJECT-TYPE
            SYNTAX INTEGER
                {
                Disable(1),
                EnableAlarm(2),
                NoAlarm(3),
                Unknown(255)
                }
            MAX-ACCESS read-write
            STATUS current
            DESCRIPTION
                "Set the status of testing.
                  1 : Do not check the netpoint.
                  2 : Check netpoint, and alarm when disconnect.
                  3 : Check netpoint, but don't alarm when disconnect."
            ::= { hwNetPointExtend1Entry 3 }

        hwNetPointState OBJECT-TYPE
            SYNTAX INTEGER
                {
                Disconneted(1),
                OnLine(2),
                Unkown(255)
                }
            MAX-ACCESS read-only
            STATUS current
            DESCRIPTION
                "the connect status of NetPoint.
                  1 : the NetPoint can not connected.
                  2 : the NetPoint is reachable."
            ::= { hwNetPointExtend1Entry 4 }

        hwNetPointIp OBJECT-TYPE
            SYNTAX IpAddress (8..16)
            MAX-ACCESS read-write
            STATUS current
            DESCRIPTION
                "the IP address of NoetPoint."
            ::= { hwNetPointExtend1Entry 5 }

        hwNetPointExtend2Table OBJECT-TYPE
            SYNTAX SEQUENCE OF HwNetPointExtend2Entry
            MAX-ACCESS not-accessible
             STATUS current
             DESCRIPTION
                "The Extended 2 Table of Net Point."
            ::= { hwNetPointExtendTable 2 }

        hwNetPointExtend2Entry OBJECT-TYPE
                        SYNTAX HwNetPointExtend2Entry
            MAX-ACCESS not-accessible
             STATUS current
             DESCRIPTION
                "The Extended 2 Table of Net Point."
            INDEX { hwNetPointIndex }
            ::= { hwNetPointExtend2Table 1 }

        HwNetPointExtend2Entry            ::= SEQUENCE {
                hwNetPointIndex
                    Unsigned32,
                hwNetPointExtend2Name
                    OCTET STRING,
                hwNetPointCheckEnable
                    INTEGER,
                hwNetPointState
                    INTEGER,
                hwNetPointIp
                    IpAddress
            }

        hwNetPointIndex OBJECT-TYPE
            SYNTAX Unsigned32
            MAX-ACCESS read-only
            STATUS current
            DESCRIPTION
                "Index of Net Point 48 to 78."
            ::= { hwNetPointExtend2Entry 1 }

        hwNetPointExtend2Name OBJECT-TYPE
            SYNTAX OCTET STRING (SIZE (1..50))
            MAX-ACCESS read-only
            STATUS current
            DESCRIPTION
                "The Name of Net Point Extend2."
            ::= { hwNetPointExtend2Entry 2 }

        hwNetPointCheckEnable OBJECT-TYPE
            SYNTAX INTEGER
                {
                Disable(1),
                EnableAlarm(2),
                NoAlarm(3),
                Unknown(255)
                }
            MAX-ACCESS read-write
            STATUS current
            DESCRIPTION
                "Set the status of testing.
                  1 : Do not check the netpoint.
                  2 : Check netpoint, and alarm when disconnect.
                  3 : Check netpoint, but don't alarm when disconnect."
            ::= { hwNetPointExtend2Entry 3 }

        hwNetPointState OBJECT-TYPE
            SYNTAX INTEGER
                {
                Disconneted(1),
                OnLine(2),
                Unkown(255)
                }
            MAX-ACCESS read-only
            STATUS current
            DESCRIPTION
                "the connect status of NetPoint.
                  1 : the NetPoint can not connected.
                  2 : the NetPoint is reachable."
            ::= { hwNetPointExtend2Entry 4 }

        hwNetPointIp OBJECT-TYPE
            SYNTAX IpAddress (8..16)
            MAX-ACCESS read-write
            STATUS current
            DESCRIPTION
                "the IP address of NoetPoint."
            ::= { hwNetPointExtend2Entry 5 }

        hwNetPointExtend3Table OBJECT-TYPE
            SYNTAX SEQUENCE OF HwNetPointExtend3Entry
            MAX-ACCESS not-accessible
             STATUS current
             DESCRIPTION
                "The Extended 3 Table of Net Point."
            ::= { hwNetPointExtendTable 3 }

        hwNetPointExtend3Entry OBJECT-TYPE
                        SYNTAX HwNetPointExtend3Entry
            MAX-ACCESS not-accessible
             STATUS current
             DESCRIPTION
                "The Extended 3 Table of Net Point."
            INDEX { hwNetPointIndex }
            ::= { hwNetPointExtend3Table 1 }

        HwNetPointExtend3Entry            ::= SEQUENCE {
                hwNetPointIndex
                    Unsigned32,
                hwNetPointExtend3Name
                    OCTET STRING,
                hwNetPointCheckEnable
                    INTEGER,
                hwNetPointState
                    INTEGER,
                hwNetPointIp
                    IpAddress
            }

        hwNetPointIndex OBJECT-TYPE
            SYNTAX Unsigned32
            MAX-ACCESS read-only
            STATUS current
            DESCRIPTION
                "Index of Net Point 79 to 100."
            ::= { hwNetPointExtend3Entry 1 }

        hwNetPointExtend3Name OBJECT-TYPE
            SYNTAX OCTET STRING (SIZE (1..50))
            MAX-ACCESS read-only
            STATUS current
            DESCRIPTION
                "The Name of Net Point Extend3."
            ::= { hwNetPointExtend3Entry 2 }

        hwNetPointCheckEnable OBJECT-TYPE
            SYNTAX INTEGER
                {
                Disable(1),
                EnableAlarm(2),
                NoAlarm(3),
                Unknown(255)
                }
            MAX-ACCESS read-write
            STATUS current
            DESCRIPTION
                "Set the status of testing.
                  1 : Do not check the netpoint.
                  2 : Check netpoint, and alarm when disconnect.
                  3 : Check netpoint, but don't alarm when disconnect."
            ::= { hwNetPointExtend3Entry 3 }

        hwNetPointState OBJECT-TYPE
            SYNTAX INTEGER
                {
                Disconneted(1),
                OnLine(2),
                Unkown(255)
                }
            MAX-ACCESS read-only
            STATUS current
            DESCRIPTION
                "the connect status of NetPoint.
                  1 : the NetPoint can not connected.
                  2 : the NetPoint is reachable."
            ::= { hwNetPointExtend3Entry 4 }

        hwNetPointIp OBJECT-TYPE
            SYNTAX IpAddress (8..16)
            MAX-ACCESS read-write
            STATUS current
            DESCRIPTION
                "the IP address of NoetPoint."
            ::= { hwNetPointExtend3Entry 5 }

        hwMonitorSummary OBJECT IDENTIFIER ::= { hwMonitorInfo 1 }

        hwMonitorId OBJECT-TYPE
            SYNTAX OCTET STRING (SIZE (0..32))
            MAX-ACCESS read-only
            STATUS current
            DESCRIPTION
                "Monitor identity,Its unique value is bar code of main control board"
            ::= { hwMonitorSummary 1 }

        hwMonitorName OBJECT-TYPE
            SYNTAX OCTET STRING (SIZE (0..8))
            MAX-ACCESS read-write
            STATUS current
            DESCRIPTION
                "Monitor name, which users can configure, is used to specify a monitor.  Otherwise, the configured character can not be any other languages except English."
            ::= { hwMonitorSummary 2 }

        hwMonitorIp OBJECT-TYPE
            SYNTAX IpAddress (8..16)
            MAX-ACCESS read-write
            STATUS current
            DESCRIPTION
                "Monitor IP address, default value is 192.168.1.168. Users need to configure the monitor IP address."
            ::= { hwMonitorSummary 3 }

        hwMonitorNetmask OBJECT-TYPE
            SYNTAX IpAddress (8..16)
            MAX-ACCESS read-write
            STATUS current
            DESCRIPTION
                "Monitor netmask, default value is 255.255.255.0. Users need to configure the monitor netmask."
            ::= { hwMonitorSummary 4 }

        hwMonitorGateway OBJECT-TYPE
            SYNTAX IpAddress (8..16)
            MAX-ACCESS read-write
            STATUS current
            DESCRIPTION
                "Monitor gateway, default value is 192.168.1.1. Users need to configure the monitor gateway."
            ::= { hwMonitorSummary 5 }

        hwMonitorDescription OBJECT-TYPE
            SYNTAX OCTET STRING (SIZE (0..127))
            MAX-ACCESS read-write
            STATUS current
            DESCRIPTION
                "Monitor description. It is of the character string type. It is used to describe the monitor information such as the monitor location, which users can configure.  Otherwise, the configured character can not be any other languages except English."
            ::= { hwMonitorSummary 6 }

        hwMonitorSubrackEsn OBJECT-TYPE
            SYNTAX OCTET STRING (SIZE (0..20))
            MAX-ACCESS read-only
            STATUS current
            DESCRIPTION
                "Monitor subrack identity,Its unique value is bar code of subrack board"
            ::= { hwMonitorSummary 7 }

        hwMonitorSoftwareVersion OBJECT-TYPE
            SYNTAX OCTET STRING (SIZE (0..25))
            MAX-ACCESS read-only
            STATUS current
            DESCRIPTION
                "Monitor software version."
            ::= { hwMonitorSummary 8 }

        hwMonitorHardwareVesion OBJECT-TYPE
            SYNTAX OCTET STRING (SIZE (0..4))
            MAX-ACCESS read-only
            STATUS current
            DESCRIPTION
                "Monitor hardware version."
            ::= { hwMonitorSummary 9 }

        hwMonitorEquipAdd OBJECT-TYPE
            SYNTAX OCTET STRING (SIZE (0..20))
            MAX-ACCESS read-write
            STATUS current
            DESCRIPTION
                "Moonitor add equipment. String Type. Format is 'equip type index'-'slot number'-'port number'-'equip address'-'timeout'. For example, such as adding UPS, set value is '1-2-3-1-2'. The 'equip type index' is:
                    Value 1 indicates UPS.
                    Value 2 indicates EA800UPS.
                    Value 3 indicates Temp/Hum.
                    Value 4 indicates UL33UPS.
                    Value 5 indicates NetCol.
                    Value 6 indicates PDU8000.
                    Value 7 indicates ATS.
                    Value 8 indicates PD510."
            ::= { hwMonitorSummary 10 }

        hwMonitorResumeSysCfg OBJECT-TYPE
            SYNTAX INTEGER
                {
                yes(1)
                }
            MAX-ACCESS read-write
            STATUS current
            DESCRIPTION
                "Monitor resume system configure."
            ::= { hwMonitorSummary 11 }

        hwMUS02A OBJECT IDENTIFIER ::= { hwIDCMonitorMIBObjects 2 }

        hwMUS02AConfigTable OBJECT-TYPE
            SYNTAX SEQUENCE OF HwMUS02AConfigEntry
            MAX-ACCESS not-accessible
             STATUS current
             DESCRIPTION
                "RS485 communication card config table. Use this table to get RS485 communication card's equipment ID and equipment name, to set serial attribute and control power output as well. "
            ::= { hwMUS02A 1 }

        hwMUS02AConfigEntry OBJECT-TYPE
                        SYNTAX HwMUS02AConfigEntry
            MAX-ACCESS not-accessible
             STATUS current
             DESCRIPTION
                "RS485 communication card config table. Use this table to get RS485 communication card's equipment ID and equipment name, to set serial attribute and control power output as well. "
            INDEX { hwMUS02AConfigIndex }
            ::= { hwMUS02AConfigTable 1 }

        HwMUS02AConfigEntry            ::= SEQUENCE {
                hwMUS02AConfigIndex
                    Integer32,
                hwMUS02AEquipId
                    Unsigned32,
                hwMUS02AEquipName
                    OCTET STRING,
                hwMUS02ACom1BaudRate
                    INTEGER,
                hwMUS02ACom1DataLength
                    INTEGER,
                hwMUS02ACom1StopBits
                    Unsigned32,
                hwMUS02ACom1Parity
                    INTEGER,
                hwMUS02ACom2BaudRate
                    INTEGER,
                hwMUS02ACom2DataLength
                    INTEGER,
                hwMUS02ACom2StopBits
                    Unsigned32,
                hwMUS02ACom2Parity
                    INTEGER,
                hwMUS02ACom3BaudRate
                    INTEGER,
                hwMUS02ACom3DataLength
                    INTEGER,
                hwMUS02ACom3StopBits
                    Unsigned32,
                hwMUS02ACom3Parity
                    INTEGER,
                hwMUS02ACom4BaudRate
                    INTEGER,
                hwMUS02ACom4DataLength
                    INTEGER,
                hwMUS02ACom4StopBits
                    Unsigned32,
                hwMUS02ACom4Parity
                    INTEGER,
                hwMUS02ACom5BaudRate
                    INTEGER,
                hwMUS02ACom5DataLength
                    INTEGER,
                hwMUS02ACom5StopBits
                    Unsigned32,
                hwMUS02ACom5Parity
                    INTEGER,
                hwMUS02ACom4PowerOutput
                    INTEGER,
                hwMUS02ACom5PowerOutput
                    INTEGER,
                hwMUS02AConfigRowStatus
                    RowStatus
            }

        hwMUS02AConfigIndex OBJECT-TYPE
            SYNTAX Integer32 (11..16)
            MAX-ACCESS read-only
            STATUS current
            DESCRIPTION
                "Index of the device configuration table for the RS485 communication card, which value range: 11 to 16. "
            ::= { hwMUS02AConfigEntry 1 }

        hwMUS02AEquipId OBJECT-TYPE
            SYNTAX Unsigned32 (11..16)
            MAX-ACCESS read-only
            STATUS current
            DESCRIPTION
                "RS485 communication card's equipment ID. Value range: 11 to 16. "
            ::= { hwMUS02AConfigEntry 2 }

        hwMUS02AEquipName OBJECT-TYPE
            SYNTAX OCTET STRING (SIZE (0..63))
            MAX-ACCESS read-write
            STATUS current
            DESCRIPTION
                "Equipment name, of the character string type, is used to specify the RS485 communication card. Users can configure it. Otherwise, the configured character can not be any other languages except English. Value range: 0 to 63. "
            ::= { hwMUS02AConfigEntry 3 }

        hwMUS02ACom1BaudRate OBJECT-TYPE
            SYNTAX INTEGER
                {
                9600(1),
                2400(2),
                4800(3),
                19200(4),
                115200(5)
                }
            MAX-ACCESS read-write
            STATUS current
            DESCRIPTION
                "COM1 port's communication baud rate, which users can configure the serial communication speed, is an enumeration type:
                  If the enumeration value is 1, it indicates baud rate equals 9600bps;
                  If the enumeration value is 2, it indicates baud rate equals 2400bps;
                  If the enumeration value is 3, it indicates baud rate equals 4800bps;
                  If the enumeration value is 4, it indicates baud rate equals 19200bps;
                  If the enumeration value is 5, it indicates baud rate equals 115200bps;"
            ::= { hwMUS02AConfigEntry 4 }

        hwMUS02ACom1DataLength OBJECT-TYPE
            SYNTAX INTEGER
                {
                8(1)
                }
            MAX-ACCESS read-only
            STATUS current
            DESCRIPTION
                "COM1 port's serial communication data length.Its value is 8,not allowed to be changed."
            ::= { hwMUS02AConfigEntry 5 }

        hwMUS02ACom1StopBits OBJECT-TYPE
            SYNTAX Unsigned32 (1..2)
            MAX-ACCESS read-write
            STATUS current
            DESCRIPTION
                "COM1 port's communication stop bit, which users can configure the serial communication stop bit length.Value range: 1 to 2. "
            ::= { hwMUS02AConfigEntry 6 }

        hwMUS02ACom1Parity OBJECT-TYPE
            SYNTAX INTEGER
                {
                none(1),
                even(2),
                odd(3)
                }
            MAX-ACCESS read-write
            STATUS current
            DESCRIPTION
                "COM1 port's communication parity, which users can configure the serial communication parity, is an enumeration type:
                  If the enumeration value is 1, it indicates none parity check;
                  If the enumeration value is 2, it indicates even parity check;
                  If the enumeration value is 3, it indicates odd parity check;"
            ::= { hwMUS02AConfigEntry 7 }

        hwMUS02ACom2BaudRate OBJECT-TYPE
            SYNTAX INTEGER
                {
                9600(1),
                2400(2),
                4800(3),
                19200(4),
                115200(5)
                }
            MAX-ACCESS read-write
            STATUS current
            DESCRIPTION
                "COM2 port's communication baud rate, which users can configure the serial communication speed, is an enumeration type:
                  If the enumeration value is 1, it indicates baud rate equals 9600bps;
                  If the enumeration value is 2, it indicates baud rate equals 2400bps;
                  If the enumeration value is 3, it indicates baud rate equals 4800bps;
                  If the enumeration value is 4, it indicates baud rate equals 19200bps;
                  If the enumeration value is 5, it indicates baud rate equals 115200bps;"
            ::= { hwMUS02AConfigEntry 8 }

        hwMUS02ACom2DataLength OBJECT-TYPE
            SYNTAX INTEGER
                {
                8(1)
                }
            MAX-ACCESS read-only
            STATUS current
            DESCRIPTION
                "COM2 port's serial communication data length.Its value is 8,not allowed to be changed."
            ::= { hwMUS02AConfigEntry 9 }

        hwMUS02ACom2StopBits OBJECT-TYPE
            SYNTAX Unsigned32 (1..2)
            MAX-ACCESS read-write
            STATUS current
            DESCRIPTION
                "COM2 port's communication stop bit, which users can configure the serial communication stop bit length.Value range: 1 to 2. "
            ::= { hwMUS02AConfigEntry 10 }

        hwMUS02ACom2Parity OBJECT-TYPE
            SYNTAX INTEGER
                {
                none(1),
                even(2),
                odd(3)
                }
            MAX-ACCESS read-write
            STATUS current
            DESCRIPTION
                "COM2 port's communication parity, which users can configure the serial communication parity, is an enumeration type:
                  If the enumeration value is 1, it indicates none parity check;
                  If the enumeration value is 2, it indicates even parity check;
                  If the enumeration value is 3, it indicates odd parity check;"
            ::= { hwMUS02AConfigEntry 11 }

        hwMUS02ACom3BaudRate OBJECT-TYPE
            SYNTAX INTEGER
                {
                9600(1),
                2400(2),
                4800(3),
                19200(4),
                115200(5)
                }
            MAX-ACCESS read-write
            STATUS current
            DESCRIPTION
                "COM3 port's communication baud rate, which users can configure the serial communication speed, is an enumeration type:
                  If the enumeration value is 1, it indicates baud rate equals 9600bps;
                  If the enumeration value is 2, it indicates baud rate equals 2400bps;
                  If the enumeration value is 3, it indicates baud rate equals 4800bps;
                  If the enumeration value is 4, it indicates baud rate equals 19200bps;
                  If the enumeration value is 5, it indicates baud rate equals 115200bps;"
            ::= { hwMUS02AConfigEntry 12 }

        hwMUS02ACom3DataLength OBJECT-TYPE
            SYNTAX INTEGER
                {
                8(1)
                }
            MAX-ACCESS read-only
            STATUS current
            DESCRIPTION
                "COM3 port's serial communication data length.Its value is 8,not allowed to be changed."
            ::= { hwMUS02AConfigEntry 13 }

        hwMUS02ACom3StopBits OBJECT-TYPE
            SYNTAX Unsigned32 (1..2)
            MAX-ACCESS read-write
            STATUS current
            DESCRIPTION
                "COM3 port's communication stop bit, which users can configure the serial communication stop bit length.Value range: 1 to 2. "
            ::= { hwMUS02AConfigEntry 14 }

        hwMUS02ACom3Parity OBJECT-TYPE
            SYNTAX INTEGER
                {
                none(1),
                even(2),
                odd(3)
                }
            MAX-ACCESS read-write
            STATUS current
            DESCRIPTION
                "COM3 port's communication parity, which users can configure the serial communication parity, is an enumeration type:
                  If the enumeration value is 1, it indicates none parity check;
                  If the enumeration value is 2, it indicates even parity check;
                  If the enumeration value is 3, it indicates odd parity check;"
            ::= { hwMUS02AConfigEntry 15 }

        hwMUS02ACom4BaudRate OBJECT-TYPE
            SYNTAX INTEGER
                {
                9600(1),
                2400(2),
                4800(3),
                19200(4),
                115200(5)
                }
            MAX-ACCESS read-write
            STATUS current
            DESCRIPTION
                "COM4 port's communication baud rate, which users can configure the serial communication speed, is an enumeration type:
                  If the enumeration value is 1, it indicates baud rate equals 9600bps;
                  If the enumeration value is 2, it indicates baud rate equals 2400bps;
                  If the enumeration value is 3, it indicates baud rate equals 4800bps;
                  If the enumeration value is 4, it indicates baud rate equals 19200bps;
                  If the enumeration value is 5, it indicates baud rate equals 115200bps;"
            ::= { hwMUS02AConfigEntry 16 }

        hwMUS02ACom4DataLength OBJECT-TYPE
            SYNTAX INTEGER
                {
                8(1)
                }
            MAX-ACCESS read-only
            STATUS current
            DESCRIPTION
                "COM4 port's serial communication data length.Its value is 8,not allowed to be changed."
            ::= { hwMUS02AConfigEntry 17 }

        hwMUS02ACom4StopBits OBJECT-TYPE
            SYNTAX Unsigned32 (1..2)
            MAX-ACCESS read-write
            STATUS current
            DESCRIPTION
                "COM4 port's communication stop bit, which users can configure the serial communication stop bit length.Value range: 1 to 2. "
            ::= { hwMUS02AConfigEntry 18 }

        hwMUS02ACom4Parity OBJECT-TYPE
            SYNTAX INTEGER
                {
                none(1),
                even(2),
                odd(3)
                }
            MAX-ACCESS read-write
            STATUS current
            DESCRIPTION
                "COM4 port's communication parity, which users can configure the serial communication parity, is an enumeration type:
                  If the enumeration value is 1, it indicates none parity check;
                  If the enumeration value is 2, it indicates even parity check;
                  If the enumeration value is 3, it indicates odd parity check;"
            ::= { hwMUS02AConfigEntry 19 }

        hwMUS02ACom5BaudRate OBJECT-TYPE
            SYNTAX INTEGER
                {
                9600(1),
                2400(2),
                4800(3),
                19200(4),
                115200(5)
                }
            MAX-ACCESS read-write
            STATUS current
            DESCRIPTION
                "COM5 port's communication baud rate, which users can configure the serial communication speed, is an enumeration type:
                  If the enumeration value is 1, it indicates baud rate equals 9600bps;
                  If the enumeration value is 2, it indicates baud rate equals 2400bps;
                  If the enumeration value is 3, it indicates baud rate equals 4800bps;
                  If the enumeration value is 4, it indicates baud rate equals 19200bps;
                  If the enumeration value is 5, it indicates baud rate equals 115200bps;"
            ::= { hwMUS02AConfigEntry 20 }

        hwMUS02ACom5DataLength OBJECT-TYPE
            SYNTAX INTEGER
                {
                8(1)
                }
            MAX-ACCESS read-only
            STATUS current
            DESCRIPTION
                "COM5 port's serial communication data length.Its value is 8,not allowed to be changed."
            ::= { hwMUS02AConfigEntry 21 }

        hwMUS02ACom5StopBits OBJECT-TYPE
            SYNTAX Unsigned32 (1..2)
            MAX-ACCESS read-write
            STATUS current
            DESCRIPTION
                "COM5 port's communication stop bit, which users can configure the serial communication stop bit length.Value range: 1 to 2. "
            ::= { hwMUS02AConfigEntry 22 }

        hwMUS02ACom5Parity OBJECT-TYPE
            SYNTAX INTEGER
                {
                none(1),
                even(2),
                odd(3)
                }
            MAX-ACCESS read-write
            STATUS current
            DESCRIPTION
                "COM5 port's communication parity, which users can configure the serial communication parity, is an enumeration type:
                  If the enumeration value is 1, it indicates none parity check;
                  If the enumeration value is 2, it indicates even parity check;
                  If the enumeration value is 3, it indicates odd parity check;"
            ::= { hwMUS02AConfigEntry 23 }

        hwMUS02ACom4PowerOutput OBJECT-TYPE
            SYNTAX INTEGER
                {
                no(1),
                yes(2)
                }
            MAX-ACCESS read-write
            STATUS current
            DESCRIPTION
                "COM4 port power output, which users can use it to turn on or off the power, is an enumeration type: 
                  If the enumeration value is 1, it indicates turn off the power;
                  If the enumeration value is 2, it indicates turn on the power;"
            ::= { hwMUS02AConfigEntry 24 }

        hwMUS02ACom5PowerOutput OBJECT-TYPE
            SYNTAX INTEGER
                {
                no(1),
                yes(2)
                }
            MAX-ACCESS read-write
            STATUS current
            DESCRIPTION
                "COM5 port power output, which users can use it to turn on or off the power, is an enumeration type: 
                  If the enumeration value is 1, it indicates turn off the power;
                  If the enumeration value is 2, it indicates turn on the power;"
            ::= { hwMUS02AConfigEntry 25 }

        hwMUS02AConfigRowStatus OBJECT-TYPE
            SYNTAX RowStatus
            MAX-ACCESS read-create
            STATUS current
            DESCRIPTION
                "RowStatus of RS485 communication card config table."
            ::= { hwMUS02AConfigEntry 100 }

        hwMUS02AOperTable OBJECT-TYPE
            SYNTAX SEQUENCE OF HwMUS02AOperEntry
            MAX-ACCESS not-accessible
             STATUS current
             DESCRIPTION
                "RS485 communication card running table. Use this table to get RS485 communication card's presence status,slot nunber,etc. "
            ::= { hwMUS02A 2 }

        hwMUS02AOperEntry OBJECT-TYPE
                        SYNTAX HwMUS02AOperEntry
            MAX-ACCESS not-accessible
             STATUS current
             DESCRIPTION
                "RS485 communication card running table. Use this table to get RS485 communication card's presence status,slot nunber,etc. "
            INDEX { hwMUS02AOperIndex }
            ::= { hwMUS02AOperTable 1 }

        HwMUS02AOperEntry            ::= SEQUENCE {
                hwMUS02AOperIndex
                    Integer32,
                hwMUS02APresenceStatus
                    INTEGER,
                hwMUS02ASlotNo
                    Unsigned32,
                hwMUS02ACom4PowerOutputStatus
                    INTEGER,
                hwMUS02ACom5PowerOutputStatus
                    INTEGER,
                hwMUS02ACom4PowerOutputAlarmStatus
                    INTEGER,
                hwMUS02ACom5PowerOutputAlarmStatus
                    INTEGER,
                hwMUS02AOperRowStatus
                    RowStatus
            }

        hwMUS02AOperIndex OBJECT-TYPE
            SYNTAX Integer32 (11..16)
            MAX-ACCESS read-only
            STATUS current
            DESCRIPTION
                "Index of the device running table for the RS485 communication card, which value range: 11 to 16. "
            ::= { hwMUS02AOperEntry 1 }

        hwMUS02APresenceStatus OBJECT-TYPE
            SYNTAX INTEGER
                {
                not_detected(1),
                detected(2),
                unknown(255)
                }
            MAX-ACCESS read-only
            STATUS current
            DESCRIPTION
                "RS485 communication card's presence status. it is an enumeration type: 
                  If the enumeration value is 1, it indicates device is not detected;
                  If the enumeration value is 2, it indicates device is detected;"
            ::= { hwMUS02AOperEntry 2 }

        hwMUS02ASlotNo OBJECT-TYPE
            SYNTAX Unsigned32 (1..6)
            MAX-ACCESS read-only
            STATUS current
            DESCRIPTION
                "RS485 communication card's slot number. Value range: 1 to 6. "
            ::= { hwMUS02AOperEntry 3 }

        hwMUS02ACom4PowerOutputStatus OBJECT-TYPE
            SYNTAX INTEGER
                {
                off(1),
                on(2),
                unknown(255)
                }
            MAX-ACCESS read-only
            STATUS current
            DESCRIPTION
                "COM4 port power output status, which shows the power is on or off, is an enumeration type: 
                  If the enumeration value is 1, it indicates the power is turned off;
                  If the enumeration value is 2, it indicates the power is turned on;"
            ::= { hwMUS02AOperEntry 4 }

        hwMUS02ACom5PowerOutputStatus OBJECT-TYPE
            SYNTAX INTEGER
                {
                off(1),
                on(2),
                unknown(255)
                }
            MAX-ACCESS read-only
            STATUS current
            DESCRIPTION
                "COM5 port power output status, which shows the power is on or off, is an enumeration type: 
                  If the enumeration value is 1, it indicates the power is turned off;
                  If the enumeration value is 2, it indicates the power is turned on;"
            ::= { hwMUS02AOperEntry 5 }

        hwMUS02ACom4PowerOutputAlarmStatus OBJECT-TYPE
            SYNTAX INTEGER
                {
                normal(1),
                alarm(2),
                unknown(255)
                }
            MAX-ACCESS read-only
            STATUS current
            DESCRIPTION
                "COM4 port power output alarm status, which shows the power status is normal or abnormal, is an enumeration type: 
                  If the enumeration value is 1, it indicates the power status is normal;
                  If the enumeration value is 2, it indicates the power status is abnormal;"
            ::= { hwMUS02AOperEntry 6 }

        hwMUS02ACom5PowerOutputAlarmStatus OBJECT-TYPE
            SYNTAX INTEGER
                {
                normal(1),
                alarm(2),
                unknown(255)
                }
            MAX-ACCESS read-only
            STATUS current
            DESCRIPTION
                "COM5 port power output alarm status, which shows the power status is normal or abnormal, is an enumeration type: 
                  If the enumeration value is 1, it indicates the power status is normal;
                  If the enumeration value is 2, it indicates the power status is abnormal;"
            ::= { hwMUS02AOperEntry 7 }

        hwMUS02AOperRowStatus OBJECT-TYPE
            SYNTAX RowStatus
            MAX-ACCESS read-create
            STATUS current
            DESCRIPTION
                "RowStatus of RS485 communication card running table."
            ::= { hwMUS02AOperEntry 100 }

        hwMUE05A OBJECT IDENTIFIER ::= { hwIDCMonitorMIBObjects 3 }

        hwMUE05AConfigTable OBJECT-TYPE
            SYNTAX SEQUENCE OF HwMUE05AConfigEntry
            MAX-ACCESS not-accessible
             STATUS current
             DESCRIPTION
                "AI and DI extension card config table. Use this table to get AI and DI extension card's equipment ID and equipment name, to set sensors attribute and control channels power output as well. "
            ::= { hwMUE05A 1 }

        hwMUE05AConfigEntry OBJECT-TYPE
                        SYNTAX HwMUE05AConfigEntry
            MAX-ACCESS not-accessible
             STATUS current
             DESCRIPTION
                "AI and DI extension card config table. Use this table to get AI and DI extension card's equipment ID and equipment name, to set sensors attribute and control channels power output as well. "
            INDEX { hwMUE05AConfigIndex }
            ::= { hwMUE05AConfigTable 1 }

        HwMUE05AConfigEntry            ::= SEQUENCE {
                hwMUE05AConfigIndex
                    Unsigned32,
                hwMUE05AEquipId
                    Unsigned32,
                hwMUE05AEquipName
                    OCTET STRING,
                hwMUE05ACh1Enable
                    INTEGER,
                hwMUE05ACh1SensorName
                    OCTET STRING,
                hwMUE05ACh1SensorType
                    INTEGER,
                hwMUE05ACh1SensorUints
                    INTEGER,
                hwMUE05ACh1MeasureUpperLimit
                    Unsigned32,
                hwMUE05ACh1MeasureLowerLimit
                    Integer32,
                hwMUE05ACh1AlarmUpperLimit
                    Unsigned32,
                hwMUE05ACh1AlarmLowerLimit
                    Integer32,
                hwMUE05ACh1PowerOutput
                    INTEGER,
                hwMUE05ACh2Enable
                    INTEGER,
                hwMUE05ACh2SensorName
                    OCTET STRING,
                hwMUE05ACh2SensorType
                    INTEGER,
                hwMUE05ACh2SensorUints
                    INTEGER,
                hwMUE05ACh2MeasureUpperLimit
                    Unsigned32,
                hwMUE05ACh2MeasureLowerLimit
                    Integer32,
                hwMUE05ACh2AlarmUpperLimit
                    Unsigned32,
                hwMUE05ACh2AlarmLowerLimit
                    Integer32,
                hwMUE05ACh2PowerOutput
                    INTEGER,
                hwMUE05ACh3Enable
                    INTEGER,
                hwMUE05ACh3SensorName
                    OCTET STRING,
                hwMUE05ACh3SensorType
                    INTEGER,
                hwMUE05ACh3SensorUints
                    INTEGER,
                hwMUE05ACh3MeasureUpperLimit
                    Unsigned32,
                hwMUE05ACh3MeasureLowerLimit
                    Integer32,
                hwMUE05ACh3AlarmUpperLimit
                    Unsigned32,
                hwMUE05ACh3AlarmLowerLimit
                    Integer32,
                hwMUE05ACh3PowerOutput
                    INTEGER,
                hwMUE05ACh4Enable
                    INTEGER,
                hwMUE05ACh4SensorName
                    OCTET STRING,
                hwMUE05ACh4SensorType
                    INTEGER,
                hwMUE05ACh4SensorUints
                    INTEGER,
                hwMUE05ACh4MeasureUpperLimit
                    Unsigned32,
                hwMUE05ACh4MeasureLowerLimit
                    Integer32,
                hwMUE05ACh4AlarmUpperLimit
                    Unsigned32,
                hwMUE05ACh4AlarmLowerLimit
                    Integer32,
                hwMUE05ACh4PowerOutput
                    INTEGER,
                hwMUE05ADoEnable
                    INTEGER,
                hwMUE05ADoOperate
                    INTEGER,
                hwMUE05ADoConfigLevel
                    INTEGER,
                hwMUE05AConfigRowStatus
                    RowStatus
            }

        hwMUE05AConfigIndex OBJECT-TYPE
            SYNTAX Unsigned32 (21..26)
            MAX-ACCESS read-only
            STATUS current
            DESCRIPTION
                "Index of the device configuration table for the AI and DI extension card, which value range: 21 to 26. "
            ::= { hwMUE05AConfigEntry 1 }

        hwMUE05AEquipId OBJECT-TYPE
            SYNTAX Unsigned32 (21..26)
            MAX-ACCESS read-only
            STATUS current
            DESCRIPTION
                "AI and DI extension card's equipment ID. Value range: 21 to 26. "
            ::= { hwMUE05AConfigEntry 2 }

        hwMUE05AEquipName OBJECT-TYPE
            SYNTAX OCTET STRING (SIZE (0..63))
            MAX-ACCESS read-write
            STATUS current
            DESCRIPTION
                "Equipment name, of the character string type, is used to specify the AI and DI extension card. Users can configure it. Otherwise, the configured character can not be any other languages except English. Value range: 0 to 63. "
            ::= { hwMUE05AConfigEntry 3 }

        hwMUE05ACh1Enable OBJECT-TYPE
            SYNTAX INTEGER
                {
                disable(1),
                enable(2)
                }
            MAX-ACCESS read-write
            STATUS current
            DESCRIPTION
                "AI/DI_1 channel enable,which user must enable it if want to insert sensors, is an enumeration type: 
                  If the enumeration value is 1, it indicates the channel  is disabled;
                  If the enumeration value is 2, it indicates  the channel  is enabled;"
            ::= { hwMUE05AConfigEntry 4 }

        hwMUE05ACh1SensorName OBJECT-TYPE
            SYNTAX OCTET STRING (SIZE (0..33))
            MAX-ACCESS read-only
            STATUS current
            DESCRIPTION
                "AI/DI_1 channel's sensor name."
            ::= { hwMUE05AConfigEntry 5 }

        hwMUE05ACh1SensorType OBJECT-TYPE
            SYNTAX INTEGER
                {
                no(1),
                nc(2),
                door(3),
                smoke(4),
                smoke_nc(5),
                leak(6),
                leak_rope(7),
                leak_nc(8),
                temp_ntc(9),
                general_4_20ma(10)
                }
            MAX-ACCESS read-write
            STATUS current
            DESCRIPTION
                "AI/DI_1 channel's sensor type,which user can configure,is normally open dry contact by default"
            ::= { hwMUE05AConfigEntry 6 }

        hwMUE05ACh1SensorUints OBJECT-TYPE
            SYNTAX INTEGER
                {
                centigrade(1),
                percent(2),
                volt(3),
                ampere(4),
                other(5)
                }
            MAX-ACCESS read-write
            STATUS current
            DESCRIPTION
                "AI/DI_1 channel's sensor unit,which user can configure,is centigrade by default"
            ::= { hwMUE05AConfigEntry 7 }

        hwMUE05ACh1MeasureUpperLimit OBJECT-TYPE
            SYNTAX Unsigned32 (25..100)
            MAX-ACCESS read-write
            STATUS current
            DESCRIPTION
                "The upper limit of sensor measurement range. Value range: 25 to 100."
            ::= { hwMUE05AConfigEntry 8 }

        hwMUE05ACh1MeasureLowerLimit OBJECT-TYPE
            SYNTAX Integer32 ( -50..50)
            MAX-ACCESS read-write
            STATUS current
            DESCRIPTION
                "The lower limit of sensor measurement range. Value range: -50 to 50."
            ::= { hwMUE05AConfigEntry 9 }

        hwMUE05ACh1AlarmUpperLimit OBJECT-TYPE
            SYNTAX Unsigned32 (25..100)
            MAX-ACCESS read-write
            STATUS current
            DESCRIPTION
                "The upper limit of sensor alarm range.  Value range form 25 to 100."
            ::= { hwMUE05AConfigEntry 10 }

        hwMUE05ACh1AlarmLowerLimit OBJECT-TYPE
            SYNTAX Integer32 ( -50..50)
            MAX-ACCESS read-write
            STATUS current
            DESCRIPTION
                "The lower limit of sensor alarm range.  Value range form -50 to 50."
            ::= { hwMUE05AConfigEntry 11 }

        hwMUE05ACh1PowerOutput OBJECT-TYPE
            SYNTAX INTEGER
                {
                yes(1),
                no(2)
                }
            MAX-ACCESS read-write
            STATUS current
            DESCRIPTION
                "AI/DI_1 channel power output, which users can use it to turn on or off the power, is an enumeration type: 
                  If the enumeration value is 1, it indicates turn on the power;
                  If the enumeration value is 2, it indicates turn off the power;"
            ::= { hwMUE05AConfigEntry 12 }

        hwMUE05ACh2Enable OBJECT-TYPE
            SYNTAX INTEGER
                {
                disable(1),
                enable(2)
                }
            MAX-ACCESS read-write
            STATUS current
            DESCRIPTION
                "AI/DI_2 channel enable,which user must enable it if want to insert sensors, is an enumeration type: 
                  If the enumeration value is 1, it indicates the channel  is disabled;
                  If the enumeration value is 2, it indicates  the channel  is enabled;"
            ::= { hwMUE05AConfigEntry 13 }

        hwMUE05ACh2SensorName OBJECT-TYPE
            SYNTAX OCTET STRING (SIZE (0..33))
            MAX-ACCESS read-only
            STATUS current
            DESCRIPTION
                "AI/DI_2 channel's sensor name."
            ::= { hwMUE05AConfigEntry 14 }

        hwMUE05ACh2SensorType OBJECT-TYPE
            SYNTAX INTEGER
                {
                no(1),
                nc(2),
                door(3),
                smoke(4),
                smoke_nc(5),
                leak(6),
                leak_rope(7),
                leak_nc(8),
                temp_ntc(9),
                general_4_20ma(10)
                }
            MAX-ACCESS read-write
            STATUS current
            DESCRIPTION
                "AI/DI_2 channel's sensor type,which user can configure,is normally open dry contact by default"
            ::= { hwMUE05AConfigEntry 15 }

        hwMUE05ACh2SensorUints OBJECT-TYPE
            SYNTAX INTEGER
                {
                centigrade(1),
                percent(2),
                volt(3),
                ampere(4),
                other(5)
                }
            MAX-ACCESS read-write
            STATUS current
            DESCRIPTION
                "AI/DI_2 channel's sensor unit,which user can configure,is centigrade by default"
            ::= { hwMUE05AConfigEntry 16 }

        hwMUE05ACh2MeasureUpperLimit OBJECT-TYPE
            SYNTAX Unsigned32 (25..100)
            MAX-ACCESS read-write
            STATUS current
            DESCRIPTION
                "The upper limit of sensor measurement range. Value range: 25 to 100."
            ::= { hwMUE05AConfigEntry 17 }

        hwMUE05ACh2MeasureLowerLimit OBJECT-TYPE
            SYNTAX Integer32 ( -50..50)
            MAX-ACCESS read-write
            STATUS current
            DESCRIPTION
                "The lower limit of sensor measurement range. Value range: -50 to 50."
            ::= { hwMUE05AConfigEntry 18 }

        hwMUE05ACh2AlarmUpperLimit OBJECT-TYPE
            SYNTAX Unsigned32 (25..100)
            MAX-ACCESS read-write
            STATUS current
            DESCRIPTION
                "The upper limit of sensor alarm range.  Value range form 25 to 100."
            ::= { hwMUE05AConfigEntry 19 }

        hwMUE05ACh2AlarmLowerLimit OBJECT-TYPE
            SYNTAX Integer32 ( -50..50)
            MAX-ACCESS read-write
            STATUS current
            DESCRIPTION
                "The lower limit of sensor alarm range.  Value range form -50 to 50."
            ::= { hwMUE05AConfigEntry 20 }

        hwMUE05ACh2PowerOutput OBJECT-TYPE
            SYNTAX INTEGER
                {
                yes(1),
                no(2)
                }
            MAX-ACCESS read-write
            STATUS current
            DESCRIPTION
                "AI/DI_2 channel power output, which users can use it to turn on or off the power, is an enumeration type: 
                  If the enumeration value is 1, it indicates turn on the power;
                  If the enumeration value is 2, it indicates turn off the power;"
            ::= { hwMUE05AConfigEntry 21 }

        hwMUE05ACh3Enable OBJECT-TYPE
            SYNTAX INTEGER
                {
                disable(1),
                enable(2)
                }
            MAX-ACCESS read-write
            STATUS current
            DESCRIPTION
                "AI/DI_3 channel enable,which user must enable it if want to insert sensors, is an enumeration type: 
                  If the enumeration value is 1, it indicates the channel  is disabled;
                  If the enumeration value is 2, it indicates  the channel  is enabled;"
            ::= { hwMUE05AConfigEntry 22 }

        hwMUE05ACh3SensorName OBJECT-TYPE
            SYNTAX OCTET STRING (SIZE (0..33))
            MAX-ACCESS read-only
            STATUS current
            DESCRIPTION
                "AI/DI_3 channel's sensor name."
            ::= { hwMUE05AConfigEntry 23 }

        hwMUE05ACh3SensorType OBJECT-TYPE
            SYNTAX INTEGER
                {
                no(1),
                nc(2),
                door(3),
                smoke(4),
                smoke_nc(5),
                leak(6),
                leak_rope(7),
                leak_nc(8),
                temp_ntc(9),
                general_4_20ma(10)
                }
            MAX-ACCESS read-write
            STATUS current
            DESCRIPTION
                "AI/DI_3 channel's sensor type,which user can configure,is normally open dry contact by default"
            ::= { hwMUE05AConfigEntry 24 }

        hwMUE05ACh3SensorUints OBJECT-TYPE
            SYNTAX INTEGER
                {
                centigrade(1),
                percent(2),
                volt(3),
                ampere(4),
                other(5)
                }
            MAX-ACCESS read-write
            STATUS current
            DESCRIPTION
                "AI/DI_3 channel's sensor unit,which user can configure,is centigrade by default"
            ::= { hwMUE05AConfigEntry 25 }

        hwMUE05ACh3MeasureUpperLimit OBJECT-TYPE
            SYNTAX Unsigned32 (25..100)
            MAX-ACCESS read-write
            STATUS current
            DESCRIPTION
                "The upper limit of sensor measurement range. Value range: 25 to 100."
            ::= { hwMUE05AConfigEntry 26 }

        hwMUE05ACh3MeasureLowerLimit OBJECT-TYPE
            SYNTAX Integer32 ( -50..50)
            MAX-ACCESS read-write
            STATUS current
            DESCRIPTION
                "The lower limit of sensor measurement range. Value range: -50 to 50."
            ::= { hwMUE05AConfigEntry 27 }

        hwMUE05ACh3AlarmUpperLimit OBJECT-TYPE
            SYNTAX Unsigned32 (25..100)
            MAX-ACCESS read-write
            STATUS current
            DESCRIPTION
                "The upper limit of sensor alarm range.  Value range form 25 to 100."
            ::= { hwMUE05AConfigEntry 28 }

        hwMUE05ACh3AlarmLowerLimit OBJECT-TYPE
            SYNTAX Integer32 ( -50..50)
            MAX-ACCESS read-write
            STATUS current
            DESCRIPTION
                "The lower limit of sensor alarm range.  Value range form -50 to 50."
            ::= { hwMUE05AConfigEntry 29 }

        hwMUE05ACh3PowerOutput OBJECT-TYPE
            SYNTAX INTEGER
                {
                yes(1),
                no(2)
                }
            MAX-ACCESS read-write
            STATUS current
            DESCRIPTION
                "AI/DI_3 channel power output, which users can use it to turn on or off the power, is an enumeration type: 
                  If the enumeration value is 1, it indicates turn on the power;
                  If the enumeration value is 2, it indicates turn off the power;"
            ::= { hwMUE05AConfigEntry 30 }

        hwMUE05ACh4Enable OBJECT-TYPE
            SYNTAX INTEGER
                {
                disable(1),
                enable(2)
                }
            MAX-ACCESS read-write
            STATUS current
            DESCRIPTION
                "AI/DI_4 channel enable,which user must enable it if want to insert sensors, is an enumeration type: 
                  If the enumeration value is 1, it indicates the channel  is disabled;
                  If the enumeration value is 2, it indicates  the channel  is enabled;"
            ::= { hwMUE05AConfigEntry 31 }

        hwMUE05ACh4SensorName OBJECT-TYPE
            SYNTAX OCTET STRING (SIZE (0..33))
            MAX-ACCESS read-only
            STATUS current
            DESCRIPTION
                "AI/DI_4 channel's sensor name."
            ::= { hwMUE05AConfigEntry 32 }

        hwMUE05ACh4SensorType OBJECT-TYPE
            SYNTAX INTEGER
                {
                no(1),
                nc(2),
                door(3),
                smoke(4),
                smoke_nc(5),
                leak(6),
                leak_rope(7),
                leak_nc(8),
                temp_ntc(9),
                general_4_20ma(10)
                }
            MAX-ACCESS read-write
            STATUS current
            DESCRIPTION
                "AI/DI_4 channel's sensor type,which user can configure,is normally open dry contact by default"
            ::= { hwMUE05AConfigEntry 33 }

        hwMUE05ACh4SensorUints OBJECT-TYPE
            SYNTAX INTEGER
                {
                centigrade(1),
                percent(2),
                volt(3),
                ampere(4),
                other(5)
                }
            MAX-ACCESS read-write
            STATUS current
            DESCRIPTION
                "AI/DI_4 channel's sensor unit,which user can configure,is centigrade by default"
            ::= { hwMUE05AConfigEntry 34 }

        hwMUE05ACh4MeasureUpperLimit OBJECT-TYPE
            SYNTAX Unsigned32 (25..100)
            MAX-ACCESS read-write
            STATUS current
            DESCRIPTION
                "The upper limit of sensor measurement range. Value range: 25 to 100."
            ::= { hwMUE05AConfigEntry 35 }

        hwMUE05ACh4MeasureLowerLimit OBJECT-TYPE
            SYNTAX Integer32 ( -50..50)
            MAX-ACCESS read-write
            STATUS current
            DESCRIPTION
                "The lower limit of sensor measurement range. Value range: -50 to 50."
            ::= { hwMUE05AConfigEntry 36 }

        hwMUE05ACh4AlarmUpperLimit OBJECT-TYPE
            SYNTAX Unsigned32 (25..100)
            MAX-ACCESS read-write
            STATUS current
            DESCRIPTION
                "The upper limit of sensor alarm range.  Value range form 25 to 100."
            ::= { hwMUE05AConfigEntry 37 }

        hwMUE05ACh4AlarmLowerLimit OBJECT-TYPE
            SYNTAX Integer32 ( -50..50)
            MAX-ACCESS read-write
            STATUS current
            DESCRIPTION
                "The lower limit of sensor alarm range.  Value range form -50 to 50."
            ::= { hwMUE05AConfigEntry 38 }

        hwMUE05ACh4PowerOutput OBJECT-TYPE
            SYNTAX INTEGER
                {
                yes(1),
                no(2)
                }
            MAX-ACCESS read-write
            STATUS current
            DESCRIPTION
                "AI/DI_4 channel power output, which users can use it to turn on or off the power, is an enumeration type: 
                  If the enumeration value is 1, it indicates turn on the power;
                  If the enumeration value is 2, it indicates turn off the power;"
            ::= { hwMUE05AConfigEntry 39 }

        hwMUE05ADoEnable OBJECT-TYPE
            SYNTAX INTEGER
                {
                disable(1),
                associate(2),
                manual(3)
                }
            MAX-ACCESS read-write
            STATUS current
            DESCRIPTION
                "AI and DI extension card's digital output enable,which users can confugure,is an enumeration type:
                  If the enumeration value is 1, it indicates DO is disabled. Any operation on it will take no effect;
                  If the enumeration value is 2, it indicates DO can be linked to some alarms;
                  If the enumeration value is 3, it indicates DO can be operated manually;"
            ::= { hwMUE05AConfigEntry 40 }

        hwMUE05ADoOperate OBJECT-TYPE
            SYNTAX INTEGER
                {
                close(1),
                open(2)
                }
            MAX-ACCESS read-write
            STATUS current
            DESCRIPTION
                "AI and DI extension card's digital output operate ,which users can use it to control DO action,is an enumeration type: 
                  If the enumeration value is 1, it indicates close DO;
                  If the enumeration value is 2, it indicates open DO;"
            ::= { hwMUE05AConfigEntry 41 }

        hwMUE05ADoConfigLevel OBJECT-TYPE
            SYNTAX INTEGER
                {
                normal_open(1),
                normal_close(2)
                }
            MAX-ACCESS read-write
            STATUS current
            DESCRIPTION
                "AI and DI extension card's digital output valid level,,which users can confugure,is an enumeration type:
                  If the enumeration value is 1, it indicates DO is normally open;
                  If the enumeration value is 2, it indicates DO is normally closed;"
            ::= { hwMUE05AConfigEntry 42 }

        hwMUE05AConfigRowStatus OBJECT-TYPE
            SYNTAX RowStatus
            MAX-ACCESS read-create
            STATUS current
            DESCRIPTION
                "RowStatus of AI and DI extension card's config table"
            ::= { hwMUE05AConfigEntry 100 }

        hwMUE05AOperTable OBJECT-TYPE
            SYNTAX SEQUENCE OF HwMUE05AOperEntry
            MAX-ACCESS not-accessible
             STATUS current
             DESCRIPTION
                "AI and DI extension card running table. Use this table to get AI and DI extension card's presence status,slot nunber,etc. "
            ::= { hwMUE05A 2 }

        hwMUE05AOperEntry OBJECT-TYPE
                        SYNTAX HwMUE05AOperEntry
            MAX-ACCESS not-accessible
             STATUS current
             DESCRIPTION
                "AI and DI extension card running table. Use this table to get AI and DI extension card's presence status,slot nunber,etc. "
            INDEX { hwMUE05AOperIndex }
            ::= { hwMUE05AOperTable 1 }

        HwMUE05AOperEntry            ::= SEQUENCE {
                hwMUE05AOperIndex
                    Unsigned32,
                hwMUE05APresenceStatus
                    INTEGER,
                hwMUE05ASlotNo
                    Unsigned32,
                hwMUE05ACh1DiStatus
                    INTEGER,
                hwMUE05ACh1AiValue
                    Integer32,
                hwMUE05ACh1SensorStatus
                    INTEGER,
                hwMUE05ACh1PowerOutputStatus
                    INTEGER,
                hwMUE05ACh1PowerOutputAlarmStatus
                    INTEGER,
                hwMUE05ACh2DiStatus
                    INTEGER,
                hwMUE05ACh2AiValue
                    Integer32,
                hwMUE05ACh2SensorStatus
                    INTEGER,
                hwMUE05ACh2PowerOutputStatus
                    INTEGER,
                hwMUE05ACh2PowerOutputAlarmStatus
                    INTEGER,
                hwMUE05ACh3DiStatus
                    INTEGER,
                hwMUE05ACh3AiValue
                    Integer32,
                hwMUE05ACh3SensorStatus
                    INTEGER,
                hwMUE05ACh3PowerOutputStatus
                    INTEGER,
                hwMUE05ACh3PowerOutputAlarmStatus
                    INTEGER,
                hwMUE05ACh4DiStatus
                    INTEGER,
                hwMUE05ACh4AiValue
                    Integer32,
                hwMUE05ACh4SensorStatus
                    INTEGER,
                hwMUE05ACh4PowerOutputStatus
                    INTEGER,
                hwMUE05ACh4PowerOutputAlarmStatus
                    INTEGER,
                hwMUE05ADoOutputStatus
                    INTEGER,
                hwMUE05AOperRowStatus
                    RowStatus
            }

        hwMUE05AOperIndex OBJECT-TYPE
            SYNTAX Unsigned32 (21..26)
            MAX-ACCESS read-only
            STATUS current
            DESCRIPTION
                "Index of the device running table for the AI and DI extension card, which value range: 21 to 26."
            ::= { hwMUE05AOperEntry 1 }

        hwMUE05APresenceStatus OBJECT-TYPE
            SYNTAX INTEGER
                {
                not_detected(1),
                detected(2),
                unknown(255)
                }
            MAX-ACCESS read-only
            STATUS current
            DESCRIPTION
                "AI and DI extension card's presence status. it is an enumeration type: 
                  If the enumeration value is 1, it indicates device is not detected;
                  If the enumeration value is 2, it indicates device is detected;"
            ::= { hwMUE05AOperEntry 2 }

        hwMUE05ASlotNo OBJECT-TYPE
            SYNTAX Unsigned32 (1..6)
            MAX-ACCESS read-only
            STATUS current
            DESCRIPTION
                "AI and DI extension card's slot number. Value range: 1 to 6. "
            ::= { hwMUE05AOperEntry 3 }

        hwMUE05ACh1DiStatus OBJECT-TYPE
            SYNTAX INTEGER
                {
                open(1),
                closed(2),
                unknown(255)
                }
            MAX-ACCESS read-only
            STATUS current
            DESCRIPTION
                "AI/DI_1 channel digital input status. it is an enumeration type: 
                  If the enumeration value is 1, it indicates sensor status is open;
                  If the enumeration value is 2, it indicates sensor status is closed;
                  If the enumeration value is 3, it indicates sensor status is unknown;"
            ::= { hwMUE05AOperEntry 4 }

        hwMUE05ACh1AiValue OBJECT-TYPE
            SYNTAX Integer32 ( -100..200)
            MAX-ACCESS read-only
            STATUS current
            DESCRIPTION
                "AI/DI_1 channel analog input signal's value. Value range: -100 to 200. Multiple: 10."
            ::= { hwMUE05AOperEntry 5 }

        hwMUE05ACh1SensorStatus OBJECT-TYPE
            SYNTAX INTEGER
                {
                normal(1),
                failure(2),
                unknown(255)
                }
            MAX-ACCESS read-only
            STATUS current
            DESCRIPTION
                "AI/DI_1 channel sensor status. it is an enumeration type: 
                  If the enumeration value is 1, it indicates sensor status is normal;
                  If the enumeration value is 2, it indicates sensor status is invalid;
                  If the enumeration value is 3, it indicates sensor status is unknown;"
            ::= { hwMUE05AOperEntry 6 }

        hwMUE05ACh1PowerOutputStatus OBJECT-TYPE
            SYNTAX INTEGER
                {
                off(1),
                on(2),
                unknown(255)
                }
            MAX-ACCESS read-only
            STATUS current
            DESCRIPTION
                "AI/DI_1 channel power output status. it is an enumeration type: 
                  If the enumeration value is 1, it indicates the power is turned off;
                  If the enumeration value is 2, it indicates the power is turned on;
                  If the enumeration value is 3, it indicates the power status is unknown;"
            ::= { hwMUE05AOperEntry 7 }

        hwMUE05ACh1PowerOutputAlarmStatus OBJECT-TYPE
            SYNTAX INTEGER
                {
                normal(1),
                alarm(2),
                unknown(255)
                }
            MAX-ACCESS read-only
            STATUS current
            DESCRIPTION
                "AI/DI_1 channel power alarm status. it is an enumeration type: 
                  If the enumeration value is 1, it indicates the power status is normal;
                  If the enumeration value is 2, it indicates the power status is abnormal;
                  If the enumeration value is 3, it indicates the power status is unknown;"
            ::= { hwMUE05AOperEntry 8 }

        hwMUE05ACh2DiStatus OBJECT-TYPE
            SYNTAX INTEGER
                {
                open(1),
                closed(2),
                unknown(255)
                }
            MAX-ACCESS read-only
            STATUS current
            DESCRIPTION
                "AI/DI_2 channel digital input status. it is an enumeration type: 
                  If the enumeration value is 1, it indicates sensor status is open;
                  If the enumeration value is 2, it indicates sensor status is closed;
                  If the enumeration value is 3, it indicates sensor status is unknown;"
            ::= { hwMUE05AOperEntry 9 }

        hwMUE05ACh2AiValue OBJECT-TYPE
            SYNTAX Integer32 ( -100..200)
            MAX-ACCESS read-only
            STATUS current
            DESCRIPTION
                "AI/DI_2 channel analog input signal's value. Value range: -100 to 200. Multiple: 10."
            ::= { hwMUE05AOperEntry 10 }

        hwMUE05ACh2SensorStatus OBJECT-TYPE
            SYNTAX INTEGER
                {
                normal(1),
                failure(2),
                unknown(255)
                }
            MAX-ACCESS read-only
            STATUS current
            DESCRIPTION
                "AI/DI_2 channel sensor status. it is an enumeration type: 
                  If the enumeration value is 1, it indicates sensor status is normal;
                  If the enumeration value is 2, it indicates sensor status is invalid;
                  If the enumeration value is 3, it indicates sensor status is unknown;"
            ::= { hwMUE05AOperEntry 11 }

        hwMUE05ACh2PowerOutputStatus OBJECT-TYPE
            SYNTAX INTEGER
                {
                off(1),
                on(2),
                unknown(255)
                }
            MAX-ACCESS read-only
            STATUS current
            DESCRIPTION
                "AI/DI_2 channel power output status. it is an enumeration type: 
                  If the enumeration value is 1, it indicates the power is turned off;
                  If the enumeration value is 2, it indicates the power is turned on;
                  If the enumeration value is 3, it indicates the power status is unknown;"
            ::= { hwMUE05AOperEntry 12 }

        hwMUE05ACh2PowerOutputAlarmStatus OBJECT-TYPE
            SYNTAX INTEGER
                {
                normal(1),
                alarm(2),
                unknown(255)
                }
            MAX-ACCESS read-only
            STATUS current
            DESCRIPTION
                "AI/DI_2 channel power alarm status. it is an enumeration type: 
                  If the enumeration value is 1, it indicates the power status is normal;
                  If the enumeration value is 2, it indicates the power status is abnormal;
                  If the enumeration value is 3, it indicates the power status is unknown;"
            ::= { hwMUE05AOperEntry 13 }

        hwMUE05ACh3DiStatus OBJECT-TYPE
            SYNTAX INTEGER
                {
                open(1),
                closed(2),
                unknown(255)
                }
            MAX-ACCESS read-only
            STATUS current
            DESCRIPTION
                "AI/DI_3 channel digital input status. it is an enumeration type: 
                  If the enumeration value is 1, it indicates sensor status is open;
                  If the enumeration value is 2, it indicates sensor status is closed;
                  If the enumeration value is 3, it indicates sensor status is unknown;"
            ::= { hwMUE05AOperEntry 14 }

        hwMUE05ACh3AiValue OBJECT-TYPE
            SYNTAX Integer32 ( -100..200)
            MAX-ACCESS read-only
            STATUS current
            DESCRIPTION
                "AI/DI_3 channel analog input signal's value. Value range: -100 to 200. Multiple: 10."
            ::= { hwMUE05AOperEntry 15 }

        hwMUE05ACh3SensorStatus OBJECT-TYPE
            SYNTAX INTEGER
                {
                normal(1),
                failure(2),
                unknown(255)
                }
            MAX-ACCESS read-only
            STATUS current
            DESCRIPTION
                "AI/DI_3 channel sensor status. it is an enumeration type: 
                  If the enumeration value is 1, it indicates sensor status is normal;
                  If the enumeration value is 2, it indicates sensor status is invalid;
                  If the enumeration value is 3, it indicates sensor status is unknown;"
            ::= { hwMUE05AOperEntry 16 }

        hwMUE05ACh3PowerOutputStatus OBJECT-TYPE
            SYNTAX INTEGER
                {
                off(1),
                on(2),
                unknown(255)
                }
            MAX-ACCESS read-only
            STATUS current
            DESCRIPTION
                "AI/DI_3 channel power output status. it is an enumeration type: 
                  If the enumeration value is 1, it indicates the power is turned off;
                  If the enumeration value is 2, it indicates the power is turned on;
                  If the enumeration value is 3, it indicates the power status is unknown;"
            ::= { hwMUE05AOperEntry 17 }

        hwMUE05ACh3PowerOutputAlarmStatus OBJECT-TYPE
            SYNTAX INTEGER
                {
                normal(1),
                alarm(2),
                unknown(255)
                }
            MAX-ACCESS read-only
            STATUS current
            DESCRIPTION
                "AI/DI_3 channel power alarm status. it is an enumeration type: 
                  If the enumeration value is 1, it indicates the power status is normal;
                  If the enumeration value is 2, it indicates the power status is abnormal;
                  If the enumeration value is 3, it indicates the power status is unknown;"
            ::= { hwMUE05AOperEntry 18 }

        hwMUE05ACh4DiStatus OBJECT-TYPE
            SYNTAX INTEGER
                {
                open(1),
                closed(2),
                unknown(255)
                }
            MAX-ACCESS read-only
            STATUS current
            DESCRIPTION
                "AI/DI_4 channel digital input status. it is an enumeration type: 
                  If the enumeration value is 1, it indicates sensor status is open;
                  If the enumeration value is 2, it indicates sensor status is closed;
                  If the enumeration value is 3, it indicates sensor status is unknown;"
            ::= { hwMUE05AOperEntry 19 }

        hwMUE05ACh4AiValue OBJECT-TYPE
            SYNTAX Integer32 ( -100..200)
            MAX-ACCESS read-only
            STATUS current
            DESCRIPTION
                "AI/DI_4 channel analog input signal's value. Value range: -100 to 200. "
            ::= { hwMUE05AOperEntry 20 }

        hwMUE05ACh4SensorStatus OBJECT-TYPE
            SYNTAX INTEGER
                {
                normal(1),
                failure(2),
                unknown(255)
                }
            MAX-ACCESS read-only
            STATUS current
            DESCRIPTION
                "AI/DI_4 channel sensor status. it is an enumeration type: 
                  If the enumeration value is 1, it indicates sensor status is normal;
                  If the enumeration value is 2, it indicates sensor status is invalid;
                  If the enumeration value is 3, it indicates sensor status is unknown;"
            ::= { hwMUE05AOperEntry 21 }

        hwMUE05ACh4PowerOutputStatus OBJECT-TYPE
            SYNTAX INTEGER
                {
                off(1),
                on(2),
                unknown(255)
                }
            MAX-ACCESS read-only
            STATUS current
            DESCRIPTION
                "AI/DI_4 channel power output status. it is an enumeration type: 
                  If the enumeration value is 1, it indicates the power is turned off;
                  If the enumeration value is 2, it indicates the power is turned on;
                  If the enumeration value is 3, it indicates the power status is unknown;"
            ::= { hwMUE05AOperEntry 22 }

        hwMUE05ACh4PowerOutputAlarmStatus OBJECT-TYPE
            SYNTAX INTEGER
                {
                normal(1),
                alarm(2),
                unknown(255)
                }
            MAX-ACCESS read-only
            STATUS current
            DESCRIPTION
                "AI/DI_4 channel power alarm status. it is an enumeration type: 
                  If the enumeration value is 1, it indicates the power status is normal;
                  If the enumeration value is 2, it indicates the power status is abnormal;
                  If the enumeration value is 3, it indicates the power status is unknown;"
            ::= { hwMUE05AOperEntry 23 }

        hwMUE05ADoOutputStatus OBJECT-TYPE
            SYNTAX INTEGER
                {
                open(1),
                closed(2),
                unknown(255)
                }
            MAX-ACCESS read-only
            STATUS current
            DESCRIPTION
                "AI and DI extension card's digital output status. it is an enumeration type: 
                  If the enumeration value is 1, it indicates the DO status is open;
                  If the enumeration value is 2, it indicates the DO status is closed;
                  If the enumeration value is 3, it indicates the DO status is unknown;"
            ::= { hwMUE05AOperEntry 24 }

        hwMUE05AOperRowStatus OBJECT-TYPE
            SYNTAX RowStatus
            MAX-ACCESS read-create
            STATUS current
            DESCRIPTION
                "RowStatus of AI and DI extension card's running table"
            ::= { hwMUE05AOperEntry 100 }

        hwMUE06A OBJECT IDENTIFIER ::= { hwIDCMonitorMIBObjects 4 }

        hwMUE06AConfigTable OBJECT-TYPE
            SYNTAX SEQUENCE OF HwMUE06AConfigEntry
            MAX-ACCESS not-accessible
             STATUS current
             DESCRIPTION
                "Independent Deployment AI and DI Board config table. Use this table to get equipment ID and equipment name, to set sensors attribute and control channels power output as well. "
            ::= { hwMUE06A 1 }

        hwMUE06AConfigEntry OBJECT-TYPE
                        SYNTAX HwMUE06AConfigEntry
            MAX-ACCESS not-accessible
             STATUS current
             DESCRIPTION
                "Independent Deployment AI and DI Board config table. Use this table to get equipment ID and equipment name, to set sensors attribute and control channels power output as well. "
            INDEX { hwMUE06AConfigIndex }
            ::= { hwMUE06AConfigTable 1 }

        HwMUE06AConfigEntry            ::= SEQUENCE {
                hwMUE06AConfigIndex
                    Integer32,
                hwMUE06AEquipId
                    Unsigned32,
                hwMUE06AEquipName
                    OCTET STRING,
                hwMUE06ACh1Enable
                    INTEGER,
                hwMUE06ACh1SensorName
                    OCTET STRING,
                hwMUE06ACh1SensorType
                    INTEGER,
                hwMUE06ACh1SensorUints
                    INTEGER,
                hwMUE06ACh1MeasureUpperLimit
                    Unsigned32,
                hwMUE06ACh1MeasureLowerLimit
                    Integer32,
                hwMUE06ACh1AlarmUpperLimit
                    Unsigned32,
                hwMUE06ACh1AlarmLowerLimit
                    Integer32,
                hwMUE06ACh1PowerOutput
                    INTEGER,
                hwMUE06ACh2Enable
                    INTEGER,
                hwMUE06ACh2SensorName
                    OCTET STRING,
                hwMUE06ACh2SensorType
                    INTEGER,
                hwMUE06ACh2SensorUints
                    INTEGER,
                hwMUE06ACh2MeasureUpperLimit
                    Unsigned32,
                hwMUE06ACh2MeasureLowerLimit
                    Integer32,
                hwMUE06ACh2AlarmUpperLimit
                    Unsigned32,
                hwMUE06ACh2AlarmLowerLimit
                    Integer32,
                hwMUE06ACh2PowerOutput
                    INTEGER,
                hwMUE06ACh3Enable
                    INTEGER,
                hwMUE06ACh3SensorName
                    OCTET STRING,
                hwMUE06ACh3SensorType
                    INTEGER,
                hwMUE06ACh3SensorUints
                    INTEGER,
                hwMUE06ACh3MeasureUpperLimit
                    Unsigned32,
                hwMUE06ACh3MeasureLowerLimit
                    Integer32,
                hwMUE06ACh3AlarmUpperLimit
                    Unsigned32,
                hwMUE06ACh3AlarmLowerLimit
                    Integer32,
                hwMUE06ACh3PowerOutput
                    INTEGER,
                hwMUE06ACh4Enable
                    INTEGER,
                hwMUE06ACh4SensorName
                    OCTET STRING,
                hwMUE06ACh4SensorType
                    INTEGER,
                hwMUE06ACh4SensorUints
                    INTEGER,
                hwMUE06ACh4MeasureUpperLimit
                    Unsigned32,
                hwMUE06ACh4MeasureLowerLimit
                    Integer32,
                hwMUE06ACh4AlarmUpperLimit
                    Unsigned32,
                hwMUE06ACh4AlarmLowerLimit
                    Integer32,
                hwMUE06ACh4PowerOutput
                    INTEGER,
                hwMUE06ACh5Enable
                    INTEGER,
                hwMUE06ACh5SensorName
                    OCTET STRING,
                hwMUE06ACh5SensorType
                    INTEGER,
                hwMUE06ACh5SensorUints
                    INTEGER,
                hwMUE06ACh5MeasureUpperLimit
                    Unsigned32,
                hwMUE06ACh5MeasureLowerLimit
                    Integer32,
                hwMUE06ACh5AlarmUpperLimit
                    Unsigned32,
                hwMUE06ACh5AlarmLowerLimit
                    Integer32,
                hwMUE06ACh5PowerOutput
                    INTEGER,
                hwMUE06ACh6Enable
                    INTEGER,
                hwMUE06ACh6SensorName
                    OCTET STRING,
                hwMUE06ACh6SensorType
                    INTEGER,
                hwMUE06ACh6SensorUints
                    INTEGER,
                hwMUE06ACh6MeasureUpperLimit
                    Unsigned32,
                hwMUE06ACh6MeasureLowerLimit
                    Integer32,
                hwMUE06ACh6AlarmUpperLimit
                    Unsigned32,
                hwMUE06ACh6AlarmLowerLimit
                    Integer32,
                hwMUE06ACh6PowerOutput
                    INTEGER,
                hwMUE06ACh7Enable
                    INTEGER,
                hwMUE06ACh7SensorName
                    OCTET STRING,
                hwMUE06ACh7SensorType
                    INTEGER,
                hwMUE06ACh7SensorUints
                    INTEGER,
                hwMUE06ACh7MeasureUpperLimit
                    Unsigned32,
                hwMUE06ACh7MeasureLowerLimit
                    Integer32,
                hwMUE06ACh7AlarmUpperLimit
                    Unsigned32,
                hwMUE06ACh7AlarmLowerLimit
                    Integer32,
                hwMUE06ACh7PowerOutput
                    INTEGER,
                hwMUE06ACh8Enable
                    INTEGER,
                hwMUE06ACh8SensorName
                    OCTET STRING,
                hwMUE06ACh8SensorType
                    INTEGER,
                hwMUE06ACh8SensorUints
                    INTEGER,
                hwMUE06ACh8MeasureUpperLimit
                    Unsigned32,
                hwMUE06ACh8MeasureLowerLimit
                    Integer32,
                hwMUE06ACh8AlarmUpperLimit
                    Unsigned32,
                hwMUE06ACh8AlarmLowerLimit
                    Integer32,
                hwMUE06ACh8PowerOutput
                    INTEGER,
                hwMUE06AConfigRowStatus
                    RowStatus
            }

        hwMUE06AConfigIndex OBJECT-TYPE
            SYNTAX Integer32 (31..38)
            MAX-ACCESS read-only
            STATUS current
            DESCRIPTION
                "Index of the device configuration table for the Independent Deployment AI and DI Board, which value range: 31 to 38. "
            ::= { hwMUE06AConfigEntry 1 }

        hwMUE06AEquipId OBJECT-TYPE
            SYNTAX Unsigned32 (31..38)
            MAX-ACCESS read-only
            STATUS current
            DESCRIPTION
                "Independent Deployment AI and DI Board's equipment ID. Value range: 31 to 38. "
            ::= { hwMUE06AConfigEntry 2 }

        hwMUE06AEquipName OBJECT-TYPE
            SYNTAX OCTET STRING (SIZE (0..63))
            MAX-ACCESS read-write
            STATUS current
            DESCRIPTION
                "Equipment name, of the character string type, is used to specify the Deployment AI and DI Board. Users can configure it. Otherwise, the configured character can not be any other languages except English. Value range: 0 to 63. "
            ::= { hwMUE06AConfigEntry 3 }

        hwMUE06ACh1Enable OBJECT-TYPE
            SYNTAX INTEGER
                {
                disable(1),
                enable(2)
                }
            MAX-ACCESS read-write
            STATUS current
            DESCRIPTION
                "AI/DI_1 channel enable,which user must enable it if want to insert sensors, is an enumeration type: 
                  If the enumeration value is 1, it indicates the channel  is disabled;
                  If the enumeration value is 2, it indicates  the channel  is enabled;"
            ::= { hwMUE06AConfigEntry 4 }

        hwMUE06ACh1SensorName OBJECT-TYPE
            SYNTAX OCTET STRING (SIZE (0..33))
            MAX-ACCESS read-only
            STATUS current
            DESCRIPTION
                "AI/DI_1 channel's sensor name."
            ::= { hwMUE06AConfigEntry 5 }

        hwMUE06ACh1SensorType OBJECT-TYPE
            SYNTAX INTEGER
                {
                no(1),
                nc(2),
                door(3),
                smoke(4),
                smoke_nc(5),
                leak(6),
                leak_rope(7),
                leak_nc(8),
                temp_ntc(9),
                general_4_20ma(10)
                }
            MAX-ACCESS read-write
            STATUS current
            DESCRIPTION
                "AI/DI_1 channel's sensor type,which user can configure,is normally open dry contact by default"
            ::= { hwMUE06AConfigEntry 6 }

        hwMUE06ACh1SensorUints OBJECT-TYPE
            SYNTAX INTEGER
                {
                centigrade(1),
                percent(2),
                volt(3),
                ampere(4),
                other(5)
                }
            MAX-ACCESS read-write
            STATUS current
            DESCRIPTION
                "AI/DI_1 channel's sensor unit,which user can configure,is centigrade by default"
            ::= { hwMUE06AConfigEntry 7 }

        hwMUE06ACh1MeasureUpperLimit OBJECT-TYPE
            SYNTAX Unsigned32 (25..100)
            MAX-ACCESS read-write
            STATUS current
            DESCRIPTION
                "The upper limit of sensor measurement range. Value range: 25 to 100."
            ::= { hwMUE06AConfigEntry 8 }

        hwMUE06ACh1MeasureLowerLimit OBJECT-TYPE
            SYNTAX Integer32 ( -50..50)
            MAX-ACCESS read-write
            STATUS current
            DESCRIPTION
                "The lower limit of sensor measurement range. Value range: -50 to 50."
            ::= { hwMUE06AConfigEntry 9 }

        hwMUE06ACh1AlarmUpperLimit OBJECT-TYPE
            SYNTAX Unsigned32 (25..100)
            MAX-ACCESS read-write
            STATUS current
            DESCRIPTION
                "The upper limit of sensor alarm range.  Value range form 25 to 100."
            ::= { hwMUE06AConfigEntry 10 }

        hwMUE06ACh1AlarmLowerLimit OBJECT-TYPE
            SYNTAX Integer32 ( -50..50)
            MAX-ACCESS read-write
            STATUS current
            DESCRIPTION
                "The lower limit of sensor alarm range.  Value range form -50 to 50."
            ::= { hwMUE06AConfigEntry 11 }

        hwMUE06ACh1PowerOutput OBJECT-TYPE
            SYNTAX INTEGER
                {
                yes(1),
                no(2)
                }
            MAX-ACCESS read-write
            STATUS current
            DESCRIPTION
                "AI/DI_1 channel power output, which users can use it to turn on or off the power, is an enumeration type: 
                  If the enumeration value is 1, it indicates turn on the power;
                  If the enumeration value is 2, it indicates turn off the power;"
            ::= { hwMUE06AConfigEntry 12 }

        hwMUE06ACh2Enable OBJECT-TYPE
            SYNTAX INTEGER
                {
                disable(1),
                enable(2)
                }
            MAX-ACCESS read-write
            STATUS current
            DESCRIPTION
                "AI/DI_2 channel enable,which user must enable it if want to insert sensors, is an enumeration type: 
                  If the enumeration value is 1, it indicates the channel  is disabled;
                  If the enumeration value is 2, it indicates  the channel  is enabled;"
            ::= { hwMUE06AConfigEntry 13 }

        hwMUE06ACh2SensorName OBJECT-TYPE
            SYNTAX OCTET STRING (SIZE (0..33))
            MAX-ACCESS read-only
            STATUS current
            DESCRIPTION
                "AI/DI_2 channel's sensor name."
            ::= { hwMUE06AConfigEntry 14 }

        hwMUE06ACh2SensorType OBJECT-TYPE
            SYNTAX INTEGER
                {
                no(1),
                nc(2),
                door(3),
                smoke(4),
                smoke_nc(5),
                leak(6),
                leak_rope(7),
                leak_nc(8),
                temp_ntc(9),
                general_4_20ma(10)
                }
            MAX-ACCESS read-write
            STATUS current
            DESCRIPTION
                "AI/DI_2 channel's sensor type,which user can configure,is normally open dry contact by default"
            ::= { hwMUE06AConfigEntry 15 }

        hwMUE06ACh2SensorUints OBJECT-TYPE
            SYNTAX INTEGER
                {
                centigrade(1),
                percent(2),
                volt(3),
                ampere(4),
                other(5)
                }
            MAX-ACCESS read-write
            STATUS current
            DESCRIPTION
                "AI/DI_2 channel's sensor unit,which user can configure,is centigrade by default"
            ::= { hwMUE06AConfigEntry 16 }

        hwMUE06ACh2MeasureUpperLimit OBJECT-TYPE
            SYNTAX Unsigned32 (25..100)
            MAX-ACCESS read-write
            STATUS current
            DESCRIPTION
                "The upper limit of sensor measurement range. Value range: 25 to 100."
            ::= { hwMUE06AConfigEntry 17 }

        hwMUE06ACh2MeasureLowerLimit OBJECT-TYPE
            SYNTAX Integer32 ( -50..50)
            MAX-ACCESS read-write
            STATUS current
            DESCRIPTION
                "The lower limit of sensor measurement range. Value range: -50 to 50."
            ::= { hwMUE06AConfigEntry 18 }

        hwMUE06ACh2AlarmUpperLimit OBJECT-TYPE
            SYNTAX Unsigned32 (25..100)
            MAX-ACCESS read-write
            STATUS current
            DESCRIPTION
                "The upper limit of sensor alarm range.  Value range form 25 to 100."
            ::= { hwMUE06AConfigEntry 19 }

        hwMUE06ACh2AlarmLowerLimit OBJECT-TYPE
            SYNTAX Integer32 ( -50..50)
            MAX-ACCESS read-write
            STATUS current
            DESCRIPTION
                "The lower limit of sensor alarm range.  Value range form -50 to 50."
            ::= { hwMUE06AConfigEntry 20 }

        hwMUE06ACh2PowerOutput OBJECT-TYPE
            SYNTAX INTEGER
                {
                yes(1),
                no(2)
                }
            MAX-ACCESS read-write
            STATUS current
            DESCRIPTION
                "AI/DI_2 channel power output, which users can use it to turn on or off the power, is an enumeration type: 
                  If the enumeration value is 1, it indicates turn on the power;
                  If the enumeration value is 2, it indicates turn off the power;"
            ::= { hwMUE06AConfigEntry 21 }

        hwMUE06ACh3Enable OBJECT-TYPE
            SYNTAX INTEGER
                {
                disable(1),
                enable(2)
                }
            MAX-ACCESS read-write
            STATUS current
            DESCRIPTION
                "AI/DI_3 channel enable,which user must enable it if want to insert sensors, is an enumeration type: 
                  If the enumeration value is 1, it indicates the channel  is disabled;
                  If the enumeration value is 2, it indicates  the channel  is enabled;"
            ::= { hwMUE06AConfigEntry 22 }

        hwMUE06ACh3SensorName OBJECT-TYPE
            SYNTAX OCTET STRING (SIZE (0..33))
            MAX-ACCESS read-only
            STATUS current
            DESCRIPTION
                "AI/DI_3 channel's sensor name."
            ::= { hwMUE06AConfigEntry 23 }

        hwMUE06ACh3SensorType OBJECT-TYPE
            SYNTAX INTEGER
                {
                no(1),
                nc(2),
                door(3),
                smoke(4),
                smoke_nc(5),
                leak(6),
                leak_rope(7),
                leak_nc(8),
                temp_ntc(9),
                general_4_20ma(10)
                }
            MAX-ACCESS read-write
            STATUS current
            DESCRIPTION
                "AI/DI_3 channel's sensor type,which user can configure,is normally open dry contact by default"
            ::= { hwMUE06AConfigEntry 24 }

        hwMUE06ACh3SensorUints OBJECT-TYPE
            SYNTAX INTEGER
                {
                centigrade(1),
                percent(2),
                volt(3),
                ampere(4),
                other(5)
                }
            MAX-ACCESS read-write
            STATUS current
            DESCRIPTION
                "AI/DI_3 channel's sensor unit,which user can configure,is centigrade by default"
            ::= { hwMUE06AConfigEntry 25 }

        hwMUE06ACh3MeasureUpperLimit OBJECT-TYPE
            SYNTAX Unsigned32 (25..100)
            MAX-ACCESS read-write
            STATUS current
            DESCRIPTION
                "The upper limit of sensor measurement range. Value range: 25 to 100."
            ::= { hwMUE06AConfigEntry 26 }

        hwMUE06ACh3MeasureLowerLimit OBJECT-TYPE
            SYNTAX Integer32 ( -50..50)
            MAX-ACCESS read-write
            STATUS current
            DESCRIPTION
                "The lower limit of sensor measurement range. Value range: -50 to 50."
            ::= { hwMUE06AConfigEntry 27 }

        hwMUE06ACh3AlarmUpperLimit OBJECT-TYPE
            SYNTAX Unsigned32 (25..100)
            MAX-ACCESS read-write
            STATUS current
            DESCRIPTION
                "The upper limit of sensor alarm range.  Value range form 25 to 100."
            ::= { hwMUE06AConfigEntry 28 }

        hwMUE06ACh3AlarmLowerLimit OBJECT-TYPE
            SYNTAX Integer32 ( -50..50)
            MAX-ACCESS read-write
            STATUS current
            DESCRIPTION
                "The lower limit of sensor alarm range.  Value range form -50 to 50."
            ::= { hwMUE06AConfigEntry 29 }

        hwMUE06ACh3PowerOutput OBJECT-TYPE
            SYNTAX INTEGER
                {
                yes(1),
                no(2)
                }
            MAX-ACCESS read-write
            STATUS current
            DESCRIPTION
                "AI/DI_3 channel power output, which users can use it to turn on or off the power, is an enumeration type: 
                  If the enumeration value is 1, it indicates turn on the power;
                  If the enumeration value is 2, it indicates turn off the power;"
            ::= { hwMUE06AConfigEntry 30 }

        hwMUE06ACh4Enable OBJECT-TYPE
            SYNTAX INTEGER
                {
                disable(1),
                enable(2)
                }
            MAX-ACCESS read-write
            STATUS current
            DESCRIPTION
                "AI/DI_4 channel enable,which user must enable it if want to insert sensors, is an enumeration type: 
                  If the enumeration value is 1, it indicates the channel  is disabled;
                  If the enumeration value is 2, it indicates  the channel  is enabled;"
            ::= { hwMUE06AConfigEntry 31 }

        hwMUE06ACh4SensorName OBJECT-TYPE
            SYNTAX OCTET STRING (SIZE (0..33))
            MAX-ACCESS read-only
            STATUS current
            DESCRIPTION
                "AI/DI_4 channel's sensor name."
            ::= { hwMUE06AConfigEntry 32 }

        hwMUE06ACh4SensorType OBJECT-TYPE
            SYNTAX INTEGER
                {
                no(1),
                nc(2),
                door(3),
                smoke(4),
                smoke_nc(5),
                leak(6),
                leak_rope(7),
                leak_nc(8),
                temp_ntc(9),
                general_4_20ma(10)
                }
            MAX-ACCESS read-write
            STATUS current
            DESCRIPTION
                "AI/DI_4 channel's sensor type,which user can configure,is normally open dry contact by default"
            ::= { hwMUE06AConfigEntry 33 }

        hwMUE06ACh4SensorUints OBJECT-TYPE
            SYNTAX INTEGER
                {
                centigrade(1),
                percent(2),
                volt(3),
                ampere(4),
                other(5)
                }
            MAX-ACCESS read-write
            STATUS current
            DESCRIPTION
                "AI/DI_4 channel's sensor unit,which user can configure,is centigrade by default"
            ::= { hwMUE06AConfigEntry 34 }

        hwMUE06ACh4MeasureUpperLimit OBJECT-TYPE
            SYNTAX Unsigned32 (25..100)
            MAX-ACCESS read-write
            STATUS current
            DESCRIPTION
                "The upper limit of sensor measurement range. Value range: 25 to 100."
            ::= { hwMUE06AConfigEntry 35 }

        hwMUE06ACh4MeasureLowerLimit OBJECT-TYPE
            SYNTAX Integer32 ( -50..50)
            MAX-ACCESS read-write
            STATUS current
            DESCRIPTION
                "The lower limit of sensor measurement range. Value range: -50 to 50."
            ::= { hwMUE06AConfigEntry 36 }

        hwMUE06ACh4AlarmUpperLimit OBJECT-TYPE
            SYNTAX Unsigned32 (25..100)
            MAX-ACCESS read-write
            STATUS current
            DESCRIPTION
                "The upper limit of sensor alarm range.  Value range form 25 to 100."
            ::= { hwMUE06AConfigEntry 37 }

        hwMUE06ACh4AlarmLowerLimit OBJECT-TYPE
            SYNTAX Integer32 ( -50..50)
            MAX-ACCESS read-write
            STATUS current
            DESCRIPTION
                "The lower limit of sensor alarm range.  Value range form -50 to 50."
            ::= { hwMUE06AConfigEntry 38 }

        hwMUE06ACh4PowerOutput OBJECT-TYPE
            SYNTAX INTEGER
                {
                yes(1),
                no(2)
                }
            MAX-ACCESS read-write
            STATUS current
            DESCRIPTION
                "AI/DI_4 channel power output, which users can use it to turn on or off the power, is an enumeration type: 
                  If the enumeration value is 1, it indicates turn on the power;
                  If the enumeration value is 2, it indicates turn off the power;"
            ::= { hwMUE06AConfigEntry 39 }

        hwMUE06ACh5Enable OBJECT-TYPE
            SYNTAX INTEGER
                {
                disable(1),
                enable(2)
                }
            MAX-ACCESS read-write
            STATUS current
            DESCRIPTION
                "AI/DI_5 channel enable,which user must enable it if want to insert sensors, is an enumeration type: 
                  If the enumeration value is 1, it indicates the channel  is disabled;
                  If the enumeration value is 2, it indicates  the channel  is enabled;"
            ::= { hwMUE06AConfigEntry 40 }

        hwMUE06ACh5SensorName OBJECT-TYPE
            SYNTAX OCTET STRING (SIZE (0..33))
            MAX-ACCESS read-only
            STATUS current
            DESCRIPTION
                "AI/DI_5 channel's sensor name."
            ::= { hwMUE06AConfigEntry 41 }

        hwMUE06ACh5SensorType OBJECT-TYPE
            SYNTAX INTEGER
                {
                no(1),
                nc(2),
                door(3),
                smoke(4),
                smoke_nc(5),
                leak(6),
                leak_rope(7),
                leak_nc(8),
                temp_ntc(9),
                general_4_20ma(10)
                }
            MAX-ACCESS read-write
            STATUS current
            DESCRIPTION
                "AI/DI_5 channel's sensor type,which user can configure,is normally open dry contact by default"
            ::= { hwMUE06AConfigEntry 42 }

        hwMUE06ACh5SensorUints OBJECT-TYPE
            SYNTAX INTEGER
                {
                centigrade(1),
                percent(2),
                volt(3),
                ampere(4),
                other(5)
                }
            MAX-ACCESS read-write
            STATUS current
            DESCRIPTION
                "AI/DI_5 channel's sensor unit,which user can configure,is centigrade by default"
            ::= { hwMUE06AConfigEntry 43 }

        hwMUE06ACh5MeasureUpperLimit OBJECT-TYPE
            SYNTAX Unsigned32 (25..100)
            MAX-ACCESS read-write
            STATUS current
            DESCRIPTION
                "The upper limit of sensor measurement range. Value range: 25 to 100."
            ::= { hwMUE06AConfigEntry 44 }

        hwMUE06ACh5MeasureLowerLimit OBJECT-TYPE
            SYNTAX Integer32 ( -50..50)
            MAX-ACCESS read-write
            STATUS current
            DESCRIPTION
                "The lower limit of sensor measurement range. Value range: -50 to 50."
            ::= { hwMUE06AConfigEntry 45 }

        hwMUE06ACh5AlarmUpperLimit OBJECT-TYPE
            SYNTAX Unsigned32 (25..100)
            MAX-ACCESS read-write
            STATUS current
            DESCRIPTION
                "The upper limit of sensor alarm range.  Value range form 25 to 100."
            ::= { hwMUE06AConfigEntry 46 }

        hwMUE06ACh5AlarmLowerLimit OBJECT-TYPE
            SYNTAX Integer32 ( -50..50)
            MAX-ACCESS read-write
            STATUS current
            DESCRIPTION
                "The lower limit of sensor alarm range.  Value range form -50 to 50."
            ::= { hwMUE06AConfigEntry 47 }

        hwMUE06ACh5PowerOutput OBJECT-TYPE
            SYNTAX INTEGER
                {
                yes(1),
                no(2)
                }
            MAX-ACCESS read-write
            STATUS current
            DESCRIPTION
                "AI/DI_5 channel power output, which users can use it to turn on or off the power, is an enumeration type: 
                  If the enumeration value is 1, it indicates turn on the power;
                  If the enumeration value is 2, it indicates turn off the power;"
            ::= { hwMUE06AConfigEntry 48 }

        hwMUE06ACh6Enable OBJECT-TYPE
            SYNTAX INTEGER
                {
                disable(1),
                enable(2)
                }
            MAX-ACCESS read-write
            STATUS current
            DESCRIPTION
                "AI/DI_6 channel enable,which user must enable it if want to insert sensors, is an enumeration type: 
                  If the enumeration value is 1, it indicates the channel  is disabled;
                  If the enumeration value is 2, it indicates  the channel  is enabled;"
            ::= { hwMUE06AConfigEntry 49 }

        hwMUE06ACh6SensorName OBJECT-TYPE
            SYNTAX OCTET STRING (SIZE (0..33))
            MAX-ACCESS read-only
            STATUS current
            DESCRIPTION
                "AI/DI_6 channel's sensor name."
            ::= { hwMUE06AConfigEntry 50 }

        hwMUE06ACh6SensorType OBJECT-TYPE
            SYNTAX INTEGER
                {
                no(1),
                nc(2),
                door(3),
                smoke(4),
                smoke_nc(5),
                leak(6),
                leak_rope(7),
                leak_nc(8),
                temp_ntc(9),
                general_4_20ma(10)
                }
            MAX-ACCESS read-write
            STATUS current
            DESCRIPTION
                "AI/DI_6 channel's sensor type,which user can configure,is normally open dry contact by default"
            ::= { hwMUE06AConfigEntry 51 }

        hwMUE06ACh6SensorUints OBJECT-TYPE
            SYNTAX INTEGER
                {
                centigrade(1),
                percent(2),
                volt(3),
                ampere(4),
                other(5)
                }
            MAX-ACCESS read-write
            STATUS current
            DESCRIPTION
                "AI/DI_6 channel's sensor unit,which user can configure,is centigrade by default"
            ::= { hwMUE06AConfigEntry 52 }

        hwMUE06ACh6MeasureUpperLimit OBJECT-TYPE
            SYNTAX Unsigned32 (25..100)
            MAX-ACCESS read-write
            STATUS current
            DESCRIPTION
                "The upper limit of sensor measurement range. Value range: 25 to 100."
            ::= { hwMUE06AConfigEntry 53 }

        hwMUE06ACh6MeasureLowerLimit OBJECT-TYPE
            SYNTAX Integer32 ( -50..50)
            MAX-ACCESS read-write
            STATUS current
            DESCRIPTION
                "The lower limit of sensor measurement range. Value range: -50 to 50."
            ::= { hwMUE06AConfigEntry 54 }

        hwMUE06ACh6AlarmUpperLimit OBJECT-TYPE
            SYNTAX Unsigned32 (25..100)
            MAX-ACCESS read-write
            STATUS current
            DESCRIPTION
                "The upper limit of sensor alarm range.  Value range form 25 to 100."
            ::= { hwMUE06AConfigEntry 55 }

        hwMUE06ACh6AlarmLowerLimit OBJECT-TYPE
            SYNTAX Integer32 ( -50..50)
            MAX-ACCESS read-write
            STATUS current
            DESCRIPTION
                "The lower limit of sensor alarm range.  Value range form -50 to 50."
            ::= { hwMUE06AConfigEntry 56 }

        hwMUE06ACh6PowerOutput OBJECT-TYPE
            SYNTAX INTEGER
                {
                yes(1),
                no(2)
                }
            MAX-ACCESS read-write
            STATUS current
            DESCRIPTION
                "AI/DI_6 channel power output, which users can use it to turn on or off the power, is an enumeration type: 
                  If the enumeration value is 1, it indicates turn on the power;
                  If the enumeration value is 2, it indicates turn off the power;"
            ::= { hwMUE06AConfigEntry 57 }

        hwMUE06ACh7Enable OBJECT-TYPE
            SYNTAX INTEGER
                {
                disable(1),
                enable(2)
                }
            MAX-ACCESS read-write
            STATUS current
            DESCRIPTION
                "AI/DI_7 channel enable,which user must enable it if want to insert sensors, is an enumeration type: 
                  If the enumeration value is 1, it indicates the channel  is disabled;
                  If the enumeration value is 2, it indicates  the channel  is enabled;"
            ::= { hwMUE06AConfigEntry 58 }

        hwMUE06ACh7SensorName OBJECT-TYPE
            SYNTAX OCTET STRING (SIZE (0..33))
            MAX-ACCESS read-only
            STATUS current
            DESCRIPTION
                "AI/DI_7 channel's sensor name."
            ::= { hwMUE06AConfigEntry 59 }

        hwMUE06ACh7SensorType OBJECT-TYPE
            SYNTAX INTEGER
                {
                no(1),
                nc(2),
                door(3),
                smoke(4),
                smoke_nc(5),
                leak(6),
                leak_rope(7),
                leak_nc(8),
                temp_ntc(9),
                general_4_20ma(10)
                }
            MAX-ACCESS read-write
            STATUS current
            DESCRIPTION
                "AI/DI_7 channel's sensor type,which user can configure,is normally open dry contact by default"
            ::= { hwMUE06AConfigEntry 60 }

        hwMUE06ACh7SensorUints OBJECT-TYPE
            SYNTAX INTEGER
                {
                centigrade(1),
                percent(2),
                volt(3),
                ampere(4),
                other(5)
                }
            MAX-ACCESS read-write
            STATUS current
            DESCRIPTION
                "AI/DI_7 channel's sensor unit,which user can configure,is centigrade by default"
            ::= { hwMUE06AConfigEntry 61 }

        hwMUE06ACh7MeasureUpperLimit OBJECT-TYPE
            SYNTAX Unsigned32 (25..100)
            MAX-ACCESS read-write
            STATUS current
            DESCRIPTION
                "The upper limit of sensor measurement range. Value range: 25 to 100."
            ::= { hwMUE06AConfigEntry 62 }

        hwMUE06ACh7MeasureLowerLimit OBJECT-TYPE
            SYNTAX Integer32 ( -50..50)
            MAX-ACCESS read-write
            STATUS current
            DESCRIPTION
                "The lower limit of sensor measurement range. Value range: -50 to 50."
            ::= { hwMUE06AConfigEntry 63 }

        hwMUE06ACh7AlarmUpperLimit OBJECT-TYPE
            SYNTAX Unsigned32 (25..100)
            MAX-ACCESS read-write
            STATUS current
            DESCRIPTION
                "The upper limit of sensor alarm range.  Value range form 25 to 100."
            ::= { hwMUE06AConfigEntry 64 }

        hwMUE06ACh7AlarmLowerLimit OBJECT-TYPE
            SYNTAX Integer32 ( -50..50)
            MAX-ACCESS read-write
            STATUS current
            DESCRIPTION
                "The lower limit of sensor alarm range.  Value range form -50 to 50."
            ::= { hwMUE06AConfigEntry 65 }

        hwMUE06ACh7PowerOutput OBJECT-TYPE
            SYNTAX INTEGER
                {
                yes(1),
                no(2)
                }
            MAX-ACCESS read-write
            STATUS current
            DESCRIPTION
                "AI/DI_7 channel power output, which users can use it to turn on or off the power, is an enumeration type: 
                  If the enumeration value is 1, it indicates turn on the power;
                  If the enumeration value is 2, it indicates turn off the power;"
            ::= { hwMUE06AConfigEntry 66 }

        hwMUE06ACh8Enable OBJECT-TYPE
            SYNTAX INTEGER
                {
                disable(1),
                enable(2)
                }
            MAX-ACCESS read-write
            STATUS current
            DESCRIPTION
                "AI/DI_8 channel enable,which user must enable it if want to insert sensors, is an enumeration type: 
                  If the enumeration value is 1, it indicates the channel  is disabled;
                  If the enumeration value is 2, it indicates  the channel  is enabled;"
            ::= { hwMUE06AConfigEntry 67 }

        hwMUE06ACh8SensorName OBJECT-TYPE
            SYNTAX OCTET STRING (SIZE (0..33))
            MAX-ACCESS read-only
            STATUS current
            DESCRIPTION
                "AI/DI_8 channel's sensor name."
            ::= { hwMUE06AConfigEntry 68 }

        hwMUE06ACh8SensorType OBJECT-TYPE
            SYNTAX INTEGER
                {
                no(1),
                nc(2),
                door(3),
                smoke(4),
                smoke_nc(5),
                leak(6),
                leak_rope(7),
                leak_nc(8),
                temp_ntc(9),
                general_4_20ma(10)
                }
            MAX-ACCESS read-write
            STATUS current
            DESCRIPTION
                "AI/DI_8 channel's sensor type,which user can configure,is normally open dry contact by default"
            ::= { hwMUE06AConfigEntry 69 }

        hwMUE06ACh8SensorUints OBJECT-TYPE
            SYNTAX INTEGER
                {
                centigrade(1),
                percent(2),
                volt(3),
                ampere(4),
                other(5)
                }
            MAX-ACCESS read-write
            STATUS current
            DESCRIPTION
                "AI/DI_8 channel's sensor unit,which user can configure,is centigrade by default"
            ::= { hwMUE06AConfigEntry 70 }

        hwMUE06ACh8MeasureUpperLimit OBJECT-TYPE
            SYNTAX Unsigned32 (25..100)
            MAX-ACCESS read-write
            STATUS current
            DESCRIPTION
                "The upper limit of sensor measurement range. Value range: 25 to 100."
            ::= { hwMUE06AConfigEntry 71 }

        hwMUE06ACh8MeasureLowerLimit OBJECT-TYPE
            SYNTAX Integer32 ( -50..50)
            MAX-ACCESS read-write
            STATUS current
            DESCRIPTION
                "The lower limit of sensor measurement range. Value range: -50 to 50."
            ::= { hwMUE06AConfigEntry 72 }

        hwMUE06ACh8AlarmUpperLimit OBJECT-TYPE
            SYNTAX Unsigned32 (25..100)
            MAX-ACCESS read-write
            STATUS current
            DESCRIPTION
                "The upper limit of sensor alarm range.  Value range form 25 to 100."
            ::= { hwMUE06AConfigEntry 73 }

        hwMUE06ACh8AlarmLowerLimit OBJECT-TYPE
            SYNTAX Integer32 ( -50..50)
            MAX-ACCESS read-write
            STATUS current
            DESCRIPTION
                "The lower limit of sensor alarm range.  Value range form -50 to 50."
            ::= { hwMUE06AConfigEntry 74 }

        hwMUE06ACh8PowerOutput OBJECT-TYPE
            SYNTAX INTEGER
                {
                yes(1),
                no(2)
                }
            MAX-ACCESS read-write
            STATUS current
            DESCRIPTION
                "AI/DI_8 channel power output, which users can use it to turn on or off the power, is an enumeration type: 
                  If the enumeration value is 1, it indicates turn on the power;
                  If the enumeration value is 2, it indicates turn off the power;"
            ::= { hwMUE06AConfigEntry 75 }

        hwMUE06AConfigRowStatus OBJECT-TYPE
            SYNTAX RowStatus
            MAX-ACCESS read-create
            STATUS current
            DESCRIPTION
                "RowStatus of Independent Deployment AI and DI Board's config table"
            ::= { hwMUE06AConfigEntry 100 }

        hwMUE06AOperTable OBJECT-TYPE
            SYNTAX SEQUENCE OF HwMUE06AOperEntry
            MAX-ACCESS not-accessible
             STATUS current
             DESCRIPTION
                "Independent Deployment AI and DI Board running table. Use this table to getIndependent Deployment AI and DI Board's presence status,slot nunber,etc. "
            ::= { hwMUE06A 2 }

        hwMUE06AOperEntry OBJECT-TYPE
                        SYNTAX HwMUE06AOperEntry
            MAX-ACCESS not-accessible
             STATUS current
             DESCRIPTION
                "Independent Deployment AI and DI Board running table. Use this table to getIndependent Deployment AI and DI Board's presence status,slot nunber,etc. "
            INDEX { hwMUE06AOperIndex }
            ::= { hwMUE06AOperTable 1 }

        HwMUE06AOperEntry            ::= SEQUENCE {
                hwMUE06AOperIndex
                    Unsigned32,
                hwMUE06APresenceStatus
                    INTEGER,
                hwMUE06ASlotNo
                    Unsigned32,
                hwMUE06APortNo
                    Unsigned32,
                hwMUE06AModbusAddr
                    Unsigned32,
                hwMUE06ACh1DiStatus
                    INTEGER,
                hwMUE06ACh1AiValue
                    Integer32,
                hwMUE06ACh1SensorStatus
                    INTEGER,
                hwMUE06ACh1PowerOutputStatus
                    INTEGER,
                hwMUE06ACh1PowerOutputAlarmStatus
                    INTEGER,
                hwMUE06ACh2DiStatus
                    INTEGER,
                hwMUE06ACh2AiValue
                    Integer32,
                hwMUE06ACh2SensorStatus
                    INTEGER,
                hwMUE06ACh2PowerOutputStatus
                    INTEGER,
                hwMUE06ACh2PowerOutputAlarmStatus
                    INTEGER,
                hwMUE06ACh3DiStatus
                    INTEGER,
                hwMUE06ACh3AiValue
                    Integer32,
                hwMUE06ACh3SensorStatus
                    INTEGER,
                hwMUE06ACh3PowerOutputStatus
                    INTEGER,
                hwMUE06ACh3PowerOutputAlarmStatus
                    INTEGER,
                hwMUE06ACh4DiStatus
                    INTEGER,
                hwMUE06ACh4AiValue
                    Integer32,
                hwMUE06ACh4SensorStatus
                    INTEGER,
                hwMUE06ACh4PowerOutputStatus
                    INTEGER,
                hwMUE06ACh4PowerOutputAlarmStatus
                    INTEGER,
                hwMUE06ACh5DiStatus
                    INTEGER,
                hwMUE06ACh5AiValue
                    Integer32,
                hwMUE06ACh5SensorStatus
                    INTEGER,
                hwMUE06ACh5PowerOutputStatus
                    INTEGER,
                hwMUE06ACh5PowerOutputAlarmStatus
                    INTEGER,
                hwMUE06ACh6DiStatus
                    INTEGER,
                hwMUE06ACh6AiValue
                    Integer32,
                hwMUE06ACh6SensorStatus
                    INTEGER,
                hwMUE06ACh6PowerOutputStatus
                    INTEGER,
                hwMUE06ACh6PowerOutputAlarmStatus
                    INTEGER,
                hwMUE06ACh7DiStatus
                    INTEGER,
                hwMUE06ACh7AiValue
                    Integer32,
                hwMUE06ACh7SensorStatus
                    INTEGER,
                hwMUE06ACh7PowerOutputStatus
                    INTEGER,
                hwMUE06ACh7PowerOutputAlarmStatus
                    INTEGER,
                hwMUE06ACh8DiStatus
                    INTEGER,
                hwMUE06ACh8AiValue
                    Integer32,
                hwMUE06ACh8SensorStatus
                    INTEGER,
                hwMUE06ACh8PowerOutputStatus
                    INTEGER,
                hwMUE06ACh8PowerOutputAlarmStatus
                    INTEGER,
                hwMUE06APowerVoltageLowAlarmStatus
                    INTEGER,
                hwMUE06AOperRowStatus
                    RowStatus
            }

        hwMUE06AOperIndex OBJECT-TYPE
            SYNTAX Unsigned32 (31..38)
            MAX-ACCESS read-only
            STATUS current
            DESCRIPTION
                "Index of the device running table for the Independent Deployment AI and DI Board, which value range: 31 to 38."
            ::= { hwMUE06AOperEntry 1 }

        hwMUE06APresenceStatus OBJECT-TYPE
            SYNTAX INTEGER
                {
                not_detected(1),
                detected(2)
                }
            MAX-ACCESS read-only
            STATUS current
            DESCRIPTION
                "Independent Deployment AI and DI Board's presence status. it is an enumeration type: 
                  If the enumeration value is 1, it indicates device is not detected;
                  If the enumeration value is 2, it indicates device is detected;"
            ::= { hwMUE06AOperEntry 2 }

        hwMUE06ASlotNo OBJECT-TYPE
            SYNTAX Unsigned32 (1..8)
            MAX-ACCESS read-only
            STATUS current
            DESCRIPTION
                "Independent Deployment AI and DI Board's slot number. Value range: 1 to 8. "
            ::= { hwMUE06AOperEntry 3 }

        hwMUE06APortNo OBJECT-TYPE
            SYNTAX Unsigned32 (4..5)
            MAX-ACCESS read-only
            STATUS current
            DESCRIPTION
                "RS485 communication card's port number. Value range: 4 to 5. "
            ::= { hwMUE06AOperEntry 4 }

        hwMUE06AModbusAddr OBJECT-TYPE
            SYNTAX Unsigned32 (1..2)
            MAX-ACCESS read-only
            STATUS current
            DESCRIPTION
                "Independent Deployment AI and DI Board's modbus address. Value range: 1 to 2. "
            ::= { hwMUE06AOperEntry 5 }

        hwMUE06ACh1DiStatus OBJECT-TYPE
            SYNTAX INTEGER
                {
                open(1),
                closed(2),
                unknown(255)
                }
            MAX-ACCESS read-only
            STATUS current
            DESCRIPTION
                "AI/DI_1 channel digital input status. it is an enumeration type: 
                  If the enumeration value is 1, it indicates sensor status is open;
                  If the enumeration value is 2, it indicates sensor status is closed;
                  If the enumeration value is 3, it indicates sensor status is unknown;"
            ::= { hwMUE06AOperEntry 6 }

        hwMUE06ACh1AiValue OBJECT-TYPE
            SYNTAX Integer32 ( -100..200)
            MAX-ACCESS read-only
            STATUS current
            DESCRIPTION
                "AI/DI_1 channel analog input signal's value. Value range: -100 to 200. Multiple: 10."
            ::= { hwMUE06AOperEntry 7 }

        hwMUE06ACh1SensorStatus OBJECT-TYPE
            SYNTAX INTEGER
                {
                normal(1),
                failure(2),
                unknown(255)
                }
            MAX-ACCESS read-only
            STATUS current
            DESCRIPTION
                "AI/DI_1 channel sensor status. it is an enumeration type: 
                  If the enumeration value is 1, it indicates sensor status is normal;
                  If the enumeration value is 2, it indicates sensor status is invalid;
                  If the enumeration value is 3, it indicates sensor status is unknown;"
            ::= { hwMUE06AOperEntry 8 }

        hwMUE06ACh1PowerOutputStatus OBJECT-TYPE
            SYNTAX INTEGER
                {
                off(1),
                on(2),
                unknown(255)
                }
            MAX-ACCESS read-only
            STATUS current
            DESCRIPTION
                "AI/DI_1 channel power output status. it is an enumeration type: 
                  If the enumeration value is 1, it indicates the power is turned off;
                  If the enumeration value is 2, it indicates the power is turned on;
                  If the enumeration value is 3, it indicates the power status is unknown;"
            ::= { hwMUE06AOperEntry 9 }

        hwMUE06ACh1PowerOutputAlarmStatus OBJECT-TYPE
            SYNTAX INTEGER
                {
                normal(1),
                alarm(2),
                unknown(255)
                }
            MAX-ACCESS read-only
            STATUS current
            DESCRIPTION
                "AI/DI_1 channel power alarm status. it is an enumeration type: 
                  If the enumeration value is 1, it indicates the power status is normal;
                  If the enumeration value is 2, it indicates the power status is abnormal;
                  If the enumeration value is 3, it indicates the power status is unknown;"
            ::= { hwMUE06AOperEntry 10 }

        hwMUE06ACh2DiStatus OBJECT-TYPE
            SYNTAX INTEGER
                {
                open(1),
                closed(2),
                unknown(255)
                }
            MAX-ACCESS read-only
            STATUS current
            DESCRIPTION
                "AI/DI_2 channel digital input status. it is an enumeration type: 
                  If the enumeration value is 1, it indicates sensor status is open;
                  If the enumeration value is 2, it indicates sensor status is closed;
                  If the enumeration value is 3, it indicates sensor status is unknown;"
            ::= { hwMUE06AOperEntry 11 }

        hwMUE06ACh2AiValue OBJECT-TYPE
            SYNTAX Integer32 ( -100..200)
            MAX-ACCESS read-only
            STATUS current
            DESCRIPTION
                "AI/DI_2 channel analog input signal's value. Value range: -100 to 200. Multiple: 10."
            ::= { hwMUE06AOperEntry 12 }

        hwMUE06ACh2SensorStatus OBJECT-TYPE
            SYNTAX INTEGER
                {
                normal(1),
                failure(2),
                unknown(255)
                }
            MAX-ACCESS read-only
            STATUS current
            DESCRIPTION
                "AI/DI_2 channel sensor status. it is an enumeration type: 
                  If the enumeration value is 1, it indicates sensor status is normal;
                  If the enumeration value is 2, it indicates sensor status is invalid;
                  If the enumeration value is 3, it indicates sensor status is unknown;"
            ::= { hwMUE06AOperEntry 13 }

        hwMUE06ACh2PowerOutputStatus OBJECT-TYPE
            SYNTAX INTEGER
                {
                off(1),
                on(2),
                unknown(255)
                }
            MAX-ACCESS read-only
            STATUS current
            DESCRIPTION
                "AI/DI_2 channel power output status. it is an enumeration type: 
                  If the enumeration value is 1, it indicates the power is turned off;
                  If the enumeration value is 2, it indicates the power is turned on;
                  If the enumeration value is 3, it indicates the power status is unknown;"
            ::= { hwMUE06AOperEntry 14 }

        hwMUE06ACh2PowerOutputAlarmStatus OBJECT-TYPE
            SYNTAX INTEGER
                {
                normal(1),
                alarm(2),
                unknown(255)
                }
            MAX-ACCESS read-only
            STATUS current
            DESCRIPTION
                "AI/DI_2 channel power alarm status. it is an enumeration type: 
                  If the enumeration value is 1, it indicates the power status is normal;
                  If the enumeration value is 2, it indicates the power status is abnormal;
                  If the enumeration value is 3, it indicates the power status is unknown;"
            ::= { hwMUE06AOperEntry 15 }

        hwMUE06ACh3DiStatus OBJECT-TYPE
            SYNTAX INTEGER
                {
                open(1),
                closed(2),
                unknown(255)
                }
            MAX-ACCESS read-only
            STATUS current
            DESCRIPTION
                "AI/DI_3 channel digital input status. it is an enumeration type: 
                  If the enumeration value is 1, it indicates sensor status is open;
                  If the enumeration value is 2, it indicates sensor status is closed;
                  If the enumeration value is 3, it indicates sensor status is unknown;"
            ::= { hwMUE06AOperEntry 16 }

        hwMUE06ACh3AiValue OBJECT-TYPE
            SYNTAX Integer32 ( -100..200)
            MAX-ACCESS read-only
            STATUS current
            DESCRIPTION
                "AI/DI_3 channel analog input signal's value. Value range: -100 to 200. Multiple: 10."
            ::= { hwMUE06AOperEntry 17 }

        hwMUE06ACh3SensorStatus OBJECT-TYPE
            SYNTAX INTEGER
                {
                normal(1),
                failure(2),
                unknown(255)
                }
            MAX-ACCESS read-only
            STATUS current
            DESCRIPTION
                "AI/DI_3 channel sensor status. it is an enumeration type: 
                  If the enumeration value is 1, it indicates sensor status is normal;
                  If the enumeration value is 2, it indicates sensor status is invalid;
                  If the enumeration value is 3, it indicates sensor status is unknown;"
            ::= { hwMUE06AOperEntry 18 }

        hwMUE06ACh3PowerOutputStatus OBJECT-TYPE
            SYNTAX INTEGER
                {
                off(1),
                on(2),
                unknown(255)
                }
            MAX-ACCESS read-only
            STATUS current
            DESCRIPTION
                "AI/DI_3 channel power output status. it is an enumeration type: 
                  If the enumeration value is 1, it indicates the power is turned off;
                  If the enumeration value is 2, it indicates the power is turned on;
                  If the enumeration value is 3, it indicates the power status is unknown;"
            ::= { hwMUE06AOperEntry 19 }

        hwMUE06ACh3PowerOutputAlarmStatus OBJECT-TYPE
            SYNTAX INTEGER
                {
                normal(1),
                alarm(2),
                unknown(255)
                }
            MAX-ACCESS read-only
            STATUS current
            DESCRIPTION
                "AI/DI_3 channel power alarm status. it is an enumeration type: 
                  If the enumeration value is 1, it indicates the power status is normal;
                  If the enumeration value is 2, it indicates the power status is abnormal;
                  If the enumeration value is 3, it indicates the power status is unknown;"
            ::= { hwMUE06AOperEntry 20 }

        hwMUE06ACh4DiStatus OBJECT-TYPE
            SYNTAX INTEGER
                {
                open(1),
                closed(2),
                unknown(255)
                }
            MAX-ACCESS read-only
            STATUS current
            DESCRIPTION
                "AI/DI_4 channel digital input status. it is an enumeration type: 
                  If the enumeration value is 1, it indicates sensor status is open;
                  If the enumeration value is 2, it indicates sensor status is closed;
                  If the enumeration value is 3, it indicates sensor status is unknown;"
            ::= { hwMUE06AOperEntry 21 }

        hwMUE06ACh4AiValue OBJECT-TYPE
            SYNTAX Integer32 ( -100..200)
            MAX-ACCESS read-only
            STATUS current
            DESCRIPTION
                "AI/DI_4 channel analog input signal's value. Value range: -100 to 200. Multiple: 10."
            ::= { hwMUE06AOperEntry 22 }

        hwMUE06ACh4SensorStatus OBJECT-TYPE
            SYNTAX INTEGER
                {
                normal(1),
                failure(2),
                unknown(255)
                }
            MAX-ACCESS read-only
            STATUS current
            DESCRIPTION
                "AI/DI_4 channel sensor status. it is an enumeration type: 
                  If the enumeration value is 1, it indicates sensor status is normal;
                  If the enumeration value is 2, it indicates sensor status is invalid;
                  If the enumeration value is 3, it indicates sensor status is unknown;"
            ::= { hwMUE06AOperEntry 23 }

        hwMUE06ACh4PowerOutputStatus OBJECT-TYPE
            SYNTAX INTEGER
                {
                off(1),
                on(2),
                unknown(255)
                }
            MAX-ACCESS read-only
            STATUS current
            DESCRIPTION
                "AI/DI_4 channel power output status. it is an enumeration type: 
                  If the enumeration value is 1, it indicates the power is turned off;
                  If the enumeration value is 2, it indicates the power is turned on;
                  If the enumeration value is 3, it indicates the power status is unknown;"
            ::= { hwMUE06AOperEntry 24 }

        hwMUE06ACh4PowerOutputAlarmStatus OBJECT-TYPE
            SYNTAX INTEGER
                {
                normal(1),
                alarm(2),
                unknown(255)
                }
            MAX-ACCESS read-only
            STATUS current
            DESCRIPTION
                "AI/DI_4 channel power alarm status. it is an enumeration type: 
                  If the enumeration value is 1, it indicates the power status is normal;
                  If the enumeration value is 2, it indicates the power status is abnormal;
                  If the enumeration value is 3, it indicates the power status is unknown;"
            ::= { hwMUE06AOperEntry 25 }

        hwMUE06ACh5DiStatus OBJECT-TYPE
            SYNTAX INTEGER
                {
                open(1),
                closed(2),
                unknown(255)
                }
            MAX-ACCESS read-only
            STATUS current
            DESCRIPTION
                "AI/DI_5 channel digital input status. it is an enumeration type: 
                  If the enumeration value is 1, it indicates sensor status is open;
                  If the enumeration value is 2, it indicates sensor status is closed;
                  If the enumeration value is 3, it indicates sensor status is unknown;"
            ::= { hwMUE06AOperEntry 26 }

        hwMUE06ACh5AiValue OBJECT-TYPE
            SYNTAX Integer32 ( -100..200)
            MAX-ACCESS read-only
            STATUS current
            DESCRIPTION
                "AI/DI_5 channel analog input signal's value. Value range: -100 to 200. Multiple: 10."
            ::= { hwMUE06AOperEntry 27 }

        hwMUE06ACh5SensorStatus OBJECT-TYPE
            SYNTAX INTEGER
                {
                normal(1),
                failure(2),
                unknown(255)
                }
            MAX-ACCESS read-only
            STATUS current
            DESCRIPTION
                "AI/DI_5 channel sensor status. it is an enumeration type: 
                  If the enumeration value is 1, it indicates sensor status is normal;
                  If the enumeration value is 2, it indicates sensor status is invalid;
                  If the enumeration value is 3, it indicates sensor status is unknown;"
            ::= { hwMUE06AOperEntry 28 }

        hwMUE06ACh5PowerOutputStatus OBJECT-TYPE
            SYNTAX INTEGER
                {
                off(1),
                on(2),
                unknown(255)
                }
            MAX-ACCESS read-only
            STATUS current
            DESCRIPTION
                "AI/DI_5 channel power output status. it is an enumeration type: 
                  If the enumeration value is 1, it indicates the power is turned off;
                  If the enumeration value is 2, it indicates the power is turned on;
                  If the enumeration value is 3, it indicates the power status is unknown;"
            ::= { hwMUE06AOperEntry 29 }

        hwMUE06ACh5PowerOutputAlarmStatus OBJECT-TYPE
            SYNTAX INTEGER
                {
                normal(1),
                alarm(2),
                unknown(255)
                }
            MAX-ACCESS read-only
            STATUS current
            DESCRIPTION
                "AI/DI_5 channel power alarm status. it is an enumeration type: 
                  If the enumeration value is 1, it indicates the power status is normal;
                  If the enumeration value is 2, it indicates the power status is abnormal;
                  If the enumeration value is 3, it indicates the power status is unknown;"
            ::= { hwMUE06AOperEntry 30 }

        hwMUE06ACh6DiStatus OBJECT-TYPE
            SYNTAX INTEGER
                {
                open(1),
                closed(2),
                unknown(255)
                }
            MAX-ACCESS read-only
            STATUS current
            DESCRIPTION
                "AI/DI_6 channel digital input status. it is an enumeration type: 
                  If the enumeration value is 1, it indicates sensor status is open;
                  If the enumeration value is 2, it indicates sensor status is closed;
                  If the enumeration value is 3, it indicates sensor status is unknown;"
            ::= { hwMUE06AOperEntry 31 }

        hwMUE06ACh6AiValue OBJECT-TYPE
            SYNTAX Integer32 ( -100..200)
            MAX-ACCESS read-only
            STATUS current
            DESCRIPTION
                "AI/DI_6 channel analog input signal's value. Value range: -100 to 200. Multiple: 10."
            ::= { hwMUE06AOperEntry 32 }

        hwMUE06ACh6SensorStatus OBJECT-TYPE
            SYNTAX INTEGER
                {
                normal(1),
                failure(2),
                unknown(255)
                }
            MAX-ACCESS read-only
            STATUS current
            DESCRIPTION
                "AI/DI_6 channel sensor status. it is an enumeration type: 
                  If the enumeration value is 1, it indicates sensor status is normal;
                  If the enumeration value is 2, it indicates sensor status is invalid;
                  If the enumeration value is 3, it indicates sensor status is unknown;"
            ::= { hwMUE06AOperEntry 33 }

        hwMUE06ACh6PowerOutputStatus OBJECT-TYPE
            SYNTAX INTEGER
                {
                off(1),
                on(2),
                unknown(255)
                }
            MAX-ACCESS read-only
            STATUS current
            DESCRIPTION
                "AI/DI_6 channel power output status. it is an enumeration type: 
                  If the enumeration value is 1, it indicates the power is turned off;
                  If the enumeration value is 2, it indicates the power is turned on;
                  If the enumeration value is 3, it indicates the power status is unknown;"
            ::= { hwMUE06AOperEntry 34 }

        hwMUE06ACh6PowerOutputAlarmStatus OBJECT-TYPE
            SYNTAX INTEGER
                {
                normal(1),
                alarm(2),
                unknown(255)
                }
            MAX-ACCESS read-only
            STATUS current
            DESCRIPTION
                "AI/DI_6 channel power alarm status. it is an enumeration type: 
                  If the enumeration value is 1, it indicates the power status is normal;
                  If the enumeration value is 2, it indicates the power status is abnormal;
                  If the enumeration value is 3, it indicates the power status is unknown;"
            ::= { hwMUE06AOperEntry 35 }

        hwMUE06ACh7DiStatus OBJECT-TYPE
            SYNTAX INTEGER
                {
                open(1),
                closed(2),
                unknown(255)
                }
            MAX-ACCESS read-only
            STATUS current
            DESCRIPTION
                "AI/DI_7 channel digital input status. it is an enumeration type: 
                  If the enumeration value is 1, it indicates sensor status is open;
                  If the enumeration value is 2, it indicates sensor status is closed;
                  If the enumeration value is 3, it indicates sensor status is unknown;"
            ::= { hwMUE06AOperEntry 36 }

        hwMUE06ACh7AiValue OBJECT-TYPE
            SYNTAX Integer32 ( -100..200)
            MAX-ACCESS read-only
            STATUS current
            DESCRIPTION
                "AI/DI_7 channel analog input signal's value. Value range: -100 to 200. Multiple: 10."
            ::= { hwMUE06AOperEntry 37 }

        hwMUE06ACh7SensorStatus OBJECT-TYPE
            SYNTAX INTEGER
                {
                normal(1),
                failure(2),
                unknown(255)
                }
            MAX-ACCESS read-only
            STATUS current
            DESCRIPTION
                "AI/DI_7 channel sensor status. it is an enumeration type: 
                  If the enumeration value is 1, it indicates sensor status is normal;
                  If the enumeration value is 2, it indicates sensor status is invalid;
                  If the enumeration value is 3, it indicates sensor status is unknown;"
            ::= { hwMUE06AOperEntry 38 }

        hwMUE06ACh7PowerOutputStatus OBJECT-TYPE
            SYNTAX INTEGER
                {
                off(1),
                on(2),
                unknown(255)
                }
            MAX-ACCESS read-only
            STATUS current
            DESCRIPTION
                "AI/DI_7 channel power output status. it is an enumeration type: 
                  If the enumeration value is 1, it indicates the power is turned off;
                  If the enumeration value is 2, it indicates the power is turned on;
                  If the enumeration value is 3, it indicates the power status is unknown;"
            ::= { hwMUE06AOperEntry 39 }

        hwMUE06ACh7PowerOutputAlarmStatus OBJECT-TYPE
            SYNTAX INTEGER
                {
                normal(1),
                alarm(2),
                unknown(255)
                }
            MAX-ACCESS read-only
            STATUS current
            DESCRIPTION
                "AI/DI_7 channel power alarm status. it is an enumeration type: 
                  If the enumeration value is 1, it indicates the power status is normal;
                  If the enumeration value is 2, it indicates the power status is abnormal;
                  If the enumeration value is 3, it indicates the power status is unknown;"
            ::= { hwMUE06AOperEntry 40 }

        hwMUE06ACh8DiStatus OBJECT-TYPE
            SYNTAX INTEGER
                {
                open(1),
                closed(2),
                unknown(255)
                }
            MAX-ACCESS read-only
            STATUS current
            DESCRIPTION
                "AI/DI_8 channel digital input status. it is an enumeration type: 
                  If the enumeration value is 1, it indicates sensor status is open;
                  If the enumeration value is 2, it indicates sensor status is closed;
                  If the enumeration value is 3, it indicates sensor status is unknown;"
            ::= { hwMUE06AOperEntry 41 }

        hwMUE06ACh8AiValue OBJECT-TYPE
            SYNTAX Integer32 ( -100..200)
            MAX-ACCESS read-only
            STATUS current
            DESCRIPTION
                "AI/DI_8 channel analog input signal's value. Value range: -100 to 200. Multiple: 10."
            ::= { hwMUE06AOperEntry 42 }

        hwMUE06ACh8SensorStatus OBJECT-TYPE
            SYNTAX INTEGER
                {
                normal(1),
                failure(2),
                unknown(255)
                }
            MAX-ACCESS read-only
            STATUS current
            DESCRIPTION
                "AI/DI_8 channel sensor status. it is an enumeration type: 
                  If the enumeration value is 1, it indicates sensor status is normal;
                  If the enumeration value is 2, it indicates sensor status is invalid;
                  If the enumeration value is 3, it indicates sensor status is unknown;"
            ::= { hwMUE06AOperEntry 43 }

        hwMUE06ACh8PowerOutputStatus OBJECT-TYPE
            SYNTAX INTEGER
                {
                off(1),
                on(2),
                unknown(255)
                }
            MAX-ACCESS read-only
            STATUS current
            DESCRIPTION
                "AI/DI_8 channel power output status. it is an enumeration type: 
                  If the enumeration value is 1, it indicates the power is turned off;
                  If the enumeration value is 2, it indicates the power is turned on;
                  If the enumeration value is 3, it indicates the power status is unknown;"
            ::= { hwMUE06AOperEntry 44 }

        hwMUE06ACh8PowerOutputAlarmStatus OBJECT-TYPE
            SYNTAX INTEGER
                {
                normal(1),
                alarm(2),
                unknown(255)
                }
            MAX-ACCESS read-only
            STATUS current
            DESCRIPTION
                "AI/DI_8 channel power alarm status. it is an enumeration type: 
                  If the enumeration value is 1, it indicates the power status is normal;
                  If the enumeration value is 2, it indicates the power status is abnormal;
                  If the enumeration value is 3, it indicates the power status is unknown;"
            ::= { hwMUE06AOperEntry 45 }

        hwMUE06APowerVoltageLowAlarmStatus OBJECT-TYPE
            SYNTAX INTEGER
                {
                normal(1),
                alarm(2),
                unknown(255)
                }
            MAX-ACCESS read-only
            STATUS current
            DESCRIPTION
                "Independent Deployment AI and DI Board's power input alarm status, it is an enumeration type: 
                  If the enumeration value is 1, it indicates the power input status is normal;
                  If the enumeration value is 2, it indicates the power input status is abnormal;
                  If the enumeration value is 3, it indicates the power input status is unknown;"
            ::= { hwMUE06AOperEntry 46 }

        hwMUE06AOperRowStatus OBJECT-TYPE
            SYNTAX RowStatus
            MAX-ACCESS read-create
            STATUS current
            DESCRIPTION
                "RowStatus of Independent Deployment AI and DI Board's running table"
            ::= { hwMUE06AOperEntry 100 }

        hwIDCUPS OBJECT IDENTIFIER ::= { hwIDCMonitorMIBObjects 5 }

        hwHuaweiUPS2000G-A OBJECT IDENTIFIER ::= { hwIDCUPS 1 }

        hwHuaweiUPS2000G-ARunningTable OBJECT-TYPE
            SYNTAX SEQUENCE OF HwHuaweiUPS2000G-ARunningEntry
            MAX-ACCESS not-accessible
             STATUS current
             DESCRIPTION
                "Running table of UPS2000G-A."
            ::= { hwHuaweiUPS2000G-A 1 }

        hwHuaweiUPS2000G-ARunningEntry OBJECT-TYPE
                        SYNTAX HwHuaweiUPS2000G-ARunningEntry
            MAX-ACCESS not-accessible
             STATUS current
             DESCRIPTION
                "Running table of UPS2000G-A."
            INDEX { hwHuaweiUPS2000G-ARunningIndex }
            ::= { hwHuaweiUPS2000G-ARunningTable 1 }

        HwHuaweiUPS2000G-ARunningEntry            ::= SEQUENCE {
                hwHuaweiUPS2000G-ARunningIndex
                    Unsigned32,
                hwHuaweiUPS2000G-AId
                    OCTET STRING,
                hwHuaweiUPS2000G-AName
                    OCTET STRING,
                hwHuaweiUPS2000G-AModel
                    Unsigned32,
                hwHuaweiUPS2000G-APowerMode
                    INTEGER,
                hwHuaweiUPS2000G-AInputMode
                    INTEGER,
                hwHuaweiUPS2000G-AOutputMode
                    INTEGER,
                hwHuaweiUPS2000G-AInnerTemperature
                    Unsigned32,
                hwHuaweiUPS2000G-AStartupStatus
                    INTEGER,
                hwHuaweiUPS2000G-AInputVoltage
                    Unsigned32,
                hwHuaweiUPS2000G-ABypassVoltage
                    Unsigned32,
                hwHuaweiUPS2000G-AOutputVoltage
                    Unsigned32,
                hwHuaweiUPS2000G-AOutputCurrent
                    Unsigned32,
                hwHuaweiUPS2000G-AOutputActivePower
                    Integer32,
                hwHuaweiUPS2000G-AOutputApparentPower
                    Integer32,
                hwHuaweiUPS2000G-ALoadRatio
                    Unsigned32,
                hwHuaweiUPS2000G-APhaseAInputVoltage
                    Unsigned32,
                hwHuaweiUPS2000G-APhaseBInputVoltage
                    Unsigned32,
                hwHuaweiUPS2000G-APhaseCInputVoltage
                    Unsigned32,
                hwHuaweiUPS2000G-AInputFrequency
                    Unsigned32,
                hwHuaweiUPS2000G-APhaseABypassVoltage
                    Unsigned32,
                hwHuaweiUPS2000G-APhaseBBypassVoltage
                    Unsigned32,
                hwHuaweiUPS2000G-APhaseCBypassVoltage
                    Unsigned32,
                hwHuaweiUPS2000G-ABypassFrequency
                    Unsigned32,
                hwHuaweiUPS2000G-APhaseAOutputVoltage
                    Unsigned32,
                hwHuaweiUPS2000G-APhaseBOutputVoltage
                    Unsigned32,
                hwHuaweiUPS2000G-APhaseCOutputVoltage
                    Unsigned32,
                hwHuaweiUPS2000G-APhaseAOutputCurrent
                    Unsigned32,
                hwHuaweiUPS2000G-APhaseBOutputCurrent
                    Unsigned32,
                hwHuaweiUPS2000G-APhaseCOutputCurrent
                    Unsigned32,
                hwHuaweiUPS2000G-AOutputFrequency
                    Unsigned32,
                hwHuaweiUPS2000G-APhaseAOutputActivePower
                    Integer32,
                hwHuaweiUPS2000G-APhaseBOutputActivePower
                    Integer32,
                hwHuaweiUPS2000G-APhaseCOutputActivePower
                    Integer32,
                hwHuaweiUPS2000G-APhaseAOutputApparentPower
                    Integer32,
                hwHuaweiUPS2000G-APhaseBOutputApparentPower
                    Integer32,
                hwHuaweiUPS2000G-APhaseCOutputApparentPower
                    Integer32,
                hwHuaweiUPS2000G-APhaseALoadRatio
                    Unsigned32,
                hwHuaweiUPS2000G-APhaseBLoadRatio
                    Unsigned32,
                hwHuaweiUPS2000G-APhaseCLoadRatio
                    Unsigned32,
                hwHuaweiUPS2000G-ABatteryVoltage
                    Unsigned32,
                hwHuaweiUPS2000G-ABatteryCurrent
                    Integer32,
                hwHuaweiUPS2000G-ABatteryStatus
                    INTEGER,
                hwHuaweiUPS2000G-ABatteryRemainRatio
                    Unsigned32,
                hwHuaweiUPS2000G-ABatteryBackupTime
                    Unsigned32,
                hwHuaweiUPS2000G-ABatteryTemperature
                    Integer32,
                hwHuaweiUPS2000G-AParallelStatus
                    INTEGER,
                hwHuaweiUPS2000G-ACommStatus
                    INTEGER,
                hwHuaweiUPS2000G-ASlotNo
                    Unsigned32,
                hwHuaweiUPS2000G-APortNo
                    Unsigned32,
                hwHuaweiUPS2000G-ASoftwareVersion
                    OCTET STRING,
                hwHuaweiUPS2000G-AModbusAddress
                    Unsigned32,
                hwHuaweiUPS2000G-AMaintBreakStatus
                    INTEGER,
                hwHuaweiUPS2000G-ARunningRowStatus
                    RowStatus
            }

        hwHuaweiUPS2000G-ARunningIndex OBJECT-TYPE
            SYNTAX Unsigned32
            MAX-ACCESS read-only
            STATUS current
            DESCRIPTION
                "Index of the device running table for the UPS2000G-A."
            ::= { hwHuaweiUPS2000G-ARunningEntry 1 }

        hwHuaweiUPS2000G-AId OBJECT-TYPE
            SYNTAX OCTET STRING
            MAX-ACCESS read-only
            STATUS current
            DESCRIPTION
                "ESN of the master device used for setting up a NetEco model. A string of characters."
            ::= { hwHuaweiUPS2000G-ARunningEntry 2 }

        hwHuaweiUPS2000G-AName OBJECT-TYPE
            SYNTAX OCTET STRING (SIZE (0..50))
            MAX-ACCESS read-only
            STATUS current
            DESCRIPTION
                "Name of the UPS system. A string of characters."
            ::= { hwHuaweiUPS2000G-ARunningEntry 3 }

        hwHuaweiUPS2000G-AModel OBJECT-TYPE
            SYNTAX Unsigned32 (1..20)
            MAX-ACCESS read-only
            STATUS current
            DESCRIPTION
                "UPS2000G-A capacity. The unit is K."
            ::= { hwHuaweiUPS2000G-ARunningEntry 4 }

        hwHuaweiUPS2000G-APowerMode OBJECT-TYPE
            SYNTAX INTEGER
                {
                nopowersupply(1),
                bypassmode(2),
                mainsmode(3),
                batterymode(4),
                mainseco(5),
                batteryeco(6),
                unknown(255)
                }
            MAX-ACCESS read-only
            STATUS current
            DESCRIPTION
                "Device power supply mode. Enumeration type.
                    Value 1 indicates no power supply.
                    Value 2 indicates bypass mode.
                    Value 3 indicates normal mode.
                    Value 4 indicates battery mode.
                    Value 5 indicates mains ECO mode.
                    Value 6 indicates battery ECO mode."
            ::= { hwHuaweiUPS2000G-ARunningEntry 5 }

        hwHuaweiUPS2000G-AInputMode OBJECT-TYPE
            SYNTAX INTEGER
                {
                singlephase(1),
                threephase(2),
                unknown(255)
                }
            MAX-ACCESS read-only
            STATUS current
            DESCRIPTION
                "Device input mode.
                   Value 1 indicates singlephase.
                   Vaule 2 indicates thressphase."
            ::= { hwHuaweiUPS2000G-ARunningEntry 6 }

        hwHuaweiUPS2000G-AOutputMode OBJECT-TYPE
            SYNTAX INTEGER
                {
                singlephase(1),
                threephase(2),
                unknown(255)
                }
            MAX-ACCESS read-only
            STATUS current
            DESCRIPTION
                "Device output mode.
                   Value 1 indicates singlephase.
                   Vaule 2 indicates thressphase."
            ::= { hwHuaweiUPS2000G-ARunningEntry 7 }

        hwHuaweiUPS2000G-AInnerTemperature OBJECT-TYPE
            SYNTAX Unsigned32 (0..300)
            MAX-ACCESS read-only
            STATUS current
            DESCRIPTION
                "Maximum temperature of the modules in the current device. An integer ranging from 0 to 300.Multiple: 10."
            ::= { hwHuaweiUPS2000G-ARunningEntry 8 }

        hwHuaweiUPS2000G-AStartupStatus OBJECT-TYPE
            SYNTAX INTEGER
                {
                shutdown(1),
                starting(2),
                startupfailed(3),
                startupdone(4),
                unknown(255)
                }
            MAX-ACCESS read-only
            STATUS current
            DESCRIPTION
                "Device Startup Status.
                   Value 1 indicates shutdown.
                   Vaule 2 indicates starting.
                   Value 3 indicates startupfailed.
                   Vaule 4 indicates startupdone."
            ::= { hwHuaweiUPS2000G-ARunningEntry 9 }

        hwHuaweiUPS2000G-AInputVoltage OBJECT-TYPE
            SYNTAX Unsigned32 (0..1000)
            MAX-ACCESS read-only
            STATUS current
            DESCRIPTION
                "Input voltage. The value ranges from 0 to 1000. 
                    The value is accurate to one decimal place on the NetEco. The unit is V.Multiple: 10."
            ::= { hwHuaweiUPS2000G-ARunningEntry 10 }

        hwHuaweiUPS2000G-ABypassVoltage OBJECT-TYPE
            SYNTAX Unsigned32 (0..1000)
            MAX-ACCESS read-only
            STATUS current
            DESCRIPTION
                "Bypass input voltage. The value ranges from 0 to 1000
                    The value is accurate to one decimal place on the NetEco. The unit is V.Multiple: 10."
            ::= { hwHuaweiUPS2000G-ARunningEntry 11 }

        hwHuaweiUPS2000G-AOutputVoltage OBJECT-TYPE
            SYNTAX Unsigned32 (0..1000)
            MAX-ACCESS read-only
            STATUS current
            DESCRIPTION
                "Rack output voltage. The value ranges from 0 to 1000. 
                    The value is accurate to one decimal place on the NetEco. The unit is V.Multiple: 10."
            ::= { hwHuaweiUPS2000G-ARunningEntry 12 }

        hwHuaweiUPS2000G-AOutputCurrent OBJECT-TYPE
            SYNTAX Unsigned32 (0..1000)
            MAX-ACCESS read-only
            STATUS current
            DESCRIPTION
                "Rack output current. The value ranges from 0 to 1000. 
                    The value is accurate to one decimal place on the NetEco. The unit is A.Multiple: 10."
            ::= { hwHuaweiUPS2000G-ARunningEntry 13 }

        hwHuaweiUPS2000G-AOutputActivePower OBJECT-TYPE
            SYNTAX Integer32 ( -1200..1200)
            MAX-ACCESS read-only
            STATUS current
            DESCRIPTION
                "Rack output active power. The value ranges from -1200 to 1200. 
                    The value is accurate to one decimal place on the NetEco. The unit is kW.Multiple: 10."
            ::= { hwHuaweiUPS2000G-ARunningEntry 14 }

        hwHuaweiUPS2000G-AOutputApparentPower OBJECT-TYPE
            SYNTAX Integer32 ( -1200..1200)
            MAX-ACCESS read-only
            STATUS current
            DESCRIPTION
                "Rack output apparent power. The value ranges from -1200 to 1200. 
                    The value is accurate to one decimal place on the NetEco. The unit is kVA.Multiple: 10."
            ::= { hwHuaweiUPS2000G-ARunningEntry 15 }

        hwHuaweiUPS2000G-ALoadRatio OBJECT-TYPE
            SYNTAX Unsigned32 (0..500)
            MAX-ACCESS read-only
            STATUS current
            DESCRIPTION
                "Rack output load ratio. The value ranges from 0 to 500 The value is accurate to one decimal place on the NetEco.Multiple: 10."
            ::= { hwHuaweiUPS2000G-ARunningEntry 16 }

        hwHuaweiUPS2000G-APhaseAInputVoltage OBJECT-TYPE
            SYNTAX Unsigned32 (0..1000)
            MAX-ACCESS read-only
            STATUS current
            DESCRIPTION
                "Input voltage phase A. The value ranges from 0 to 1000. 
                    The value is accurate to one decimal place on the NetEco. The unit is V.Multiple: 10."
            ::= { hwHuaweiUPS2000G-ARunningEntry 17 }

        hwHuaweiUPS2000G-APhaseBInputVoltage OBJECT-TYPE
            SYNTAX Unsigned32 (0..1000)
            MAX-ACCESS read-only
            STATUS current
            DESCRIPTION
                "Input voltage phase B. The value ranges from 0 to 1000. 
                    The value is accurate to one decimal place on the NetEco. The unit is V.Multiple: 10."
            ::= { hwHuaweiUPS2000G-ARunningEntry 18 }

        hwHuaweiUPS2000G-APhaseCInputVoltage OBJECT-TYPE
            SYNTAX Unsigned32 (0..1000)
            MAX-ACCESS read-only
            STATUS current
            DESCRIPTION
                "Input voltage phase C. The value ranges from 0 to 1000. 
                    The value is accurate to one decimal place on the NetEco. The unit is V.Multiple: 10."
            ::= { hwHuaweiUPS2000G-ARunningEntry 19 }

        hwHuaweiUPS2000G-AInputFrequency OBJECT-TYPE
            SYNTAX Unsigned32 (0..100)
            MAX-ACCESS read-only
            STATUS current
            DESCRIPTION
                "Input frequency. The value ranges from 0 to 100. 
                    The value is accurate to two decimal place on the NetEco. The unit is Hz.Multiple: 10."
            ::= { hwHuaweiUPS2000G-ARunningEntry 20 }

        hwHuaweiUPS2000G-APhaseABypassVoltage OBJECT-TYPE
            SYNTAX Unsigned32 (0..1000)
            MAX-ACCESS read-only
            STATUS current
            DESCRIPTION
                "Bypass input voltage phase A. The value ranges from 0 to 1000 
                    The value is accurate to one decimal place on the NetEco. The unit is V.Multiple: 10."
            ::= { hwHuaweiUPS2000G-ARunningEntry 21 }

        hwHuaweiUPS2000G-APhaseBBypassVoltage OBJECT-TYPE
            SYNTAX Unsigned32 (0..1000)
            MAX-ACCESS read-only
            STATUS current
            DESCRIPTION
                "Bypass input voltage phase B. The value ranges from 0 to 1000 
                    The value is accurate to one decimal place on the NetEco. The unit is V.Multiple: 10."
            ::= { hwHuaweiUPS2000G-ARunningEntry 22 }

        hwHuaweiUPS2000G-APhaseCBypassVoltage OBJECT-TYPE
            SYNTAX Unsigned32 (0..1000)
            MAX-ACCESS read-only
            STATUS current
            DESCRIPTION
                "Bypass input voltage phase C. The value ranges from 0 to 1000 
                    The value is accurate to one decimal place on the NetEco. The unit is V.Multiple: 10."
            ::= { hwHuaweiUPS2000G-ARunningEntry 23 }

        hwHuaweiUPS2000G-ABypassFrequency OBJECT-TYPE
            SYNTAX Unsigned32 (0..100)
            MAX-ACCESS read-only
            STATUS current
            DESCRIPTION
                "Bypass input frequency. The value ranges from 0 to 100 
                    The value is accurate to two decimal place on the NetEco. The unit is Hz.Multiple: 10."
            ::= { hwHuaweiUPS2000G-ARunningEntry 24 }

        hwHuaweiUPS2000G-APhaseAOutputVoltage OBJECT-TYPE
            SYNTAX Unsigned32 (0..1000)
            MAX-ACCESS read-only
            STATUS current
            DESCRIPTION
                "Rack phase A output voltage. The value ranges from 0 to 1000. 
                    The value is accurate to one decimal place on the NetEco. The unit is V.Multiple: 10."
            ::= { hwHuaweiUPS2000G-ARunningEntry 25 }

        hwHuaweiUPS2000G-APhaseBOutputVoltage OBJECT-TYPE
            SYNTAX Unsigned32 (0..1000)
            MAX-ACCESS read-only
            STATUS current
            DESCRIPTION
                "Rack phase B output voltage. The value ranges from 0 to 1000. 
                    The value is accurate to one decimal place on the NetEco. The unit is V.Multiple: 10."
            ::= { hwHuaweiUPS2000G-ARunningEntry 26 }

        hwHuaweiUPS2000G-APhaseCOutputVoltage OBJECT-TYPE
            SYNTAX Unsigned32 (0..1000)
            MAX-ACCESS read-only
            STATUS current
            DESCRIPTION
                "Rack phase C output voltage. The value ranges from 0 to  1000.
                    The value is accurate to one decimal place on the NetEco. The unit is V.Multiple: 10."
            ::= { hwHuaweiUPS2000G-ARunningEntry 27 }

        hwHuaweiUPS2000G-APhaseAOutputCurrent OBJECT-TYPE
            SYNTAX Unsigned32 (0..1000)
            MAX-ACCESS read-only
            STATUS current
            DESCRIPTION
                "Rack phase A output current. The value ranges from 0 to 1000. 
                    The value is accurate to one decimal place on the NetEco. The unit is A.Multiple: 10."
            ::= { hwHuaweiUPS2000G-ARunningEntry 28 }

        hwHuaweiUPS2000G-APhaseBOutputCurrent OBJECT-TYPE
            SYNTAX Unsigned32 (0..1000)
            MAX-ACCESS read-only
            STATUS current
            DESCRIPTION
                "Rack phase B output current. The value ranges from 0 to 1000. 
                    The value is accurate to one decimal place on the NetEco. The unit is A.Multiple: 10."
            ::= { hwHuaweiUPS2000G-ARunningEntry 29 }

        hwHuaweiUPS2000G-APhaseCOutputCurrent OBJECT-TYPE
            SYNTAX Unsigned32 (0..1000)
            MAX-ACCESS read-only
            STATUS current
            DESCRIPTION
                "Rack phase C output current. The value ranges from 0 to 1000. 
                    The value is accurate to one decimal place on the NetEco. The unit is A.Multiple: 10."
            ::= { hwHuaweiUPS2000G-ARunningEntry 30 }

        hwHuaweiUPS2000G-AOutputFrequency OBJECT-TYPE
            SYNTAX Unsigned32 (0..100)
            MAX-ACCESS read-only
            STATUS current
            DESCRIPTION
                "Rack output frequency. The value ranges from 0 to 100. 
                    The value is accurate to two decimal place on the NetEco. The unit is Hz.Multiple: 10."
            ::= { hwHuaweiUPS2000G-ARunningEntry 31 }

        hwHuaweiUPS2000G-APhaseAOutputActivePower OBJECT-TYPE
            SYNTAX Integer32 ( -1200..1200)
            MAX-ACCESS read-only
            STATUS current
            DESCRIPTION
                "Rack phase A output active power. The value ranges from -1200 to 1200. 
                    The value is accurate to one decimal place on the NetEco. The unit is kW.Multiple: 10."
            ::= { hwHuaweiUPS2000G-ARunningEntry 32 }

        hwHuaweiUPS2000G-APhaseBOutputActivePower OBJECT-TYPE
            SYNTAX Integer32 ( -1200..1200)
            MAX-ACCESS read-only
            STATUS current
            DESCRIPTION
                "Rack phase B output active power. The value ranges from -1200 to 1200. 
                    The value is accurate to one decimal place on the NetEco. The unit is kW.Multiple: 10."
            ::= { hwHuaweiUPS2000G-ARunningEntry 33 }

        hwHuaweiUPS2000G-APhaseCOutputActivePower OBJECT-TYPE
            SYNTAX Integer32 ( -1200..1200)
            MAX-ACCESS read-only
            STATUS current
            DESCRIPTION
                "Rack phase C output active power. The value ranges from -1200 to 1200. 
                    The value is accurate to one decimal place on the NetEco. The unit is kW.Multiple: 10."
            ::= { hwHuaweiUPS2000G-ARunningEntry 34 }

        hwHuaweiUPS2000G-APhaseAOutputApparentPower OBJECT-TYPE
            SYNTAX Integer32 ( -1200..1200)
            MAX-ACCESS read-only
            STATUS current
            DESCRIPTION
                "Rack phase A output apparent power. The value ranges from -1200 to 1200. 
                    The value is accurate to one decimal place on the NetEco. The unit is kVA.Multiple: 10."
            ::= { hwHuaweiUPS2000G-ARunningEntry 35 }

        hwHuaweiUPS2000G-APhaseBOutputApparentPower OBJECT-TYPE
            SYNTAX Integer32 ( -1200..1200)
            MAX-ACCESS read-only
            STATUS current
            DESCRIPTION
                "Rack phase B output apparent power. The value ranges from -1200 to 1200. 
                    The value is accurate to one decimal place on the NetEco. The unit is kVA.Multiple: 10."
            ::= { hwHuaweiUPS2000G-ARunningEntry 36 }

        hwHuaweiUPS2000G-APhaseCOutputApparentPower OBJECT-TYPE
            SYNTAX Integer32 ( -1200..1200)
            MAX-ACCESS read-only
            STATUS current
            DESCRIPTION
                "Rack phase C output apparent power. The value ranges from -1200 to 1200. 
                    The value is accurate to one decimal place on the NetEco. The unit is kVA.Multiple: 10."
            ::= { hwHuaweiUPS2000G-ARunningEntry 37 }

        hwHuaweiUPS2000G-APhaseALoadRatio OBJECT-TYPE
            SYNTAX Unsigned32 (0..500)
            MAX-ACCESS read-only
            STATUS current
            DESCRIPTION
                "Rack phase A output load ratio. The value ranges from 0 to 500 The value is accurate to one decimal place on the NetEco.Multiple: 10."
            ::= { hwHuaweiUPS2000G-ARunningEntry 38 }

        hwHuaweiUPS2000G-APhaseBLoadRatio OBJECT-TYPE
            SYNTAX Unsigned32 (0..500)
            MAX-ACCESS read-only
            STATUS current
            DESCRIPTION
                "Rack phase B output load ratio. The value ranges from 0 to 500 The value is accurate to one decimal place on the NetEco.Multiple: 10."
            ::= { hwHuaweiUPS2000G-ARunningEntry 39 }

        hwHuaweiUPS2000G-APhaseCLoadRatio OBJECT-TYPE
            SYNTAX Unsigned32 (0..500)
            MAX-ACCESS read-only
            STATUS current
            DESCRIPTION
                "Rack phase C output load ratio. The value ranges from 0 to 500 The value is accurate to one decimal place on the NetEco.Multiple: 10."
            ::= { hwHuaweiUPS2000G-ARunningEntry 40 }

        hwHuaweiUPS2000G-ABatteryVoltage OBJECT-TYPE
            SYNTAX Unsigned32 (0..2000)
            MAX-ACCESS read-only
            STATUS current
            DESCRIPTION
                "Battery Voltage. It is a real-time analog parameter. 
                    Value range: 0 to 2000, Unit: V, and the value is accurate to one decimal place (.1).Multiple: 10."
            ::= { hwHuaweiUPS2000G-ARunningEntry 41 }

        hwHuaweiUPS2000G-ABatteryCurrent OBJECT-TYPE
            SYNTAX Integer32 ( -3000..3000)
            MAX-ACCESS read-only
            STATUS current
            DESCRIPTION
                "Battery Total Current. It is a real-time analog parameter. 
                    Value range: -3000 to 3000, Unit: A, and the value is accurate to one decimal place (.1).Multiple: 10."
            ::= { hwHuaweiUPS2000G-ARunningEntry 42 }

        hwHuaweiUPS2000G-ABatteryStatus OBJECT-TYPE
            SYNTAX INTEGER
                {
                hibernation(1),
                floatcharging(2),
                equalizedcharging(3),
                discharging(4),
                unknown(255)
                }
            MAX-ACCESS read-only
            STATUS current
            DESCRIPTION
                "Battery status. Enumeration type.
                    Value 1 indicates that no battery is connected.
                    Value 2 indicates that the battery is not charging or discharging.
                    Value 3 indicates hibernation.
                    Value 4 indicates float charging.
                    Value 5 indicates equalized charging.
                    Value 6 indicates discharging."
            ::= { hwHuaweiUPS2000G-ARunningEntry 43 }

        hwHuaweiUPS2000G-ABatteryRemainRatio OBJECT-TYPE
            SYNTAX Unsigned32 (0..100)
            MAX-ACCESS read-only
            STATUS current
            DESCRIPTION
                "Battery Capacity Left. Value range: 0 to 100, Unit: %, and the value is an integer."
            ::= { hwHuaweiUPS2000G-ARunningEntry 44 }

        hwHuaweiUPS2000G-ABatteryBackupTime OBJECT-TYPE
            SYNTAX Unsigned32 (0..2880)
            MAX-ACCESS read-only
            STATUS current
            DESCRIPTION
                "Battery Backup Time. Value range: 0 to 2880, Unit: Min, and the value is an integer."
            ::= { hwHuaweiUPS2000G-ARunningEntry 45 }

        hwHuaweiUPS2000G-ABatteryTemperature OBJECT-TYPE
            SYNTAX Integer32 ( -20..80)
            MAX-ACCESS read-only
            STATUS current
            DESCRIPTION
                "Battery temperature.Value range: -20 to 80, Unit:degC,  and the value is accurate to one decimal place (.1). Multiple: 10."
            ::= { hwHuaweiUPS2000G-ARunningEntry 46 }

        hwHuaweiUPS2000G-AParallelStatus OBJECT-TYPE
            SYNTAX INTEGER
                {
                single(1),
                parallel(2),
                unknown(255)
                }
            MAX-ACCESS read-only
            STATUS current
            DESCRIPTION
                "Device Parallel Status.
                   Value 1 indicates single.
                   Vaule 2 indicates parallel."
            ::= { hwHuaweiUPS2000G-ARunningEntry 47 }

        hwHuaweiUPS2000G-ACommStatus OBJECT-TYPE
            SYNTAX INTEGER
                {
                ok(1),
                fail(2),
                unknown(255)
                }
            MAX-ACCESS read-only
            STATUS current
            DESCRIPTION
                "Device communication status.
                   Value 1 indicates ok.
                   Vaule 2 indicates fail."
            ::= { hwHuaweiUPS2000G-ARunningEntry 48 }

        hwHuaweiUPS2000G-ASlotNo OBJECT-TYPE
            SYNTAX Unsigned32 (0..6)
            MAX-ACCESS read-only
            STATUS current
            DESCRIPTION
                "Device Slot No.Value range: 0 to 6."
            ::= { hwHuaweiUPS2000G-ARunningEntry 49 }

        hwHuaweiUPS2000G-APortNo OBJECT-TYPE
            SYNTAX Unsigned32 (1..5)
            MAX-ACCESS read-only
            STATUS current
            DESCRIPTION
                "Device Port No.Value range: 1 to 5."
            ::= { hwHuaweiUPS2000G-ARunningEntry 50 }

        hwHuaweiUPS2000G-ASoftwareVersion OBJECT-TYPE
            SYNTAX OCTET STRING (SIZE (0..32))
            MAX-ACCESS read-only
            STATUS current
            DESCRIPTION
                "Device software version number. A string of characters."
            ::= { hwHuaweiUPS2000G-ARunningEntry 51 }

        hwHuaweiUPS2000G-AModbusAddress OBJECT-TYPE
            SYNTAX Unsigned32 (0..247)
            MAX-ACCESS read-only
            STATUS current
            DESCRIPTION
                "Device Modubs Address."
            ::= { hwHuaweiUPS2000G-ARunningEntry 52 }

        hwHuaweiUPS2000G-AMaintBreakStatus OBJECT-TYPE
            SYNTAX INTEGER
                {
                open(0),
                close(1),
                unkown(255)
                }
            MAX-ACCESS read-only
            STATUS current
            DESCRIPTION
                "Maintenance Breaker Status."
            ::= { hwHuaweiUPS2000G-ARunningEntry 53 }

        hwHuaweiUPS2000G-ARunningRowStatus OBJECT-TYPE
            SYNTAX RowStatus
            MAX-ACCESS read-create
            STATUS current
            DESCRIPTION
                "RowStatus of Running UPS2000G-A."
            ::= { hwHuaweiUPS2000G-ARunningEntry 100 }

        hwHuaweiUPS2000G-AConfigTable OBJECT-TYPE
            SYNTAX SEQUENCE OF HwHuaweiUPS2000G-AConfigEntry
            MAX-ACCESS not-accessible
             STATUS current
             DESCRIPTION
                "The config table of UPS2000G-A."
            ::= { hwHuaweiUPS2000G-A 2 }

        hwHuaweiUPS2000G-AConfigEntry OBJECT-TYPE
                        SYNTAX HwHuaweiUPS2000G-AConfigEntry
            MAX-ACCESS not-accessible
             STATUS current
             DESCRIPTION
                "The config table of UPS2000G-A."
            INDEX { hwHuaweiUPS2000G-AConfigIndex }
            ::= { hwHuaweiUPS2000G-AConfigTable 1 }

        HwHuaweiUPS2000G-AConfigEntry            ::= SEQUENCE {
                hwHuaweiUPS2000G-AConfigIndex
                    Unsigned32,
                hwHuaweiUPS2000G-AStartup
                    INTEGER,
                hwHuaweiUPS2000G-AShutdown
                    INTEGER,
                hwHuaweiUPS2000G-AConfigRowStatus
                    RowStatus
            }

        hwHuaweiUPS2000G-AConfigIndex OBJECT-TYPE
            SYNTAX Unsigned32
            MAX-ACCESS read-only
            STATUS current
            DESCRIPTION
                "The index of config table of UPS2000G-A."
            ::= { hwHuaweiUPS2000G-AConfigEntry 1 }

        hwHuaweiUPS2000G-AStartup OBJECT-TYPE
            SYNTAX INTEGER
                {
                yes(1)
                }
            MAX-ACCESS read-write
            STATUS current
            DESCRIPTION
                "Startup the Device."
            ::= { hwHuaweiUPS2000G-AConfigEntry 2 }

        hwHuaweiUPS2000G-AShutdown OBJECT-TYPE
            SYNTAX INTEGER
                {
                yes(1)
                }
            MAX-ACCESS read-write
            STATUS current
            DESCRIPTION
                "Shutdown the Device."
            ::= { hwHuaweiUPS2000G-AConfigEntry 3 }

        hwHuaweiUPS2000G-AConfigRowStatus OBJECT-TYPE
            SYNTAX RowStatus
            MAX-ACCESS read-create
            STATUS current
            DESCRIPTION
                "RowStatus of config table UPS2000-A."
            ::= { hwHuaweiUPS2000G-AConfigEntry 100 }

        hwHuaweiUPS2000G-B OBJECT IDENTIFIER ::= { hwIDCUPS 2 }

        hwHuaweiUPS2000G-BRunningTable OBJECT-TYPE
            SYNTAX SEQUENCE OF HwHuaweiUPS2000G-BRunningEntry
            MAX-ACCESS not-accessible
             STATUS current
             DESCRIPTION
                "The Running table of UPS2000G-B."
            ::= { hwHuaweiUPS2000G-B 1 }

        hwHuaweiUPS2000G-BRunningEntry OBJECT-TYPE
                        SYNTAX HwHuaweiUPS2000G-BRunningEntry
            MAX-ACCESS not-accessible
             STATUS current
             DESCRIPTION
                "The Running table of UPS2000G-B."
            INDEX { hwHuaweiUPS2000G-BRunningIndex }
            ::= { hwHuaweiUPS2000G-BRunningTable 1 }

        HwHuaweiUPS2000G-BRunningEntry            ::= SEQUENCE {
                hwHuaweiUPS2000G-BRunningIndex
                    Unsigned32,
                hwHuaweiUPS2000G-BRunningName
                    OCTET STRING,
                hwHuaweiUPS2000G-BRunningCommStatus
                    INTEGER,
                hwHuaweiUPS2000G-BRunningSlotNo
                    Unsigned32,
                hwHuaweiUPS2000G-BRunningPortNo
                    Unsigned32,
                hwHuaweiUPS2000G-BRunningSoftwareVersion
                    OCTET STRING,
                hwHuaweiUPS2000G-BRunningModBusAddr
                    Unsigned32,
                hwHuaweiUPS2000G-BRunningESN
                    OCTET STRING,
                hwHuaweiUPS2000G-BRunningUPSModel
                    OCTET STRING,
                hwHuaweiUPS2000G-BRunningWorkingModel
                    INTEGER,
                hwHuaweiUPS2000G-BRunningInputVoltage
                    Unsigned32,
                hwHuaweiUPS2000G-BRunningInputFrequency
                    Unsigned32,
                hwHuaweiUPS2000G-BRunningOutputVoltage
                    Unsigned32,
                hwHuaweiUPS2000G-BRunningOutputFrequency
                    Unsigned32,
                hwHuaweiUPS2000G-BRunningOutputCurrent
                    Unsigned32,
                hwHuaweiUPS2000G-BRunningLoadRatio
                    Unsigned32,
                hwHuaweiUPS2000G-BRunningPositiveBusVoltage
                    Unsigned32,
                hwHuaweiUPS2000G-BRunningNegtiveBusVoltage
                    Unsigned32,
                hwHuaweiUPS2000G-BRunningPositveBatteryVoltage
                    Unsigned32,
                hwHuaweiUPS2000G-BRunningMaxDetectedTemperature
                    Unsigned32,
                hwHuaweiUPS2000G-BRunningBatteryVoltage
                    Unsigned32,
                hwHuaweiUPS2000G-BRunningBatteryNumber
                    Unsigned32,
                hwHuaweiUPS2000G-BRunningBatteryGroupNumber
                    Unsigned32,
                hwHuaweiUPS2000G-BRunningBatteryCapacity
                    Unsigned32,
                hwHuaweiUPS2000G-BRunningBatteryRemainTime
                    Unsigned32,
                hwHuaweiUPS2000G-BRunningBatteryStandardVoltagePerUnit
                    Unsigned32,
                hwHuaweiUPS2000G-BRunningInputPhase
                    Unsigned32,
                hwHuaweiUPS2000G-BRunningOutputPhase
                    Unsigned32,
                hwHuaweiUPS2000G-BRunningNominalInputVoltage
                    Unsigned32,
                hwHuaweiUPS2000G-BRunningOutputPowerFactor
                    Unsigned32,
                hwHuaweiUPS2000G-BRunningOutputRatedPower
                    Unsigned32,
                hwHuaweiUPS2000G-BRunningRatedBatteryVoltage
                    Unsigned32,
                hwHuaweiUPS2000G-BRunningRatedOutputCurrent
                    Unsigned32,
                hwHuaweiUPS2000G-BRunningRatedOutputFrequency
                    Unsigned32,
                hwHuaweiUPS2000G-BRunningRatedOutputVoltage
                    Unsigned32,
                hwHuaweiUPS2000G-BRunningRatedBatteryNumber
                    Unsigned32,
                hwHuaweiUPS2000G-BRunningRowStatus
                    RowStatus
            }

        hwHuaweiUPS2000G-BRunningIndex OBJECT-TYPE
            SYNTAX Unsigned32
            MAX-ACCESS read-only
            STATUS current
            DESCRIPTION
                "Index of the device config table for the UPS2000G-B."
            ::= { hwHuaweiUPS2000G-BRunningEntry 1 }

        hwHuaweiUPS2000G-BRunningName OBJECT-TYPE
            SYNTAX OCTET STRING (SIZE (0..50))
            MAX-ACCESS read-only
            STATUS current
            DESCRIPTION
                "the name of device."
            ::= { hwHuaweiUPS2000G-BRunningEntry 2 }

        hwHuaweiUPS2000G-BRunningCommStatus OBJECT-TYPE
            SYNTAX INTEGER
                {
                ok(1),
                fail(2),
                unknown(255)
                }
            MAX-ACCESS read-only
            STATUS current
            DESCRIPTION
                "Communication Status
                    Value 1 indicates noraml.
                    Value 2 indicates fail."
            ::= { hwHuaweiUPS2000G-BRunningEntry 3 }

        hwHuaweiUPS2000G-BRunningSlotNo OBJECT-TYPE
            SYNTAX Unsigned32 (0..6)
            MAX-ACCESS read-only
            STATUS current
            DESCRIPTION
                "the Slot of Device."
            ::= { hwHuaweiUPS2000G-BRunningEntry 4 }

        hwHuaweiUPS2000G-BRunningPortNo OBJECT-TYPE
            SYNTAX Unsigned32 (1..5)
            MAX-ACCESS read-only
            STATUS current
            DESCRIPTION
                "the Port No. of Device."
            ::= { hwHuaweiUPS2000G-BRunningEntry 5 }

        hwHuaweiUPS2000G-BRunningSoftwareVersion OBJECT-TYPE
            SYNTAX OCTET STRING (SIZE (0..32))
            MAX-ACCESS read-only
            STATUS current
            DESCRIPTION
                "Device software version number. A string of characters."
            ::= { hwHuaweiUPS2000G-BRunningEntry 6 }

        hwHuaweiUPS2000G-BRunningModBusAddr OBJECT-TYPE
            SYNTAX Unsigned32 (1..254)
            MAX-ACCESS read-only
            STATUS current
            DESCRIPTION
                "the modbus Address of the device."
            ::= { hwHuaweiUPS2000G-BRunningEntry 7 }

        hwHuaweiUPS2000G-BRunningESN OBJECT-TYPE
            SYNTAX OCTET STRING (SIZE (0..20))
            MAX-ACCESS read-only
            STATUS current
            DESCRIPTION
                "ESN of the master device used for setting up a NetEco model. A string of characters."
            ::= { hwHuaweiUPS2000G-BRunningEntry 8 }

        hwHuaweiUPS2000G-BRunningUPSModel OBJECT-TYPE
            SYNTAX OCTET STRING (SIZE (0..20))
            MAX-ACCESS read-only
            STATUS current
            DESCRIPTION
                "System capacity. A string of characters."
            ::= { hwHuaweiUPS2000G-BRunningEntry 9 }

        hwHuaweiUPS2000G-BRunningWorkingModel OBJECT-TYPE
            SYNTAX INTEGER
                {
                poweronmode(1),
                standbymode(2),
                bypassmode(3),
                linemode(4),
                batterymode(5),
                batterytestmode(6),
                faultmode(7),
                he_eco(8),
                convertermode(9),
                shutdownmode(10),
                unknown(255)
                }
            MAX-ACCESS read-only
            STATUS current
            DESCRIPTION
                "Device Running Status.
                   Value 1 indicates poweron.
                   Vaule 2 indicates standby.
                   Value 3 indicates bypass.
                   Vaule 4 indicates line.
                   Vaule 5 indicates battery.
                   Vaule 6 indicates batterytest.
                   Value 7 indicates fault.
                   Vaule 8 indicates he_eco.
                   Vaule 9 indicates converter.
                   Value 10 indicates shutdown."
            ::= { hwHuaweiUPS2000G-BRunningEntry 10 }

        hwHuaweiUPS2000G-BRunningInputVoltage OBJECT-TYPE
            SYNTAX Unsigned32 (0..1000)
            MAX-ACCESS read-only
            STATUS current
            DESCRIPTION
                "Input voltage. The value ranges from 0 to 1000. 
                    The value is accurate to one decimal place on the NetEco. The unit is V.Multiple: 10."
            ::= { hwHuaweiUPS2000G-BRunningEntry 11 }

        hwHuaweiUPS2000G-BRunningInputFrequency OBJECT-TYPE
            SYNTAX Unsigned32 (0..100)
            MAX-ACCESS read-only
            STATUS current
            DESCRIPTION
                "Input frequency. The value ranges from 0 to 100. 
                    The value is accurate to two decimal place on the NetEco. The unit is Hz.Multiple: 10."
            ::= { hwHuaweiUPS2000G-BRunningEntry 12 }

        hwHuaweiUPS2000G-BRunningOutputVoltage OBJECT-TYPE
            SYNTAX Unsigned32 (0..1000)
            MAX-ACCESS read-only
            STATUS current
            DESCRIPTION
                "Rack output voltage. The value ranges from 0 to 1000. 
                    The value is accurate to one decimal place on the NetEco. The unit is V.Multiple: 10."
            ::= { hwHuaweiUPS2000G-BRunningEntry 13 }

        hwHuaweiUPS2000G-BRunningOutputFrequency OBJECT-TYPE
            SYNTAX Unsigned32 (0..100)
            MAX-ACCESS read-only
            STATUS current
            DESCRIPTION
                "Rack output frequency. The value ranges from 0 to 100. 
                    The value is accurate to two decimal place on the NetEco. The unit is Hz.Multiple: 10."
            ::= { hwHuaweiUPS2000G-BRunningEntry 14 }

        hwHuaweiUPS2000G-BRunningOutputCurrent OBJECT-TYPE
            SYNTAX Unsigned32 (0..1000)
            MAX-ACCESS read-only
            STATUS current
            DESCRIPTION
                "Rack output current. The value ranges from 0 to 1000. 
                    The value is accurate to one decimal place on the NetEco. The unit is A.Multiple: 10."
            ::= { hwHuaweiUPS2000G-BRunningEntry 15 }

        hwHuaweiUPS2000G-BRunningLoadRatio OBJECT-TYPE
            SYNTAX Unsigned32 (0..100)
            MAX-ACCESS read-only
            STATUS current
            DESCRIPTION
                "Rack output load ratio. The value ranges from 0 to 500.
                 The value is accurate to one decimal place on the NetEco."
            ::= { hwHuaweiUPS2000G-BRunningEntry 16 }

        hwHuaweiUPS2000G-BRunningPositiveBusVoltage OBJECT-TYPE
            SYNTAX Unsigned32 (0..1000)
            MAX-ACCESS read-only
            STATUS current
            DESCRIPTION
                "Positive Bus Voltage. The unit is V.Multiple: 10."
            ::= { hwHuaweiUPS2000G-BRunningEntry 17 }

        hwHuaweiUPS2000G-BRunningNegtiveBusVoltage OBJECT-TYPE
            SYNTAX Unsigned32 (0..1000)
            MAX-ACCESS read-only
            STATUS current
            DESCRIPTION
                "Negtive Bus Voltage.The unit is V.Multiple: 10."
            ::= { hwHuaweiUPS2000G-BRunningEntry 18 }

        hwHuaweiUPS2000G-BRunningPositveBatteryVoltage OBJECT-TYPE
            SYNTAX Unsigned32 (0..1000)
            MAX-ACCESS read-only
            STATUS current
            DESCRIPTION
                "Positive Battery Voltage.The unit is V.Multiple: 10."
            ::= { hwHuaweiUPS2000G-BRunningEntry 19 }

        hwHuaweiUPS2000G-BRunningMaxDetectedTemperature OBJECT-TYPE
            SYNTAX Unsigned32 (0..1000)
            MAX-ACCESS read-only
            STATUS current
            DESCRIPTION
                "the max temperature of detected.The value of ranges from 0 to 1000.Multiple: 10."
            ::= { hwHuaweiUPS2000G-BRunningEntry 20 }

        hwHuaweiUPS2000G-BRunningBatteryVoltage OBJECT-TYPE
            SYNTAX Unsigned32 (0..1000)
            MAX-ACCESS read-only
            STATUS current
            DESCRIPTION
                "the voltage of battery.The value of ranges from 0 to 1000.The unit is V.Multiple: 10."
            ::= { hwHuaweiUPS2000G-BRunningEntry 21 }

        hwHuaweiUPS2000G-BRunningBatteryNumber OBJECT-TYPE
            SYNTAX Unsigned32 (0..100)
            MAX-ACCESS read-only
            STATUS current
            DESCRIPTION
                "the number of battery.The value of ranges from 0 to 100."
            ::= { hwHuaweiUPS2000G-BRunningEntry 22 }

        hwHuaweiUPS2000G-BRunningBatteryGroupNumber OBJECT-TYPE
            SYNTAX Unsigned32 (0..100)
            MAX-ACCESS read-only
            STATUS current
            DESCRIPTION
                "the number of battery group.The value of ranges from 0 to 100."
            ::= { hwHuaweiUPS2000G-BRunningEntry 23 }

        hwHuaweiUPS2000G-BRunningBatteryCapacity OBJECT-TYPE
            SYNTAX Unsigned32 (0..100)
            MAX-ACCESS read-only
            STATUS current
            DESCRIPTION
                "the capacity of battery.The value of ranges from 0 to 100."
            ::= { hwHuaweiUPS2000G-BRunningEntry 24 }

        hwHuaweiUPS2000G-BRunningBatteryRemainTime OBJECT-TYPE
            SYNTAX Unsigned32 (0..36000)
            MAX-ACCESS read-only
            STATUS current
            DESCRIPTION
                "the remain time of battery.The value of ranges from 0 to 36000. The unit is S."
            ::= { hwHuaweiUPS2000G-BRunningEntry 25 }

        hwHuaweiUPS2000G-BRunningBatteryStandardVoltagePerUnit OBJECT-TYPE
            SYNTAX Unsigned32 (0..1000)
            MAX-ACCESS read-only
            STATUS current
            DESCRIPTION
                "the standard voltage per battery unit. The value of ranges from 0 to 1000.The unit is V.Multiple: 10."
            ::= { hwHuaweiUPS2000G-BRunningEntry 26 }

        hwHuaweiUPS2000G-BRunningInputPhase OBJECT-TYPE
            SYNTAX Unsigned32 (0..5)
            MAX-ACCESS read-only
            STATUS current
            DESCRIPTION
                "Phase of input."
            ::= { hwHuaweiUPS2000G-BRunningEntry 27 }

        hwHuaweiUPS2000G-BRunningOutputPhase OBJECT-TYPE
            SYNTAX Unsigned32 (0..5)
            MAX-ACCESS read-only
            STATUS current
            DESCRIPTION
                "Phase of output."
            ::= { hwHuaweiUPS2000G-BRunningEntry 28 }

        hwHuaweiUPS2000G-BRunningNominalInputVoltage OBJECT-TYPE
            SYNTAX Unsigned32 (0..1000)
            MAX-ACCESS read-only
            STATUS current
            DESCRIPTION
                "Norminal input voltage. The value ranges from 0 to 10000. 
                    The value is accurate to one decimal place on the NetEco. The unit is V."
            ::= { hwHuaweiUPS2000G-BRunningEntry 29 }

        hwHuaweiUPS2000G-BRunningOutputPowerFactor OBJECT-TYPE
            SYNTAX Unsigned32 (0..100)
            MAX-ACCESS read-only
            STATUS current
            DESCRIPTION
                "output power factor.The value ranges from 0 to 100."
            ::= { hwHuaweiUPS2000G-BRunningEntry 30 }

        hwHuaweiUPS2000G-BRunningOutputRatedPower OBJECT-TYPE
            SYNTAX Unsigned32 (0..1000000)
            MAX-ACCESS read-only
            STATUS current
            DESCRIPTION
                "output rated power.The value ranges from 0 to 1000000."
            ::= { hwHuaweiUPS2000G-BRunningEntry 31 }

        hwHuaweiUPS2000G-BRunningRatedBatteryVoltage OBJECT-TYPE
            SYNTAX Unsigned32 (0..1000)
            MAX-ACCESS read-only
            STATUS current
            DESCRIPTION
                "Rated Battery voltage. The value ranges from 0 to 1000. 
                    The value is accurate to one decimal place on the NetEco. The unit is V.Multiple: 10."
            ::= { hwHuaweiUPS2000G-BRunningEntry 32 }

        hwHuaweiUPS2000G-BRunningRatedOutputCurrent OBJECT-TYPE
            SYNTAX Unsigned32 (0..1000)
            MAX-ACCESS read-only
            STATUS current
            DESCRIPTION
                "Rated Battery output current. The value ranges from 0 to 1000. 
                    The value is accurate to one decimal place on the NetEco. The unit is A.Multiple: 10."
            ::= { hwHuaweiUPS2000G-BRunningEntry 33 }

        hwHuaweiUPS2000G-BRunningRatedOutputFrequency OBJECT-TYPE
            SYNTAX Unsigned32 (0..100)
            MAX-ACCESS read-only
            STATUS current
            DESCRIPTION
                "Rated output frequency. The value ranges from 0 to 100. 
                    The value is accurate to one decimal place on the NetEco. The unit is Hz.Multiple: 10."
            ::= { hwHuaweiUPS2000G-BRunningEntry 34 }

        hwHuaweiUPS2000G-BRunningRatedOutputVoltage OBJECT-TYPE
            SYNTAX Unsigned32 (0..1000)
            MAX-ACCESS read-only
            STATUS current
            DESCRIPTION
                "Rated output voltage. The value ranges from 0 to 1000. 
                    The value is accurate to one decimal place on the NetEco. The unit is V.Multiple: 10."
            ::= { hwHuaweiUPS2000G-BRunningEntry 35 }

        hwHuaweiUPS2000G-BRunningRatedBatteryNumber OBJECT-TYPE
            SYNTAX Unsigned32 (0..10)
            MAX-ACCESS read-only
            STATUS current
            DESCRIPTION
                "Battery number.Value range: 1 to 10,and the value is an integer."
            ::= { hwHuaweiUPS2000G-BRunningEntry 36 }

        hwHuaweiUPS2000G-BRunningRowStatus OBJECT-TYPE
            SYNTAX RowStatus
            MAX-ACCESS read-create
            STATUS current
            DESCRIPTION
                "The rowstatus of UPS2000G-B."
            ::= { hwHuaweiUPS2000G-BRunningEntry 100 }

        hwHuaweiUPS5000E OBJECT IDENTIFIER ::= { hwIDCUPS 3 }

        hwHuaweiUPS5000ERunningTable OBJECT-TYPE
            SYNTAX SEQUENCE OF HwHuaweiUPS5000ERunningEntry
            MAX-ACCESS not-accessible
             STATUS current
             DESCRIPTION
                "The Running table of UPS5000E."
            ::= { hwHuaweiUPS5000E 1 }

        hwHuaweiUPS5000ERunningEntry OBJECT-TYPE
                        SYNTAX HwHuaweiUPS5000ERunningEntry
            MAX-ACCESS not-accessible
             STATUS current
             DESCRIPTION
                "The Running table of UPS5000E."
            INDEX { hwHuaweiUPS5000ERunningIndex }
            ::= { hwHuaweiUPS5000ERunningTable 1 }

        HwHuaweiUPS5000ERunningEntry            ::= SEQUENCE {
                hwHuaweiUPS5000ERunningIndex
                    Unsigned32,
                hwHuaweiUPS5000ERunningName
                    OCTET STRING,
                hwUPS5000ECommunicationStatus
                    INTEGER,
                hwUPS5000ESlot
                    Unsigned32,
                hwUPS5000EPort
                    Unsigned32,
                hwUPS5000EModbusAddress
                    Unsigned32,
                hwUPS5000ESoftwareVersion
                    OCTET STRING,
                hwUPS5000EESN
                    OCTET STRING,
                hwUPS5000EUPSModel
                    Unsigned32,
                hwUPS5000EPowerMode
                    INTEGER,
                hwUPS5000ERunningStatus
                    INTEGER,
                hwUPS5000EBatteryStatus
                    INTEGER,
                hwUPS5000EAInputVoltage
                    Integer32,
                hwUPS5000EBInputVoltage
                    Integer32,
                hwUPS5000ECInputVoltage
                    Integer32,
                hwUPS5000EABInputLineVoltage
                    Integer32,
                hwUPS5000EBCInputLineVoltage
                    Integer32,
                hwUPS5000ECAInputLineVoltage
                    Integer32,
                hwUPS5000EAInputCurrent
                    Integer32,
                hwUPS5000EBInputCurrent
                    Integer32,
                hwUPS5000ECInputCurrent
                    Integer32,
                hwUPS5000EInputFrequency
                    Integer32,
                hwUPS5000EAInputPowFactor
                    Integer32,
                hwUPS5000EBInputPowFactor
                    Integer32,
                hwUPS5000ECInputPowFactor
                    Integer32,
                hwUPS5000EPosDCBusVol
                    Integer32,
                hwUPS5000ENegDCBusVol
                    Integer32,
                hwUPS5000EBypAInputVoltage
                    Integer32,
                hwUPS5000EBypBInputVoltage
                    Integer32,
                hwUPS5000EBypCInputVoltage
                    Integer32,
                hwUPS5000EBypABLineVoltage
                    Integer32,
                hwUPS5000EBypBCLineVoltage
                    Integer32,
                hwUPS5000EBypCALineVoltage
                    Integer32,
                hwUPS5000EBypInputFrequency
                    Integer32,
                hwUPS5000EEnvironTemperature
                    Integer32,
                hwUPS5000EEnvironHumidity
                    Integer32,
                hwUPS5000ERackOutputAVol
                    Integer32,
                hwUPS5000ERackOutputBVol
                    Integer32,
                hwUPS5000ERackOutputCVol
                    Integer32,
                hwUPS5000ERackABOutLineVol
                    Integer32,
                hwUPS5000ERackBCOutLineVol
                    Integer32,
                hwUPS5000ERackCAOutLineVol
                    Integer32,
                hwUPS5000ERackAOutCurrent
                    Integer32,
                hwUPS5000ERackBOutCurrent
                    Integer32,
                hwUPS5000ERackCOutCurrent
                    Integer32,
                hwUPS5000ERackOutputFreq
                    Integer32,
                hwUPS5000ERackAOutActivePow
                    Integer32,
                hwUPS5000ERackBOutActivePow
                    Integer32,
                hwUPS5000ERackCOutActivePow
                    Integer32,
                hwUPS5000ERackAOutAppearPow
                    Integer32,
                hwUPS5000ERackBOutAppearPow
                    Integer32,
                hwUPS5000ERackCOutAppearPow
                    Integer32,
                hwUPS5000ERackAOutReactivePow
                    Integer32,
                hwUPS5000ERackBOutReactivePow
                    Integer32,
                hwUPS5000ERackCOutReactivePow
                    Integer32,
                hwUPS5000ERackAOutPowerFactor
                    Integer32,
                hwUPS5000ERackBOutPowerFactor
                    Integer32,
                hwUPS5000ERackCOutPowerFactor
                    Integer32,
                hwUPS5000ERackAOutputLoadRatio
                    Integer32,
                hwUPS5000ERackBOutputLoadRatio
                    Integer32,
                hwUPS5000ERackCOutputLoadRatio
                    Integer32,
                hwUPS5000ERackphAoutputCrestratio
                    Integer32,
                hwUPS5000ERackphBoutputCrestratio
                    Integer32,
                hwUPS5000ERackphCoutputCrestratio
                    Integer32,
                hwUPS5000ESysAOutActivePow
                    Integer32,
                hwUPS5000ESysBOutActivePow
                    Integer32,
                hwUPS5000ESysCOutActivePow
                    Integer32,
                hwUPS5000ESysAOutAppearPow
                    Integer32,
                hwUPS5000ESysBOutAppearPow
                    Integer32,
                hwUPS5000ESysCOutAppearPow
                    Integer32,
                hwUPS5000ESysAOutReactivePow
                    Integer32,
                hwUPS5000ESysBOutReactivePow
                    Integer32,
                hwUPS5000ESysCOutReactivePow
                    Integer32,
                hwUPS5000EPosbatteryvoltage
                    Integer32,
                hwUPS5000ENegbatteryvoltage
                    Integer32,
                hwUPS5000EPosbatterycurrent
                    Integer32,
                hwUPS5000ENegbatterycurrent
                    Integer32,
                hwUPS5000EBatteryTemperature
                    Integer32,
                hwUPS5000EBackupTime
                    Unsigned32,
                hwUPS5000EBatteryremainingcapacity
                    Unsigned32,
                hwUPS5000ERowStatus
                    RowStatus
            }

        hwHuaweiUPS5000ERunningIndex OBJECT-TYPE
            SYNTAX Unsigned32
            MAX-ACCESS read-only
            STATUS current
            DESCRIPTION
                "Index of the device config table for the UPS5000E."
            ::= { hwHuaweiUPS5000ERunningEntry 1 }

        hwHuaweiUPS5000ERunningName OBJECT-TYPE
            SYNTAX OCTET STRING (SIZE (0..50))
            MAX-ACCESS read-only
            STATUS current
            DESCRIPTION
                "the name of device."
            ::= { hwHuaweiUPS5000ERunningEntry 2 }

        hwUPS5000ECommunicationStatus OBJECT-TYPE
            SYNTAX INTEGER
                {
                ok(1),
                fail(2),
                unknown(255)
                }
            MAX-ACCESS read-only
            STATUS current
            DESCRIPTION
                "Communication Status
                    Value 1 indicates noraml.
                    Value 2 indicates fail."
            ::= { hwHuaweiUPS5000ERunningEntry 3 }

        hwUPS5000ESlot OBJECT-TYPE
            SYNTAX Unsigned32 (0..6)
            MAX-ACCESS read-only
            STATUS current
            DESCRIPTION
                "The Slot of Device."
            ::= { hwHuaweiUPS5000ERunningEntry 4 }

        hwUPS5000EPort OBJECT-TYPE
            SYNTAX Unsigned32 (1..5)
            MAX-ACCESS read-only
            STATUS current
            DESCRIPTION
                "The Port No. of Device."
            ::= { hwHuaweiUPS5000ERunningEntry 5 }

        hwUPS5000EModbusAddress OBJECT-TYPE
            SYNTAX Unsigned32 (0..247)
            MAX-ACCESS read-only
            STATUS current
            DESCRIPTION
                "The modbus Address of the device."
            ::= { hwHuaweiUPS5000ERunningEntry 6 }

        hwUPS5000ESoftwareVersion OBJECT-TYPE
            SYNTAX OCTET STRING (SIZE (0..32))
            MAX-ACCESS read-only
            STATUS current
            DESCRIPTION
                "Software Version.A string of characters."
            ::= { hwHuaweiUPS5000ERunningEntry 7 }

        hwUPS5000EESN OBJECT-TYPE
            SYNTAX OCTET STRING (SIZE (0..32))
            MAX-ACCESS read-only
            STATUS current
            DESCRIPTION
                "ESN. A string of characters."
            ::= { hwHuaweiUPS5000ERunningEntry 8 }

        hwUPS5000EUPSModel OBJECT-TYPE
            SYNTAX Unsigned32 (0..5000)
            MAX-ACCESS read-only
            STATUS current
            DESCRIPTION
                "UPS Model, Units : kW. Multi: 1."
            ::= { hwHuaweiUPS5000ERunningEntry 9 }

        hwUPS5000EPowerMode OBJECT-TYPE
            SYNTAX INTEGER
                {
                NoPowerSupplied(1),
                BypassMode(2),
                NormalMode(3),
                BatteryMode(4),
                Source-shareMode(5),
                unknown(255)
                }
            MAX-ACCESS read-only
            STATUS current
            DESCRIPTION
                "Power Mode.
                  Value 1 indicates No power supplied.
                  Value 2 indicates Bypass mode.
                  Value 3 indicates Normal mode.
                  Value 4 indicates Battery mode.
                  Value 5 indicates Source-share mode."
            ::= { hwHuaweiUPS5000ERunningEntry 10 }

        hwUPS5000ERunningStatus OBJECT-TYPE
            SYNTAX INTEGER
                {
                Single(1),
                Parallel(2),
                SingleECO(3),
                ParallelECO(4),
                Self-load(5),
                ConverterMode(6),
                unknown(255)
                }
            MAX-ACCESS read-only
            STATUS current
            DESCRIPTION
                "Running Status.
                 Value 1 indicates Single.
                 Value 2 indicates Parallel.
                 Value 3 indicates Single ECO.
                 Value 4 indicates Parallel ECO.
                 Value 5 indicates Self-load.
                 Value 6 indicates Converter mode."
            ::= { hwHuaweiUPS5000ERunningEntry 11 }

        hwUPS5000EBatteryStatus OBJECT-TYPE
            SYNTAX INTEGER
                {
                NotConnected(1),
                Connected(2),
                Hibernation(3),
                FloatCharging(4),
                EqualizedCharging(5),
                Discharging(6),
                unknown(255)
                }
            MAX-ACCESS read-only
            STATUS current
            DESCRIPTION
                "Battery Status.
                 Value 1 indicates Not connected
                 Value 2 indicates Connected
                 Value 3 indicates Hibernation
                 Value 4 indicates Float Charging
                 Value 5 indicates Equalized Charging
                 Value 6 indicates Discharging"
            ::= { hwHuaweiUPS5000ERunningEntry 12 }

        hwUPS5000EAInputVoltage OBJECT-TYPE
            SYNTAX Integer32 (0..1000)
            MAX-ACCESS read-only
            STATUS current
            DESCRIPTION
                "A Input Voltage, Units : V. Multi: 10."
            ::= { hwHuaweiUPS5000ERunningEntry 13 }

        hwUPS5000EBInputVoltage OBJECT-TYPE
            SYNTAX Integer32 (0..1000)
            MAX-ACCESS read-only
            STATUS current
            DESCRIPTION
                "B Input Voltage, Units : V. Multi: 10."
            ::= { hwHuaweiUPS5000ERunningEntry 14 }

        hwUPS5000ECInputVoltage OBJECT-TYPE
            SYNTAX Integer32 (0..1000)
            MAX-ACCESS read-only
            STATUS current
            DESCRIPTION
                "C Input Voltage, Units : V. Multi: 10."
            ::= { hwHuaweiUPS5000ERunningEntry 15 }

        hwUPS5000EABInputLineVoltage OBJECT-TYPE
            SYNTAX Integer32 (0..2000)
            MAX-ACCESS read-only
            STATUS current
            DESCRIPTION
                "AB Input Line Voltage, Units : V. Multi: 10."
            ::= { hwHuaweiUPS5000ERunningEntry 16 }

        hwUPS5000EBCInputLineVoltage OBJECT-TYPE
            SYNTAX Integer32 (0..2000)
            MAX-ACCESS read-only
            STATUS current
            DESCRIPTION
                "BC Input Line Voltage, Units : V. Multi: 10."
            ::= { hwHuaweiUPS5000ERunningEntry 17 }

        hwUPS5000ECAInputLineVoltage OBJECT-TYPE
            SYNTAX Integer32 (0..2000)
            MAX-ACCESS read-only
            STATUS current
            DESCRIPTION
                "CA Input Line Voltage, Units : V. Multi: 10."
            ::= { hwHuaweiUPS5000ERunningEntry 18 }

        hwUPS5000EAInputCurrent OBJECT-TYPE
            SYNTAX Integer32 (0..6000)
            MAX-ACCESS read-only
            STATUS current
            DESCRIPTION
                "A Input Current, Units : A. Multi: 10."
            ::= { hwHuaweiUPS5000ERunningEntry 19 }

        hwUPS5000EBInputCurrent OBJECT-TYPE
            SYNTAX Integer32 (0..6000)
            MAX-ACCESS read-only
            STATUS current
            DESCRIPTION
                "B Input Current, Units : A. Multi: 10."
            ::= { hwHuaweiUPS5000ERunningEntry 20 }

        hwUPS5000ECInputCurrent OBJECT-TYPE
            SYNTAX Integer32 (0..6000)
            MAX-ACCESS read-only
            STATUS current
            DESCRIPTION
                "C Input Current, Units : A. Multi: 10."
            ::= { hwHuaweiUPS5000ERunningEntry 21 }

        hwUPS5000EInputFrequency OBJECT-TYPE
            SYNTAX Integer32 (0..100)
            MAX-ACCESS read-only
            STATUS current
            DESCRIPTION
                "Input Frequency, Units : Hz. Multi: 100."
            ::= { hwHuaweiUPS5000ERunningEntry 22 }

        hwUPS5000EAInputPowFactor OBJECT-TYPE
            SYNTAX Integer32 (-1..1)
            MAX-ACCESS read-only
            STATUS current
            DESCRIPTION
                "A Input Pow Factor, Multi: 100."
            ::= { hwHuaweiUPS5000ERunningEntry 23 }

        hwUPS5000EBInputPowFactor OBJECT-TYPE
            SYNTAX Integer32 (-1..1)
            MAX-ACCESS read-only
            STATUS current
            DESCRIPTION
                "B Input Pow Factor, Multi: 100."
            ::= { hwHuaweiUPS5000ERunningEntry 24 }

        hwUPS5000ECInputPowFactor OBJECT-TYPE
            SYNTAX Integer32 (-1..1)
            MAX-ACCESS read-only
            STATUS current
            DESCRIPTION
                "C Input Pow Factor, Multi: 100."
            ::= { hwHuaweiUPS5000ERunningEntry 25 }

        hwUPS5000EPosDCBusVol OBJECT-TYPE
            SYNTAX Integer32 (0..1000)
            MAX-ACCESS read-only
            STATUS current
            DESCRIPTION
                "Pos DCBus Vol, Units : V. Multi: 10."
            ::= { hwHuaweiUPS5000ERunningEntry 26 }

        hwUPS5000ENegDCBusVol OBJECT-TYPE
            SYNTAX Integer32 (0..1000)
            MAX-ACCESS read-only
            STATUS current
            DESCRIPTION
                "Neg DCBus Vol, Units : V. Multi: 10."
            ::= { hwHuaweiUPS5000ERunningEntry 27 }

        hwUPS5000EBypAInputVoltage OBJECT-TYPE
            SYNTAX Integer32 (0..1000)
            MAX-ACCESS read-only
            STATUS current
            DESCRIPTION
                "Byp A Input Voltage, Units : V. Multi: 10."
            ::= { hwHuaweiUPS5000ERunningEntry 28 }

        hwUPS5000EBypBInputVoltage OBJECT-TYPE
            SYNTAX Integer32 (0..1000)
            MAX-ACCESS read-only
            STATUS current
            DESCRIPTION
                "Byp B Input Voltage, Units : V. Multi: 10."
            ::= { hwHuaweiUPS5000ERunningEntry 29 }

        hwUPS5000EBypCInputVoltage OBJECT-TYPE
            SYNTAX Integer32 (0..1000)
            MAX-ACCESS read-only
            STATUS current
            DESCRIPTION
                "Byp C Input Voltage, Units : V. Multi: 10."
            ::= { hwHuaweiUPS5000ERunningEntry 30 }

        hwUPS5000EBypABLineVoltage OBJECT-TYPE
            SYNTAX Integer32 (0..2000)
            MAX-ACCESS read-only
            STATUS current
            DESCRIPTION
                "Byp AB  Line Voltage, Units : V. Multi: 10."
            ::= { hwHuaweiUPS5000ERunningEntry 31 }

        hwUPS5000EBypBCLineVoltage OBJECT-TYPE
            SYNTAX Integer32 (0..2000)
            MAX-ACCESS read-only
            STATUS current
            DESCRIPTION
                "Byp BC  Line Voltage, Units : V. Multi: 10."
            ::= { hwHuaweiUPS5000ERunningEntry 32 }

        hwUPS5000EBypCALineVoltage OBJECT-TYPE
            SYNTAX Integer32 (0..2000)
            MAX-ACCESS read-only
            STATUS current
            DESCRIPTION
                "Byp CA  Line Voltage, Units : V. Multi: 10."
            ::= { hwHuaweiUPS5000ERunningEntry 33 }

        hwUPS5000EBypInputFrequency OBJECT-TYPE
            SYNTAX Integer32 (0..100)
            MAX-ACCESS read-only
            STATUS current
            DESCRIPTION
                "Byp Input Frequency, Units : Hz. Multi: 100."
            ::= { hwHuaweiUPS5000ERunningEntry 34 }

        hwUPS5000EEnvironTemperature OBJECT-TYPE
            SYNTAX Integer32 (-50..120)
            MAX-ACCESS read-only
            STATUS current
            DESCRIPTION
                "Environ Temperature, Units : degC. Multi: 10."
            ::= { hwHuaweiUPS5000ERunningEntry 35 }

        hwUPS5000EEnvironHumidity OBJECT-TYPE
            SYNTAX Integer32 (0..100)
            MAX-ACCESS read-only
            STATUS current
            DESCRIPTION
                "Environ Humidity, Units : %. Multi: 10."
            ::= { hwHuaweiUPS5000ERunningEntry 36 }

        hwUPS5000ERackOutputAVol OBJECT-TYPE
            SYNTAX Integer32 (0..1000)
            MAX-ACCESS read-only
            STATUS current
            DESCRIPTION
                "Rack Output A Vol, Units : V. Multi: 10."
            ::= { hwHuaweiUPS5000ERunningEntry 37 }

        hwUPS5000ERackOutputBVol OBJECT-TYPE
            SYNTAX Integer32 (0..1000)
            MAX-ACCESS read-only
            STATUS current
            DESCRIPTION
                "Rack Output B Vol, Units : V. Multi: 10."
            ::= { hwHuaweiUPS5000ERunningEntry 38 }

        hwUPS5000ERackOutputCVol OBJECT-TYPE
            SYNTAX Integer32 (0..1000)
            MAX-ACCESS read-only
            STATUS current
            DESCRIPTION
                "Rack Output C Vol, Units : V. Multi: 10."
            ::= { hwHuaweiUPS5000ERunningEntry 39 }

        hwUPS5000ERackABOutLineVol OBJECT-TYPE
            SYNTAX Integer32 (0..2000)
            MAX-ACCESS read-only
            STATUS current
            DESCRIPTION
                "Rack AB Out Line Vol, Units : V. Multi: 10."
            ::= { hwHuaweiUPS5000ERunningEntry 40 }

        hwUPS5000ERackBCOutLineVol OBJECT-TYPE
            SYNTAX Integer32 (0..2000)
            MAX-ACCESS read-only
            STATUS current
            DESCRIPTION
                "Rack BC Out Line Vol, Units : V. Multi: 10."
            ::= { hwHuaweiUPS5000ERunningEntry 41 }

        hwUPS5000ERackCAOutLineVol OBJECT-TYPE
            SYNTAX Integer32 (0..2000)
            MAX-ACCESS read-only
            STATUS current
            DESCRIPTION
                "Rack CA Out Line Vol, Units : V. Multi: 10."
            ::= { hwHuaweiUPS5000ERunningEntry 42 }

        hwUPS5000ERackAOutCurrent OBJECT-TYPE
            SYNTAX Integer32 (0..6000)
            MAX-ACCESS read-only
            STATUS current
            DESCRIPTION
                "Rack A Out Current , Units : A. Multi: 10."
            ::= { hwHuaweiUPS5000ERunningEntry 43 }

        hwUPS5000ERackBOutCurrent OBJECT-TYPE
            SYNTAX Integer32 (0..6000)
            MAX-ACCESS read-only
            STATUS current
            DESCRIPTION
                "Rack B Out Current , Units : A. Multi: 10."
            ::= { hwHuaweiUPS5000ERunningEntry 44 }

        hwUPS5000ERackCOutCurrent OBJECT-TYPE
            SYNTAX Integer32 (0..6000)
            MAX-ACCESS read-only
            STATUS current
            DESCRIPTION
                "Rack C Out Current , Units : A. Multi: 10."
            ::= { hwHuaweiUPS5000ERunningEntry 45 }

        hwUPS5000ERackOutputFreq OBJECT-TYPE
            SYNTAX Integer32 (0..100)
            MAX-ACCESS read-only
            STATUS current
            DESCRIPTION
                "Rack Output Freq, Units : Hz. Multi: 100."
            ::= { hwHuaweiUPS5000ERunningEntry 46 }

        hwUPS5000ERackAOutActivePow OBJECT-TYPE
            SYNTAX Integer32 (-1200..1200)
            MAX-ACCESS read-only
            STATUS current
            DESCRIPTION
                "Rack A Out Active Pow, Units : kW. Multi: 10."
            ::= { hwHuaweiUPS5000ERunningEntry 47 }

        hwUPS5000ERackBOutActivePow OBJECT-TYPE
            SYNTAX Integer32 (-1200..1200)
            MAX-ACCESS read-only
            STATUS current
            DESCRIPTION
                "Rack B Out Active Pow, Units : kW. Multi: 10."
            ::= { hwHuaweiUPS5000ERunningEntry 48 }

        hwUPS5000ERackCOutActivePow OBJECT-TYPE
            SYNTAX Integer32 (-1200..1200)
            MAX-ACCESS read-only
            STATUS current
            DESCRIPTION
                "Rack C Out Active Pow, Units : kW. Multi: 10."
            ::= { hwHuaweiUPS5000ERunningEntry 49 }

        hwUPS5000ERackAOutAppearPow OBJECT-TYPE
            SYNTAX Integer32 (-1200..1200)
            MAX-ACCESS read-only
            STATUS current
            DESCRIPTION
                "Rack A Out Appear Pow, Units : kVA. Multi: 10."
            ::= { hwHuaweiUPS5000ERunningEntry 50 }

        hwUPS5000ERackBOutAppearPow OBJECT-TYPE
            SYNTAX Integer32 (-1200..1200)
            MAX-ACCESS read-only
            STATUS current
            DESCRIPTION
                "Rack B Out Appear Pow, Units : kVA. Multi: 10."
            ::= { hwHuaweiUPS5000ERunningEntry 51 }

        hwUPS5000ERackCOutAppearPow OBJECT-TYPE
            SYNTAX Integer32 (-1200..1200)
            MAX-ACCESS read-only
            STATUS current
            DESCRIPTION
                "Rack C Out Appear Pow, Units : kVA. Multi: 10."
            ::= { hwHuaweiUPS5000ERunningEntry 52 }

        hwUPS5000ERackAOutReactivePow OBJECT-TYPE
            SYNTAX Integer32 (-1200..1200)
            MAX-ACCESS read-only
            STATUS current
            DESCRIPTION
                "Rack A Out Reactive Pow, Units : kVAR. Multi: 10."
            ::= { hwHuaweiUPS5000ERunningEntry 53 }

        hwUPS5000ERackBOutReactivePow OBJECT-TYPE
            SYNTAX Integer32 (-1200..1200)
            MAX-ACCESS read-only
            STATUS current
            DESCRIPTION
                "Rack B Out Reactive Pow, Units : kVAR. Multi: 10."
            ::= { hwHuaweiUPS5000ERunningEntry 54 }

        hwUPS5000ERackCOutReactivePow OBJECT-TYPE
            SYNTAX Integer32 (-1200..1200)
            MAX-ACCESS read-only
            STATUS current
            DESCRIPTION
                "Rack C Out Reactive Pow, Units : kVAR. Multi: 10."
            ::= { hwHuaweiUPS5000ERunningEntry 55 }

        hwUPS5000ERackAOutPowerFactor OBJECT-TYPE
            SYNTAX Integer32 (-1..1)
            MAX-ACCESS read-only
            STATUS current
            DESCRIPTION
                "Rack A Out Power Factor. Multi: 100."
            ::= { hwHuaweiUPS5000ERunningEntry 56 }

        hwUPS5000ERackBOutPowerFactor OBJECT-TYPE
            SYNTAX Integer32 (-1..1)
            MAX-ACCESS read-only
            STATUS current
            DESCRIPTION
                "Rack B Out Power Factor. Multi: 100."
            ::= { hwHuaweiUPS5000ERunningEntry 57 }

        hwUPS5000ERackCOutPowerFactor OBJECT-TYPE
            SYNTAX Integer32 (-1..1)
            MAX-ACCESS read-only
            STATUS current
            DESCRIPTION
                "Rack C Out Power Factor. Multi: 100."
            ::= { hwHuaweiUPS5000ERunningEntry 58 }

        hwUPS5000ERackAOutputLoadRatio OBJECT-TYPE
            SYNTAX Integer32 (0..500)
            MAX-ACCESS read-only
            STATUS current
            DESCRIPTION
                "Rack A Output Load Ratio, Units : %. Multi: 10."
            ::= { hwHuaweiUPS5000ERunningEntry 59 }

        hwUPS5000ERackBOutputLoadRatio OBJECT-TYPE
            SYNTAX Integer32 (0..500)
            MAX-ACCESS read-only
            STATUS current
            DESCRIPTION
                "Rack B Output Load Ratio, Units : %. Multi: 10."
            ::= { hwHuaweiUPS5000ERunningEntry 60 }

        hwUPS5000ERackCOutputLoadRatio OBJECT-TYPE
            SYNTAX Integer32 (0..500)
            MAX-ACCESS read-only
            STATUS current
            DESCRIPTION
                "Rack C Output Load Ratio, Units : %. Multi: 10."
            ::= { hwHuaweiUPS5000ERunningEntry 61 }

        hwUPS5000ERackphAoutputCrestratio OBJECT-TYPE
            SYNTAX Integer32 (0..100)
            MAX-ACCESS read-only
            STATUS current
            DESCRIPTION
                "Rack ph. A output Crest ratio, Multi: 10."
            ::= { hwHuaweiUPS5000ERunningEntry 62 }

        hwUPS5000ERackphBoutputCrestratio OBJECT-TYPE
            SYNTAX Integer32 (0..100)
            MAX-ACCESS read-only
            STATUS current
            DESCRIPTION
                "Rack ph. B output Crest ratio, Multi: 10."
            ::= { hwHuaweiUPS5000ERunningEntry 63 }

        hwUPS5000ERackphCoutputCrestratio OBJECT-TYPE
            SYNTAX Integer32 (0..100)
            MAX-ACCESS read-only
            STATUS current
            DESCRIPTION
                "Rack ph. C output Crest ratio, Multi: 10."
            ::= { hwHuaweiUPS5000ERunningEntry 64 }

        hwUPS5000ESysAOutActivePow OBJECT-TYPE
            SYNTAX Integer32 (-12000..12000)
            MAX-ACCESS read-only
            STATUS current
            DESCRIPTION
                "Sys A Out Active Pow, Units : kW. Multi: 10."
            ::= { hwHuaweiUPS5000ERunningEntry 65 }

        hwUPS5000ESysBOutActivePow OBJECT-TYPE
            SYNTAX Integer32 (-12000..12000)
            MAX-ACCESS read-only
            STATUS current
            DESCRIPTION
                "Sys B Out Active Pow, Units : kW. Multi: 10."
            ::= { hwHuaweiUPS5000ERunningEntry 66 }

        hwUPS5000ESysCOutActivePow OBJECT-TYPE
            SYNTAX Integer32 (-12000..12000)
            MAX-ACCESS read-only
            STATUS current
            DESCRIPTION
                "Sys C Out Active Pow, Units : kW. Multi: 10."
            ::= { hwHuaweiUPS5000ERunningEntry 67 }

        hwUPS5000ESysAOutAppearPow OBJECT-TYPE
            SYNTAX Integer32 (-12000..12000)
            MAX-ACCESS read-only
            STATUS current
            DESCRIPTION
                "Sys A Out Appear Pow, Units : kVA. Multi: 10."
            ::= { hwHuaweiUPS5000ERunningEntry 68 }

        hwUPS5000ESysBOutAppearPow OBJECT-TYPE
            SYNTAX Integer32 (-12000..12000)
            MAX-ACCESS read-only
            STATUS current
            DESCRIPTION
                "Sys B Out Appear Pow, Units : kVA. Multi: 10."
            ::= { hwHuaweiUPS5000ERunningEntry 69 }

        hwUPS5000ESysCOutAppearPow OBJECT-TYPE
            SYNTAX Integer32 (-12000..12000)
            MAX-ACCESS read-only
            STATUS current
            DESCRIPTION
                "Sys C Out Appear Pow, Units : kVA. Multi: 10."
            ::= { hwHuaweiUPS5000ERunningEntry 70 }

        hwUPS5000ESysAOutReactivePow OBJECT-TYPE
            SYNTAX Integer32 (-12000..12000)
            MAX-ACCESS read-only
            STATUS current
            DESCRIPTION
                "Sys A Out Reactive Pow, Units : kVAR. Multi: 10."
            ::= { hwHuaweiUPS5000ERunningEntry 71 }

        hwUPS5000ESysBOutReactivePow OBJECT-TYPE
            SYNTAX Integer32 (-12000..12000)
            MAX-ACCESS read-only
            STATUS current
            DESCRIPTION
                "Sys B Out Reactive Pow, Units : kVAR. Multi: 10."
            ::= { hwHuaweiUPS5000ERunningEntry 72 }

        hwUPS5000ESysCOutReactivePow OBJECT-TYPE
            SYNTAX Integer32 (-12000..12000)
            MAX-ACCESS read-only
            STATUS current
            DESCRIPTION
                "Sys C Out Reactive Pow, Units : kVAR. Multi: 10."
            ::= { hwHuaweiUPS5000ERunningEntry 73 }

        hwUPS5000EPosbatteryvoltage OBJECT-TYPE
            SYNTAX Integer32 (0..1000)
            MAX-ACCESS read-only
            STATUS current
            DESCRIPTION
                "Pos. battery voltage, Units : V. Multi: 10."
            ::= { hwHuaweiUPS5000ERunningEntry 74 }

        hwUPS5000ENegbatteryvoltage OBJECT-TYPE
            SYNTAX Integer32 (0..1000)
            MAX-ACCESS read-only
            STATUS current
            DESCRIPTION
                "Neg. battery voltage, Units : V. Multi: 10."
            ::= { hwHuaweiUPS5000ERunningEntry 75 }

        hwUPS5000EPosbatterycurrent OBJECT-TYPE
            SYNTAX Integer32 (-60000..60000)
            MAX-ACCESS read-only
            STATUS current
            DESCRIPTION
                "Pos. battery current, Units : A. Multi: 10."
            ::= { hwHuaweiUPS5000ERunningEntry 76 }

        hwUPS5000ENegbatterycurrent OBJECT-TYPE
            SYNTAX Integer32 (-60000..60000)
            MAX-ACCESS read-only
            STATUS current
            DESCRIPTION
                "Neg. battery current, Units : A. Multi: 10."
            ::= { hwHuaweiUPS5000ERunningEntry 77 }

        hwUPS5000EBatteryTemperature OBJECT-TYPE
            SYNTAX Integer32 (-20..80)
            MAX-ACCESS read-only
            STATUS current
            DESCRIPTION
                "Battery Temperature, Units : degC. Multi: 10."
            ::= { hwHuaweiUPS5000ERunningEntry 78 }

        hwUPS5000EBackupTime OBJECT-TYPE
            SYNTAX Unsigned32 (0..65534)
            MAX-ACCESS read-only
            STATUS current
            DESCRIPTION
                "Backup Time, Units : s. Multi: 1."
            ::= { hwHuaweiUPS5000ERunningEntry 79 }

        hwUPS5000EBatteryremainingcapacity OBJECT-TYPE
            SYNTAX Unsigned32 (0..100)
            MAX-ACCESS read-only
            STATUS current
            DESCRIPTION
                "Battery  remaining capacity, Units : %. Multi: 1."
            ::= { hwHuaweiUPS5000ERunningEntry 80 }

        hwUPS5000ERowStatus OBJECT-TYPE
            SYNTAX RowStatus
            MAX-ACCESS read-create
            STATUS current
            DESCRIPTION
                "The row status of Deviece."
            ::= { hwHuaweiUPS5000ERunningEntry 100 }

        hwIDCFans OBJECT IDENTIFIER ::= { hwIDCMonitorMIBObjects 6 }

        hwFB3000W OBJECT IDENTIFIER ::= { hwIDCFans 1 }

        hwFB3000WRunningTable OBJECT-TYPE
            SYNTAX SEQUENCE OF HwFB3000WRunningEntry
            MAX-ACCESS not-accessible
             STATUS current
             DESCRIPTION
                "Running table of Fan 3000."
            ::= { hwFB3000W 1 }

        hwFB3000WRunningEntry OBJECT-TYPE
                        SYNTAX HwFB3000WRunningEntry
            MAX-ACCESS not-accessible
             STATUS current
             DESCRIPTION
                "Running table of Fan 3000."
            INDEX { hwFB3000WRunningIndex }
            ::= { hwFB3000WRunningTable 1 }

        HwFB3000WRunningEntry            ::= SEQUENCE {
                hwFB3000WRunningIndex
                    Unsigned32,
                hwFB3000WAddr
                    Unsigned32,
                hwFB3000WName
                    OCTET STRING,
                hwFB3000WDeviceStatus
                    INTEGER,
                hwFB3000WSpeed
                    Unsigned32,
                hwFB3000WAirOutletTemperature
                    Integer32,
                hwFB3000WHighTempAlarmThres
                    Integer32,
                hwFB3000WLowTempAlarmThres
                    Integer32,
                hwFB3000WOutletTempSensorFault
                    Unsigned32,
                hwFB3000WHighTempAlarm
                    Unsigned32,
                hwFB3000WLowTempAlarm
                    Unsigned32,
                hwFB3000WConsoleFault
                    Unsigned32,
                hwFB3000WFault
                    Unsigned32,
                hwFB3000WCommStatus
                    INTEGER,
                hwFB3000WRunningRowStatus
                    RowStatus
            }

        hwFB3000WRunningIndex OBJECT-TYPE
            SYNTAX Unsigned32
            MAX-ACCESS read-only
            STATUS current
            DESCRIPTION
                "Index of the device running table for the Fan."
            ::= { hwFB3000WRunningEntry 1 }

        hwFB3000WAddr OBJECT-TYPE
            SYNTAX Unsigned32
            MAX-ACCESS read-only
            STATUS current
            DESCRIPTION
                "Device Address."
            ::= { hwFB3000WRunningEntry 2 }

        hwFB3000WName OBJECT-TYPE
            SYNTAX OCTET STRING
            MAX-ACCESS read-write
            STATUS current
            DESCRIPTION
                "Device Name."
            ::= { hwFB3000WRunningEntry 3 }

        hwFB3000WDeviceStatus OBJECT-TYPE
            SYNTAX INTEGER
                {
                standby(1),
                running(2),
                unknown(255)
                }
            MAX-ACCESS read-only
            STATUS current
            DESCRIPTION
                "Device Status.
                    Value 1 indicates standby.
                    Value 2 indicates running.
                "
            ::= { hwFB3000WRunningEntry 4 }

        hwFB3000WSpeed OBJECT-TYPE
            SYNTAX Unsigned32 (0..6000)
            MAX-ACCESS read-only
            STATUS current
            DESCRIPTION
                "Fan Speed."
            ::= { hwFB3000WRunningEntry 5 }

        hwFB3000WAirOutletTemperature OBJECT-TYPE
            SYNTAX Integer32 ( -126..127)
            MAX-ACCESS read-only
            STATUS current
            DESCRIPTION
                "Air Outlet Temperature. The value ranges from -126 to 127. The unit is degC."
            ::= { hwFB3000WRunningEntry 6 }

        hwFB3000WHighTempAlarmThres OBJECT-TYPE
            SYNTAX Integer32 (20..80)
            MAX-ACCESS read-write
            STATUS current
            DESCRIPTION
                "High Temperature Alarm Thres.The value ranges from 20 to 80. The unit is degC."
            ::= { hwFB3000WRunningEntry 7 }

        hwFB3000WLowTempAlarmThres OBJECT-TYPE
            SYNTAX Integer32 ( -40..10)
            MAX-ACCESS read-write
            STATUS current
            DESCRIPTION
                "Low Temperature Alarm Thres.The value ranges from -40 to 10. The unit is degC."
            ::= { hwFB3000WRunningEntry 8 }

        hwFB3000WOutletTempSensorFault OBJECT-TYPE
            SYNTAX Unsigned32 (0..1)
            MAX-ACCESS read-only
            STATUS current
            DESCRIPTION
                "Air Outlet TS Fault."
            ::= { hwFB3000WRunningEntry 9 }

        hwFB3000WHighTempAlarm OBJECT-TYPE
            SYNTAX Unsigned32 (0..1)
            MAX-ACCESS read-only
            STATUS current
            DESCRIPTION
                "High Temperature Alarm."
            ::= { hwFB3000WRunningEntry 10 }

        hwFB3000WLowTempAlarm OBJECT-TYPE
            SYNTAX Unsigned32 (0..1)
            MAX-ACCESS read-only
            STATUS current
            DESCRIPTION
                "Low Temperature Alarm."
            ::= { hwFB3000WRunningEntry 11 }

        hwFB3000WConsoleFault OBJECT-TYPE
            SYNTAX Unsigned32 (0..1)
            MAX-ACCESS read-only
            STATUS current
            DESCRIPTION
                "Console Fault"
            ::= { hwFB3000WRunningEntry 12 }

        hwFB3000WFault OBJECT-TYPE
            SYNTAX Unsigned32 (0..1)
            MAX-ACCESS read-only
            STATUS current
            DESCRIPTION
                "Fan Alarm"
            ::= { hwFB3000WRunningEntry 13 }

        hwFB3000WCommStatus OBJECT-TYPE
            SYNTAX INTEGER
                {
                comm_normal(1),
                comm_fail(2),
                unknown(255)
                }
            MAX-ACCESS read-only
            STATUS current
            DESCRIPTION
                "Communication Status
                    Value 1 indicates noraml.
                    Value 2 indicates fail."
            ::= { hwFB3000WRunningEntry 14 }

        hwFB3000WRunningRowStatus OBJECT-TYPE
            SYNTAX RowStatus
            MAX-ACCESS read-create
            STATUS current
            DESCRIPTION
                "RowStatus of config table Fan."
            ::= { hwFB3000WRunningEntry 100 }

        hwFB3000WConfigTable OBJECT-TYPE
            SYNTAX SEQUENCE OF HwFB3000WConfigEntry
            MAX-ACCESS not-accessible
             STATUS current
             DESCRIPTION
                "The config table of Fan3000W."
            ::= { hwFB3000W 2 }

        hwFB3000WConfigEntry OBJECT-TYPE
                        SYNTAX HwFB3000WConfigEntry
            MAX-ACCESS not-accessible
             STATUS current
             DESCRIPTION
                "The config table of Fan3000W."
            INDEX { hwFB3000WConfigIndex }
            ::= { hwFB3000WConfigTable 1 }

        HwFB3000WConfigEntry            ::= SEQUENCE {
                hwFB3000WConfigIndex
                    Unsigned32,
                hwFB3000WReset
                    INTEGER,
                hwFB3000WSyncTime
                    INTEGER,
                hwFB3000WConfigRowStatus
                    RowStatus
            }

        hwFB3000WConfigIndex OBJECT-TYPE
            SYNTAX Unsigned32
            MAX-ACCESS read-only
            STATUS current
            DESCRIPTION
                "Index of the device config table for the Fan."
            ::= { hwFB3000WConfigEntry 1 }

        hwFB3000WReset OBJECT-TYPE
            SYNTAX INTEGER
                {
                yes(1)
                }
            MAX-ACCESS read-write
            STATUS current
            DESCRIPTION
                "FAN Reset."
            ::= { hwFB3000WConfigEntry 2 }

        hwFB3000WSyncTime OBJECT-TYPE
            SYNTAX INTEGER
                {
                yes(1)
                }
            MAX-ACCESS read-write
            STATUS current
            DESCRIPTION
                "Synchronize Time."
            ::= { hwFB3000WConfigEntry 3 }

        hwFB3000WConfigRowStatus OBJECT-TYPE
            SYNTAX RowStatus
            MAX-ACCESS read-create
            STATUS current
            DESCRIPTION
                "The rawstatus of fan 3000W."
            ::= { hwFB3000WConfigEntry 100 }

        hwIDCEnvUnits OBJECT IDENTIFIER ::= { hwIDCMonitorMIBObjects 7 }

        hwEnvParameter OBJECT IDENTIFIER ::= { hwIDCEnvUnits 1 }

        hwEnvGPRS OBJECT IDENTIFIER ::= { hwEnvParameter 1 }

        hwEnvGPRSId OBJECT-TYPE
            SYNTAX Unsigned32 (1..6)
            MAX-ACCESS read-only
            STATUS current
            DESCRIPTION
                "the Slot of Device."
            ::= { hwEnvGPRS 1 }

        hwEnvGPRSName OBJECT-TYPE
            SYNTAX OCTET STRING
            MAX-ACCESS read-write
            STATUS current
            DESCRIPTION
                "the Name of Device."
            ::= { hwEnvGPRS 2 }

        hwEnvGPRSDI1 OBJECT-TYPE
            SYNTAX INTEGER
                {
                closed(1),
                open(2),
                unknown(255)
                }
            MAX-ACCESS read-only
            STATUS current
            DESCRIPTION
                "DI_1 Status"
            ::= { hwEnvGPRS 3 }

        hwEnvGPRSDI2 OBJECT-TYPE
            SYNTAX INTEGER
                {
                closed(1),
                open(2),
                unknown(255)
                }
            MAX-ACCESS read-only
            STATUS current
            DESCRIPTION
                "DI_2 Status"
            ::= { hwEnvGPRS 4 }

        hwEnvGPRSDI3 OBJECT-TYPE
            SYNTAX INTEGER
                {
                closed(1),
                open(2),
                unknown(255)
                }
            MAX-ACCESS read-only
            STATUS current
            DESCRIPTION
                "DI_3 Status"
            ::= { hwEnvGPRS 5 }

        hwEnvGPRSDI4 OBJECT-TYPE
            SYNTAX INTEGER
                {
                closed(1),
                open(2),
                unknown(255)
                }
            MAX-ACCESS read-only
            STATUS current
            DESCRIPTION
                "DI_4 Status"
            ::= { hwEnvGPRS 6 }

        hwEnvGPRSDI5 OBJECT-TYPE
            SYNTAX INTEGER
                {
                closed(1),
                open(2),
                unknown(255)
                }
            MAX-ACCESS read-only
            STATUS current
            DESCRIPTION
                "DI_5 Status"
            ::= { hwEnvGPRS 7 }

        hwEnvGPRSDI6 OBJECT-TYPE
            SYNTAX INTEGER
                {
                closed(1),
                open(2),
                unknown(255)
                }
            MAX-ACCESS read-only
            STATUS current
            DESCRIPTION
                "DI_6 Status"
            ::= { hwEnvGPRS 8 }

        hwEnvGPRSConfig OBJECT IDENTIFIER ::= { hwEnvGPRS 20 }

        hwEnvGPRSEnableDI1 OBJECT-TYPE
            SYNTAX INTEGER
                {
                enable(1),
                disable(2),
                unknown(255)
                }
            MAX-ACCESS read-write
            STATUS current
            DESCRIPTION
                "DI_1 channel enable,which user must enable it if want to insert sensors, is an enumeration type: 
                  If the enumeration value is 1, it indicates the channel  is enabled;
                  If the enumeration value is 2, it indicates  the channel  is disabled;"
            ::= { hwEnvGPRSConfig 1 }

        hwEnvGPRSConfigDI1Level OBJECT-TYPE
            SYNTAX INTEGER
                {
                nc(1),
                no(2),
                unknown(255)
                }
            MAX-ACCESS read-write
            STATUS current
            DESCRIPTION
                "DI6 channel level,which user must enable it if want to insert sensors, is an enumeration type: 
                  If the enumeration value is 1, it indicates the channel  is nc;
                  If the enumeration value is 2, it indicates  the channel  is no;"
            ::= { hwEnvGPRSConfig 2 }

        hwEnvGPRSEnableDI2 OBJECT-TYPE
            SYNTAX INTEGER
                {
                enable(1),
                disable(2),
                unknown(255)
                }
            MAX-ACCESS read-write
            STATUS current
            DESCRIPTION
                "DI_2 channel enable,which user must enable it if want to insert sensors, is an enumeration type: 
                  If the enumeration value is 1, it indicates the channel  is enabled;
                  If the enumeration value is 2, it indicates  the channel  is disabled;"
            ::= { hwEnvGPRSConfig 3 }

        hwEnvGPRSConfigDI2Level OBJECT-TYPE
            SYNTAX INTEGER
                {
                nc(1),
                no(2),
                unknown(255)
                }
            MAX-ACCESS read-write
            STATUS current
            DESCRIPTION
                "DI_2 channel level,which user must enable it if want to insert sensors, is an enumeration type: 
                  If the enumeration value is 1, it indicates the channel  is nc;
                  If the enumeration value is 2, it indicates  the channel  is no;"
            ::= { hwEnvGPRSConfig 4 }

        hwEnvGPRSEnableDI3 OBJECT-TYPE
            SYNTAX INTEGER
                {
                enable(1),
                disable(2),
                unknown(255)
                }
            MAX-ACCESS read-write
            STATUS current
            DESCRIPTION
                "DI_3 channel enable,which user must enable it if want to insert sensors, is an enumeration type: 
                  If the enumeration value is 1, it indicates the channel  is enabled;
                  If the enumeration value is 2, it indicates  the channel  is disabled;"
            ::= { hwEnvGPRSConfig 5 }

        hwEnvGPRSConfigDI3Level OBJECT-TYPE
            SYNTAX INTEGER
                {
                nc(1),
                no(2),
                unknown(255)
                }
            MAX-ACCESS read-write
            STATUS current
            DESCRIPTION
                "DI_4 channel level,which user must enable it if want to insert sensors, is an enumeration type: 
                  If the enumeration value is 1, it indicates the channel  is nc;
                  If the enumeration value is 2, it indicates  the channel  is no;"
            ::= { hwEnvGPRSConfig 6 }

        hwEnvGPRSEnableDI4 OBJECT-TYPE
            SYNTAX INTEGER
                {
                enable(1),
                disable(2),
                unknown(255)
                }
            MAX-ACCESS read-write
            STATUS current
            DESCRIPTION
                "DI_4 channel enable,which user must enable it if want to insert sensors, is an enumeration type: 
                  If the enumeration value is 1, it indicates the channel  is enabled;
                  If the enumeration value is 2, it indicates  the channel  is disabled;"
            ::= { hwEnvGPRSConfig 7 }

        hwEnvGPRSConfigDI4Level OBJECT-TYPE
            SYNTAX INTEGER
                {
                nc(1),
                no(2),
                unknown(255)
                }
            MAX-ACCESS read-write
            STATUS current
            DESCRIPTION
                "DI_4 channel level,which user must enable it if want to insert sensors, is an enumeration type: 
                  If the enumeration value is 1, it indicates the channel  is nc;
                  If the enumeration value is 2, it indicates  the channel  is no;"
            ::= { hwEnvGPRSConfig 8 }

        hwEnvGPRSEnableDI5 OBJECT-TYPE
            SYNTAX INTEGER
                {
                enable(1),
                disable(2),
                unknown(255)
                }
            MAX-ACCESS read-write
            STATUS current
            DESCRIPTION
                "DI_5 channel enable,which user must enable it if want to insert sensors, is an enumeration type: 
                  If the enumeration value is 1, it indicates the channel  is enabled;
                  If the enumeration value is 2, it indicates  the channel  is disabled;"
            ::= { hwEnvGPRSConfig 9 }

        hwEnvGPRSConfigDI5Level OBJECT-TYPE
            SYNTAX INTEGER
                {
                nc(1),
                no(2),
                unknown(255)
                }
            MAX-ACCESS read-write
            STATUS current
            DESCRIPTION
                "DI_5 channel level,which user must enable it if want to insert sensors, is an enumeration type: 
                  If the enumeration value is 1, it indicates the channel  is nc;
                  If the enumeration value is 2, it indicates  the channel  is no;"
            ::= { hwEnvGPRSConfig 10 }

        hwEnvGPRSEnableDI6 OBJECT-TYPE
            SYNTAX INTEGER
                {
                enable(1),
                disable(2),
                unknown(255)
                }
            MAX-ACCESS read-write
            STATUS current
            DESCRIPTION
                "DI_6 channel enable,which user must enable it if want to insert sensors, is an enumeration type: 
                  If the enumeration value is 1, it indicates the channel  is enabled;
                  If the enumeration value is 2, it indicates  the channel  is disabled;"
            ::= { hwEnvGPRSConfig 11 }

        hwEnvGPRSConfigDI6Level OBJECT-TYPE
            SYNTAX INTEGER
                {
                nc(1),
                no(2),
                unknown(255)
                }
            MAX-ACCESS read-write
            STATUS current
            DESCRIPTION
                "DI_6 channel level,which user must enable it if want to insert sensors, is an enumeration type: 
                  If the enumeration value is 1, it indicates the channel  is nc;
                  If the enumeration value is 2, it indicates  the channel  is no;"
            ::= { hwEnvGPRSConfig 12 }

        hwEnvGPRSEnableDO1 OBJECT-TYPE
            SYNTAX INTEGER
                {
                manual(1),
                disable(2),
                associate(3)
                }
            MAX-ACCESS read-write
            STATUS current
            DESCRIPTION
                "DO1 channel enable,which user must enable it if want to insert sensors, is an enumeration type: 
                  If the enumeration value is 1, it indicates the channel  is manual;
                  If the enumeration value is 2, it indicates  the channel  is disable;
                  If the enumeration value is 3, it indicates  the channel  is dassociate;"
            ::= { hwEnvGPRSConfig 13 }

        hwEnvGPRSConfigDO1Level OBJECT-TYPE
            SYNTAX INTEGER
                {
                nc(1),
                no(2),
                unknown(255)
                }
            MAX-ACCESS read-write
            STATUS current
            DESCRIPTION
                "DO2 channel level,which user must enable it if want to insert sensors, is an enumeration type: 
                  If the enumeration value is 1, it indicates the channel  is nc;
                  If the enumeration value is 2, it indicates  the channel  is no;"
            ::= { hwEnvGPRSConfig 14 }

        hwEnvGPRSEnableDO2 OBJECT-TYPE
            SYNTAX INTEGER
                {
                manual(1),
                disable(2),
                associate(3)
                }
            MAX-ACCESS read-write
            STATUS current
            DESCRIPTION
                "DO2 channel enable,which user must enable it if want to insert sensors, is an enumeration type: 
                  If the enumeration value is 1, it indicates the channel  is manual;
                  If the enumeration value is 2, it indicates  the channel  is disable;
                  If the enumeration value is 3, it indicates  the channel  is dassociate;"
            ::= { hwEnvGPRSConfig 15 }

        hwEnvGPRSConfigDO2Level OBJECT-TYPE
            SYNTAX INTEGER
                {
                nc(1),
                no(2),
                unknown(255)
                }
            MAX-ACCESS read-write
            STATUS current
            DESCRIPTION
                "DO2 channel level,which user must enable it if want to insert sensors, is an enumeration type: 
                  If the enumeration value is 1, it indicates the channel  is nc;
                  If the enumeration value is 2, it indicates  the channel  is no;"
            ::= { hwEnvGPRSConfig 16 }

        hwEnvGPRSStatus OBJECT IDENTIFIER ::= { hwEnvGPRS 9 }

        hwEnvGPRSExist OBJECT-TYPE
            SYNTAX INTEGER
                {
                not_exist(1),
                exist(2),
                unknown(255)
                }
            MAX-ACCESS read-only
            STATUS current
            DESCRIPTION
                "The GPRS Equipment exist status."
            ::= { hwEnvGPRSStatus 1 }

        hwEnvGPRSSIMcardExist OBJECT-TYPE
            SYNTAX INTEGER
                {
                not_exist(1),
                exist(2),
                unknown(255)
                }
            MAX-ACCESS read-only
            STATUS current
            DESCRIPTION
                "The GPRS SIM card exist status."
            ::= { hwEnvGPRSStatus 2 }

        hwEnvGPRSSMSStatus OBJECT-TYPE
            SYNTAX INTEGER
                {
                failure(1),
                success(2),
                unknown(255)
                }
            MAX-ACCESS read-only
            STATUS current
            DESCRIPTION
                "The GPRS SMS service status."
            ::= { hwEnvGPRSStatus 3 }

        hwEnvGPRSSignalStrength OBJECT-TYPE
            SYNTAX Integer32 (0..100)
            MAX-ACCESS read-only
            STATUS current
            DESCRIPTION
                "The strength of  GPRS signal.Unit : %.Multiple 10."
            ::= { hwEnvGPRSStatus 4 }

        hwEnvTempHum OBJECT IDENTIFIER ::= { hwEnvParameter 2 }

        hwHuaweiTempHum OBJECT IDENTIFIER ::= { hwEnvTempHum 1 }

        hwHuaweiTempHumRunningTable OBJECT-TYPE
            SYNTAX SEQUENCE OF HwHuaweiTempHumRunningEntry
            MAX-ACCESS not-accessible
             STATUS current
             DESCRIPTION
                "The running table of Huawei TempHum Equipment."
            ::= { hwHuaweiTempHum 1 }

        hwHuaweiTempHumRunningEntry OBJECT-TYPE
                        SYNTAX HwHuaweiTempHumRunningEntry
            MAX-ACCESS not-accessible
             STATUS current
             DESCRIPTION
                "The running table of Huawei TempHum Equipment."
            INDEX { hwHuaweiTempHumRunningIndex }
            ::= { hwHuaweiTempHumRunningTable 1 }

        HwHuaweiTempHumRunningEntry            ::= SEQUENCE {
                hwHuaweiTempHumRunningIndex
                    Unsigned32,
                hwHuaweiTempHumCommStatus
                    INTEGER,
                hwHuaweiTempHumSlotNo
                    Unsigned32,
                hwHuaweiTempHumPortNo
                    Unsigned32,
                hwHuaweiTempHumTemperature
                    Integer32,
                hwHuaweiTempHumHumidity
                    Integer32,
                hwHuaweiTempHumModbusAddr
                    Unsigned32,
                hwHuaweiTempHumName
                    OCTET STRING,
                hwHuaweiTempHumRunningRowStatus
                    RowStatus
            }

        hwHuaweiTempHumRunningIndex OBJECT-TYPE
            SYNTAX Unsigned32
            MAX-ACCESS read-only
            STATUS current
            DESCRIPTION
                "Index of the device running table for the TempHum."
            ::= { hwHuaweiTempHumRunningEntry 1 }

        hwHuaweiTempHumCommStatus OBJECT-TYPE
            SYNTAX INTEGER
                {
                ok(1),
                fail(2),
                unknown(255)
                }
            MAX-ACCESS read-only
            STATUS current
            DESCRIPTION
                "Communication Status
                    Value 1 indicates noraml.
                    Value 2 indicates fail."
            ::= { hwHuaweiTempHumRunningEntry 2 }

        hwHuaweiTempHumSlotNo OBJECT-TYPE
            SYNTAX Unsigned32 (0..6)
            MAX-ACCESS read-only
            STATUS current
            DESCRIPTION
                "the Slot No. of Device."
            ::= { hwHuaweiTempHumRunningEntry 3 }

        hwHuaweiTempHumPortNo OBJECT-TYPE
            SYNTAX Unsigned32 (1..5)
            MAX-ACCESS read-only
            STATUS current
            DESCRIPTION
                "the Port No. of Device."
            ::= { hwHuaweiTempHumRunningEntry 4 }

        hwHuaweiTempHumTemperature OBJECT-TYPE
            SYNTAX Integer32 ( -20..80)
            MAX-ACCESS read-only
            STATUS current
            DESCRIPTION
                "Temperature.Value range: -20 to 80, Unit:degC. Multiple 10."
            ::= { hwHuaweiTempHumRunningEntry 5 }

        hwHuaweiTempHumHumidity OBJECT-TYPE
            SYNTAX Integer32 (0..100)
            MAX-ACCESS read-only
            STATUS current
            DESCRIPTION
                "Humidity.Value range: 0 to 100."
            ::= { hwHuaweiTempHumRunningEntry 6 }

        hwHuaweiTempHumModbusAddr OBJECT-TYPE
            SYNTAX Unsigned32 (1..254)
            MAX-ACCESS read-only
            STATUS current
            DESCRIPTION
                "the modbus Address of the device."
            ::= { hwHuaweiTempHumRunningEntry 7 }

        hwHuaweiTempHumName OBJECT-TYPE
            SYNTAX OCTET STRING (SIZE (0..50))
            MAX-ACCESS read-only
            STATUS current
            DESCRIPTION
                "the name of device."
            ::= { hwHuaweiTempHumRunningEntry 8 }

        hwHuaweiTempHumRunningRowStatus OBJECT-TYPE
            SYNTAX RowStatus
            MAX-ACCESS read-create
            STATUS current
            DESCRIPTION
                "The RowStatus of Huawei TempHum Equipment."
            ::= { hwHuaweiTempHumRunningEntry 100 }

        hwHuaweiTempHumConfigTable OBJECT-TYPE
            SYNTAX SEQUENCE OF HwHuaweiTempHumConfigEntry
            MAX-ACCESS not-accessible
             STATUS current
             DESCRIPTION
                "The Config Table of Huawei TempHum Equipment."
            ::= { hwHuaweiTempHum 2 }

        hwHuaweiTempHumConfigEntry OBJECT-TYPE
                        SYNTAX HwHuaweiTempHumConfigEntry
            MAX-ACCESS not-accessible
             STATUS current
             DESCRIPTION
                "The Config Table of Huawei TempHum Equipment."
            INDEX { hwHuaweiTempHumConfigIndex }
            ::= { hwHuaweiTempHumConfigTable 1 }

        HwHuaweiTempHumConfigEntry            ::= SEQUENCE {
                hwHuaweiTempHumConfigIndex
                    Unsigned32,
                hwHuaweiTempHumHighTemperatureAlarmPoint
                    Integer32,
                hwHuaweiTempHumLowTemperatureAlarmPoint
                    Integer32,
                hwHuaweiTempHumHighHumidityAlarmPoint
                    Integer32,
                hwHuaweiTempHumLowHumidityAlarmPoint
                    Integer32,
                hwHuaweiTempHumConfigRowStatus
                    RowStatus
            }

        hwHuaweiTempHumConfigIndex OBJECT-TYPE
            SYNTAX Unsigned32
            MAX-ACCESS read-only
            STATUS current
            DESCRIPTION
                "Index of the device config table for the TempHum."
            ::= { hwHuaweiTempHumConfigEntry 1 }

        hwHuaweiTempHumHighTemperatureAlarmPoint OBJECT-TYPE
            SYNTAX Integer32 (20..100)
            MAX-ACCESS read-write
            STATUS current
            DESCRIPTION
                "High Temperature Alarm Point.The value ranges from 20 to 100. The unit is degC.Multiple 10."
            ::= { hwHuaweiTempHumConfigEntry 2 }

        hwHuaweiTempHumLowTemperatureAlarmPoint OBJECT-TYPE
            SYNTAX Integer32 ( -20..19)
            MAX-ACCESS read-write
            STATUS current
            DESCRIPTION
                "Low Temperature Alarm Point..The value ranges from -20 to 19. The unit is degC.Multiple 10."
            ::= { hwHuaweiTempHumConfigEntry 3 }

        hwHuaweiTempHumHighHumidityAlarmPoint OBJECT-TYPE
            SYNTAX Integer32 (50..100)
            MAX-ACCESS read-write
            STATUS current
            DESCRIPTION
                "High Humidity Alarm Point.The value ranges from 50 to 100."
            ::= { hwHuaweiTempHumConfigEntry 4 }

        hwHuaweiTempHumLowHumidityAlarmPoint OBJECT-TYPE
            SYNTAX Integer32 (0..19)
            MAX-ACCESS read-write
            STATUS current
            DESCRIPTION
                "Low Humidity Alarm Point.The value ranges from 0 to 19."
            ::= { hwHuaweiTempHumConfigEntry 5 }

        hwHuaweiTempHumConfigRowStatus OBJECT-TYPE
            SYNTAX RowStatus
            MAX-ACCESS read-create
            STATUS current
            DESCRIPTION
                "The config rowstatus of huawei temphum equipment."
            ::= { hwHuaweiTempHumConfigEntry 100 }

        hwPolymerTempHum OBJECT IDENTIFIER ::= { hwEnvTempHum 2 }

        hwPolymerTempHumRunningTable OBJECT-TYPE
            SYNTAX SEQUENCE OF HwPolymerTempHumRunningEntry
            MAX-ACCESS not-accessible
             STATUS current
             DESCRIPTION
                "The running table of Polymer TempHum Equipment."
            ::= { hwPolymerTempHum 1 }

        hwPolymerTempHumRunningEntry OBJECT-TYPE
                        SYNTAX HwPolymerTempHumRunningEntry
            MAX-ACCESS not-accessible
             STATUS current
             DESCRIPTION
                "The running table of Polymer TempHum Equipment."
            INDEX { hwPolymerTempHumRunningIndex }
            ::= { hwPolymerTempHumRunningTable 1 }

        HwPolymerTempHumRunningEntry            ::= SEQUENCE {
                hwPolymerTempHumRunningIndex
                    Unsigned32,
                hwPolymerTempHumCommStatus
                    INTEGER,
                hwPolymerTempHumSlotNo
                    Unsigned32,
                hwPolymerTempHumPortNo
                    Unsigned32,
                hwPolymerTempHumTemperature
                    Integer32,
                hwPolymerTempHumHumidity
                    Integer32,
                hwPolymerTempHumModbusAddr
                    Unsigned32,
                hwPolymerTempHumName
                    OCTET STRING,
                hwPolymerTempHumRunningRowStatus
                    RowStatus
            }

        hwPolymerTempHumRunningIndex OBJECT-TYPE
            SYNTAX Unsigned32
            MAX-ACCESS read-only
            STATUS current
            DESCRIPTION
                "Index of the device running table for the TempHum."
            ::= { hwPolymerTempHumRunningEntry 1 }

        hwPolymerTempHumCommStatus OBJECT-TYPE
            SYNTAX INTEGER
                {
                ok(1),
                fail(2),
                unknown(255)
                }
            MAX-ACCESS read-only
            STATUS current
            DESCRIPTION
                "Communication Status
                    Value 1 indicates noraml.
                    Value 2 indicates fail."
            ::= { hwPolymerTempHumRunningEntry 2 }

        hwPolymerTempHumSlotNo OBJECT-TYPE
            SYNTAX Unsigned32 (0..6)
            MAX-ACCESS read-only
            STATUS current
            DESCRIPTION
                "the Slot No. of Device."
            ::= { hwPolymerTempHumRunningEntry 3 }

        hwPolymerTempHumPortNo OBJECT-TYPE
            SYNTAX Unsigned32 (1..5)
            MAX-ACCESS read-only
            STATUS current
            DESCRIPTION
                "the Port No. of Device."
            ::= { hwPolymerTempHumRunningEntry 4 }

        hwPolymerTempHumTemperature OBJECT-TYPE
            SYNTAX Integer32 ( -20..70)
            MAX-ACCESS read-only
            STATUS current
            DESCRIPTION
                "Temperature.Value range: -20 to 70, Unit:degC. Multiple 10."
            ::= { hwPolymerTempHumRunningEntry 5 }

        hwPolymerTempHumHumidity OBJECT-TYPE
            SYNTAX Integer32 (0..100)
            MAX-ACCESS read-only
            STATUS current
            DESCRIPTION
                "Humidity.Value range: 0 to 100, Unit:%. Multiple 10."
            ::= { hwPolymerTempHumRunningEntry 6 }

        hwPolymerTempHumModbusAddr OBJECT-TYPE
            SYNTAX Unsigned32 (1..254)
            MAX-ACCESS read-only
            STATUS current
            DESCRIPTION
                "the modbus Address of the device."
            ::= { hwPolymerTempHumRunningEntry 7 }

        hwPolymerTempHumName OBJECT-TYPE
            SYNTAX OCTET STRING (SIZE (0..50))
            MAX-ACCESS read-only
            STATUS current
            DESCRIPTION
                "the name of device."
            ::= { hwPolymerTempHumRunningEntry 8 }

        hwPolymerTempHumRunningRowStatus OBJECT-TYPE
            SYNTAX RowStatus
            MAX-ACCESS read-create
            STATUS current
            DESCRIPTION
                "The RowStatus of Polymer TempHum Equipment."
            ::= { hwPolymerTempHumRunningEntry 100 }

        hwPolymerTempHumConfigTable OBJECT-TYPE
            SYNTAX SEQUENCE OF HwPolymerTempHumConfigEntry
            MAX-ACCESS not-accessible
             STATUS current
             DESCRIPTION
                "The Config Table of Polymer TempHum Equipment."
            ::= { hwPolymerTempHum 2 }

        hwPolymerTempHumConfigEntry OBJECT-TYPE
                        SYNTAX HwPolymerTempHumConfigEntry
            MAX-ACCESS not-accessible
             STATUS current
             DESCRIPTION
                "The Config Table of Polymer TempHum Equipment."
            INDEX { hwPolymerTempHumConfigIndex }
            ::= { hwPolymerTempHumConfigTable 1 }

        HwPolymerTempHumConfigEntry            ::= SEQUENCE {
                hwPolymerTempHumConfigIndex
                    Unsigned32,
                hwPolymerTempHumHighTemperatureAlarmPoint
                    Integer32,
                hwPolymerTempHumLowTemperatureAlarmPoint
                    Integer32,
                hwPolymerTempHumHighHumidityAlarmPoint
                    Integer32,
                hwPolymerTempHumLowHumidityAlarmPoint
                    Integer32,
                hwPolymerTempHumConfigRowStatus
                    RowStatus
            }

        hwPolymerTempHumConfigIndex OBJECT-TYPE
            SYNTAX Unsigned32
            MAX-ACCESS read-only
            STATUS current
            DESCRIPTION
                "Index of the device config table for the TempHum."
            ::= { hwPolymerTempHumConfigEntry 1 }

        hwPolymerTempHumHighTemperatureAlarmPoint OBJECT-TYPE
            SYNTAX Integer32 (20..70)
            MAX-ACCESS read-write
            STATUS current
            DESCRIPTION
                "High Temperature Alarm Point.The value ranges from 20 to 70. The unit is degC.Multiple 10."
            ::= { hwPolymerTempHumConfigEntry 2 }

        hwPolymerTempHumLowTemperatureAlarmPoint OBJECT-TYPE
            SYNTAX Integer32 ( -20..19)
            MAX-ACCESS read-write
            STATUS current
            DESCRIPTION
                "Low Temperature Alarm Point..The value ranges from -20 to 19. The unit is degC.Multiple 10."
            ::= { hwPolymerTempHumConfigEntry 3 }

        hwPolymerTempHumHighHumidityAlarmPoint OBJECT-TYPE
            SYNTAX Integer32 (50..100)
            MAX-ACCESS read-write
            STATUS current
            DESCRIPTION
                "High Humidity Alarm Point.The value ranges from 50 to 100, Unit:%. Multiple 10."
            ::= { hwPolymerTempHumConfigEntry 4 }

        hwPolymerTempHumLowHumidityAlarmPoint OBJECT-TYPE
            SYNTAX Integer32 (0..19)
            MAX-ACCESS read-write
            STATUS current
            DESCRIPTION
                "Low Humidity Alarm Point.The value ranges from 0 to 19, Unit:%. Multiple 10."
            ::= { hwPolymerTempHumConfigEntry 5 }

        hwPolymerTempHumConfigRowStatus OBJECT-TYPE
            SYNTAX RowStatus
            MAX-ACCESS read-create
            STATUS current
            DESCRIPTION
                "The config rowstatus of polymer temphum equipment."
            ::= { hwPolymerTempHumConfigEntry 100 }

        hwIDCATS OBJECT IDENTIFIER ::= { hwIDCMonitorMIBObjects 8 }

        hwOMD800 OBJECT IDENTIFIER ::= { hwIDCATS 1 }

        hwOMD800RunningTable OBJECT-TYPE
            SYNTAX SEQUENCE OF HwOMD800RunningEntry
            MAX-ACCESS not-accessible
             STATUS current
             DESCRIPTION
                "The Running table of OMD800."
            ::= { hwOMD800 1 }

        hwOMD800RunningEntry OBJECT-TYPE
                        SYNTAX HwOMD800RunningEntry
            MAX-ACCESS not-accessible
             STATUS current
             DESCRIPTION
                "The Running table of OMD800."
            INDEX { hwOMD800RunningIndex }
            ::= { hwOMD800RunningTable 1 }

        HwOMD800RunningEntry            ::= SEQUENCE {
                hwOMD800RunningIndex
                    Unsigned32,
                hwOMD800RunningName
                    OCTET STRING,
                hwOMD800RunningCommStatus
                    INTEGER,
                hwOMD800RunningSlotNo
                    Unsigned32,
                hwOMD800RunningPortNo
                    Unsigned32,
                hwOMD800RunningModBusAddr
                    Unsigned32,
                hwOMD800RunningSoftwareVersion
                    OCTET STRING,
                hwOMD800RunningESN
                    OCTET STRING,
                hwOMD800RunningLN1PowerStatus
                    INTEGER,
                hwOMD800RunningLN2PowerStatus
                    INTEGER,
                hwOMD800RunningSwitchStatus
                    INTEGER,
                hwOMD800RunningGeneratorStatus
                    INTEGER,
                hwOMD800RunningChangeSwitchIStatus
                    INTEGER,
                hwOMD800RunningChangeSwitchIIStatus
                    INTEGER,
                hwOMD800RunningSecLoadStatus
                    INTEGER,
                hwOMD800RunningRowStatus
                    RowStatus
            }

        hwOMD800RunningIndex OBJECT-TYPE
            SYNTAX Unsigned32
            MAX-ACCESS read-only
            STATUS current
            DESCRIPTION
                "Index of the device config table for the OMD800."
            ::= { hwOMD800RunningEntry 1 }

        hwOMD800RunningName OBJECT-TYPE
            SYNTAX OCTET STRING (SIZE (0..50))
            MAX-ACCESS read-only
            STATUS current
            DESCRIPTION
                "the name of device."
            ::= { hwOMD800RunningEntry 2 }

        hwOMD800RunningCommStatus OBJECT-TYPE
            SYNTAX INTEGER
                {
                ok(1),
                fail(2),
                unknown(255)
                }
            MAX-ACCESS read-only
            STATUS current
            DESCRIPTION
                "Communication Status
                    Value 1 indicates noraml.
                    Value 2 indicates fail."
            ::= { hwOMD800RunningEntry 3 }

        hwOMD800RunningSlotNo OBJECT-TYPE
            SYNTAX Unsigned32 (0..6)
            MAX-ACCESS read-only
            STATUS current
            DESCRIPTION
                "the Slot of Device."
            ::= { hwOMD800RunningEntry 4 }

        hwOMD800RunningPortNo OBJECT-TYPE
            SYNTAX Unsigned32 (1..5)
            MAX-ACCESS read-only
            STATUS current
            DESCRIPTION
                "the Port No. of Device."
            ::= { hwOMD800RunningEntry 5 }

        hwOMD800RunningModBusAddr OBJECT-TYPE
            SYNTAX Unsigned32 (1..247)
            MAX-ACCESS read-only
            STATUS current
            DESCRIPTION
                "the modbus Address of the device."
            ::= { hwOMD800RunningEntry 6 }

        hwOMD800RunningSoftwareVersion OBJECT-TYPE
            SYNTAX OCTET STRING (SIZE (0..32))
            MAX-ACCESS read-only
            STATUS current
            DESCRIPTION
                "Device software version number. A string of characters."
            ::= { hwOMD800RunningEntry 7 }

        hwOMD800RunningESN OBJECT-TYPE
            SYNTAX OCTET STRING (SIZE (0..20))
            MAX-ACCESS read-only
            STATUS current
            DESCRIPTION
                "ESN of the master device used for setting up a NetEco model. A string of characters."
            ::= { hwOMD800RunningEntry 8 }

        hwOMD800RunningLN1PowerStatus OBJECT-TYPE
            SYNTAX INTEGER
                {
                VoltageNormal(1),
                VoltageIsZero(2),
                Undervoltage(3),
                Overvoltage(4),
                PhaseMissing(5),
                PhaseVolUnbalance(6),
                PhaseSequenceError(7),
                FrequencyOutOfRange(8),
                Unkown(255)
                }
            MAX-ACCESS read-only
            STATUS current
            DESCRIPTION
                "LN1 Power Status.
                 Value 1 indicates VoltageNormal.
                 Value 2 indicates VoltageIsZero.
                 Value 3 indicates Undervoltage.
                 Value 4 indicates Overvoltage.
                 Value 5 indicates PhaseMissing.
                 Value 6 indicates PhaseVolUnbalance.
                 Value 7 indicates PhaseSequenceError.
                 Value 8 indicates FrequencyOutOfRange."
            ::= { hwOMD800RunningEntry 9 }

        hwOMD800RunningLN2PowerStatus OBJECT-TYPE
            SYNTAX INTEGER
                {
                VoltageNormal(1),
                VoltageIsZero(2),
                Undervoltage(3),
                Overvoltage(4),
                PhaseMissing(5),
                PhaseVolUnbalance(6),
                PhaseSequenceError(7),
                FrequencyOutOfRange(8),
                Unkown(255)
                }
            MAX-ACCESS read-only
            STATUS current
            DESCRIPTION
                "LN2 Power Status.
                 Value 1 indicates VoltageNormal.
                 Value 2 indicates VoltageIsZero.
                 Value 3 indicates Undervoltage.
                 Value 4 indicates Overvoltage.
                 Value 5 indicates PhaseMissing.
                 Value 6 indicates PhaseVolUnbalance.
                 Value 7 indicates PhaseSequenceError.
                 Value 8 indicates FrequencyOutOfRange."
            ::= { hwOMD800RunningEntry 10 }

        hwOMD800RunningSwitchStatus OBJECT-TYPE
            SYNTAX INTEGER
                {
                NoConversion(1),
                Converting(2),
                Converted(3),
                ConvertingBackToMain(4),
                ConvertFail(5),
                Unkown(255)
                }
            MAX-ACCESS read-only
            STATUS current
            DESCRIPTION
                "Switch Status.
                 Value 1 indicates NoConversion.
                 Value 2 indicates Converting.
                 Value 3 indicates Converted.
                 Value 4 indicates ConvertingBackToMain.
                 Value 5 indicates ConvertFail."
            ::= { hwOMD800RunningEntry 11 }

        hwOMD800RunningGeneratorStatus OBJECT-TYPE
            SYNTAX INTEGER
                {
                Stop(1),
                Run(2),
                Unkown(255)
                }
            MAX-ACCESS read-only
            STATUS current
            DESCRIPTION
                "Generator Status.
                 Value 1 indicates Stop.
                 Value 2 indicates Run."
            ::= { hwOMD800RunningEntry 12 }

        hwOMD800RunningChangeSwitchIStatus OBJECT-TYPE
            SYNTAX INTEGER
                {
                Open(1),
                Close(2),
                Unkown(255)
                }
            MAX-ACCESS read-only
            STATUS current
            DESCRIPTION
                "Change Switch I Status.
                 Value 1 indicates Open.
                 Value 2 indicates Close."
            ::= { hwOMD800RunningEntry 13 }

        hwOMD800RunningChangeSwitchIIStatus OBJECT-TYPE
            SYNTAX INTEGER
                {
                Open(1),
                Close(2),
                Unkown(255)
                }
            MAX-ACCESS read-only
            STATUS current
            DESCRIPTION
                "Change Switch II Status.
                 Value 1 indicates Open.
                 Value 2 indicates Close."
            ::= { hwOMD800RunningEntry 14 }

        hwOMD800RunningSecLoadStatus OBJECT-TYPE
            SYNTAX INTEGER
                {
                Open(1),
                Close(2),
                Unkown(255)
                }
            MAX-ACCESS read-only
            STATUS current
            DESCRIPTION
                "Sec. Load Status.
                 Value 1 indicates Open.
                 Value 2 indicates Close."
            ::= { hwOMD800RunningEntry 15 }

        hwOMD800RunningRowStatus OBJECT-TYPE
            SYNTAX RowStatus
            MAX-ACCESS read-create
            STATUS current
            DESCRIPTION
                "The rowstatus of OMD800."
            ::= { hwOMD800RunningEntry 100 }

        hwIDCPDU OBJECT IDENTIFIER ::= { hwIDCMonitorMIBObjects 9 }

        hwPDU8000Single OBJECT IDENTIFIER ::= { hwIDCPDU 1 }

        hwPDU8000SingleTable OBJECT-TYPE
            SYNTAX SEQUENCE OF HwPDU8000SingleEntry
            MAX-ACCESS not-accessible
             STATUS current
             DESCRIPTION
                "The Table of PDU8000 Single Equipment."
            ::= { hwPDU8000Single 1 }

        hwPDU8000SingleEntry OBJECT-TYPE
                        SYNTAX HwPDU8000SingleEntry
            MAX-ACCESS not-accessible
             STATUS current
             DESCRIPTION
                "The Table of PDU8000 Single Equipment."
            INDEX { hwPDU8000SingleIndex }
            ::= { hwPDU8000SingleTable 1 }

        HwPDU8000SingleEntry            ::= SEQUENCE {
                hwPDU8000SingleIndex
                    Unsigned32,
                hwPDU8000SingleName
                    OCTET STRING,
                hwPDU8000SingleCommunicationStatus
                    INTEGER,
                hwPDU8000SingleSlotNo
                    Unsigned32,
                hwPDU8000SinglePortNo
                    Unsigned32,
                hwPDU8000SingleModbusAddr
                    Unsigned32,
                hwPDU8000SingleSoftwareVersion
                    OCTET STRING,
                hwPDU8000SingleESN
                    OCTET STRING,
                hwPDU8000SingleInputMode
                    INTEGER,
                hwPDU8000SingleL1inputphasevoltage
                    Integer32,
                hwPDU8000SingleL2inputphasevoltage
                    Integer32,
                hwPDU8000SingleL3inputphasevoltage
                    Integer32,
                hwPDU8000SingleL1L2inputlinevoltage
                    Integer32,
                hwPDU8000SingleL2L3inputlinevoltage
                    Integer32,
                hwPDU8000SingleL3L1inputlinevoltage
                    Integer32,
                hwPDU8000SingleL1inputcurrent
                    Integer32,
                hwPDU8000SingleL2inputcurrent
                    Integer32,
                hwPDU8000SingleL3inputcurrent
                    Integer32,
                hwPDU8000Singleinputfrequency
                    Integer32,
                hwPDU8000SingleL1inputactivepower
                    Integer32,
                hwPDU8000SingleL2inputactivepower
                    Integer32,
                hwPDU8000SingleL3inputactivepower
                    Integer32,
                hwPDU8000SingleL1inputapparentpower
                    Integer32,
                hwPDU8000SingleL2inputapparentpower
                    Integer32,
                hwPDU8000SingleL3inputapparentpower
                    Integer32,
                hwPDU8000SingleL1inputreactivepower
                    Integer32,
                hwPDU8000SingleL2inputreactivepower
                    Integer32,
                hwPDU8000SingleL3inputreactivepower
                    Integer32,
                hwPDU8000SingleL1inputpowerfactor
                    Integer32,
                hwPDU8000SingleL2inputpowerfactor
                    Integer32,
                hwPDU8000SingleL3inputpowerfactor
                    Integer32,
                hwPDU8000Singleinputactiveelectricenergy
                    Integer32,
                hwPDU8000SingleL1inputpowerloadrate
                    Unsigned32,
                hwPDU8000SingleL2inputpowerloadrate
                    Unsigned32,
                hwPDU8000SingleL3inputpowerloadrate
                    Unsigned32,
                hwPDU8000SingleNwirecurrent
                    Integer32,
                hwPDU8000SingleL1THDurate
                    Integer32,
                hwPDU8000SingleL2THDurate
                    Integer32,
                hwPDU8000SingleL3THDurate
                    Integer32,
                hwPDU8000SingleL1THDirate
                    Integer32,
                hwPDU8000SingleL2THDirate
                    Integer32,
                hwPDU8000SingleL3THDirate
                    Integer32,
                hwPDU8000Singletotalinputactivepower
                    Integer32,
                hwPDU8000Singletotalinputapparentpower
                    Integer32,
                hwPDU8000Singletotalinputreactivepower
                    Integer32,
                hwPDU8000SingleRowStatus
                    RowStatus
            }

        hwPDU8000SingleIndex OBJECT-TYPE
            SYNTAX Unsigned32
            MAX-ACCESS read-only
            STATUS current
            DESCRIPTION
                "The Id of PDU8000 Single."
            ::= { hwPDU8000SingleEntry 1 }

        hwPDU8000SingleName OBJECT-TYPE
            SYNTAX OCTET STRING (SIZE (0..50))
            MAX-ACCESS read-only
            STATUS current
            DESCRIPTION
                "The Name of PDU8000 Single."
            ::= { hwPDU8000SingleEntry 2 }

        hwPDU8000SingleCommunicationStatus OBJECT-TYPE
            SYNTAX INTEGER
                {
                ok(1),
                fail(2),
                unknown(255)
                }
            MAX-ACCESS read-only
            STATUS current
            DESCRIPTION
                "Communication Status."
            ::= { hwPDU8000SingleEntry 3 }

        hwPDU8000SingleSlotNo OBJECT-TYPE
            SYNTAX Unsigned32 (0..6)
            MAX-ACCESS read-only
            STATUS current
            DESCRIPTION
                "Slot No."
            ::= { hwPDU8000SingleEntry 4 }

        hwPDU8000SinglePortNo OBJECT-TYPE
            SYNTAX Unsigned32 (1..5)
            MAX-ACCESS read-only
            STATUS current
            DESCRIPTION
                "Port No."
            ::= { hwPDU8000SingleEntry 5 }

        hwPDU8000SingleModbusAddr OBJECT-TYPE
            SYNTAX Unsigned32 (0..247)
            MAX-ACCESS read-only
            STATUS current
            DESCRIPTION
                "Modbus Addr."
            ::= { hwPDU8000SingleEntry 6 }

        hwPDU8000SingleSoftwareVersion OBJECT-TYPE
            SYNTAX OCTET STRING (SIZE (0..32))
            MAX-ACCESS read-only
            STATUS current
            DESCRIPTION
                "The software version of equipment."
            ::= { hwPDU8000SingleEntry 7 }

        hwPDU8000SingleESN OBJECT-TYPE
            SYNTAX OCTET STRING (SIZE (0..20))
            MAX-ACCESS read-only
            STATUS current
            DESCRIPTION
                "The ESN of equipment."
            ::= { hwPDU8000SingleEntry 8 }

        hwPDU8000SingleInputMode OBJECT-TYPE
            SYNTAX INTEGER
                {
                SingleMode(1),
                DualMode(2),
                Dual1Way(3),
                Dual2Way(4),
                from380to380Transformer(5),
                from480to208Transformer(6),
                unkown(255)
                }
            MAX-ACCESS read-only
            STATUS current
            DESCRIPTION
                "Input Mode."
            ::= { hwPDU8000SingleEntry 9 }

        hwPDU8000SingleL1inputphasevoltage OBJECT-TYPE
            SYNTAX Integer32 (0..1000)
            MAX-ACCESS read-only
            STATUS current
            DESCRIPTION
                "L1 input phase voltage. Unit:V. Multi:10"
            ::= { hwPDU8000SingleEntry 10 }

        hwPDU8000SingleL2inputphasevoltage OBJECT-TYPE
            SYNTAX Integer32 (0..1000)
            MAX-ACCESS read-only
            STATUS current
            DESCRIPTION
                "L2 input phase voltage. Unit:V. Multi:10"
            ::= { hwPDU8000SingleEntry 11 }

        hwPDU8000SingleL3inputphasevoltage OBJECT-TYPE
            SYNTAX Integer32 (0..1000)
            MAX-ACCESS read-only
            STATUS current
            DESCRIPTION
                "L3 input phase voltage. Unit:V. Multi:10"
            ::= { hwPDU8000SingleEntry 12 }

        hwPDU8000SingleL1L2inputlinevoltage OBJECT-TYPE
            SYNTAX Integer32 (0..1000)
            MAX-ACCESS read-only
            STATUS current
            DESCRIPTION
                "L1-L2 input line voltage. Unit:V. Multi:10"
            ::= { hwPDU8000SingleEntry 13 }

        hwPDU8000SingleL2L3inputlinevoltage OBJECT-TYPE
            SYNTAX Integer32 (0..1000)
            MAX-ACCESS read-only
            STATUS current
            DESCRIPTION
                "L2-L3 input line voltage. Unit:V. Multi:10"
            ::= { hwPDU8000SingleEntry 14 }

        hwPDU8000SingleL3L1inputlinevoltage OBJECT-TYPE
            SYNTAX Integer32 (0..1000)
            MAX-ACCESS read-only
            STATUS current
            DESCRIPTION
                "L3-L1input line voltage. Unit:V. Multi:10"
            ::= { hwPDU8000SingleEntry 15 }

        hwPDU8000SingleL1inputcurrent OBJECT-TYPE
            SYNTAX Integer32 (0..800)
            MAX-ACCESS read-only
            STATUS current
            DESCRIPTION
                "L1 input current. Unit:A. Multi:10"
            ::= { hwPDU8000SingleEntry 16 }

        hwPDU8000SingleL2inputcurrent OBJECT-TYPE
            SYNTAX Integer32 (0..800)
            MAX-ACCESS read-only
            STATUS current
            DESCRIPTION
                "L2 input current. Unit:A. Multi:10"
            ::= { hwPDU8000SingleEntry 17 }

        hwPDU8000SingleL3inputcurrent OBJECT-TYPE
            SYNTAX Integer32 (0..800)
            MAX-ACCESS read-only
            STATUS current
            DESCRIPTION
                "L3 input current. Unit:A. Multi:10"
            ::= { hwPDU8000SingleEntry 18 }

        hwPDU8000Singleinputfrequency OBJECT-TYPE
            SYNTAX Integer32 (0..100)
            MAX-ACCESS read-only
            STATUS current
            DESCRIPTION
                "input frequency. Unit:Hz. Multi:100"
            ::= { hwPDU8000SingleEntry 19 }

        hwPDU8000SingleL1inputactivepower OBJECT-TYPE
            SYNTAX Integer32 (-250..250)
            MAX-ACCESS read-only
            STATUS current
            DESCRIPTION
                "L1 input active power. Unit:kW. Multi:10"
            ::= { hwPDU8000SingleEntry 20 }

        hwPDU8000SingleL2inputactivepower OBJECT-TYPE
            SYNTAX Integer32 (-250..250)
            MAX-ACCESS read-only
            STATUS current
            DESCRIPTION
                "L2 input active power. Unit:kW. Multi:10"
            ::= { hwPDU8000SingleEntry 21 }

        hwPDU8000SingleL3inputactivepower OBJECT-TYPE
            SYNTAX Integer32 (-250..250)
            MAX-ACCESS read-only
            STATUS current
            DESCRIPTION
                "L3 input active power. Unit:kW. Multi:10"
            ::= { hwPDU8000SingleEntry 22 }

        hwPDU8000SingleL1inputapparentpower OBJECT-TYPE
            SYNTAX Integer32 (-250..250)
            MAX-ACCESS read-only
            STATUS current
            DESCRIPTION
                "L1 input apparent power. Unit:kVA. Multi:10"
            ::= { hwPDU8000SingleEntry 23 }

        hwPDU8000SingleL2inputapparentpower OBJECT-TYPE
            SYNTAX Integer32 (-250..250)
            MAX-ACCESS read-only
            STATUS current
            DESCRIPTION
                "L2 input apparent power. Unit:kVA. Multi:10"
            ::= { hwPDU8000SingleEntry 24 }

        hwPDU8000SingleL3inputapparentpower OBJECT-TYPE
            SYNTAX Integer32 (-250..250)
            MAX-ACCESS read-only
            STATUS current
            DESCRIPTION
                "L3 input apparent power. Unit:kVA. Multi:10"
            ::= { hwPDU8000SingleEntry 25 }

        hwPDU8000SingleL1inputreactivepower OBJECT-TYPE
            SYNTAX Integer32 (-250..250)
            MAX-ACCESS read-only
            STATUS current
            DESCRIPTION
                "L1 input reactive power. Unit:kVAR. Multi:10"
            ::= { hwPDU8000SingleEntry 26 }

        hwPDU8000SingleL2inputreactivepower OBJECT-TYPE
            SYNTAX Integer32 (-250..250)
            MAX-ACCESS read-only
            STATUS current
            DESCRIPTION
                "L2 input reactive power. Unit:kVAR. Multi:10"
            ::= { hwPDU8000SingleEntry 27 }

        hwPDU8000SingleL3inputreactivepower OBJECT-TYPE
            SYNTAX Integer32 (-250..250)
            MAX-ACCESS read-only
            STATUS current
            DESCRIPTION
                "L3 input reactive power. Unit:kVAR. Multi:10"
            ::= { hwPDU8000SingleEntry 28 }

        hwPDU8000SingleL1inputpowerfactor OBJECT-TYPE
            SYNTAX Integer32 (-1..1)
            MAX-ACCESS read-only
            STATUS current
            DESCRIPTION
                "L1 input power factor. Multi:100"
            ::= { hwPDU8000SingleEntry 29 }

        hwPDU8000SingleL2inputpowerfactor OBJECT-TYPE
            SYNTAX Integer32 (-1..1)
            MAX-ACCESS read-only
            STATUS current
            DESCRIPTION
                "L2 input power factor. Multi:100"
            ::= { hwPDU8000SingleEntry 30 }

        hwPDU8000SingleL3inputpowerfactor OBJECT-TYPE
            SYNTAX Integer32 (-1..1)
            MAX-ACCESS read-only
            STATUS current
            DESCRIPTION
                "L3 input power factor. Multi:100"
            ::= { hwPDU8000SingleEntry 31 }

        hwPDU8000Singleinputactiveelectricenergy OBJECT-TYPE
            SYNTAX Integer32 (0..21474836)
            MAX-ACCESS read-only
            STATUS current
            DESCRIPTION
                "input active electric energy. Unit:kWh. Multi:100"
            ::= { hwPDU8000SingleEntry 32 }

        hwPDU8000SingleL1inputpowerloadrate OBJECT-TYPE
            SYNTAX Unsigned32 (0..150)
            MAX-ACCESS read-only
            STATUS current
            DESCRIPTION
                "L1 input power load rate. Unit:%."
            ::= { hwPDU8000SingleEntry 33 }

        hwPDU8000SingleL2inputpowerloadrate OBJECT-TYPE
            SYNTAX Unsigned32 (0..150)
            MAX-ACCESS read-only
            STATUS current
            DESCRIPTION
                "L2 input power load rate. Unit:%."
            ::= { hwPDU8000SingleEntry 34 }

        hwPDU8000SingleL3inputpowerloadrate OBJECT-TYPE
            SYNTAX Unsigned32 (0..150)
            MAX-ACCESS read-only
            STATUS current
            DESCRIPTION
                "L3 input power load rate. Unit:%."
            ::= { hwPDU8000SingleEntry 35 }

        hwPDU8000SingleNwirecurrent OBJECT-TYPE
            SYNTAX Integer32 (0..1000)
            MAX-ACCESS read-only
            STATUS current
            DESCRIPTION
                "N wire current. Unit:A. Multi:10"
            ::= { hwPDU8000SingleEntry 36 }

        hwPDU8000SingleL1THDurate OBJECT-TYPE
            SYNTAX Integer32 (0..100)
            MAX-ACCESS read-only
            STATUS current
            DESCRIPTION
                "L1 THD-u rate. Unit:%. Multi:100"
            ::= { hwPDU8000SingleEntry 37 }

        hwPDU8000SingleL2THDurate OBJECT-TYPE
            SYNTAX Integer32 (0..100)
            MAX-ACCESS read-only
            STATUS current
            DESCRIPTION
                "L2 THD-u rate. Unit:%. Multi:100"
            ::= { hwPDU8000SingleEntry 38 }

        hwPDU8000SingleL3THDurate OBJECT-TYPE
            SYNTAX Integer32 (0..100)
            MAX-ACCESS read-only
            STATUS current
            DESCRIPTION
                "L3 THD-u rate. Unit:%. Multi:100"
            ::= { hwPDU8000SingleEntry 39 }

        hwPDU8000SingleL1THDirate OBJECT-TYPE
            SYNTAX Integer32 (0..100)
            MAX-ACCESS read-only
            STATUS current
            DESCRIPTION
                "L1 THD-i rate. Unit:%. Multi:100"
            ::= { hwPDU8000SingleEntry 40 }

        hwPDU8000SingleL2THDirate OBJECT-TYPE
            SYNTAX Integer32 (0..100)
            MAX-ACCESS read-only
            STATUS current
            DESCRIPTION
                "L2 THD-i rate. Unit:%. Multi:100"
            ::= { hwPDU8000SingleEntry 41 }

        hwPDU8000SingleL3THDirate OBJECT-TYPE
            SYNTAX Integer32 (0..100)
            MAX-ACCESS read-only
            STATUS current
            DESCRIPTION
                "L3 THD-i rate. Unit:%. Multi:100"
            ::= { hwPDU8000SingleEntry 42 }

        hwPDU8000Singletotalinputactivepower OBJECT-TYPE
            SYNTAX Integer32 (-750..750)
            MAX-ACCESS read-only
            STATUS current
            DESCRIPTION
                "total input active power. Unit:kW. Multi:10"
            ::= { hwPDU8000SingleEntry 43 }

        hwPDU8000Singletotalinputapparentpower OBJECT-TYPE
            SYNTAX Integer32 (-750..750)
            MAX-ACCESS read-only
            STATUS current
            DESCRIPTION
                "total input apparent power. Unit:kVA. Multi:10"
            ::= { hwPDU8000SingleEntry 44 }

        hwPDU8000Singletotalinputreactivepower OBJECT-TYPE
            SYNTAX Integer32 (-750..750)
            MAX-ACCESS read-only
            STATUS current
            DESCRIPTION
                "total input reactive power. Unit:kVAR. Multi:10"
            ::= { hwPDU8000SingleEntry 45 }

        hwPDU8000SingleRowStatus OBJECT-TYPE
            SYNTAX RowStatus
            MAX-ACCESS read-only
            STATUS current
            DESCRIPTION
                "The RowStatus of PDU8000 Single."
            ::= { hwPDU8000SingleEntry 100 }

        hwPDU8000SingleMode1_2Table OBJECT-TYPE
            SYNTAX SEQUENCE OF HwPDU8000SingleMode1_2Entry
            MAX-ACCESS not-accessible
             STATUS current
             DESCRIPTION
                "The table of PDU8000 Single Mode 1 and 2."
            ::= { hwPDU8000Single 2 }

        hwPDU8000SingleMode1_2Entry OBJECT-TYPE
                        SYNTAX HwPDU8000SingleMode1_2Entry
            MAX-ACCESS not-accessible
             STATUS current
             DESCRIPTION
                "The table of PDU8000 Single Mode 1 and 2."
            INDEX { hwPDU8000SingleMode1_2Index }
            ::= { hwPDU8000SingleMode1_2Table 1 }

        HwPDU8000SingleMode1_2Entry            ::= SEQUENCE {
                hwPDU8000SingleMode1_2Index
                    Unsigned32,
                hwPDU8000SingleMod1Branch1L1outputactiveelectricenergy
                    Integer32,
                hwPDU8000SingleMod1Branch1L2outputactiveelectricenergy
                    Integer32,
                hwPDU8000SingleMod1Branch1L3outputactiveelectricenergy
                    Integer32,
                hwPDU8000SingleMod1Branch2L1outputactiveelectricenergy
                    Integer32,
                hwPDU8000SingleMod1Branch2L2outputactiveelectricenergy
                    Integer32,
                hwPDU8000SingleMod1Branch2L3outputactiveelectricenergy
                    Integer32,
                hwPDU8000SingleMod1Branch3L1outputactiveelectricenergy
                    Integer32,
                hwPDU8000SingleMod1Branch3L2outputactiveelectricenergy
                    Integer32,
                hwPDU8000SingleMod1Branch3L3outputactiveelectricenergy
                    Integer32,
                hwPDU8000SingleMod1Branch4L1outputactiveelectricenergy
                    Integer32,
                hwPDU8000SingleMod1Branch4L2outputactiveelectricenergy
                    Integer32,
                hwPDU8000SingleMod1Branch4L3outputactiveelectricenergy
                    Integer32,
                hwPDU8000SingleMod1Branch5L1outputactiveelectricenergy
                    Integer32,
                hwPDU8000SingleMod1Branch5L2outputactiveelectricenergy
                    Integer32,
                hwPDU8000SingleMod1Branch5L3outputactiveelectricenergy
                    Integer32,
                hwPDU8000SingleMod1Branch6L1outputactiveelectricenergy
                    Integer32,
                hwPDU8000SingleMod1Branch6L2outputactiveelectricenergy
                    Integer32,
                hwPDU8000SingleMod1Branch6L3outputactiveelectricenergy
                    Integer32,
                hwPDU8000SingleMod1Branch7L1outputactiveelectricenergy
                    Integer32,
                hwPDU8000SingleMod1Branch7L2outputactiveelectricenergy
                    Integer32,
                hwPDU8000SingleMod1Branch7L3outputactiveelectricenergy
                    Integer32,
                hwPDU8000SingleMod1Branch8L1outputactiveelectricenergy
                    Integer32,
                hwPDU8000SingleMod1Branch8L2outputactiveelectricenergy
                    Integer32,
                hwPDU8000SingleMod1Branch8L3outputactiveelectricenergy
                    Integer32,
                hwPDU8000SingleMod1Branch9L1outputactiveelectricenergy
                    Integer32,
                hwPDU8000SingleMod1Branch9L2outputactiveelectricenergy
                    Integer32,
                hwPDU8000SingleMod1Branch9L3outputactiveelectricenergy
                    Integer32,
                hwPDU8000SingleMod1Branch10L1outputactiveelectricenergy
                    Integer32,
                hwPDU8000SingleMod1Branch10L2outputactiveelectricenergy
                    Integer32,
                hwPDU8000SingleMod1Branch10L3outputactiveelectricenergy
                    Integer32,
                hwPDU8000SingleMod1Branch11L1outputactiveelectricenergy
                    Integer32,
                hwPDU8000SingleMod1Branch11L2outputactiveelectricenergy
                    Integer32,
                hwPDU8000SingleMod1Branch11L3outputactiveelectricenergy
                    Integer32,
                hwPDU8000SingleMod1Branch12L1outputactiveelectricenergy
                    Integer32,
                hwPDU8000SingleMod1Branch12L2outputactiveelectricenergy
                    Integer32,
                hwPDU8000SingleMod1Branch12L3outputactiveelectricenergy
                    Integer32,
                hwPDU8000SingleMod2Branch1L1outputactiveelectricenergy
                    Integer32,
                hwPDU8000SingleMod2Branch1L2outputactiveelectricenergy
                    Integer32,
                hwPDU8000SingleMod2Branch1L3outputactiveelectricenergy
                    Integer32,
                hwPDU8000SingleMod2Branch2L1outputactiveelectricenergy
                    Integer32,
                hwPDU8000SingleMod2Branch2L2outputactiveelectricenergy
                    Integer32,
                hwPDU8000SingleMod2Branch2L3outputactiveelectricenergy
                    Integer32,
                hwPDU8000SingleMod2Branch3L1outputactiveelectricenergy
                    Integer32,
                hwPDU8000SingleMod2Branch3L2outputactiveelectricenergy
                    Integer32,
                hwPDU8000SingleMod2Branch3L3outputactiveelectricenergy
                    Integer32,
                hwPDU8000SingleMod2Branch4L1outputactiveelectricenergy
                    Integer32,
                hwPDU8000SingleMod2Branch4L2outputactiveelectricenergy
                    Integer32,
                hwPDU8000SingleMod2Branch4L3outputactiveelectricenergy
                    Integer32,
                hwPDU8000SingleMod2Branch5L1outputactiveelectricenergy
                    Integer32,
                hwPDU8000SingleMod2Branch5L2outputactiveelectricenergy
                    Integer32,
                hwPDU8000SingleMod2Branch5L3outputactiveelectricenergy
                    Integer32,
                hwPDU8000SingleMod2Branch6L1outputactiveelectricenergy
                    Integer32,
                hwPDU8000SingleMod2Branch6L2outputactiveelectricenergy
                    Integer32,
                hwPDU8000SingleMod2Branch6L3outputactiveelectricenergy
                    Integer32,
                hwPDU8000SingleMod2Branch7L1outputactiveelectricenergy
                    Integer32,
                hwPDU8000SingleMod2Branch7L2outputactiveelectricenergy
                    Integer32,
                hwPDU8000SingleMod2Branch7L3outputactiveelectricenergy
                    Integer32,
                hwPDU8000SingleMod2Branch8L1outputactiveelectricenergy
                    Integer32,
                hwPDU8000SingleMod2Branch8L2outputactiveelectricenergy
                    Integer32,
                hwPDU8000SingleMod2Branch8L3outputactiveelectricenergy
                    Integer32,
                hwPDU8000SingleMod2Branch9L1outputactiveelectricenergy
                    Integer32,
                hwPDU8000SingleMod2Branch9L2outputactiveelectricenergy
                    Integer32,
                hwPDU8000SingleMod2Branch9L3outputactiveelectricenergy
                    Integer32,
                hwPDU8000SingleMod2Branch10L1outputactiveelectricenergy
                    Integer32,
                hwPDU8000SingleMod2Branch10L2outputactiveelectricenergy
                    Integer32,
                hwPDU8000SingleMod2Branch10L3outputactiveelectricenergy
                    Integer32,
                hwPDU8000SingleMod2Branch11L1outputactiveelectricenergy
                    Integer32,
                hwPDU8000SingleMod2Branch11L2outputactiveelectricenergy
                    Integer32,
                hwPDU8000SingleMod2Branch11L3outputactiveelectricenergy
                    Integer32,
                hwPDU8000SingleMod2Branch12L1outputactiveelectricenergy
                    Integer32,
                hwPDU8000SingleMod2Branch12L2outputactiveelectricenergy
                    Integer32,
                hwPDU8000SingleMod2Branch12L3outputactiveelectricenergy
                    Integer32,
                hwPDU8000SingleMode1_2RowStatus
                    RowStatus
            }

        hwPDU8000SingleMode1_2Index OBJECT-TYPE
            SYNTAX Unsigned32
            MAX-ACCESS read-only
            STATUS current
            DESCRIPTION
                "The equip id of PDU8000 Single Mode 1 and 2."
            ::= { hwPDU8000SingleMode1_2Entry 1 }

        hwPDU8000SingleMod1Branch1L1outputactiveelectricenergy OBJECT-TYPE
            SYNTAX Integer32 (0..21474836)
            MAX-ACCESS read-only
            STATUS current
            DESCRIPTION
                "Branch 1 L1 output active electric energy. Unit:KWh. Multi:100"
            ::= { hwPDU8000SingleMode1_2Entry 2 }

        hwPDU8000SingleMod1Branch1L2outputactiveelectricenergy OBJECT-TYPE
            SYNTAX Integer32 (0..21474836)
            MAX-ACCESS read-only
            STATUS current
            DESCRIPTION
                "Branch 1 L2 output active electric energy. Unit:KWh. Multi:100"
            ::= { hwPDU8000SingleMode1_2Entry 3 }

        hwPDU8000SingleMod1Branch1L3outputactiveelectricenergy OBJECT-TYPE
            SYNTAX Integer32 (0..21474836)
            MAX-ACCESS read-only
            STATUS current
            DESCRIPTION
                "Branch 1 L3 output active electric energy. Unit:KWh. Multi:100"
            ::= { hwPDU8000SingleMode1_2Entry 4 }

        hwPDU8000SingleMod1Branch2L1outputactiveelectricenergy OBJECT-TYPE
            SYNTAX Integer32 (0..21474836)
            MAX-ACCESS read-only
            STATUS current
            DESCRIPTION
                "Branch 2 L1 output active electric energy. Unit:KWh. Multi:100"
            ::= { hwPDU8000SingleMode1_2Entry 5 }

        hwPDU8000SingleMod1Branch2L2outputactiveelectricenergy OBJECT-TYPE
            SYNTAX Integer32 (0..21474836)
            MAX-ACCESS read-only
            STATUS current
            DESCRIPTION
                "Branch 2 L2 output active electric energy. Unit:KWh. Multi:100"
            ::= { hwPDU8000SingleMode1_2Entry 6 }

        hwPDU8000SingleMod1Branch2L3outputactiveelectricenergy OBJECT-TYPE
            SYNTAX Integer32 (0..21474836)
            MAX-ACCESS read-only
            STATUS current
            DESCRIPTION
                "Branch 2 L3 output active electric energy. Unit:KWh. Multi:100"
            ::= { hwPDU8000SingleMode1_2Entry 7 }

        hwPDU8000SingleMod1Branch3L1outputactiveelectricenergy OBJECT-TYPE
            SYNTAX Integer32 (0..21474836)
            MAX-ACCESS read-only
            STATUS current
            DESCRIPTION
                "Branch 3 L1 output active electric energy. Unit:KWh. Multi:100"
            ::= { hwPDU8000SingleMode1_2Entry 8 }

        hwPDU8000SingleMod1Branch3L2outputactiveelectricenergy OBJECT-TYPE
            SYNTAX Integer32 (0..21474836)
            MAX-ACCESS read-only
            STATUS current
            DESCRIPTION
                "Branch 3 L2 output active electric energy. Unit:KWh. Multi:100"
            ::= { hwPDU8000SingleMode1_2Entry 9 }

        hwPDU8000SingleMod1Branch3L3outputactiveelectricenergy OBJECT-TYPE
            SYNTAX Integer32 (0..21474836)
            MAX-ACCESS read-only
            STATUS current
            DESCRIPTION
                "Branch 3 L3 output active electric energy. Unit:KWh. Multi:100"
            ::= { hwPDU8000SingleMode1_2Entry 10 }

        hwPDU8000SingleMod1Branch4L1outputactiveelectricenergy OBJECT-TYPE
            SYNTAX Integer32 (0..21474836)
            MAX-ACCESS read-only
            STATUS current
            DESCRIPTION
                "Branch 4 L1 output active electric energy. Unit:KWh. Multi:100"
            ::= { hwPDU8000SingleMode1_2Entry 11 }

        hwPDU8000SingleMod1Branch4L2outputactiveelectricenergy OBJECT-TYPE
            SYNTAX Integer32 (0..21474836)
            MAX-ACCESS read-only
            STATUS current
            DESCRIPTION
                "Branch 4 L2 output active electric energy. Unit:KWh. Multi:100"
            ::= { hwPDU8000SingleMode1_2Entry 12 }

        hwPDU8000SingleMod1Branch4L3outputactiveelectricenergy OBJECT-TYPE
            SYNTAX Integer32 (0..21474836)
            MAX-ACCESS read-only
            STATUS current
            DESCRIPTION
                "Branch 4 L3 output active electric energy. Unit:KWh. Multi:100"
            ::= { hwPDU8000SingleMode1_2Entry 13 }

        hwPDU8000SingleMod1Branch5L1outputactiveelectricenergy OBJECT-TYPE
            SYNTAX Integer32 (0..21474836)
            MAX-ACCESS read-only
            STATUS current
            DESCRIPTION
                "Branch 5 L1 output active electric energy. Unit:KWh. Multi:100"
            ::= { hwPDU8000SingleMode1_2Entry 14 }

        hwPDU8000SingleMod1Branch5L2outputactiveelectricenergy OBJECT-TYPE
            SYNTAX Integer32 (0..21474836)
            MAX-ACCESS read-only
            STATUS current
            DESCRIPTION
                "Branch 5 L2 output active electric energy. Unit:KWh. Multi:100"
            ::= { hwPDU8000SingleMode1_2Entry 15 }

        hwPDU8000SingleMod1Branch5L3outputactiveelectricenergy OBJECT-TYPE
            SYNTAX Integer32 (0..21474836)
            MAX-ACCESS read-only
            STATUS current
            DESCRIPTION
                "Branch 5 L3 output active electric energy. Unit:KWh. Multi:100"
            ::= { hwPDU8000SingleMode1_2Entry 16 }

        hwPDU8000SingleMod1Branch6L1outputactiveelectricenergy OBJECT-TYPE
            SYNTAX Integer32 (0..21474836)
            MAX-ACCESS read-only
            STATUS current
            DESCRIPTION
                "Branch 6 L1 output active electric energy. Unit:KWh. Multi:100"
            ::= { hwPDU8000SingleMode1_2Entry 17 }

        hwPDU8000SingleMod1Branch6L2outputactiveelectricenergy OBJECT-TYPE
            SYNTAX Integer32 (0..21474836)
            MAX-ACCESS read-only
            STATUS current
            DESCRIPTION
                "Branch 6 L2 output active electric energy. Unit:KWh. Multi:100"
            ::= { hwPDU8000SingleMode1_2Entry 18 }

        hwPDU8000SingleMod1Branch6L3outputactiveelectricenergy OBJECT-TYPE
            SYNTAX Integer32 (0..21474836)
            MAX-ACCESS read-only
            STATUS current
            DESCRIPTION
                "Branch 6 L3 output active electric energy. Unit:KWh. Multi:100"
            ::= { hwPDU8000SingleMode1_2Entry 19 }

        hwPDU8000SingleMod1Branch7L1outputactiveelectricenergy OBJECT-TYPE
            SYNTAX Integer32 (0..21474836)
            MAX-ACCESS read-only
            STATUS current
            DESCRIPTION
                "Branch 7 L1 output active electric energy. Unit:KWh. Multi:100"
            ::= { hwPDU8000SingleMode1_2Entry 20 }

        hwPDU8000SingleMod1Branch7L2outputactiveelectricenergy OBJECT-TYPE
            SYNTAX Integer32 (0..21474836)
            MAX-ACCESS read-only
            STATUS current
            DESCRIPTION
                "Branch 7 L2 output active electric energy. Unit:KWh. Multi:100"
            ::= { hwPDU8000SingleMode1_2Entry 21 }

        hwPDU8000SingleMod1Branch7L3outputactiveelectricenergy OBJECT-TYPE
            SYNTAX Integer32 (0..21474836)
            MAX-ACCESS read-only
            STATUS current
            DESCRIPTION
                "Branch 7 L3 output active electric energy. Unit:KWh. Multi:100"
            ::= { hwPDU8000SingleMode1_2Entry 22 }

        hwPDU8000SingleMod1Branch8L1outputactiveelectricenergy OBJECT-TYPE
            SYNTAX Integer32 (0..21474836)
            MAX-ACCESS read-only
            STATUS current
            DESCRIPTION
                "Branch 8 L1 output active electric energy. Unit:KWh. Multi:100"
            ::= { hwPDU8000SingleMode1_2Entry 23 }

        hwPDU8000SingleMod1Branch8L2outputactiveelectricenergy OBJECT-TYPE
            SYNTAX Integer32 (0..21474836)
            MAX-ACCESS read-only
            STATUS current
            DESCRIPTION
                "Branch 8 L2 output active electric energy. Unit:KWh. Multi:100"
            ::= { hwPDU8000SingleMode1_2Entry 24 }

        hwPDU8000SingleMod1Branch8L3outputactiveelectricenergy OBJECT-TYPE
            SYNTAX Integer32 (0..21474836)
            MAX-ACCESS read-only
            STATUS current
            DESCRIPTION
                "Branch 8 L3 output active electric energy. Unit:KWh. Multi:100"
            ::= { hwPDU8000SingleMode1_2Entry 25 }

        hwPDU8000SingleMod1Branch9L1outputactiveelectricenergy OBJECT-TYPE
            SYNTAX Integer32 (0..21474836)
            MAX-ACCESS read-only
            STATUS current
            DESCRIPTION
                "Branch 9 L1 output active electric energy. Unit:KWh. Multi:100"
            ::= { hwPDU8000SingleMode1_2Entry 26 }

        hwPDU8000SingleMod1Branch9L2outputactiveelectricenergy OBJECT-TYPE
            SYNTAX Integer32 (0..21474836)
            MAX-ACCESS read-only
            STATUS current
            DESCRIPTION
                "Branch 9 L2 output active electric energy. Unit:KWh. Multi:100"
            ::= { hwPDU8000SingleMode1_2Entry 27 }

        hwPDU8000SingleMod1Branch9L3outputactiveelectricenergy OBJECT-TYPE
            SYNTAX Integer32 (0..21474836)
            MAX-ACCESS read-only
            STATUS current
            DESCRIPTION
                "Branch 9 L3 output active electric energy. Unit:KWh. Multi:100"
            ::= { hwPDU8000SingleMode1_2Entry 28 }

        hwPDU8000SingleMod1Branch10L1outputactiveelectricenergy OBJECT-TYPE
            SYNTAX Integer32 (0..21474836)
            MAX-ACCESS read-only
            STATUS current
            DESCRIPTION
                "Branch 10 L1 output active electric energy. Unit:KWh. Multi:100"
            ::= { hwPDU8000SingleMode1_2Entry 29 }

        hwPDU8000SingleMod1Branch10L2outputactiveelectricenergy OBJECT-TYPE
            SYNTAX Integer32 (0..21474836)
            MAX-ACCESS read-only
            STATUS current
            DESCRIPTION
                "Branch 10 L2 output active electric energy. Unit:KWh. Multi:100"
            ::= { hwPDU8000SingleMode1_2Entry 30 }

        hwPDU8000SingleMod1Branch10L3outputactiveelectricenergy OBJECT-TYPE
            SYNTAX Integer32 (0..21474836)
            MAX-ACCESS read-only
            STATUS current
            DESCRIPTION
                "Branch 10 L3 output active electric energy. Unit:KWh. Multi:100"
            ::= { hwPDU8000SingleMode1_2Entry 31 }

        hwPDU8000SingleMod1Branch11L1outputactiveelectricenergy OBJECT-TYPE
            SYNTAX Integer32 (0..21474836)
            MAX-ACCESS read-only
            STATUS current
            DESCRIPTION
                "Branch 11 L1 output active electric energy. Unit:KWh. Multi:100"
            ::= { hwPDU8000SingleMode1_2Entry 32 }

        hwPDU8000SingleMod1Branch11L2outputactiveelectricenergy OBJECT-TYPE
            SYNTAX Integer32 (0..21474836)
            MAX-ACCESS read-only
            STATUS current
            DESCRIPTION
                "Branch 11 L2 output active electric energy. Unit:KWh. Multi:100"
            ::= { hwPDU8000SingleMode1_2Entry 33 }

        hwPDU8000SingleMod1Branch11L3outputactiveelectricenergy OBJECT-TYPE
            SYNTAX Integer32 (0..21474836)
            MAX-ACCESS read-only
            STATUS current
            DESCRIPTION
                "Branch 11 L3 output active electric energy. Unit:KWh. Multi:100"
            ::= { hwPDU8000SingleMode1_2Entry 34 }

        hwPDU8000SingleMod1Branch12L1outputactiveelectricenergy OBJECT-TYPE
            SYNTAX Integer32 (0..21474836)
            MAX-ACCESS read-only
            STATUS current
            DESCRIPTION
                "Branch 12 L1 output active electric energy. Unit:KWh. Multi:100"
            ::= { hwPDU8000SingleMode1_2Entry 35 }

        hwPDU8000SingleMod1Branch12L2outputactiveelectricenergy OBJECT-TYPE
            SYNTAX Integer32 (0..21474836)
            MAX-ACCESS read-only
            STATUS current
            DESCRIPTION
                "Branch 12 L2 output active electric energy. Unit:KWh. Multi:100"
            ::= { hwPDU8000SingleMode1_2Entry 36 }

        hwPDU8000SingleMod1Branch12L3outputactiveelectricenergy OBJECT-TYPE
            SYNTAX Integer32 (0..21474836)
            MAX-ACCESS read-only
            STATUS current
            DESCRIPTION
                "Branch 12 L3 output active electric energy. Unit:KWh. Multi:100"
            ::= { hwPDU8000SingleMode1_2Entry 37 }

        hwPDU8000SingleMod2Branch1L1outputactiveelectricenergy OBJECT-TYPE
            SYNTAX Integer32 (0..21474836)
            MAX-ACCESS read-only
            STATUS current
            DESCRIPTION
                "Branch 1 L1 output active electric energy. Unit:KWh. Multi:100"
            ::= { hwPDU8000SingleMode1_2Entry 38 }

        hwPDU8000SingleMod2Branch1L2outputactiveelectricenergy OBJECT-TYPE
            SYNTAX Integer32 (0..21474836)
            MAX-ACCESS read-only
            STATUS current
            DESCRIPTION
                "Branch 1 L2 output active electric energy. Unit:KWh. Multi:100"
            ::= { hwPDU8000SingleMode1_2Entry 39 }

        hwPDU8000SingleMod2Branch1L3outputactiveelectricenergy OBJECT-TYPE
            SYNTAX Integer32 (0..21474836)
            MAX-ACCESS read-only
            STATUS current
            DESCRIPTION
                "Branch 1 L3 output active electric energy. Unit:KWh. Multi:100"
            ::= { hwPDU8000SingleMode1_2Entry 40 }

        hwPDU8000SingleMod2Branch2L1outputactiveelectricenergy OBJECT-TYPE
            SYNTAX Integer32 (0..21474836)
            MAX-ACCESS read-only
            STATUS current
            DESCRIPTION
                "Branch 2 L1 output active electric energy. Unit:KWh. Multi:100"
            ::= { hwPDU8000SingleMode1_2Entry 41 }

        hwPDU8000SingleMod2Branch2L2outputactiveelectricenergy OBJECT-TYPE
            SYNTAX Integer32 (0..21474836)
            MAX-ACCESS read-only
            STATUS current
            DESCRIPTION
                "Branch 2 L2 output active electric energy. Unit:KWh. Multi:100"
            ::= { hwPDU8000SingleMode1_2Entry 42 }

        hwPDU8000SingleMod2Branch2L3outputactiveelectricenergy OBJECT-TYPE
            SYNTAX Integer32 (0..21474836)
            MAX-ACCESS read-only
            STATUS current
            DESCRIPTION
                "Branch 2 L3 output active electric energy. Unit:KWh. Multi:100"
            ::= { hwPDU8000SingleMode1_2Entry 43 }

        hwPDU8000SingleMod2Branch3L1outputactiveelectricenergy OBJECT-TYPE
            SYNTAX Integer32 (0..21474836)
            MAX-ACCESS read-only
            STATUS current
            DESCRIPTION
                "Branch 3 L1 output active electric energy. Unit:KWh. Multi:100"
            ::= { hwPDU8000SingleMode1_2Entry 44 }

        hwPDU8000SingleMod2Branch3L2outputactiveelectricenergy OBJECT-TYPE
            SYNTAX Integer32 (0..21474836)
            MAX-ACCESS read-only
            STATUS current
            DESCRIPTION
                "Branch 3 L2 output active electric energy. Unit:KWh. Multi:100"
            ::= { hwPDU8000SingleMode1_2Entry 45 }

        hwPDU8000SingleMod2Branch3L3outputactiveelectricenergy OBJECT-TYPE
            SYNTAX Integer32 (0..21474836)
            MAX-ACCESS read-only
            STATUS current
            DESCRIPTION
                "Branch 3 L3 output active electric energy. Unit:KWh. Multi:100"
            ::= { hwPDU8000SingleMode1_2Entry 46 }

        hwPDU8000SingleMod2Branch4L1outputactiveelectricenergy OBJECT-TYPE
            SYNTAX Integer32 (0..21474836)
            MAX-ACCESS read-only
            STATUS current
            DESCRIPTION
                "Branch 4 L1 output active electric energy. Unit:KWh. Multi:100"
            ::= { hwPDU8000SingleMode1_2Entry 47 }

        hwPDU8000SingleMod2Branch4L2outputactiveelectricenergy OBJECT-TYPE
            SYNTAX Integer32 (0..21474836)
            MAX-ACCESS read-only
            STATUS current
            DESCRIPTION
                "Branch 4 L2 output active electric energy. Unit:KWh. Multi:100"
            ::= { hwPDU8000SingleMode1_2Entry 48 }

        hwPDU8000SingleMod2Branch4L3outputactiveelectricenergy OBJECT-TYPE
            SYNTAX Integer32 (0..21474836)
            MAX-ACCESS read-only
            STATUS current
            DESCRIPTION
                "Branch 4 L3 output active electric energy. Unit:KWh. Multi:100"
            ::= { hwPDU8000SingleMode1_2Entry 49 }

        hwPDU8000SingleMod2Branch5L1outputactiveelectricenergy OBJECT-TYPE
            SYNTAX Integer32 (0..21474836)
            MAX-ACCESS read-only
            STATUS current
            DESCRIPTION
                "Branch 5 L1 output active electric energy. Unit:KWh. Multi:100"
            ::= { hwPDU8000SingleMode1_2Entry 50 }

        hwPDU8000SingleMod2Branch5L2outputactiveelectricenergy OBJECT-TYPE
            SYNTAX Integer32 (0..21474836)
            MAX-ACCESS read-only
            STATUS current
            DESCRIPTION
                "Branch 5 L2 output active electric energy. Unit:KWh. Multi:100"
            ::= { hwPDU8000SingleMode1_2Entry 51 }

        hwPDU8000SingleMod2Branch5L3outputactiveelectricenergy OBJECT-TYPE
            SYNTAX Integer32 (0..21474836)
            MAX-ACCESS read-only
            STATUS current
            DESCRIPTION
                "Branch 5 L3 output active electric energy. Unit:KWh. Multi:100"
            ::= { hwPDU8000SingleMode1_2Entry 52 }

        hwPDU8000SingleMod2Branch6L1outputactiveelectricenergy OBJECT-TYPE
            SYNTAX Integer32 (0..21474836)
            MAX-ACCESS read-only
            STATUS current
            DESCRIPTION
                "Branch 6 L1 output active electric energy. Unit:KWh. Multi:100"
            ::= { hwPDU8000SingleMode1_2Entry 53 }

        hwPDU8000SingleMod2Branch6L2outputactiveelectricenergy OBJECT-TYPE
            SYNTAX Integer32 (0..21474836)
            MAX-ACCESS read-only
            STATUS current
            DESCRIPTION
                "Branch 6 L2 output active electric energy. Unit:KWh. Multi:100"
            ::= { hwPDU8000SingleMode1_2Entry 54 }

        hwPDU8000SingleMod2Branch6L3outputactiveelectricenergy OBJECT-TYPE
            SYNTAX Integer32 (0..21474836)
            MAX-ACCESS read-only
            STATUS current
            DESCRIPTION
                "Branch 6 L3 output active electric energy. Unit:KWh. Multi:100"
            ::= { hwPDU8000SingleMode1_2Entry 55 }

        hwPDU8000SingleMod2Branch7L1outputactiveelectricenergy OBJECT-TYPE
            SYNTAX Integer32 (0..21474836)
            MAX-ACCESS read-only
            STATUS current
            DESCRIPTION
                "Branch 7 L1 output active electric energy. Unit:KWh. Multi:100"
            ::= { hwPDU8000SingleMode1_2Entry 56 }

        hwPDU8000SingleMod2Branch7L2outputactiveelectricenergy OBJECT-TYPE
            SYNTAX Integer32 (0..21474836)
            MAX-ACCESS read-only
            STATUS current
            DESCRIPTION
                "Branch 7 L2 output active electric energy. Unit:KWh. Multi:100"
            ::= { hwPDU8000SingleMode1_2Entry 57 }

        hwPDU8000SingleMod2Branch7L3outputactiveelectricenergy OBJECT-TYPE
            SYNTAX Integer32 (0..21474836)
            MAX-ACCESS read-only
            STATUS current
            DESCRIPTION
                "Branch 7 L3 output active electric energy. Unit:KWh. Multi:100"
            ::= { hwPDU8000SingleMode1_2Entry 58 }

        hwPDU8000SingleMod2Branch8L1outputactiveelectricenergy OBJECT-TYPE
            SYNTAX Integer32 (0..21474836)
            MAX-ACCESS read-only
            STATUS current
            DESCRIPTION
                "Branch 8 L1 output active electric energy. Unit:KWh. Multi:100"
            ::= { hwPDU8000SingleMode1_2Entry 59 }

        hwPDU8000SingleMod2Branch8L2outputactiveelectricenergy OBJECT-TYPE
            SYNTAX Integer32 (0..21474836)
            MAX-ACCESS read-only
            STATUS current
            DESCRIPTION
                "Branch 8 L2 output active electric energy. Unit:KWh. Multi:100"
            ::= { hwPDU8000SingleMode1_2Entry 60 }

        hwPDU8000SingleMod2Branch8L3outputactiveelectricenergy OBJECT-TYPE
            SYNTAX Integer32 (0..21474836)
            MAX-ACCESS read-only
            STATUS current
            DESCRIPTION
                "Branch 8 L3 output active electric energy. Unit:KWh. Multi:100"
            ::= { hwPDU8000SingleMode1_2Entry 61 }

        hwPDU8000SingleMod2Branch9L1outputactiveelectricenergy OBJECT-TYPE
            SYNTAX Integer32 (0..21474836)
            MAX-ACCESS read-only
            STATUS current
            DESCRIPTION
                "Branch 9 L1 output active electric energy. Unit:KWh. Multi:100"
            ::= { hwPDU8000SingleMode1_2Entry 62 }

        hwPDU8000SingleMod2Branch9L2outputactiveelectricenergy OBJECT-TYPE
            SYNTAX Integer32 (0..21474836)
            MAX-ACCESS read-only
            STATUS current
            DESCRIPTION
                "Branch 9 L2 output active electric energy. Unit:KWh. Multi:100"
            ::= { hwPDU8000SingleMode1_2Entry 63 }

        hwPDU8000SingleMod2Branch9L3outputactiveelectricenergy OBJECT-TYPE
            SYNTAX Integer32 (0..21474836)
            MAX-ACCESS read-only
            STATUS current
            DESCRIPTION
                "Branch 9 L3 output active electric energy. Unit:KWh. Multi:100"
            ::= { hwPDU8000SingleMode1_2Entry 64 }

        hwPDU8000SingleMod2Branch10L1outputactiveelectricenergy OBJECT-TYPE
            SYNTAX Integer32 (0..21474836)
            MAX-ACCESS read-only
            STATUS current
            DESCRIPTION
                "Branch 10 L1 output active electric energy. Unit:KWh. Multi:100"
            ::= { hwPDU8000SingleMode1_2Entry 65 }

        hwPDU8000SingleMod2Branch10L2outputactiveelectricenergy OBJECT-TYPE
            SYNTAX Integer32 (0..21474836)
            MAX-ACCESS read-only
            STATUS current
            DESCRIPTION
                "Branch 10 L2 output active electric energy. Unit:KWh. Multi:100"
            ::= { hwPDU8000SingleMode1_2Entry 66 }

        hwPDU8000SingleMod2Branch10L3outputactiveelectricenergy OBJECT-TYPE
            SYNTAX Integer32 (0..21474836)
            MAX-ACCESS read-only
            STATUS current
            DESCRIPTION
                "Branch 10 L3 output active electric energy. Unit:KWh. Multi:100"
            ::= { hwPDU8000SingleMode1_2Entry 67 }

        hwPDU8000SingleMod2Branch11L1outputactiveelectricenergy OBJECT-TYPE
            SYNTAX Integer32 (0..21474836)
            MAX-ACCESS read-only
            STATUS current
            DESCRIPTION
                "Branch 11 L1 output active electric energy. Unit:KWh. Multi:100"
            ::= { hwPDU8000SingleMode1_2Entry 68 }

        hwPDU8000SingleMod2Branch11L2outputactiveelectricenergy OBJECT-TYPE
            SYNTAX Integer32 (0..21474836)
            MAX-ACCESS read-only
            STATUS current
            DESCRIPTION
                "Branch 11 L2 output active electric energy. Unit:KWh. Multi:100"
            ::= { hwPDU8000SingleMode1_2Entry 69 }

        hwPDU8000SingleMod2Branch11L3outputactiveelectricenergy OBJECT-TYPE
            SYNTAX Integer32 (0..21474836)
            MAX-ACCESS read-only
            STATUS current
            DESCRIPTION
                "Branch 11 L3 output active electric energy. Unit:KWh. Multi:100"
            ::= { hwPDU8000SingleMode1_2Entry 70 }

        hwPDU8000SingleMod2Branch12L1outputactiveelectricenergy OBJECT-TYPE
            SYNTAX Integer32 (0..21474836)
            MAX-ACCESS read-only
            STATUS current
            DESCRIPTION
                "Branch 12 L1 output active electric energy. Unit:KWh. Multi:100"
            ::= { hwPDU8000SingleMode1_2Entry 71 }

        hwPDU8000SingleMod2Branch12L2outputactiveelectricenergy OBJECT-TYPE
            SYNTAX Integer32 (0..21474836)
            MAX-ACCESS read-only
            STATUS current
            DESCRIPTION
                "Branch 12 L2 output active electric energy. Unit:KWh. Multi:100"
            ::= { hwPDU8000SingleMode1_2Entry 72 }

        hwPDU8000SingleMod2Branch12L3outputactiveelectricenergy OBJECT-TYPE
            SYNTAX Integer32 (0..21474836)
            MAX-ACCESS read-only
            STATUS current
            DESCRIPTION
                "Branch 12 L3 output active electric energy. Unit:KWh. Multi:100"
            ::= { hwPDU8000SingleMode1_2Entry 73 }

        hwPDU8000SingleMode1_2RowStatus OBJECT-TYPE
            SYNTAX RowStatus
            MAX-ACCESS read-create
            STATUS current
            DESCRIPTION
                "The row status of Deviece."
            ::= { hwPDU8000SingleMode1_2Entry 100 }

        hwPDU8000SingleMode3_4Table OBJECT-TYPE
            SYNTAX SEQUENCE OF HwPDU8000SingleMode3_4Entry
            MAX-ACCESS not-accessible
             STATUS current
             DESCRIPTION
                "The table of PDU8000 Single Mode 3 and 4."
            ::= { hwPDU8000Single 3 }

        hwPDU8000SingleMode3_4Entry OBJECT-TYPE
                        SYNTAX HwPDU8000SingleMode3_4Entry
            MAX-ACCESS not-accessible
             STATUS current
             DESCRIPTION
                "The table of PDU8000 Single Mode 3 and 4."
            INDEX { hwPDU8000SingleMode3_4Index }
            ::= { hwPDU8000SingleMode3_4Table 1 }

        HwPDU8000SingleMode3_4Entry            ::= SEQUENCE {
                hwPDU8000SingleMode3_4Index
                    Unsigned32,
                hwPDU8000SingleMod3Branch1L1outputactiveelectricenergy
                    Integer32,
                hwPDU8000SingleMod3Branch1L2outputactiveelectricenergy
                    Integer32,
                hwPDU8000SingleMod3Branch1L3outputactiveelectricenergy
                    Integer32,
                hwPDU8000SingleMod3Branch2L1outputactiveelectricenergy
                    Integer32,
                hwPDU8000SingleMod3Branch2L2outputactiveelectricenergy
                    Integer32,
                hwPDU8000SingleMod3Branch2L3outputactiveelectricenergy
                    Integer32,
                hwPDU8000SingleMod3Branch3L1outputactiveelectricenergy
                    Integer32,
                hwPDU8000SingleMod3Branch3L2outputactiveelectricenergy
                    Integer32,
                hwPDU8000SingleMod3Branch3L3outputactiveelectricenergy
                    Integer32,
                hwPDU8000SingleMod3Branch4L1outputactiveelectricenergy
                    Integer32,
                hwPDU8000SingleMod3Branch4L2outputactiveelectricenergy
                    Integer32,
                hwPDU8000SingleMod3Branch4L3outputactiveelectricenergy
                    Integer32,
                hwPDU8000SingleMod3Branch5L1outputactiveelectricenergy
                    Integer32,
                hwPDU8000SingleMod3Branch5L2outputactiveelectricenergy
                    Integer32,
                hwPDU8000SingleMod3Branch5L3outputactiveelectricenergy
                    Integer32,
                hwPDU8000SingleMod3Branch6L1outputactiveelectricenergy
                    Integer32,
                hwPDU8000SingleMod3Branch6L2outputactiveelectricenergy
                    Integer32,
                hwPDU8000SingleMod3Branch6L3outputactiveelectricenergy
                    Integer32,
                hwPDU8000SingleMod3Branch7L1outputactiveelectricenergy
                    Integer32,
                hwPDU8000SingleMod3Branch7L2outputactiveelectricenergy
                    Integer32,
                hwPDU8000SingleMod3Branch7L3outputactiveelectricenergy
                    Integer32,
                hwPDU8000SingleMod3Branch8L1outputactiveelectricenergy
                    Integer32,
                hwPDU8000SingleMod3Branch8L2outputactiveelectricenergy
                    Integer32,
                hwPDU8000SingleMod3Branch8L3outputactiveelectricenergy
                    Integer32,
                hwPDU8000SingleMod3Branch9L1outputactiveelectricenergy
                    Integer32,
                hwPDU8000SingleMod3Branch9L2outputactiveelectricenergy
                    Integer32,
                hwPDU8000SingleMod3Branch9L3outputactiveelectricenergy
                    Integer32,
                hwPDU8000SingleMod3Branch10L1outputactiveelectricenergy
                    Integer32,
                hwPDU8000SingleMod3Branch10L2outputactiveelectricenergy
                    Integer32,
                hwPDU8000SingleMod3Branch10L3outputactiveelectricenergy
                    Integer32,
                hwPDU8000SingleMod3Branch11L1outputactiveelectricenergy
                    Integer32,
                hwPDU8000SingleMod3Branch11L2outputactiveelectricenergy
                    Integer32,
                hwPDU8000SingleMod3Branch11L3outputactiveelectricenergy
                    Integer32,
                hwPDU8000SingleMod3Branch12L1outputactiveelectricenergy
                    Integer32,
                hwPDU8000SingleMod3Branch12L2outputactiveelectricenergy
                    Integer32,
                hwPDU8000SingleMod3Branch12L3outputactiveelectricenergy
                    Integer32,
                hwPDU8000SingleMod4Branch1L1outputactiveelectricenergy
                    Integer32,
                hwPDU8000SingleMod4Branch1L2outputactiveelectricenergy
                    Integer32,
                hwPDU8000SingleMod4Branch1L3outputactiveelectricenergy
                    Integer32,
                hwPDU8000SingleMod4Branch2L1outputactiveelectricenergy
                    Integer32,
                hwPDU8000SingleMod4Branch2L2outputactiveelectricenergy
                    Integer32,
                hwPDU8000SingleMod4Branch2L3outputactiveelectricenergy
                    Integer32,
                hwPDU8000SingleMod4Branch3L1outputactiveelectricenergy
                    Integer32,
                hwPDU8000SingleMod4Branch3L2outputactiveelectricenergy
                    Integer32,
                hwPDU8000SingleMod4Branch3L3outputactiveelectricenergy
                    Integer32,
                hwPDU8000SingleMod4Branch4L1outputactiveelectricenergy
                    Integer32,
                hwPDU8000SingleMod4Branch4L2outputactiveelectricenergy
                    Integer32,
                hwPDU8000SingleMod4Branch4L3outputactiveelectricenergy
                    Integer32,
                hwPDU8000SingleMod4Branch5L1outputactiveelectricenergy
                    Integer32,
                hwPDU8000SingleMod4Branch5L2outputactiveelectricenergy
                    Integer32,
                hwPDU8000SingleMod4Branch5L3outputactiveelectricenergy
                    Integer32,
                hwPDU8000SingleMod4Branch6L1outputactiveelectricenergy
                    Integer32,
                hwPDU8000SingleMod4Branch6L2outputactiveelectricenergy
                    Integer32,
                hwPDU8000SingleMod4Branch6L3outputactiveelectricenergy
                    Integer32,
                hwPDU8000SingleMod4Branch7L1outputactiveelectricenergy
                    Integer32,
                hwPDU8000SingleMod4Branch7L2outputactiveelectricenergy
                    Integer32,
                hwPDU8000SingleMod4Branch7L3outputactiveelectricenergy
                    Integer32,
                hwPDU8000SingleMod4Branch8L1outputactiveelectricenergy
                    Integer32,
                hwPDU8000SingleMod4Branch8L2outputactiveelectricenergy
                    Integer32,
                hwPDU8000SingleMod4Branch8L3outputactiveelectricenergy
                    Integer32,
                hwPDU8000SingleMod4Branch9L1outputactiveelectricenergy
                    Integer32,
                hwPDU8000SingleMod4Branch9L2outputactiveelectricenergy
                    Integer32,
                hwPDU8000SingleMod4Branch9L3outputactiveelectricenergy
                    Integer32,
                hwPDU8000SingleMod4Branch10L1outputactiveelectricenergy
                    Integer32,
                hwPDU8000SingleMod4Branch10L2outputactiveelectricenergy
                    Integer32,
                hwPDU8000SingleMod4Branch10L3outputactiveelectricenergy
                    Integer32,
                hwPDU8000SingleMod4Branch11L1outputactiveelectricenergy
                    Integer32,
                hwPDU8000SingleMod4Branch11L2outputactiveelectricenergy
                    Integer32,
                hwPDU8000SingleMod4Branch11L3outputactiveelectricenergy
                    Integer32,
                hwPDU8000SingleMod4Branch12L1outputactiveelectricenergy
                    Integer32,
                hwPDU8000SingleMod4Branch12L2outputactiveelectricenergy
                    Integer32,
                hwPDU8000SingleMod4Branch12L3outputactiveelectricenergy
                    Integer32,
                hwPDU8000SingleMode3_4RowStatus
                    RowStatus
            }

        hwPDU8000SingleMode3_4Index OBJECT-TYPE
            SYNTAX Unsigned32
            MAX-ACCESS read-only
            STATUS current
            DESCRIPTION
                "The equip id of PDU8000 Single Mode 3 and 4."
            ::= { hwPDU8000SingleMode3_4Entry 1 }

        hwPDU8000SingleMod3Branch1L1outputactiveelectricenergy OBJECT-TYPE
            SYNTAX Integer32 (0..21474836)
            MAX-ACCESS read-only
            STATUS current
            DESCRIPTION
                "Branch 1 L1 output active electric energy. Unit:KWh. Multi:100"
            ::= { hwPDU8000SingleMode3_4Entry 2 }

        hwPDU8000SingleMod3Branch1L2outputactiveelectricenergy OBJECT-TYPE
            SYNTAX Integer32 (0..21474836)
            MAX-ACCESS read-only
            STATUS current
            DESCRIPTION
                "Branch 1 L2 output active electric energy. Unit:KWh. Multi:100"
            ::= { hwPDU8000SingleMode3_4Entry 3 }

        hwPDU8000SingleMod3Branch1L3outputactiveelectricenergy OBJECT-TYPE
            SYNTAX Integer32 (0..21474836)
            MAX-ACCESS read-only
            STATUS current
            DESCRIPTION
                "Branch 1 L3 output active electric energy. Unit:KWh. Multi:100"
            ::= { hwPDU8000SingleMode3_4Entry 4 }

        hwPDU8000SingleMod3Branch2L1outputactiveelectricenergy OBJECT-TYPE
            SYNTAX Integer32 (0..21474836)
            MAX-ACCESS read-only
            STATUS current
            DESCRIPTION
                "Branch 2 L1 output active electric energy. Unit:KWh. Multi:100"
            ::= { hwPDU8000SingleMode3_4Entry 5 }

        hwPDU8000SingleMod3Branch2L2outputactiveelectricenergy OBJECT-TYPE
            SYNTAX Integer32 (0..21474836)
            MAX-ACCESS read-only
            STATUS current
            DESCRIPTION
                "Branch 2 L2 output active electric energy. Unit:KWh. Multi:100"
            ::= { hwPDU8000SingleMode3_4Entry 6 }

        hwPDU8000SingleMod3Branch2L3outputactiveelectricenergy OBJECT-TYPE
            SYNTAX Integer32 (0..21474836)
            MAX-ACCESS read-only
            STATUS current
            DESCRIPTION
                "Branch 2 L3 output active electric energy. Unit:KWh. Multi:100"
            ::= { hwPDU8000SingleMode3_4Entry 7 }

        hwPDU8000SingleMod3Branch3L1outputactiveelectricenergy OBJECT-TYPE
            SYNTAX Integer32 (0..21474836)
            MAX-ACCESS read-only
            STATUS current
            DESCRIPTION
                "Branch 3 L1 output active electric energy. Unit:KWh. Multi:100"
            ::= { hwPDU8000SingleMode3_4Entry 8 }

        hwPDU8000SingleMod3Branch3L2outputactiveelectricenergy OBJECT-TYPE
            SYNTAX Integer32 (0..21474836)
            MAX-ACCESS read-only
            STATUS current
            DESCRIPTION
                "Branch 3 L2 output active electric energy. Unit:KWh. Multi:100"
            ::= { hwPDU8000SingleMode3_4Entry 9 }

        hwPDU8000SingleMod3Branch3L3outputactiveelectricenergy OBJECT-TYPE
            SYNTAX Integer32 (0..21474836)
            MAX-ACCESS read-only
            STATUS current
            DESCRIPTION
                "Branch 3 L3 output active electric energy. Unit:KWh. Multi:100"
            ::= { hwPDU8000SingleMode3_4Entry 10 }

        hwPDU8000SingleMod3Branch4L1outputactiveelectricenergy OBJECT-TYPE
            SYNTAX Integer32 (0..21474836)
            MAX-ACCESS read-only
            STATUS current
            DESCRIPTION
                "Branch 4 L1 output active electric energy. Unit:KWh. Multi:100"
            ::= { hwPDU8000SingleMode3_4Entry 11 }

        hwPDU8000SingleMod3Branch4L2outputactiveelectricenergy OBJECT-TYPE
            SYNTAX Integer32 (0..21474836)
            MAX-ACCESS read-only
            STATUS current
            DESCRIPTION
                "Branch 4 L2 output active electric energy. Unit:KWh. Multi:100"
            ::= { hwPDU8000SingleMode3_4Entry 12 }

        hwPDU8000SingleMod3Branch4L3outputactiveelectricenergy OBJECT-TYPE
            SYNTAX Integer32 (0..21474836)
            MAX-ACCESS read-only
            STATUS current
            DESCRIPTION
                "Branch 4 L3 output active electric energy. Unit:KWh. Multi:100"
            ::= { hwPDU8000SingleMode3_4Entry 13 }

        hwPDU8000SingleMod3Branch5L1outputactiveelectricenergy OBJECT-TYPE
            SYNTAX Integer32 (0..21474836)
            MAX-ACCESS read-only
            STATUS current
            DESCRIPTION
                "Branch 5 L1 output active electric energy. Unit:KWh. Multi:100"
            ::= { hwPDU8000SingleMode3_4Entry 14 }

        hwPDU8000SingleMod3Branch5L2outputactiveelectricenergy OBJECT-TYPE
            SYNTAX Integer32 (0..21474836)
            MAX-ACCESS read-only
            STATUS current
            DESCRIPTION
                "Branch 5 L2 output active electric energy. Unit:KWh. Multi:100"
            ::= { hwPDU8000SingleMode3_4Entry 15 }

        hwPDU8000SingleMod3Branch5L3outputactiveelectricenergy OBJECT-TYPE
            SYNTAX Integer32 (0..21474836)
            MAX-ACCESS read-only
            STATUS current
            DESCRIPTION
                "Branch 5 L3 output active electric energy. Unit:KWh. Multi:100"
            ::= { hwPDU8000SingleMode3_4Entry 16 }

        hwPDU8000SingleMod3Branch6L1outputactiveelectricenergy OBJECT-TYPE
            SYNTAX Integer32 (0..21474836)
            MAX-ACCESS read-only
            STATUS current
            DESCRIPTION
                "Branch 6 L1 output active electric energy. Unit:KWh. Multi:100"
            ::= { hwPDU8000SingleMode3_4Entry 17 }

        hwPDU8000SingleMod3Branch6L2outputactiveelectricenergy OBJECT-TYPE
            SYNTAX Integer32 (0..21474836)
            MAX-ACCESS read-only
            STATUS current
            DESCRIPTION
                "Branch 6 L2 output active electric energy. Unit:KWh. Multi:100"
            ::= { hwPDU8000SingleMode3_4Entry 18 }

        hwPDU8000SingleMod3Branch6L3outputactiveelectricenergy OBJECT-TYPE
            SYNTAX Integer32 (0..21474836)
            MAX-ACCESS read-only
            STATUS current
            DESCRIPTION
                "Branch 6 L3 output active electric energy. Unit:KWh. Multi:100"
            ::= { hwPDU8000SingleMode3_4Entry 19 }

        hwPDU8000SingleMod3Branch7L1outputactiveelectricenergy OBJECT-TYPE
            SYNTAX Integer32 (0..21474836)
            MAX-ACCESS read-only
            STATUS current
            DESCRIPTION
                "Branch 7 L1 output active electric energy. Unit:KWh. Multi:100"
            ::= { hwPDU8000SingleMode3_4Entry 20 }

        hwPDU8000SingleMod3Branch7L2outputactiveelectricenergy OBJECT-TYPE
            SYNTAX Integer32 (0..21474836)
            MAX-ACCESS read-only
            STATUS current
            DESCRIPTION
                "Branch 7 L2 output active electric energy. Unit:KWh. Multi:100"
            ::= { hwPDU8000SingleMode3_4Entry 21 }

        hwPDU8000SingleMod3Branch7L3outputactiveelectricenergy OBJECT-TYPE
            SYNTAX Integer32 (0..21474836)
            MAX-ACCESS read-only
            STATUS current
            DESCRIPTION
                "Branch 7 L3 output active electric energy. Unit:KWh. Multi:100"
            ::= { hwPDU8000SingleMode3_4Entry 22 }

        hwPDU8000SingleMod3Branch8L1outputactiveelectricenergy OBJECT-TYPE
            SYNTAX Integer32 (0..21474836)
            MAX-ACCESS read-only
            STATUS current
            DESCRIPTION
                "Branch 8 L1 output active electric energy. Unit:KWh. Multi:100"
            ::= { hwPDU8000SingleMode3_4Entry 23 }

        hwPDU8000SingleMod3Branch8L2outputactiveelectricenergy OBJECT-TYPE
            SYNTAX Integer32 (0..21474836)
            MAX-ACCESS read-only
            STATUS current
            DESCRIPTION
                "Branch 8 L2 output active electric energy. Unit:KWh. Multi:100"
            ::= { hwPDU8000SingleMode3_4Entry 24 }

        hwPDU8000SingleMod3Branch8L3outputactiveelectricenergy OBJECT-TYPE
            SYNTAX Integer32 (0..21474836)
            MAX-ACCESS read-only
            STATUS current
            DESCRIPTION
                "Branch 8 L3 output active electric energy. Unit:KWh. Multi:100"
            ::= { hwPDU8000SingleMode3_4Entry 25 }

        hwPDU8000SingleMod3Branch9L1outputactiveelectricenergy OBJECT-TYPE
            SYNTAX Integer32 (0..21474836)
            MAX-ACCESS read-only
            STATUS current
            DESCRIPTION
                "Branch 9 L1 output active electric energy. Unit:KWh. Multi:100"
            ::= { hwPDU8000SingleMode3_4Entry 26 }

        hwPDU8000SingleMod3Branch9L2outputactiveelectricenergy OBJECT-TYPE
            SYNTAX Integer32 (0..21474836)
            MAX-ACCESS read-only
            STATUS current
            DESCRIPTION
                "Branch 9 L2 output active electric energy. Unit:KWh. Multi:100"
            ::= { hwPDU8000SingleMode3_4Entry 27 }

        hwPDU8000SingleMod3Branch9L3outputactiveelectricenergy OBJECT-TYPE
            SYNTAX Integer32 (0..21474836)
            MAX-ACCESS read-only
            STATUS current
            DESCRIPTION
                "Branch 9 L3 output active electric energy. Unit:KWh. Multi:100"
            ::= { hwPDU8000SingleMode3_4Entry 28 }

        hwPDU8000SingleMod3Branch10L1outputactiveelectricenergy OBJECT-TYPE
            SYNTAX Integer32 (0..21474836)
            MAX-ACCESS read-only
            STATUS current
            DESCRIPTION
                "Branch 10 L1 output active electric energy. Unit:KWh. Multi:100"
            ::= { hwPDU8000SingleMode3_4Entry 29 }

        hwPDU8000SingleMod3Branch10L2outputactiveelectricenergy OBJECT-TYPE
            SYNTAX Integer32 (0..21474836)
            MAX-ACCESS read-only
            STATUS current
            DESCRIPTION
                "Branch 10 L2 output active electric energy. Unit:KWh. Multi:100"
            ::= { hwPDU8000SingleMode3_4Entry 30 }

        hwPDU8000SingleMod3Branch10L3outputactiveelectricenergy OBJECT-TYPE
            SYNTAX Integer32 (0..21474836)
            MAX-ACCESS read-only
            STATUS current
            DESCRIPTION
                "Branch 10 L3 output active electric energy. Unit:KWh. Multi:100"
            ::= { hwPDU8000SingleMode3_4Entry 31 }

        hwPDU8000SingleMod3Branch11L1outputactiveelectricenergy OBJECT-TYPE
            SYNTAX Integer32 (0..21474836)
            MAX-ACCESS read-only
            STATUS current
            DESCRIPTION
                "Branch 11 L1 output active electric energy. Unit:KWh. Multi:100"
            ::= { hwPDU8000SingleMode3_4Entry 32 }

        hwPDU8000SingleMod3Branch11L2outputactiveelectricenergy OBJECT-TYPE
            SYNTAX Integer32 (0..21474836)
            MAX-ACCESS read-only
            STATUS current
            DESCRIPTION
                "Branch 11 L2 output active electric energy. Unit:KWh. Multi:100"
            ::= { hwPDU8000SingleMode3_4Entry 33 }

        hwPDU8000SingleMod3Branch11L3outputactiveelectricenergy OBJECT-TYPE
            SYNTAX Integer32 (0..21474836)
            MAX-ACCESS read-only
            STATUS current
            DESCRIPTION
                "Branch 11 L3 output active electric energy. Unit:KWh. Multi:100"
            ::= { hwPDU8000SingleMode3_4Entry 34 }

        hwPDU8000SingleMod3Branch12L1outputactiveelectricenergy OBJECT-TYPE
            SYNTAX Integer32 (0..21474836)
            MAX-ACCESS read-only
            STATUS current
            DESCRIPTION
                "Branch 12 L1 output active electric energy. Unit:KWh. Multi:100"
            ::= { hwPDU8000SingleMode3_4Entry 35 }

        hwPDU8000SingleMod3Branch12L2outputactiveelectricenergy OBJECT-TYPE
            SYNTAX Integer32 (0..21474836)
            MAX-ACCESS read-only
            STATUS current
            DESCRIPTION
                "Branch 12 L2 output active electric energy. Unit:KWh. Multi:100"
            ::= { hwPDU8000SingleMode3_4Entry 36 }

        hwPDU8000SingleMod3Branch12L3outputactiveelectricenergy OBJECT-TYPE
            SYNTAX Integer32 (0..21474836)
            MAX-ACCESS read-only
            STATUS current
            DESCRIPTION
                "Branch 12 L3 output active electric energy. Unit:KWh. Multi:100"
            ::= { hwPDU8000SingleMode3_4Entry 37 }

        hwPDU8000SingleMod4Branch1L1outputactiveelectricenergy OBJECT-TYPE
            SYNTAX Integer32 (0..21474836)
            MAX-ACCESS read-only
            STATUS current
            DESCRIPTION
                "Branch 1 L1 output active electric energy. Unit:KWh. Multi:100"
            ::= { hwPDU8000SingleMode3_4Entry 38 }

        hwPDU8000SingleMod4Branch1L2outputactiveelectricenergy OBJECT-TYPE
            SYNTAX Integer32 (0..21474836)
            MAX-ACCESS read-only
            STATUS current
            DESCRIPTION
                "Branch 1 L2 output active electric energy. Unit:KWh. Multi:100"
            ::= { hwPDU8000SingleMode3_4Entry 39 }

        hwPDU8000SingleMod4Branch1L3outputactiveelectricenergy OBJECT-TYPE
            SYNTAX Integer32 (0..21474836)
            MAX-ACCESS read-only
            STATUS current
            DESCRIPTION
                "Branch 1 L3 output active electric energy. Unit:KWh. Multi:100"
            ::= { hwPDU8000SingleMode3_4Entry 40 }

        hwPDU8000SingleMod4Branch2L1outputactiveelectricenergy OBJECT-TYPE
            SYNTAX Integer32 (0..21474836)
            MAX-ACCESS read-only
            STATUS current
            DESCRIPTION
                "Branch 2 L1 output active electric energy. Unit:KWh. Multi:100"
            ::= { hwPDU8000SingleMode3_4Entry 41 }

        hwPDU8000SingleMod4Branch2L2outputactiveelectricenergy OBJECT-TYPE
            SYNTAX Integer32 (0..21474836)
            MAX-ACCESS read-only
            STATUS current
            DESCRIPTION
                "Branch 2 L2 output active electric energy. Unit:KWh. Multi:100"
            ::= { hwPDU8000SingleMode3_4Entry 42 }

        hwPDU8000SingleMod4Branch2L3outputactiveelectricenergy OBJECT-TYPE
            SYNTAX Integer32 (0..21474836)
            MAX-ACCESS read-only
            STATUS current
            DESCRIPTION
                "Branch 2 L3 output active electric energy. Unit:KWh. Multi:100"
            ::= { hwPDU8000SingleMode3_4Entry 43 }

        hwPDU8000SingleMod4Branch3L1outputactiveelectricenergy OBJECT-TYPE
            SYNTAX Integer32 (0..21474836)
            MAX-ACCESS read-only
            STATUS current
            DESCRIPTION
                "Branch 3 L1 output active electric energy. Unit:KWh. Multi:100"
            ::= { hwPDU8000SingleMode3_4Entry 44 }

        hwPDU8000SingleMod4Branch3L2outputactiveelectricenergy OBJECT-TYPE
            SYNTAX Integer32 (0..21474836)
            MAX-ACCESS read-only
            STATUS current
            DESCRIPTION
                "Branch 3 L2 output active electric energy. Unit:KWh. Multi:100"
            ::= { hwPDU8000SingleMode3_4Entry 45 }

        hwPDU8000SingleMod4Branch3L3outputactiveelectricenergy OBJECT-TYPE
            SYNTAX Integer32 (0..21474836)
            MAX-ACCESS read-only
            STATUS current
            DESCRIPTION
                "Branch 3 L3 output active electric energy. Unit:KWh. Multi:100"
            ::= { hwPDU8000SingleMode3_4Entry 46 }

        hwPDU8000SingleMod4Branch4L1outputactiveelectricenergy OBJECT-TYPE
            SYNTAX Integer32 (0..21474836)
            MAX-ACCESS read-only
            STATUS current
            DESCRIPTION
                "Branch 4 L1 output active electric energy. Unit:KWh. Multi:100"
            ::= { hwPDU8000SingleMode3_4Entry 47 }

        hwPDU8000SingleMod4Branch4L2outputactiveelectricenergy OBJECT-TYPE
            SYNTAX Integer32 (0..21474836)
            MAX-ACCESS read-only
            STATUS current
            DESCRIPTION
                "Branch 4 L2 output active electric energy. Unit:KWh. Multi:100"
            ::= { hwPDU8000SingleMode3_4Entry 48 }

        hwPDU8000SingleMod4Branch4L3outputactiveelectricenergy OBJECT-TYPE
            SYNTAX Integer32 (0..21474836)
            MAX-ACCESS read-only
            STATUS current
            DESCRIPTION
                "Branch 4 L3 output active electric energy. Unit:KWh. Multi:100"
            ::= { hwPDU8000SingleMode3_4Entry 49 }

        hwPDU8000SingleMod4Branch5L1outputactiveelectricenergy OBJECT-TYPE
            SYNTAX Integer32 (0..21474836)
            MAX-ACCESS read-only
            STATUS current
            DESCRIPTION
                "Branch 5 L1 output active electric energy. Unit:KWh. Multi:100"
            ::= { hwPDU8000SingleMode3_4Entry 50 }

        hwPDU8000SingleMod4Branch5L2outputactiveelectricenergy OBJECT-TYPE
            SYNTAX Integer32 (0..21474836)
            MAX-ACCESS read-only
            STATUS current
            DESCRIPTION
                "Branch 5 L2 output active electric energy. Unit:KWh. Multi:100"
            ::= { hwPDU8000SingleMode3_4Entry 51 }

        hwPDU8000SingleMod4Branch5L3outputactiveelectricenergy OBJECT-TYPE
            SYNTAX Integer32 (0..21474836)
            MAX-ACCESS read-only
            STATUS current
            DESCRIPTION
                "Branch 5 L3 output active electric energy. Unit:KWh. Multi:100"
            ::= { hwPDU8000SingleMode3_4Entry 52 }

        hwPDU8000SingleMod4Branch6L1outputactiveelectricenergy OBJECT-TYPE
            SYNTAX Integer32 (0..21474836)
            MAX-ACCESS read-only
            STATUS current
            DESCRIPTION
                "Branch 6 L1 output active electric energy. Unit:KWh. Multi:100"
            ::= { hwPDU8000SingleMode3_4Entry 53 }

        hwPDU8000SingleMod4Branch6L2outputactiveelectricenergy OBJECT-TYPE
            SYNTAX Integer32 (0..21474836)
            MAX-ACCESS read-only
            STATUS current
            DESCRIPTION
                "Branch 6 L2 output active electric energy. Unit:KWh. Multi:100"
            ::= { hwPDU8000SingleMode3_4Entry 54 }

        hwPDU8000SingleMod4Branch6L3outputactiveelectricenergy OBJECT-TYPE
            SYNTAX Integer32 (0..21474836)
            MAX-ACCESS read-only
            STATUS current
            DESCRIPTION
                "Branch 6 L3 output active electric energy. Unit:KWh. Multi:100"
            ::= { hwPDU8000SingleMode3_4Entry 55 }

        hwPDU8000SingleMod4Branch7L1outputactiveelectricenergy OBJECT-TYPE
            SYNTAX Integer32 (0..21474836)
            MAX-ACCESS read-only
            STATUS current
            DESCRIPTION
                "Branch 7 L1 output active electric energy. Unit:KWh. Multi:100"
            ::= { hwPDU8000SingleMode3_4Entry 56 }

        hwPDU8000SingleMod4Branch7L2outputactiveelectricenergy OBJECT-TYPE
            SYNTAX Integer32 (0..21474836)
            MAX-ACCESS read-only
            STATUS current
            DESCRIPTION
                "Branch 7 L2 output active electric energy. Unit:KWh. Multi:100"
            ::= { hwPDU8000SingleMode3_4Entry 57 }

        hwPDU8000SingleMod4Branch7L3outputactiveelectricenergy OBJECT-TYPE
            SYNTAX Integer32 (0..21474836)
            MAX-ACCESS read-only
            STATUS current
            DESCRIPTION
                "Branch 7 L3 output active electric energy. Unit:KWh. Multi:100"
            ::= { hwPDU8000SingleMode3_4Entry 58 }

        hwPDU8000SingleMod4Branch8L1outputactiveelectricenergy OBJECT-TYPE
            SYNTAX Integer32 (0..21474836)
            MAX-ACCESS read-only
            STATUS current
            DESCRIPTION
                "Branch 8 L1 output active electric energy. Unit:KWh. Multi:100"
            ::= { hwPDU8000SingleMode3_4Entry 59 }

        hwPDU8000SingleMod4Branch8L2outputactiveelectricenergy OBJECT-TYPE
            SYNTAX Integer32 (0..21474836)
            MAX-ACCESS read-only
            STATUS current
            DESCRIPTION
                "Branch 8 L2 output active electric energy. Unit:KWh. Multi:100"
            ::= { hwPDU8000SingleMode3_4Entry 60 }

        hwPDU8000SingleMod4Branch8L3outputactiveelectricenergy OBJECT-TYPE
            SYNTAX Integer32 (0..21474836)
            MAX-ACCESS read-only
            STATUS current
            DESCRIPTION
                "Branch 8 L3 output active electric energy. Unit:KWh. Multi:100"
            ::= { hwPDU8000SingleMode3_4Entry 61 }

        hwPDU8000SingleMod4Branch9L1outputactiveelectricenergy OBJECT-TYPE
            SYNTAX Integer32 (0..21474836)
            MAX-ACCESS read-only
            STATUS current
            DESCRIPTION
                "Branch 9 L1 output active electric energy. Unit:KWh. Multi:100"
            ::= { hwPDU8000SingleMode3_4Entry 62 }

        hwPDU8000SingleMod4Branch9L2outputactiveelectricenergy OBJECT-TYPE
            SYNTAX Integer32 (0..21474836)
            MAX-ACCESS read-only
            STATUS current
            DESCRIPTION
                "Branch 9 L2 output active electric energy. Unit:KWh. Multi:100"
            ::= { hwPDU8000SingleMode3_4Entry 63 }

        hwPDU8000SingleMod4Branch9L3outputactiveelectricenergy OBJECT-TYPE
            SYNTAX Integer32 (0..21474836)
            MAX-ACCESS read-only
            STATUS current
            DESCRIPTION
                "Branch 9 L3 output active electric energy. Unit:KWh. Multi:100"
            ::= { hwPDU8000SingleMode3_4Entry 64 }

        hwPDU8000SingleMod4Branch10L1outputactiveelectricenergy OBJECT-TYPE
            SYNTAX Integer32 (0..21474836)
            MAX-ACCESS read-only
            STATUS current
            DESCRIPTION
                "Branch 10 L1 output active electric energy. Unit:KWh. Multi:100"
            ::= { hwPDU8000SingleMode3_4Entry 65 }

        hwPDU8000SingleMod4Branch10L2outputactiveelectricenergy OBJECT-TYPE
            SYNTAX Integer32 (0..21474836)
            MAX-ACCESS read-only
            STATUS current
            DESCRIPTION
                "Branch 10 L2 output active electric energy. Unit:KWh. Multi:100"
            ::= { hwPDU8000SingleMode3_4Entry 66 }

        hwPDU8000SingleMod4Branch10L3outputactiveelectricenergy OBJECT-TYPE
            SYNTAX Integer32 (0..21474836)
            MAX-ACCESS read-only
            STATUS current
            DESCRIPTION
                "Branch 10 L3 output active electric energy. Unit:KWh. Multi:100"
            ::= { hwPDU8000SingleMode3_4Entry 67 }

        hwPDU8000SingleMod4Branch11L1outputactiveelectricenergy OBJECT-TYPE
            SYNTAX Integer32 (0..21474836)
            MAX-ACCESS read-only
            STATUS current
            DESCRIPTION
                "Branch 11 L1 output active electric energy. Unit:KWh. Multi:100"
            ::= { hwPDU8000SingleMode3_4Entry 68 }

        hwPDU8000SingleMod4Branch11L2outputactiveelectricenergy OBJECT-TYPE
            SYNTAX Integer32 (0..21474836)
            MAX-ACCESS read-only
            STATUS current
            DESCRIPTION
                "Branch 11 L2 output active electric energy. Unit:KWh. Multi:100"
            ::= { hwPDU8000SingleMode3_4Entry 69 }

        hwPDU8000SingleMod4Branch11L3outputactiveelectricenergy OBJECT-TYPE
            SYNTAX Integer32 (0..21474836)
            MAX-ACCESS read-only
            STATUS current
            DESCRIPTION
                "Branch 11 L3 output active electric energy. Unit:KWh. Multi:100"
            ::= { hwPDU8000SingleMode3_4Entry 70 }

        hwPDU8000SingleMod4Branch12L1outputactiveelectricenergy OBJECT-TYPE
            SYNTAX Integer32 (0..21474836)
            MAX-ACCESS read-only
            STATUS current
            DESCRIPTION
                "Branch 12 L1 output active electric energy. Unit:KWh. Multi:100"
            ::= { hwPDU8000SingleMode3_4Entry 71 }

        hwPDU8000SingleMod4Branch12L2outputactiveelectricenergy OBJECT-TYPE
            SYNTAX Integer32 (0..21474836)
            MAX-ACCESS read-only
            STATUS current
            DESCRIPTION
                "Branch 12 L2 output active electric energy. Unit:KWh. Multi:100"
            ::= { hwPDU8000SingleMode3_4Entry 72 }

        hwPDU8000SingleMod4Branch12L3outputactiveelectricenergy OBJECT-TYPE
            SYNTAX Integer32 (0..21474836)
            MAX-ACCESS read-only
            STATUS current
            DESCRIPTION
                "Branch 12 L3 output active electric energy. Unit:KWh. Multi:100"
            ::= { hwPDU8000SingleMode3_4Entry 73 }

        hwPDU8000SingleMode3_4RowStatus OBJECT-TYPE
            SYNTAX RowStatus
            MAX-ACCESS read-create
            STATUS current
            DESCRIPTION
                "The row status of Deviece."
            ::= { hwPDU8000SingleMode3_4Entry 100 }

        hwPDU8000Dual OBJECT IDENTIFIER ::= { hwIDCPDU 2 }

        hwPDU8000DualTable OBJECT-TYPE
            SYNTAX SEQUENCE OF HwPDU8000DualEntry
            MAX-ACCESS not-accessible
             STATUS current
             DESCRIPTION
                "The table of PDU8000 Dual Equipments."
            ::= { hwPDU8000Dual 1 }

        hwPDU8000DualEntry OBJECT-TYPE
                        SYNTAX HwPDU8000DualEntry
            MAX-ACCESS not-accessible
             STATUS current
             DESCRIPTION
                "The table of PDU8000 Dual Equipments."
            INDEX { hwPDU8000TableDualIndex }
            ::= { hwPDU8000DualTable 1 }

        HwPDU8000DualEntry            ::= SEQUENCE {
                hwPDU8000TableDualIndex
                    Unsigned32,
                hwPDU8000DualName
                    OCTET STRING,
                hwPDU8000DualCommunicationStatus
                    INTEGER,
                hwPDU8000DualSlotNo
                    Unsigned32,
                hwPDU8000DualPortNo
                    Unsigned32,
                hwPDU8000DualModbusAddr
                    Unsigned32,
                hwPDU8000DualSoftwareVersion
                    OCTET STRING,
                hwPDU8000DualESN
                    OCTET STRING,
                hwPDU8000DualInputMode
                    INTEGER,
                hwPDU8000DualMaininput1L1inputphasevoltage
                    Integer32,
                hwPDU8000DualMaininput1L2inputphasevoltage
                    Integer32,
                hwPDU8000DualMaininput1L3inputphasevoltage
                    Integer32,
                hwPDU8000DualMaininput1L1L2inputlinevoltage
                    Integer32,
                hwPDU8000DualMaininput1L2L3inputlinevoltage
                    Integer32,
                hwPDU8000DualMaininput1L1L3inputlinevoltage
                    Integer32,
                hwPDU8000DualMaininput1L1inputcurrent
                    Integer32,
                hwPDU8000DualMaininput1L2inputcurrent
                    Integer32,
                hwPDU8000DualMaininput1L3inputcurrent
                    Integer32,
                hwPDU8000DualMaininput1inputfrequency
                    Integer32,
                hwPDU8000DualMaininput1L1inputactivepower
                    Integer32,
                hwPDU8000DualMaininput1L2inputactivepower
                    Integer32,
                hwPDU8000DualMaininput1L3inputactivepower
                    Integer32,
                hwPDU8000DualMaininput1L1inputapparentpower
                    Integer32,
                hwPDU8000DualMaininput1L2inputapparentpower
                    Integer32,
                hwPDU8000DualMaininput1L3inputapparentpower
                    Integer32,
                hwPDU8000DualMaininput1L1inputreactivepower
                    Integer32,
                hwPDU8000DualMaininput1L2inputreactivepower
                    Integer32,
                hwPDU8000DualMaininput1L3inputreactivepower
                    Integer32,
                hwPDU8000DualMaininput1L1inputpowerfactor
                    Integer32,
                hwPDU8000DualMaininput1L2inputpowerfactor
                    Integer32,
                hwPDU8000DualMaininput1L3inputpowerfactor
                    Integer32,
                hwPDU8000DualMaininput1inputactiveelectricenergy
                    Unsigned32,
                hwPDU8000DualMaininput1L1inputpowerloadrate
                    Unsigned32,
                hwPDU8000DualMaininput1L2inputpowerloadrate
                    Unsigned32,
                hwPDU8000DualMaininput1L3inputpowerloadrate
                    Integer32,
                hwPDU8000DualMaininput1Nwirecurrent
                    Integer32,
                hwPDU8000DualMaininput1L1THDurate
                    Integer32,
                hwPDU8000DualMaininput1L2THDurate
                    Integer32,
                hwPDU8000DualMaininput1L3THDurate
                    Integer32,
                hwPDU8000DualMaininput1L1THDirate
                    Integer32,
                hwPDU8000DualMaininput1L2THDirate
                    Integer32,
                hwPDU8000DualMaininput1L3THDirate
                    Integer32,
                hwPDU8000DualMaininput1totalinputactivepower
                    Integer32,
                hwPDU8000DualMaininput1totalinputapparentpower
                    Integer32,
                hwPDU8000DualMaininput1totalinputreactivepower
                    Integer32,
                hwPDU8000DualMaininput2L1inputphasevoltage
                    Integer32,
                hwPDU8000DualMaininput2L2inputphasevoltage
                    Integer32,
                hwPDU8000DualMaininput2L3inputphasevoltage
                    Integer32,
                hwPDU8000DualMaininput2L1L2inputlinevoltage
                    Integer32,
                hwPDU8000DualMaininput2L2L3inputlinevoltage
                    Integer32,
                hwPDU8000DualMaininput2L1L3inputlinevoltage
                    Integer32,
                hwPDU8000DualMaininput2L1inputcurrent
                    Integer32,
                hwPDU8000DualMaininput2L2inputcurrent
                    Integer32,
                hwPDU8000DualMaininput2L3inputcurrent
                    Integer32,
                hwPDU8000DualMaininput2inputfrequency
                    Integer32,
                hwPDU8000DualMaininput2L1inputactivepower
                    Integer32,
                hwPDU8000DualMaininput2L2inputactivepower
                    Integer32,
                hwPDU8000DualMaininput2L3inputactivepower
                    Integer32,
                hwPDU8000DualMaininput2L1inputapparentpower
                    Integer32,
                hwPDU8000DualMaininput2L2inputapparentpower
                    Integer32,
                hwPDU8000DualMaininput2L3inputapparentpower
                    Integer32,
                hwPDU8000DualMaininput2L1inputreactivepower
                    Integer32,
                hwPDU8000DualMaininput2L2inputreactivepower
                    Integer32,
                hwPDU8000DualMaininput2L3inputreactivepower
                    Integer32,
                hwPDU8000DualMaininput2L1inputpowerfactor
                    Integer32,
                hwPDU8000DualMaininput2L2inputpowerfactor
                    Integer32,
                hwPDU8000DualMaininput2L3inputpowerfactor
                    Integer32,
                hwPDU8000DualMaininput2inputactiveelectricenergy
                    Integer32,
                hwPDU8000DualMaininput2L1inputpowerloadrate
                    Integer32,
                hwPDU8000DualMaininput2L2inputpowerloadrate
                    Integer32,
                hwPDU8000DualMaininput2L3inputpowerloadrate
                    Integer32,
                hwPDU8000DualMaininput2Nwirecurrent
                    Integer32,
                hwPDU8000DualMaininput2L1THDurate
                    Integer32,
                hwPDU8000DualMaininput2L2THDurate
                    Integer32,
                hwPDU8000DualMaininput2L3THDurate
                    Integer32,
                hwPDU8000DualMaininput2L1THDirate
                    Integer32,
                hwPDU8000DualMaininput2L2THDirate
                    Integer32,
                hwPDU8000DualMaininput2L3THDirate
                    Integer32,
                hwPDU8000DualMaininput2totalinputactivepower
                    Integer32,
                hwPDU8000DualMaininput2totalinputapparentpower
                    Integer32,
                hwPDU8000DualMaininput2totalinputreactivepower
                    Integer32,
                hwPDU8000DualRowStatus
                    RowStatus
            }

        hwPDU8000TableDualIndex OBJECT-TYPE
            SYNTAX Unsigned32
            MAX-ACCESS read-only
            STATUS current
            DESCRIPTION
                "The Id of PDU8000 Dual"
            ::= { hwPDU8000DualEntry 1 }

        hwPDU8000DualName OBJECT-TYPE
            SYNTAX OCTET STRING (SIZE (0..50))
            MAX-ACCESS read-only
            STATUS current
            DESCRIPTION
                "The name of PDU8000 Dual"
            ::= { hwPDU8000DualEntry 2 }

        hwPDU8000DualCommunicationStatus OBJECT-TYPE
            SYNTAX INTEGER
                {
                ok(1),
                fail(2),
                unknown(255)
                }
            MAX-ACCESS read-only
            STATUS current
            DESCRIPTION
                "Communication Status."
            ::= { hwPDU8000DualEntry 3 }

        hwPDU8000DualSlotNo OBJECT-TYPE
            SYNTAX Unsigned32 (0..6)
            MAX-ACCESS read-only
            STATUS current
            DESCRIPTION
                "Slot No."
            ::= { hwPDU8000DualEntry 4 }

        hwPDU8000DualPortNo OBJECT-TYPE
            SYNTAX Unsigned32 (1..5)
            MAX-ACCESS read-only
            STATUS current
            DESCRIPTION
                "Port No."
            ::= { hwPDU8000DualEntry 5 }

        hwPDU8000DualModbusAddr OBJECT-TYPE
            SYNTAX Unsigned32 (0..247)
            MAX-ACCESS read-only
            STATUS current
            DESCRIPTION
                "Modbus Addr."
            ::= { hwPDU8000DualEntry 6 }

        hwPDU8000DualSoftwareVersion OBJECT-TYPE
            SYNTAX OCTET STRING (SIZE (0..32))
            MAX-ACCESS read-only
            STATUS current
            DESCRIPTION
                "The software version of equipment."
            ::= { hwPDU8000DualEntry 7 }

        hwPDU8000DualESN OBJECT-TYPE
            SYNTAX OCTET STRING (SIZE (0..20))
            MAX-ACCESS read-only
            STATUS current
            DESCRIPTION
                "The ESN of equipment."
            ::= { hwPDU8000DualEntry 8 }

        hwPDU8000DualInputMode OBJECT-TYPE
            SYNTAX INTEGER
                {
                SingleMode(1),
                DualMode(2),
                Dual1Way(3),
                Dual2Way(4),
                from380to380Transformer(5),
                from480to208Transformer(6),
                unkown(255)
                }
            MAX-ACCESS read-only
            STATUS current
            DESCRIPTION
                "Input Mode."
            ::= { hwPDU8000DualEntry 9 }

        hwPDU8000DualMaininput1L1inputphasevoltage OBJECT-TYPE
            SYNTAX Integer32 (0..1000)
            MAX-ACCESS read-only
            STATUS current
            DESCRIPTION
                "Main input 1 L1 input phase voltage. Unit:V. Multi:10"
            ::= { hwPDU8000DualEntry 10 }

        hwPDU8000DualMaininput1L2inputphasevoltage OBJECT-TYPE
            SYNTAX Integer32 (0..1000)
            MAX-ACCESS read-only
            STATUS current
            DESCRIPTION
                "Main input 1 L2 input phase voltage. Unit:V. Multi:10"
            ::= { hwPDU8000DualEntry 11 }

        hwPDU8000DualMaininput1L3inputphasevoltage OBJECT-TYPE
            SYNTAX Integer32 (0..1000)
            MAX-ACCESS read-only
            STATUS current
            DESCRIPTION
                "Main input 1 L3 input phase voltage. Unit:V. Multi:10"
            ::= { hwPDU8000DualEntry 12 }

        hwPDU8000DualMaininput1L1L2inputlinevoltage OBJECT-TYPE
            SYNTAX Integer32 (0..1000)
            MAX-ACCESS read-only
            STATUS current
            DESCRIPTION
                "Main input 1 L1-L2 input line voltage. Unit:V. Multi:10"
            ::= { hwPDU8000DualEntry 13 }

        hwPDU8000DualMaininput1L2L3inputlinevoltage OBJECT-TYPE
            SYNTAX Integer32 (0..1000)
            MAX-ACCESS read-only
            STATUS current
            DESCRIPTION
                "Main input 1 L2-L3 input line voltage. Unit:V. Multi:10"
            ::= { hwPDU8000DualEntry 14 }

        hwPDU8000DualMaininput1L1L3inputlinevoltage OBJECT-TYPE
            SYNTAX Integer32 (0..1000)
            MAX-ACCESS read-only
            STATUS current
            DESCRIPTION
                "Main input 1 L1-L3 input line voltage. Unit:V. Multi:10"
            ::= { hwPDU8000DualEntry 15 }

        hwPDU8000DualMaininput1L1inputcurrent OBJECT-TYPE
            SYNTAX Integer32 (0..800)
            MAX-ACCESS read-only
            STATUS current
            DESCRIPTION
                "Main input 1 L1 input current. Unit:A. Multi:10"
            ::= { hwPDU8000DualEntry 16 }

        hwPDU8000DualMaininput1L2inputcurrent OBJECT-TYPE
            SYNTAX Integer32 (0..800)
            MAX-ACCESS read-only
            STATUS current
            DESCRIPTION
                "Main input 1 L2 input current. Unit:A. Multi:10"
            ::= { hwPDU8000DualEntry 17 }

        hwPDU8000DualMaininput1L3inputcurrent OBJECT-TYPE
            SYNTAX Integer32 (0..800)
            MAX-ACCESS read-only
            STATUS current
            DESCRIPTION
                "Main input 1 L3 input current. Unit:A. Multi:10"
            ::= { hwPDU8000DualEntry 18 }

        hwPDU8000DualMaininput1inputfrequency OBJECT-TYPE
            SYNTAX Integer32 (0..100)
            MAX-ACCESS read-only
            STATUS current
            DESCRIPTION
                "Main input 1 input frequency. Unit:Hz. Multi:100"
            ::= { hwPDU8000DualEntry 19 }

        hwPDU8000DualMaininput1L1inputactivepower OBJECT-TYPE
            SYNTAX Integer32 (-250..250)
            MAX-ACCESS read-only
            STATUS current
            DESCRIPTION
                "Main input 1 L1 input active power. Unit:KW. Multi:10"
            ::= { hwPDU8000DualEntry 20 }

        hwPDU8000DualMaininput1L2inputactivepower OBJECT-TYPE
            SYNTAX Integer32 (-250..250)
            MAX-ACCESS read-only
            STATUS current
            DESCRIPTION
                "Main input 1 L2 input active power. Unit:KW. Multi:10"
            ::= { hwPDU8000DualEntry 21 }

        hwPDU8000DualMaininput1L3inputactivepower OBJECT-TYPE
            SYNTAX Integer32 (-250..250)
            MAX-ACCESS read-only
            STATUS current
            DESCRIPTION
                "Main input 1 L3 input active power. Unit:KW. Multi:10"
            ::= { hwPDU8000DualEntry 22 }

        hwPDU8000DualMaininput1L1inputapparentpower OBJECT-TYPE
            SYNTAX Integer32 (-250..250)
            MAX-ACCESS read-only
            STATUS current
            DESCRIPTION
                "Main input 1 L1 input apparent power. Unit:KVA. Multi:10"
            ::= { hwPDU8000DualEntry 23 }

        hwPDU8000DualMaininput1L2inputapparentpower OBJECT-TYPE
            SYNTAX Integer32 (-250..250)
            MAX-ACCESS read-only
            STATUS current
            DESCRIPTION
                "Main input 1 L2 input apparent power. Unit:KVA. Multi:10"
            ::= { hwPDU8000DualEntry 24 }

        hwPDU8000DualMaininput1L3inputapparentpower OBJECT-TYPE
            SYNTAX Integer32 (-250..250)
            MAX-ACCESS read-only
            STATUS current
            DESCRIPTION
                "Main input 1 L3 input apparent power. Unit:KVA. Multi:10"
            ::= { hwPDU8000DualEntry 25 }

        hwPDU8000DualMaininput1L1inputreactivepower OBJECT-TYPE
            SYNTAX Integer32 (-250..250)
            MAX-ACCESS read-only
            STATUS current
            DESCRIPTION
                "Main input 1 L1 input reactive power. Unit:KVAR. Multi:10"
            ::= { hwPDU8000DualEntry 26 }

        hwPDU8000DualMaininput1L2inputreactivepower OBJECT-TYPE
            SYNTAX Integer32 (-250..250)
            MAX-ACCESS read-only
            STATUS current
            DESCRIPTION
                "Main input 1 L2 input reactive power. Unit:KVAR. Multi:10"
            ::= { hwPDU8000DualEntry 27 }

        hwPDU8000DualMaininput1L3inputreactivepower OBJECT-TYPE
            SYNTAX Integer32 (-250..250)
            MAX-ACCESS read-only
            STATUS current
            DESCRIPTION
                "Main input 1 L3 input reactive power. Unit:KVAR. Multi:10"
            ::= { hwPDU8000DualEntry 28 }

        hwPDU8000DualMaininput1L1inputpowerfactor OBJECT-TYPE
            SYNTAX Integer32 (-1..1)
            MAX-ACCESS read-only
            STATUS current
            DESCRIPTION
                "Main input 1 L1 input power factor. Multi:100"
            ::= { hwPDU8000DualEntry 29 }

        hwPDU8000DualMaininput1L2inputpowerfactor OBJECT-TYPE
            SYNTAX Integer32 (-1..1)
            MAX-ACCESS read-only
            STATUS current
            DESCRIPTION
                "Main input 1 L2 input power factor. Multi:100"
            ::= { hwPDU8000DualEntry 30 }

        hwPDU8000DualMaininput1L3inputpowerfactor OBJECT-TYPE
            SYNTAX Integer32 (-1..1)
            MAX-ACCESS read-only
            STATUS current
            DESCRIPTION
                "Main input 1 L3 input power factor. Multi:100"
            ::= { hwPDU8000DualEntry 31 }

        hwPDU8000DualMaininput1inputactiveelectricenergy OBJECT-TYPE
            SYNTAX Unsigned32 (0..21474836)
            MAX-ACCESS read-only
            STATUS current
            DESCRIPTION
                "Main input 1 input active electric energy. Unit:KWh. Multi:100"
            ::= { hwPDU8000DualEntry 32 }

        hwPDU8000DualMaininput1L1inputpowerloadrate OBJECT-TYPE
            SYNTAX Unsigned32 (0..150)
            MAX-ACCESS read-only
            STATUS current
            DESCRIPTION
                "Main input 1 L1 input power load rate. Unit:%."
            ::= { hwPDU8000DualEntry 33 }

        hwPDU8000DualMaininput1L2inputpowerloadrate OBJECT-TYPE
            SYNTAX Unsigned32 (0..150)
            MAX-ACCESS read-only
            STATUS current
            DESCRIPTION
                "Main input 1 L2 input power load rate. Unit:%."
            ::= { hwPDU8000DualEntry 34 }

        hwPDU8000DualMaininput1L3inputpowerloadrate OBJECT-TYPE
            SYNTAX Integer32 (0..150)
            MAX-ACCESS read-only
            STATUS current
            DESCRIPTION
                "Main input 1 L3 input power load rate. Unit:%."
            ::= { hwPDU8000DualEntry 35 }

        hwPDU8000DualMaininput1Nwirecurrent OBJECT-TYPE
            SYNTAX Integer32 (0..1000)
            MAX-ACCESS read-only
            STATUS current
            DESCRIPTION
                "Main input 1 N wire current. Unit:A. Multi:10"
            ::= { hwPDU8000DualEntry 36 }

        hwPDU8000DualMaininput1L1THDurate OBJECT-TYPE
            SYNTAX Integer32 (0..100)
            MAX-ACCESS read-only
            STATUS current
            DESCRIPTION
                "Main input 1 L1 THD-u rate. Unit:%. Multi:100"
            ::= { hwPDU8000DualEntry 37 }

        hwPDU8000DualMaininput1L2THDurate OBJECT-TYPE
            SYNTAX Integer32 (0..100)
            MAX-ACCESS read-only
            STATUS current
            DESCRIPTION
                "Main input 1 L2 THD-u rate. Unit:%. Multi:100"
            ::= { hwPDU8000DualEntry 38 }

        hwPDU8000DualMaininput1L3THDurate OBJECT-TYPE
            SYNTAX Integer32 (0..100)
            MAX-ACCESS read-only
            STATUS current
            DESCRIPTION
                "Main input 1 L3 THD-u rate. Unit:%. Multi:100"
            ::= { hwPDU8000DualEntry 39 }

        hwPDU8000DualMaininput1L1THDirate OBJECT-TYPE
            SYNTAX Integer32 (0..100)
            MAX-ACCESS read-only
            STATUS current
            DESCRIPTION
                "Main input 1 L1 THD-i rate. Unit:%. Multi:100"
            ::= { hwPDU8000DualEntry 40 }

        hwPDU8000DualMaininput1L2THDirate OBJECT-TYPE
            SYNTAX Integer32 (0..100)
            MAX-ACCESS read-only
            STATUS current
            DESCRIPTION
                "Main input 1 L2 THD-i rate. Unit:%. Multi:100"
            ::= { hwPDU8000DualEntry 41 }

        hwPDU8000DualMaininput1L3THDirate OBJECT-TYPE
            SYNTAX Integer32 (0..100)
            MAX-ACCESS read-only
            STATUS current
            DESCRIPTION
                "Main input 1 L3 THD-i rate. Unit:%. Multi:100"
            ::= { hwPDU8000DualEntry 42 }

        hwPDU8000DualMaininput1totalinputactivepower OBJECT-TYPE
            SYNTAX Integer32 (-750..750)
            MAX-ACCESS read-only
            STATUS current
            DESCRIPTION
                "Main input 1 total input active power. Unit:KW. Multi:10"
            ::= { hwPDU8000DualEntry 43 }

        hwPDU8000DualMaininput1totalinputapparentpower OBJECT-TYPE
            SYNTAX Integer32 (-750..750)
            MAX-ACCESS read-only
            STATUS current
            DESCRIPTION
                "Main input 1 total input apparent power. Unit:KVA. Multi:10"
            ::= { hwPDU8000DualEntry 44 }

        hwPDU8000DualMaininput1totalinputreactivepower OBJECT-TYPE
            SYNTAX Integer32 (-750..750)
            MAX-ACCESS read-only
            STATUS current
            DESCRIPTION
                "Main input 1 total input reactive power. Unit:KVAR. Multi:10"
            ::= { hwPDU8000DualEntry 45 }

        hwPDU8000DualMaininput2L1inputphasevoltage OBJECT-TYPE
            SYNTAX Integer32 (0..1000)
            MAX-ACCESS read-only
            STATUS current
            DESCRIPTION
                "Main input 2 L1 input phase voltage. Unit:V. Multi:10"
            ::= { hwPDU8000DualEntry 46 }

        hwPDU8000DualMaininput2L2inputphasevoltage OBJECT-TYPE
            SYNTAX Integer32 (0..1000)
            MAX-ACCESS read-only
            STATUS current
            DESCRIPTION
                "Main input 2 L2 input phase voltage. Unit:V. Multi:10"
            ::= { hwPDU8000DualEntry 47 }

        hwPDU8000DualMaininput2L3inputphasevoltage OBJECT-TYPE
            SYNTAX Integer32 (0..1000)
            MAX-ACCESS read-only
            STATUS current
            DESCRIPTION
                "Main input 2 L3 input phase voltage. Unit:V. Multi:10"
            ::= { hwPDU8000DualEntry 48 }

        hwPDU8000DualMaininput2L1L2inputlinevoltage OBJECT-TYPE
            SYNTAX Integer32 (0..1000)
            MAX-ACCESS read-only
            STATUS current
            DESCRIPTION
                "Main input 2 L1-L2 input line voltage. Unit:V. Multi:10"
            ::= { hwPDU8000DualEntry 49 }

        hwPDU8000DualMaininput2L2L3inputlinevoltage OBJECT-TYPE
            SYNTAX Integer32 (0..1000)
            MAX-ACCESS read-only
            STATUS current
            DESCRIPTION
                "Main input 2 L2-L3 input line voltage. Unit:V. Multi:10"
            ::= { hwPDU8000DualEntry 50 }

        hwPDU8000DualMaininput2L1L3inputlinevoltage OBJECT-TYPE
            SYNTAX Integer32 (0..1000)
            MAX-ACCESS read-only
            STATUS current
            DESCRIPTION
                "Main input 2 L1-L3 input line voltage. Unit:V. Multi:10"
            ::= { hwPDU8000DualEntry 51 }

        hwPDU8000DualMaininput2L1inputcurrent OBJECT-TYPE
            SYNTAX Integer32 (0..800)
            MAX-ACCESS read-only
            STATUS current
            DESCRIPTION
                "Main input 2 L1 input current. Unit:A. Multi:10"
            ::= { hwPDU8000DualEntry 52 }

        hwPDU8000DualMaininput2L2inputcurrent OBJECT-TYPE
            SYNTAX Integer32 (0..800)
            MAX-ACCESS read-only
            STATUS current
            DESCRIPTION
                "Main input 2 L2 input current. Unit:A. Multi:10"
            ::= { hwPDU8000DualEntry 53 }

        hwPDU8000DualMaininput2L3inputcurrent OBJECT-TYPE
            SYNTAX Integer32 (0..800)
            MAX-ACCESS read-only
            STATUS current
            DESCRIPTION
                "Main input 2 L3 input current. Unit:A. Multi:10"
            ::= { hwPDU8000DualEntry 54 }

        hwPDU8000DualMaininput2inputfrequency OBJECT-TYPE
            SYNTAX Integer32 (0..100)
            MAX-ACCESS read-only
            STATUS current
            DESCRIPTION
                "Main input 2 input frequency. Unit:Hz. Multi:100"
            ::= { hwPDU8000DualEntry 55 }

        hwPDU8000DualMaininput2L1inputactivepower OBJECT-TYPE
            SYNTAX Integer32 (-250..250)
            MAX-ACCESS read-only
            STATUS current
            DESCRIPTION
                "Main input 2 L1 input active power. Unit:KW. Multi:10"
            ::= { hwPDU8000DualEntry 56 }

        hwPDU8000DualMaininput2L2inputactivepower OBJECT-TYPE
            SYNTAX Integer32 (-250..250)
            MAX-ACCESS read-only
            STATUS current
            DESCRIPTION
                "Main input 2 L2 input active power. Unit:KW. Multi:10"
            ::= { hwPDU8000DualEntry 57 }

        hwPDU8000DualMaininput2L3inputactivepower OBJECT-TYPE
            SYNTAX Integer32 (-250..250)
            MAX-ACCESS read-only
            STATUS current
            DESCRIPTION
                "Main input 2 L3 input active power. Unit:KW. Multi:10"
            ::= { hwPDU8000DualEntry 58 }

        hwPDU8000DualMaininput2L1inputapparentpower OBJECT-TYPE
            SYNTAX Integer32 (-250..250)
            MAX-ACCESS read-only
            STATUS current
            DESCRIPTION
                "Main input 2 L1 input apparent power. Unit:KVA. Multi:10"
            ::= { hwPDU8000DualEntry 59 }

        hwPDU8000DualMaininput2L2inputapparentpower OBJECT-TYPE
            SYNTAX Integer32 (-250..250)
            MAX-ACCESS read-only
            STATUS current
            DESCRIPTION
                "Main input 2 L2 input apparent power. Unit:KVA. Multi:10"
            ::= { hwPDU8000DualEntry 60 }

        hwPDU8000DualMaininput2L3inputapparentpower OBJECT-TYPE
            SYNTAX Integer32 (-250..250)
            MAX-ACCESS read-only
            STATUS current
            DESCRIPTION
                "Main input 2 L3 input apparent power. Unit:KVA. Multi:10"
            ::= { hwPDU8000DualEntry 61 }

        hwPDU8000DualMaininput2L1inputreactivepower OBJECT-TYPE
            SYNTAX Integer32 (-250..250)
            MAX-ACCESS read-only
            STATUS current
            DESCRIPTION
                "Main input 2 L1 input reactive power. Unit:KVAR. Multi:10"
            ::= { hwPDU8000DualEntry 62 }

        hwPDU8000DualMaininput2L2inputreactivepower OBJECT-TYPE
            SYNTAX Integer32 (-250..250)
            MAX-ACCESS read-only
            STATUS current
            DESCRIPTION
                "Main input 2 L2 input reactive power. Unit:KVAR. Multi:10"
            ::= { hwPDU8000DualEntry 63 }

        hwPDU8000DualMaininput2L3inputreactivepower OBJECT-TYPE
            SYNTAX Integer32 (-250..250)
            MAX-ACCESS read-only
            STATUS current
            DESCRIPTION
                "Main input 2 L3 input reactive power. Unit:KVAR. Multi:10"
            ::= { hwPDU8000DualEntry 64 }

        hwPDU8000DualMaininput2L1inputpowerfactor OBJECT-TYPE
            SYNTAX Integer32 (-1..1)
            MAX-ACCESS read-only
            STATUS current
            DESCRIPTION
                "Main input 2 L1 input power factor. Multi:100"
            ::= { hwPDU8000DualEntry 65 }

        hwPDU8000DualMaininput2L2inputpowerfactor OBJECT-TYPE
            SYNTAX Integer32 (-1..1)
            MAX-ACCESS read-only
            STATUS current
            DESCRIPTION
                "Main input 2 L2 input power factor. Multi:100"
            ::= { hwPDU8000DualEntry 66 }

        hwPDU8000DualMaininput2L3inputpowerfactor OBJECT-TYPE
            SYNTAX Integer32 (-1..1)
            MAX-ACCESS read-only
            STATUS current
            DESCRIPTION
                "Main input 2 L3 input power factor. Multi:100"
            ::= { hwPDU8000DualEntry 67 }

        hwPDU8000DualMaininput2inputactiveelectricenergy OBJECT-TYPE
            SYNTAX Integer32 (0..21474836)
            MAX-ACCESS read-only
            STATUS current
            DESCRIPTION
                "Main input 2 input active electric energy. Unit:KWh. Multi:100"
            ::= { hwPDU8000DualEntry 68 }

        hwPDU8000DualMaininput2L1inputpowerloadrate OBJECT-TYPE
            SYNTAX Integer32 (0..150)
            MAX-ACCESS read-only
            STATUS current
            DESCRIPTION
                "Main input 2 L1 input power load rate. Unit:%."
            ::= { hwPDU8000DualEntry 69 }

        hwPDU8000DualMaininput2L2inputpowerloadrate OBJECT-TYPE
            SYNTAX Integer32 (0..150)
            MAX-ACCESS read-only
            STATUS current
            DESCRIPTION
                "Main input 2 L2 input power load rate. Unit:%."
            ::= { hwPDU8000DualEntry 70 }

        hwPDU8000DualMaininput2L3inputpowerloadrate OBJECT-TYPE
            SYNTAX Integer32 (0..150)
            MAX-ACCESS read-only
            STATUS current
            DESCRIPTION
                "Main input 2 L3 input power load rate. Unit:%."
            ::= { hwPDU8000DualEntry 71 }

        hwPDU8000DualMaininput2Nwirecurrent OBJECT-TYPE
            SYNTAX Integer32 (0..1000)
            MAX-ACCESS read-only
            STATUS current
            DESCRIPTION
                "Main input 2 N wire current. Unit:A. Multi:10"
            ::= { hwPDU8000DualEntry 72 }

        hwPDU8000DualMaininput2L1THDurate OBJECT-TYPE
            SYNTAX Integer32 (0..100)
            MAX-ACCESS read-only
            STATUS current
            DESCRIPTION
                "Main input 2 L1 THD-u rate. Unit:%. Multi:100"
            ::= { hwPDU8000DualEntry 73 }

        hwPDU8000DualMaininput2L2THDurate OBJECT-TYPE
            SYNTAX Integer32 (0..100)
            MAX-ACCESS read-only
            STATUS current
            DESCRIPTION
                "Main input 2 L2 THD-u rate. Unit:%. Multi:100"
            ::= { hwPDU8000DualEntry 74 }

        hwPDU8000DualMaininput2L3THDurate OBJECT-TYPE
            SYNTAX Integer32 (0..100)
            MAX-ACCESS read-only
            STATUS current
            DESCRIPTION
                "Main input 2 L3 THD-u rate. Unit:%. Multi:100"
            ::= { hwPDU8000DualEntry 75 }

        hwPDU8000DualMaininput2L1THDirate OBJECT-TYPE
            SYNTAX Integer32 (0..100)
            MAX-ACCESS read-only
            STATUS current
            DESCRIPTION
                "Main input 2 L1 THD-i rate. Unit:%. Multi:100"
            ::= { hwPDU8000DualEntry 76 }

        hwPDU8000DualMaininput2L2THDirate OBJECT-TYPE
            SYNTAX Integer32 (0..100)
            MAX-ACCESS read-only
            STATUS current
            DESCRIPTION
                "Main input 2 L2 THD-i rate. Unit:%. Multi:100"
            ::= { hwPDU8000DualEntry 77 }

        hwPDU8000DualMaininput2L3THDirate OBJECT-TYPE
            SYNTAX Integer32 (0..100)
            MAX-ACCESS read-only
            STATUS current
            DESCRIPTION
                "Main input 2 L3 THD-i rate. Unit:%. Multi:100"
            ::= { hwPDU8000DualEntry 78 }

        hwPDU8000DualMaininput2totalinputactivepower OBJECT-TYPE
            SYNTAX Integer32 (-750..750)
            MAX-ACCESS read-only
            STATUS current
            DESCRIPTION
                "Main input 2 total input active power. Unit:KW. Multi:10"
            ::= { hwPDU8000DualEntry 79 }

        hwPDU8000DualMaininput2totalinputapparentpower OBJECT-TYPE
            SYNTAX Integer32 (-750..750)
            MAX-ACCESS read-only
            STATUS current
            DESCRIPTION
                "Main input 2 total input apparent power. Unit:KVA. Multi:10"
            ::= { hwPDU8000DualEntry 80 }

        hwPDU8000DualMaininput2totalinputreactivepower OBJECT-TYPE
            SYNTAX Integer32 (-750..750)
            MAX-ACCESS read-only
            STATUS current
            DESCRIPTION
                "Main input 2 total input reactive power. Unit:KVAR. Multi:10"
            ::= { hwPDU8000DualEntry 81 }

        hwPDU8000DualRowStatus OBJECT-TYPE
            SYNTAX RowStatus
            MAX-ACCESS read-create
            STATUS current
            DESCRIPTION
                "The RowStatus of PDU8000"
            ::= { hwPDU8000DualEntry 100 }

        hwPDU8000DualMode1_2Table OBJECT-TYPE
            SYNTAX SEQUENCE OF HwPDU8000DualMode1_2Entry
            MAX-ACCESS not-accessible
             STATUS current
             DESCRIPTION
                "The table of PDU8000 Dual Module 1 and 2."
            ::= { hwPDU8000Dual 2 }

        hwPDU8000DualMode1_2Entry OBJECT-TYPE
                        SYNTAX HwPDU8000DualMode1_2Entry
            MAX-ACCESS not-accessible
             STATUS current
             DESCRIPTION
                "The table of PDU8000 Dual Module 1 and 2."
            INDEX { hwPDU8000DualMode1_2Index }
            ::= { hwPDU8000DualMode1_2Table 1 }

        HwPDU8000DualMode1_2Entry            ::= SEQUENCE {
                hwPDU8000DualMode1_2Index
                    Unsigned32,
                hwPDU8000DualMod1Branch1L1outputactiveelectricenergy
                    Integer32,
                hwPDU8000DualMod1Branch1L2outputactiveelectricenergy
                    Integer32,
                hwPDU8000DualMod1Branch1L3outputactiveelectricenergy
                    Integer32,
                hwPDU8000DualMod1Branch2L1outputactiveelectricenergy
                    Integer32,
                hwPDU8000DualMod1Branch2L2outputactiveelectricenergy
                    Integer32,
                hwPDU8000DualMod1Branch2L3outputactiveelectricenergy
                    Integer32,
                hwPDU8000DualMod1Branch3L1outputactiveelectricenergy
                    Integer32,
                hwPDU8000DualMod1Branch3L2outputactiveelectricenergy
                    Integer32,
                hwPDU8000DualMod1Branch3L3outputactiveelectricenergy
                    Integer32,
                hwPDU8000DualMod1Branch4L1outputactiveelectricenergy
                    Integer32,
                hwPDU8000DualMod1Branch4L2outputactiveelectricenergy
                    Integer32,
                hwPDU8000DualMod1Branch4L3outputactiveelectricenergy
                    Integer32,
                hwPDU8000DualMod1Branch5L1outputactiveelectricenergy
                    Integer32,
                hwPDU8000DualMod1Branch5L2outputactiveelectricenergy
                    Integer32,
                hwPDU8000DualMod1Branch5L3outputactiveelectricenergy
                    Integer32,
                hwPDU8000DualMod1Branch6L1outputactiveelectricenergy
                    Integer32,
                hwPDU8000DualMod1Branch6L2outputactiveelectricenergy
                    Integer32,
                hwPDU8000DualMod1Branch6L3outputactiveelectricenergy
                    Integer32,
                hwPDU8000DualMod1Branch7L1outputactiveelectricenergy
                    Integer32,
                hwPDU8000DualMod1Branch7L2outputactiveelectricenergy
                    Integer32,
                hwPDU8000DualMod1Branch7L3outputactiveelectricenergy
                    Integer32,
                hwPDU8000DualMod1Branch8L1outputactiveelectricenergy
                    Integer32,
                hwPDU8000DualMod1Branch8L2outputactiveelectricenergy
                    Integer32,
                hwPDU8000DualMod1Branch8L3outputactiveelectricenergy
                    Integer32,
                hwPDU8000DualMod1Branch9L1outputactiveelectricenergy
                    Integer32,
                hwPDU8000DualMod1Branch9L2outputactiveelectricenergy
                    Integer32,
                hwPDU8000DualMod1Branch9L3outputactiveelectricenergy
                    Integer32,
                hwPDU8000DualMod1Branch10L1outputactiveelectricenergy
                    Integer32,
                hwPDU8000DualMod1Branch10L2outputactiveelectricenergy
                    Integer32,
                hwPDU8000DualMod1Branch10L3outputactiveelectricenergy
                    Integer32,
                hwPDU8000DualMod1Branch11L1outputactiveelectricenergy
                    Integer32,
                hwPDU8000DualMod1Branch11L2outputactiveelectricenergy
                    Integer32,
                hwPDU8000DualMod1Branch11L3outputactiveelectricenergy
                    Integer32,
                hwPDU8000DualMod1Branch12L1outputactiveelectricenergy
                    Integer32,
                hwPDU8000DualMod1Branch12L2outputactiveelectricenergy
                    Integer32,
                hwPDU8000DualMod1Branch12L3outputactiveelectricenergy
                    Integer32,
                hwPDU8000DualMod2Branch1L1outputactiveelectricenergy
                    Integer32,
                hwPDU8000DualMod2Branch1L2outputactiveelectricenergy
                    Integer32,
                hwPDU8000DualMod2Branch1L3outputactiveelectricenergy
                    Integer32,
                hwPDU8000DualMod2Branch2L1outputactiveelectricenergy
                    Integer32,
                hwPDU8000DualMod2Branch2L2outputactiveelectricenergy
                    Integer32,
                hwPDU8000DualMod2Branch2L3outputactiveelectricenergy
                    Integer32,
                hwPDU8000DualMod2Branch3L1outputactiveelectricenergy
                    Integer32,
                hwPDU8000DualMod2Branch3L2outputactiveelectricenergy
                    Integer32,
                hwPDU8000DualMod2Branch3L3outputactiveelectricenergy
                    Integer32,
                hwPDU8000DualMod2Branch4L1outputactiveelectricenergy
                    Integer32,
                hwPDU8000DualMod2Branch4L2outputactiveelectricenergy
                    Integer32,
                hwPDU8000DualMod2Branch4L3outputactiveelectricenergy
                    Integer32,
                hwPDU8000DualMod2Branch5L1outputactiveelectricenergy
                    Integer32,
                hwPDU8000DualMod2Branch5L2outputactiveelectricenergy
                    Integer32,
                hwPDU8000DualMod2Branch5L3outputactiveelectricenergy
                    Integer32,
                hwPDU8000DualMod2Branch6L1outputactiveelectricenergy
                    Integer32,
                hwPDU8000DualMod2Branch6L2outputactiveelectricenergy
                    Integer32,
                hwPDU8000DualMod2Branch6L3outputactiveelectricenergy
                    Integer32,
                hwPDU8000DualMod2Branch7L1outputactiveelectricenergy
                    Integer32,
                hwPDU8000DualMod2Branch7L2outputactiveelectricenergy
                    Integer32,
                hwPDU8000DualMod2Branch7L3outputactiveelectricenergy
                    Integer32,
                hwPDU8000DualMod2Branch8L1outputactiveelectricenergy
                    Integer32,
                hwPDU8000DualMod2Branch8L2outputactiveelectricenergy
                    Integer32,
                hwPDU8000DualMod2Branch8L3outputactiveelectricenergy
                    Integer32,
                hwPDU8000DualMod2Branch9L1outputactiveelectricenergy
                    Integer32,
                hwPDU8000DualMod2Branch9L2outputactiveelectricenergy
                    Integer32,
                hwPDU8000DualMod2Branch9L3outputactiveelectricenergy
                    Integer32,
                hwPDU8000DualMod2Branch10L1outputactiveelectricenergy
                    Integer32,
                hwPDU8000DualMod2Branch10L2outputactiveelectricenergy
                    Integer32,
                hwPDU8000DualMod2Branch10L3outputactiveelectricenergy
                    Integer32,
                hwPDU8000DualMod2Branch11L1outputactiveelectricenergy
                    Integer32,
                hwPDU8000DualMod2Branch11L2outputactiveelectricenergy
                    Integer32,
                hwPDU8000DualMod2Branch11L3outputactiveelectricenergy
                    Integer32,
                hwPDU8000DualMod2Branch12L1outputactiveelectricenergy
                    Integer32,
                hwPDU8000DualMod2Branch12L2outputactiveelectricenergy
                    Integer32,
                hwPDU8000DualMod2Branch12L3outputactiveelectricenergy
                    Integer32,
                hwPDU8000DualMode1_2RowStatus
                    RowStatus
            }

        hwPDU8000DualMode1_2Index OBJECT-TYPE
            SYNTAX Unsigned32
            MAX-ACCESS read-only
            STATUS current
            DESCRIPTION
                "The index of PDU8000 Dual Module 1 and 2."
            ::= { hwPDU8000DualMode1_2Entry 1 }

        hwPDU8000DualMod1Branch1L1outputactiveelectricenergy OBJECT-TYPE
            SYNTAX Integer32 (0..21474836)
            MAX-ACCESS read-only
            STATUS current
            DESCRIPTION
                "Branch 1 L1 output active electric energy. Unit:KWh. Multi:100"
            ::= { hwPDU8000DualMode1_2Entry 2 }

        hwPDU8000DualMod1Branch1L2outputactiveelectricenergy OBJECT-TYPE
            SYNTAX Integer32 (0..21474836)
            MAX-ACCESS read-only
            STATUS current
            DESCRIPTION
                "Branch 1 L2 output active electric energy. Unit:KWh. Multi:100"
            ::= { hwPDU8000DualMode1_2Entry 3 }

        hwPDU8000DualMod1Branch1L3outputactiveelectricenergy OBJECT-TYPE
            SYNTAX Integer32 (0..21474836)
            MAX-ACCESS read-only
            STATUS current
            DESCRIPTION
                "Branch 1 L3 output active electric energy. Unit:KWh. Multi:100"
            ::= { hwPDU8000DualMode1_2Entry 4 }

        hwPDU8000DualMod1Branch2L1outputactiveelectricenergy OBJECT-TYPE
            SYNTAX Integer32 (0..21474836)
            MAX-ACCESS read-only
            STATUS current
            DESCRIPTION
                "Branch 2 L1 output active electric energy. Unit:KWh. Multi:100"
            ::= { hwPDU8000DualMode1_2Entry 5 }

        hwPDU8000DualMod1Branch2L2outputactiveelectricenergy OBJECT-TYPE
            SYNTAX Integer32 (0..21474836)
            MAX-ACCESS read-only
            STATUS current
            DESCRIPTION
                "Branch 2 L2 output active electric energy. Unit:KWh. Multi:100"
            ::= { hwPDU8000DualMode1_2Entry 6 }

        hwPDU8000DualMod1Branch2L3outputactiveelectricenergy OBJECT-TYPE
            SYNTAX Integer32 (0..21474836)
            MAX-ACCESS read-only
            STATUS current
            DESCRIPTION
                "Branch 2 L3 output active electric energy. Unit:KWh. Multi:100"
            ::= { hwPDU8000DualMode1_2Entry 7 }

        hwPDU8000DualMod1Branch3L1outputactiveelectricenergy OBJECT-TYPE
            SYNTAX Integer32 (0..21474836)
            MAX-ACCESS read-only
            STATUS current
            DESCRIPTION
                "Branch 3 L1 output active electric energy. Unit:KWh. Multi:100"
            ::= { hwPDU8000DualMode1_2Entry 8 }

        hwPDU8000DualMod1Branch3L2outputactiveelectricenergy OBJECT-TYPE
            SYNTAX Integer32 (0..21474836)
            MAX-ACCESS read-only
            STATUS current
            DESCRIPTION
                "Branch 3 L2 output active electric energy. Unit:KWh. Multi:100"
            ::= { hwPDU8000DualMode1_2Entry 9 }

        hwPDU8000DualMod1Branch3L3outputactiveelectricenergy OBJECT-TYPE
            SYNTAX Integer32 (0..21474836)
            MAX-ACCESS read-only
            STATUS current
            DESCRIPTION
                "Branch 3 L3 output active electric energy. Unit:KWh. Multi:100"
            ::= { hwPDU8000DualMode1_2Entry 10 }

        hwPDU8000DualMod1Branch4L1outputactiveelectricenergy OBJECT-TYPE
            SYNTAX Integer32 (0..21474836)
            MAX-ACCESS read-only
            STATUS current
            DESCRIPTION
                "Branch 4 L1 output active electric energy. Unit:KWh. Multi:100"
            ::= { hwPDU8000DualMode1_2Entry 11 }

        hwPDU8000DualMod1Branch4L2outputactiveelectricenergy OBJECT-TYPE
            SYNTAX Integer32 (0..21474836)
            MAX-ACCESS read-only
            STATUS current
            DESCRIPTION
                "Branch 4 L2 output active electric energy. Unit:KWh. Multi:100"
            ::= { hwPDU8000DualMode1_2Entry 12 }

        hwPDU8000DualMod1Branch4L3outputactiveelectricenergy OBJECT-TYPE
            SYNTAX Integer32 (0..21474836)
            MAX-ACCESS read-only
            STATUS current
            DESCRIPTION
                "Branch 4 L3 output active electric energy. Unit:KWh. Multi:100"
            ::= { hwPDU8000DualMode1_2Entry 13 }

        hwPDU8000DualMod1Branch5L1outputactiveelectricenergy OBJECT-TYPE
            SYNTAX Integer32 (0..21474836)
            MAX-ACCESS read-only
            STATUS current
            DESCRIPTION
                "Branch 5 L1 output active electric energy. Unit:KWh. Multi:100"
            ::= { hwPDU8000DualMode1_2Entry 14 }

        hwPDU8000DualMod1Branch5L2outputactiveelectricenergy OBJECT-TYPE
            SYNTAX Integer32 (0..21474836)
            MAX-ACCESS read-only
            STATUS current
            DESCRIPTION
                "Branch 5 L2 output active electric energy. Unit:KWh. Multi:100"
            ::= { hwPDU8000DualMode1_2Entry 15 }

        hwPDU8000DualMod1Branch5L3outputactiveelectricenergy OBJECT-TYPE
            SYNTAX Integer32 (0..21474836)
            MAX-ACCESS read-only
            STATUS current
            DESCRIPTION
                "Branch 5 L3 output active electric energy. Unit:KWh. Multi:100"
            ::= { hwPDU8000DualMode1_2Entry 16 }

        hwPDU8000DualMod1Branch6L1outputactiveelectricenergy OBJECT-TYPE
            SYNTAX Integer32 (0..21474836)
            MAX-ACCESS read-only
            STATUS current
            DESCRIPTION
                "Branch 6 L1 output active electric energy. Unit:KWh. Multi:100"
            ::= { hwPDU8000DualMode1_2Entry 17 }

        hwPDU8000DualMod1Branch6L2outputactiveelectricenergy OBJECT-TYPE
            SYNTAX Integer32 (0..21474836)
            MAX-ACCESS read-only
            STATUS current
            DESCRIPTION
                "Branch 6 L2 output active electric energy. Unit:KWh. Multi:100"
            ::= { hwPDU8000DualMode1_2Entry 18 }

        hwPDU8000DualMod1Branch6L3outputactiveelectricenergy OBJECT-TYPE
            SYNTAX Integer32 (0..21474836)
            MAX-ACCESS read-only
            STATUS current
            DESCRIPTION
                "Branch 6 L3 output active electric energy. Unit:KWh. Multi:100"
            ::= { hwPDU8000DualMode1_2Entry 19 }

        hwPDU8000DualMod1Branch7L1outputactiveelectricenergy OBJECT-TYPE
            SYNTAX Integer32 (0..21474836)
            MAX-ACCESS read-only
            STATUS current
            DESCRIPTION
                "Branch 7 L1 output active electric energy. Unit:KWh. Multi:100"
            ::= { hwPDU8000DualMode1_2Entry 20 }

        hwPDU8000DualMod1Branch7L2outputactiveelectricenergy OBJECT-TYPE
            SYNTAX Integer32 (0..21474836)
            MAX-ACCESS read-only
            STATUS current
            DESCRIPTION
                "Branch 7 L2 output active electric energy. Unit:KWh. Multi:100"
            ::= { hwPDU8000DualMode1_2Entry 21 }

        hwPDU8000DualMod1Branch7L3outputactiveelectricenergy OBJECT-TYPE
            SYNTAX Integer32 (0..21474836)
            MAX-ACCESS read-only
            STATUS current
            DESCRIPTION
                "Branch 7 L3 output active electric energy. Unit:KWh. Multi:100"
            ::= { hwPDU8000DualMode1_2Entry 22 }

        hwPDU8000DualMod1Branch8L1outputactiveelectricenergy OBJECT-TYPE
            SYNTAX Integer32 (0..21474836)
            MAX-ACCESS read-only
            STATUS current
            DESCRIPTION
                "Branch 8 L1 output active electric energy. Unit:KWh. Multi:100"
            ::= { hwPDU8000DualMode1_2Entry 23 }

        hwPDU8000DualMod1Branch8L2outputactiveelectricenergy OBJECT-TYPE
            SYNTAX Integer32 (0..21474836)
            MAX-ACCESS read-only
            STATUS current
            DESCRIPTION
                "Branch 8 L2 output active electric energy. Unit:KWh. Multi:100"
            ::= { hwPDU8000DualMode1_2Entry 24 }

        hwPDU8000DualMod1Branch8L3outputactiveelectricenergy OBJECT-TYPE
            SYNTAX Integer32 (0..21474836)
            MAX-ACCESS read-only
            STATUS current
            DESCRIPTION
                "Branch 8 L3 output active electric energy. Unit:KWh. Multi:100"
            ::= { hwPDU8000DualMode1_2Entry 25 }

        hwPDU8000DualMod1Branch9L1outputactiveelectricenergy OBJECT-TYPE
            SYNTAX Integer32 (0..21474836)
            MAX-ACCESS read-only
            STATUS current
            DESCRIPTION
                "Branch 9 L1 output active electric energy. Unit:KWh. Multi:100"
            ::= { hwPDU8000DualMode1_2Entry 26 }

        hwPDU8000DualMod1Branch9L2outputactiveelectricenergy OBJECT-TYPE
            SYNTAX Integer32 (0..21474836)
            MAX-ACCESS read-only
            STATUS current
            DESCRIPTION
                "Branch 9 L2 output active electric energy. Unit:KWh. Multi:100"
            ::= { hwPDU8000DualMode1_2Entry 27 }

        hwPDU8000DualMod1Branch9L3outputactiveelectricenergy OBJECT-TYPE
            SYNTAX Integer32 (0..21474836)
            MAX-ACCESS read-only
            STATUS current
            DESCRIPTION
                "Branch 9 L3 output active electric energy. Unit:KWh. Multi:100"
            ::= { hwPDU8000DualMode1_2Entry 28 }

        hwPDU8000DualMod1Branch10L1outputactiveelectricenergy OBJECT-TYPE
            SYNTAX Integer32 (0..21474836)
            MAX-ACCESS read-only
            STATUS current
            DESCRIPTION
                "Branch 10 L1 output active electric energy. Unit:KWh. Multi:100"
            ::= { hwPDU8000DualMode1_2Entry 29 }

        hwPDU8000DualMod1Branch10L2outputactiveelectricenergy OBJECT-TYPE
            SYNTAX Integer32 (0..21474836)
            MAX-ACCESS read-only
            STATUS current
            DESCRIPTION
                "Branch 10 L2 output active electric energy. Unit:KWh. Multi:100"
            ::= { hwPDU8000DualMode1_2Entry 30 }

        hwPDU8000DualMod1Branch10L3outputactiveelectricenergy OBJECT-TYPE
            SYNTAX Integer32 (0..21474836)
            MAX-ACCESS read-only
            STATUS current
            DESCRIPTION
                "Branch 10 L3 output active electric energy. Unit:KWh. Multi:100"
            ::= { hwPDU8000DualMode1_2Entry 31 }

        hwPDU8000DualMod1Branch11L1outputactiveelectricenergy OBJECT-TYPE
            SYNTAX Integer32 (0..21474836)
            MAX-ACCESS read-only
            STATUS current
            DESCRIPTION
                "Branch 11 L1 output active electric energy. Unit:KWh. Multi:100"
            ::= { hwPDU8000DualMode1_2Entry 32 }

        hwPDU8000DualMod1Branch11L2outputactiveelectricenergy OBJECT-TYPE
            SYNTAX Integer32 (0..21474836)
            MAX-ACCESS read-only
            STATUS current
            DESCRIPTION
                "Branch 11 L2 output active electric energy. Unit:KWh. Multi:100"
            ::= { hwPDU8000DualMode1_2Entry 33 }

        hwPDU8000DualMod1Branch11L3outputactiveelectricenergy OBJECT-TYPE
            SYNTAX Integer32 (0..21474836)
            MAX-ACCESS read-only
            STATUS current
            DESCRIPTION
                "Branch 11 L3 output active electric energy. Unit:KWh. Multi:100"
            ::= { hwPDU8000DualMode1_2Entry 34 }

        hwPDU8000DualMod1Branch12L1outputactiveelectricenergy OBJECT-TYPE
            SYNTAX Integer32 (0..21474836)
            MAX-ACCESS read-only
            STATUS current
            DESCRIPTION
                "Branch 12 L1 output active electric energy. Unit:KWh. Multi:100"
            ::= { hwPDU8000DualMode1_2Entry 35 }

        hwPDU8000DualMod1Branch12L2outputactiveelectricenergy OBJECT-TYPE
            SYNTAX Integer32 (0..21474836)
            MAX-ACCESS read-only
            STATUS current
            DESCRIPTION
                "Branch 12 L2 output active electric energy. Unit:KWh. Multi:100"
            ::= { hwPDU8000DualMode1_2Entry 36 }

        hwPDU8000DualMod1Branch12L3outputactiveelectricenergy OBJECT-TYPE
            SYNTAX Integer32 (0..21474836)
            MAX-ACCESS read-only
            STATUS current
            DESCRIPTION
                "Branch 12 L3 output active electric energy. Unit:KWh. Multi:100"
            ::= { hwPDU8000DualMode1_2Entry 37 }

        hwPDU8000DualMod2Branch1L1outputactiveelectricenergy OBJECT-TYPE
            SYNTAX Integer32 (0..21474836)
            MAX-ACCESS read-only
            STATUS current
            DESCRIPTION
                "Branch 1 L1 output active electric energy. Unit:KWh. Multi:100"
            ::= { hwPDU8000DualMode1_2Entry 38 }

        hwPDU8000DualMod2Branch1L2outputactiveelectricenergy OBJECT-TYPE
            SYNTAX Integer32 (0..21474836)
            MAX-ACCESS read-only
            STATUS current
            DESCRIPTION
                "Branch 1 L2 output active electric energy. Unit:KWh. Multi:100"
            ::= { hwPDU8000DualMode1_2Entry 39 }

        hwPDU8000DualMod2Branch1L3outputactiveelectricenergy OBJECT-TYPE
            SYNTAX Integer32 (0..21474836)
            MAX-ACCESS read-only
            STATUS current
            DESCRIPTION
                "Branch 1 L3 output active electric energy. Unit:KWh. Multi:100"
            ::= { hwPDU8000DualMode1_2Entry 40 }

        hwPDU8000DualMod2Branch2L1outputactiveelectricenergy OBJECT-TYPE
            SYNTAX Integer32 (0..21474836)
            MAX-ACCESS read-only
            STATUS current
            DESCRIPTION
                "Branch 2 L1 output active electric energy. Unit:KWh. Multi:100"
            ::= { hwPDU8000DualMode1_2Entry 41 }

        hwPDU8000DualMod2Branch2L2outputactiveelectricenergy OBJECT-TYPE
            SYNTAX Integer32 (0..21474836)
            MAX-ACCESS read-only
            STATUS current
            DESCRIPTION
                "Branch 2 L2 output active electric energy. Unit:KWh. Multi:100"
            ::= { hwPDU8000DualMode1_2Entry 42 }

        hwPDU8000DualMod2Branch2L3outputactiveelectricenergy OBJECT-TYPE
            SYNTAX Integer32 (0..21474836)
            MAX-ACCESS read-only
            STATUS current
            DESCRIPTION
                "Branch 2 L3 output active electric energy. Unit:KWh. Multi:100"
            ::= { hwPDU8000DualMode1_2Entry 43 }

        hwPDU8000DualMod2Branch3L1outputactiveelectricenergy OBJECT-TYPE
            SYNTAX Integer32 (0..21474836)
            MAX-ACCESS read-only
            STATUS current
            DESCRIPTION
                "Branch 3 L1 output active electric energy. Unit:KWh. Multi:100"
            ::= { hwPDU8000DualMode1_2Entry 44 }

        hwPDU8000DualMod2Branch3L2outputactiveelectricenergy OBJECT-TYPE
            SYNTAX Integer32 (0..21474836)
            MAX-ACCESS read-only
            STATUS current
            DESCRIPTION
                "Branch 3 L2 output active electric energy. Unit:KWh. Multi:100"
            ::= { hwPDU8000DualMode1_2Entry 45 }

        hwPDU8000DualMod2Branch3L3outputactiveelectricenergy OBJECT-TYPE
            SYNTAX Integer32 (0..21474836)
            MAX-ACCESS read-only
            STATUS current
            DESCRIPTION
                "Branch 3 L3 output active electric energy. Unit:KWh. Multi:100"
            ::= { hwPDU8000DualMode1_2Entry 46 }

        hwPDU8000DualMod2Branch4L1outputactiveelectricenergy OBJECT-TYPE
            SYNTAX Integer32 (0..21474836)
            MAX-ACCESS read-only
            STATUS current
            DESCRIPTION
                "Branch 4 L1 output active electric energy. Unit:KWh. Multi:100"
            ::= { hwPDU8000DualMode1_2Entry 47 }

        hwPDU8000DualMod2Branch4L2outputactiveelectricenergy OBJECT-TYPE
            SYNTAX Integer32 (0..21474836)
            MAX-ACCESS read-only
            STATUS current
            DESCRIPTION
                "Branch 4 L2 output active electric energy. Unit:KWh. Multi:100"
            ::= { hwPDU8000DualMode1_2Entry 48 }

        hwPDU8000DualMod2Branch4L3outputactiveelectricenergy OBJECT-TYPE
            SYNTAX Integer32 (0..21474836)
            MAX-ACCESS read-only
            STATUS current
            DESCRIPTION
                "Branch 4 L3 output active electric energy. Unit:KWh. Multi:100"
            ::= { hwPDU8000DualMode1_2Entry 49 }

        hwPDU8000DualMod2Branch5L1outputactiveelectricenergy OBJECT-TYPE
            SYNTAX Integer32 (0..21474836)
            MAX-ACCESS read-only
            STATUS current
            DESCRIPTION
                "Branch 5 L1 output active electric energy. Unit:KWh. Multi:100"
            ::= { hwPDU8000DualMode1_2Entry 50 }

        hwPDU8000DualMod2Branch5L2outputactiveelectricenergy OBJECT-TYPE
            SYNTAX Integer32 (0..21474836)
            MAX-ACCESS read-only
            STATUS current
            DESCRIPTION
                "Branch 5 L2 output active electric energy. Unit:KWh. Multi:100"
            ::= { hwPDU8000DualMode1_2Entry 51 }

        hwPDU8000DualMod2Branch5L3outputactiveelectricenergy OBJECT-TYPE
            SYNTAX Integer32 (0..21474836)
            MAX-ACCESS read-only
            STATUS current
            DESCRIPTION
                "Branch 5 L3 output active electric energy. Unit:KWh. Multi:100"
            ::= { hwPDU8000DualMode1_2Entry 52 }

        hwPDU8000DualMod2Branch6L1outputactiveelectricenergy OBJECT-TYPE
            SYNTAX Integer32 (0..21474836)
            MAX-ACCESS read-only
            STATUS current
            DESCRIPTION
                "Branch 6 L1 output active electric energy. Unit:KWh. Multi:100"
            ::= { hwPDU8000DualMode1_2Entry 53 }

        hwPDU8000DualMod2Branch6L2outputactiveelectricenergy OBJECT-TYPE
            SYNTAX Integer32 (0..21474836)
            MAX-ACCESS read-only
            STATUS current
            DESCRIPTION
                "Branch 6 L2 output active electric energy. Unit:KWh. Multi:100"
            ::= { hwPDU8000DualMode1_2Entry 54 }

        hwPDU8000DualMod2Branch6L3outputactiveelectricenergy OBJECT-TYPE
            SYNTAX Integer32 (0..21474836)
            MAX-ACCESS read-only
            STATUS current
            DESCRIPTION
                "Branch 6 L3 output active electric energy. Unit:KWh. Multi:100"
            ::= { hwPDU8000DualMode1_2Entry 55 }

        hwPDU8000DualMod2Branch7L1outputactiveelectricenergy OBJECT-TYPE
            SYNTAX Integer32 (0..21474836)
            MAX-ACCESS read-only
            STATUS current
            DESCRIPTION
                "Branch 7 L1 output active electric energy. Unit:KWh. Multi:100"
            ::= { hwPDU8000DualMode1_2Entry 56 }

        hwPDU8000DualMod2Branch7L2outputactiveelectricenergy OBJECT-TYPE
            SYNTAX Integer32 (0..21474836)
            MAX-ACCESS read-only
            STATUS current
            DESCRIPTION
                "Branch 7 L2 output active electric energy. Unit:KWh. Multi:100"
            ::= { hwPDU8000DualMode1_2Entry 57 }

        hwPDU8000DualMod2Branch7L3outputactiveelectricenergy OBJECT-TYPE
            SYNTAX Integer32 (0..21474836)
            MAX-ACCESS read-only
            STATUS current
            DESCRIPTION
                "Branch 7 L3 output active electric energy. Unit:KWh. Multi:100"
            ::= { hwPDU8000DualMode1_2Entry 58 }

        hwPDU8000DualMod2Branch8L1outputactiveelectricenergy OBJECT-TYPE
            SYNTAX Integer32 (0..21474836)
            MAX-ACCESS read-only
            STATUS current
            DESCRIPTION
                "Branch 8 L1 output active electric energy. Unit:KWh. Multi:100"
            ::= { hwPDU8000DualMode1_2Entry 59 }

        hwPDU8000DualMod2Branch8L2outputactiveelectricenergy OBJECT-TYPE
            SYNTAX Integer32 (0..21474836)
            MAX-ACCESS read-only
            STATUS current
            DESCRIPTION
                "Branch 8 L2 output active electric energy. Unit:KWh. Multi:100"
            ::= { hwPDU8000DualMode1_2Entry 60 }

        hwPDU8000DualMod2Branch8L3outputactiveelectricenergy OBJECT-TYPE
            SYNTAX Integer32 (0..21474836)
            MAX-ACCESS read-only
            STATUS current
            DESCRIPTION
                "Branch 8 L3 output active electric energy. Unit:KWh. Multi:100"
            ::= { hwPDU8000DualMode1_2Entry 61 }

        hwPDU8000DualMod2Branch9L1outputactiveelectricenergy OBJECT-TYPE
            SYNTAX Integer32 (0..21474836)
            MAX-ACCESS read-only
            STATUS current
            DESCRIPTION
                "Branch 9 L1 output active electric energy. Unit:KWh. Multi:100"
            ::= { hwPDU8000DualMode1_2Entry 62 }

        hwPDU8000DualMod2Branch9L2outputactiveelectricenergy OBJECT-TYPE
            SYNTAX Integer32 (0..21474836)
            MAX-ACCESS read-only
            STATUS current
            DESCRIPTION
                "Branch 9 L2 output active electric energy. Unit:KWh. Multi:100"
            ::= { hwPDU8000DualMode1_2Entry 63 }

        hwPDU8000DualMod2Branch9L3outputactiveelectricenergy OBJECT-TYPE
            SYNTAX Integer32 (0..21474836)
            MAX-ACCESS read-only
            STATUS current
            DESCRIPTION
                "Branch 9 L3 output active electric energy. Unit:KWh. Multi:100"
            ::= { hwPDU8000DualMode1_2Entry 64 }

        hwPDU8000DualMod2Branch10L1outputactiveelectricenergy OBJECT-TYPE
            SYNTAX Integer32 (0..21474836)
            MAX-ACCESS read-only
            STATUS current
            DESCRIPTION
                "Branch 10 L1 output active electric energy. Unit:KWh. Multi:100"
            ::= { hwPDU8000DualMode1_2Entry 65 }

        hwPDU8000DualMod2Branch10L2outputactiveelectricenergy OBJECT-TYPE
            SYNTAX Integer32 (0..21474836)
            MAX-ACCESS read-only
            STATUS current
            DESCRIPTION
                "Branch 10 L2 output active electric energy. Unit:KWh. Multi:100"
            ::= { hwPDU8000DualMode1_2Entry 66 }

        hwPDU8000DualMod2Branch10L3outputactiveelectricenergy OBJECT-TYPE
            SYNTAX Integer32 (0..21474836)
            MAX-ACCESS read-only
            STATUS current
            DESCRIPTION
                "Branch 10 L3 output active electric energy. Unit:KWh. Multi:100"
            ::= { hwPDU8000DualMode1_2Entry 67 }

        hwPDU8000DualMod2Branch11L1outputactiveelectricenergy OBJECT-TYPE
            SYNTAX Integer32 (0..21474836)
            MAX-ACCESS read-only
            STATUS current
            DESCRIPTION
                "Branch 11 L1 output active electric energy. Unit:KWh. Multi:100"
            ::= { hwPDU8000DualMode1_2Entry 68 }

        hwPDU8000DualMod2Branch11L2outputactiveelectricenergy OBJECT-TYPE
            SYNTAX Integer32 (0..21474836)
            MAX-ACCESS read-only
            STATUS current
            DESCRIPTION
                "Branch 11 L2 output active electric energy. Unit:KWh. Multi:100"
            ::= { hwPDU8000DualMode1_2Entry 69 }

        hwPDU8000DualMod2Branch11L3outputactiveelectricenergy OBJECT-TYPE
            SYNTAX Integer32 (0..21474836)
            MAX-ACCESS read-only
            STATUS current
            DESCRIPTION
                "Branch 11 L3 output active electric energy. Unit:KWh. Multi:100"
            ::= { hwPDU8000DualMode1_2Entry 70 }

        hwPDU8000DualMod2Branch12L1outputactiveelectricenergy OBJECT-TYPE
            SYNTAX Integer32 (0..21474836)
            MAX-ACCESS read-only
            STATUS current
            DESCRIPTION
                "Branch 12 L1 output active electric energy. Unit:KWh. Multi:100"
            ::= { hwPDU8000DualMode1_2Entry 71 }

        hwPDU8000DualMod2Branch12L2outputactiveelectricenergy OBJECT-TYPE
            SYNTAX Integer32 (0..21474836)
            MAX-ACCESS read-only
            STATUS current
            DESCRIPTION
                "Branch 12 L2 output active electric energy. Unit:KWh. Multi:100"
            ::= { hwPDU8000DualMode1_2Entry 72 }

        hwPDU8000DualMod2Branch12L3outputactiveelectricenergy OBJECT-TYPE
            SYNTAX Integer32 (0..21474836)
            MAX-ACCESS read-only
            STATUS current
            DESCRIPTION
                "Branch 12 L3 output active electric energy. Unit:KWh. Multi:100"
            ::= { hwPDU8000DualMode1_2Entry 73 }

        hwPDU8000DualMode1_2RowStatus OBJECT-TYPE
            SYNTAX RowStatus
            MAX-ACCESS read-create
            STATUS current
            DESCRIPTION
                "The row status of Deviece."
            ::= { hwPDU8000DualMode1_2Entry 100 }

        hwPDU8000DualMode3_4Table OBJECT-TYPE
            SYNTAX SEQUENCE OF HwPDU8000DualMode3_4Entry
            MAX-ACCESS not-accessible
             STATUS current
             DESCRIPTION
                "The table of PDU8000 Dual Module 3 and 4."
            ::= { hwPDU8000Dual 3 }

        hwPDU8000DualMode3_4Entry OBJECT-TYPE
                        SYNTAX HwPDU8000DualMode3_4Entry
            MAX-ACCESS not-accessible
             STATUS current
             DESCRIPTION
                "The table of PDU8000 Dual Module 3 and 4."
            INDEX { hwPDU8000DualMode3_4Index }
            ::= { hwPDU8000DualMode3_4Table 1 }

        HwPDU8000DualMode3_4Entry            ::= SEQUENCE {
                hwPDU8000DualMode3_4Index
                    Unsigned32,
                hwPDU8000DualMod3Branch1L1outputactiveelectricenergy
                    Integer32,
                hwPDU8000DualMod3Branch1L2outputactiveelectricenergy
                    Integer32,
                hwPDU8000DualMod3Branch1L3outputactiveelectricenergy
                    Integer32,
                hwPDU8000DualMod3Branch2L1outputactiveelectricenergy
                    Integer32,
                hwPDU8000DualMod3Branch2L2outputactiveelectricenergy
                    Integer32,
                hwPDU8000DualMod3Branch2L3outputactiveelectricenergy
                    Integer32,
                hwPDU8000DualMod3Branch3L1outputactiveelectricenergy
                    Integer32,
                hwPDU8000DualMod3Branch3L2outputactiveelectricenergy
                    Integer32,
                hwPDU8000DualMod3Branch3L3outputactiveelectricenergy
                    Integer32,
                hwPDU8000DualMod3Branch4L1outputactiveelectricenergy
                    Integer32,
                hwPDU8000DualMod3Branch4L2outputactiveelectricenergy
                    Integer32,
                hwPDU8000DualMod3Branch4L3outputactiveelectricenergy
                    Integer32,
                hwPDU8000DualMod3Branch5L1outputactiveelectricenergy
                    Integer32,
                hwPDU8000DualMod3Branch5L2outputactiveelectricenergy
                    Integer32,
                hwPDU8000DualMod3Branch5L3outputactiveelectricenergy
                    Integer32,
                hwPDU8000DualMod3Branch6L1outputactiveelectricenergy
                    Integer32,
                hwPDU8000DualMod3Branch6L2outputactiveelectricenergy
                    Integer32,
                hwPDU8000DualMod3Branch6L3outputactiveelectricenergy
                    Integer32,
                hwPDU8000DualMod3Branch7L1outputactiveelectricenergy
                    Integer32,
                hwPDU8000DualMod3Branch7L2outputactiveelectricenergy
                    Integer32,
                hwPDU8000DualMod3Branch7L3outputactiveelectricenergy
                    Integer32,
                hwPDU8000DualMod3Branch8L1outputactiveelectricenergy
                    Integer32,
                hwPDU8000DualMod3Branch8L2outputactiveelectricenergy
                    Integer32,
                hwPDU8000DualMod3Branch8L3outputactiveelectricenergy
                    Integer32,
                hwPDU8000DualMod3Branch9L1outputactiveelectricenergy
                    Integer32,
                hwPDU8000DualMod3Branch9L2outputactiveelectricenergy
                    Integer32,
                hwPDU8000DualMod3Branch9L3outputactiveelectricenergy
                    Integer32,
                hwPDU8000DualMod3Branch10L1outputactiveelectricenergy
                    Integer32,
                hwPDU8000DualMod3Branch10L2outputactiveelectricenergy
                    Integer32,
                hwPDU8000DualMod3Branch10L3outputactiveelectricenergy
                    Integer32,
                hwPDU8000DualMod3Branch11L1outputactiveelectricenergy
                    Integer32,
                hwPDU8000DualMod3Branch11L2outputactiveelectricenergy
                    Integer32,
                hwPDU8000DualMod3Branch11L3outputactiveelectricenergy
                    Integer32,
                hwPDU8000DualMod3Branch12L1outputactiveelectricenergy
                    Integer32,
                hwPDU8000DualMod3Branch12L2outputactiveelectricenergy
                    Integer32,
                hwPDU8000DualMod3Branch12L3outputactiveelectricenergy
                    Integer32,
                hwPDU8000DualMod4Branch1L1outputactiveelectricenergy
                    Integer32,
                hwPDU8000DualMod4Branch1L2outputactiveelectricenergy
                    Integer32,
                hwPDU8000DualMod4Branch1L3outputactiveelectricenergy
                    Integer32,
                hwPDU8000DualMod4Branch2L1outputactiveelectricenergy
                    Integer32,
                hwPDU8000DualMod4Branch2L2outputactiveelectricenergy
                    Integer32,
                hwPDU8000DualMod4Branch2L3outputactiveelectricenergy
                    Integer32,
                hwPDU8000DualMod4Branch3L1outputactiveelectricenergy
                    Integer32,
                hwPDU8000DualMod4Branch3L2outputactiveelectricenergy
                    Integer32,
                hwPDU8000DualMod4Branch3L3outputactiveelectricenergy
                    Integer32,
                hwPDU8000DualMod4Branch4L1outputactiveelectricenergy
                    Integer32,
                hwPDU8000DualMod4Branch4L2outputactiveelectricenergy
                    Integer32,
                hwPDU8000DualMod4Branch4L3outputactiveelectricenergy
                    Integer32,
                hwPDU8000DualMod4Branch5L1outputactiveelectricenergy
                    Integer32,
                hwPDU8000DualMod4Branch5L2outputactiveelectricenergy
                    Integer32,
                hwPDU8000DualMod4Branch5L3outputactiveelectricenergy
                    Integer32,
                hwPDU8000DualMod4Branch6L1outputactiveelectricenergy
                    Integer32,
                hwPDU8000DualMod4Branch6L2outputactiveelectricenergy
                    Integer32,
                hwPDU8000DualMod4Branch6L3outputactiveelectricenergy
                    Integer32,
                hwPDU8000DualMod4Branch7L1outputactiveelectricenergy
                    Integer32,
                hwPDU8000DualMod4Branch7L2outputactiveelectricenergy
                    Integer32,
                hwPDU8000DualMod4Branch7L3outputactiveelectricenergy
                    Integer32,
                hwPDU8000DualMod4Branch8L1outputactiveelectricenergy
                    Integer32,
                hwPDU8000DualMod4Branch8L2outputactiveelectricenergy
                    Integer32,
                hwPDU8000DualMod4Branch8L3outputactiveelectricenergy
                    Integer32,
                hwPDU8000DualMod4Branch9L1outputactiveelectricenergy
                    Integer32,
                hwPDU8000DualMod4Branch9L2outputactiveelectricenergy
                    Integer32,
                hwPDU8000DualMod4Branch9L3outputactiveelectricenergy
                    Integer32,
                hwPDU8000DualMod4Branch10L1outputactiveelectricenergy
                    Integer32,
                hwPDU8000DualMod4Branch10L2outputactiveelectricenergy
                    Integer32,
                hwPDU8000DualMod4Branch10L3outputactiveelectricenergy
                    Integer32,
                hwPDU8000DualMod4Branch11L1outputactiveelectricenergy
                    Integer32,
                hwPDU8000DualMod4Branch11L2outputactiveelectricenergy
                    Integer32,
                hwPDU8000DualMod4Branch11L3outputactiveelectricenergy
                    Integer32,
                hwPDU8000DualMod4Branch12L1outputactiveelectricenergy
                    Integer32,
                hwPDU8000DualMod4Branch12L2outputactiveelectricenergy
                    Integer32,
                hwPDU8000DualMod4Branch12L3outputactiveelectricenergy
                    Integer32,
                hwPDU8000DualMode3_4RowStatus
                    RowStatus
            }

        hwPDU8000DualMode3_4Index OBJECT-TYPE
            SYNTAX Unsigned32
            MAX-ACCESS read-only
            STATUS current
            DESCRIPTION
                "The index of PDU8000 Dual Module 3 and 4."
            ::= { hwPDU8000DualMode3_4Entry 1 }

        hwPDU8000DualMod3Branch1L1outputactiveelectricenergy OBJECT-TYPE
            SYNTAX Integer32 (0..21474836)
            MAX-ACCESS read-only
            STATUS current
            DESCRIPTION
                "Branch 1 L1 output active electric energy. Unit:KWh. Multi:100"
            ::= { hwPDU8000DualMode3_4Entry 2 }

        hwPDU8000DualMod3Branch1L2outputactiveelectricenergy OBJECT-TYPE
            SYNTAX Integer32 (0..21474836)
            MAX-ACCESS read-only
            STATUS current
            DESCRIPTION
                "Branch 1 L2 output active electric energy. Unit:KWh. Multi:100"
            ::= { hwPDU8000DualMode3_4Entry 3 }

        hwPDU8000DualMod3Branch1L3outputactiveelectricenergy OBJECT-TYPE
            SYNTAX Integer32 (0..21474836)
            MAX-ACCESS read-only
            STATUS current
            DESCRIPTION
                "Branch 1 L3 output active electric energy. Unit:KWh. Multi:100"
            ::= { hwPDU8000DualMode3_4Entry 4 }

        hwPDU8000DualMod3Branch2L1outputactiveelectricenergy OBJECT-TYPE
            SYNTAX Integer32 (0..21474836)
            MAX-ACCESS read-only
            STATUS current
            DESCRIPTION
                "Branch 2 L1 output active electric energy. Unit:KWh. Multi:100"
            ::= { hwPDU8000DualMode3_4Entry 5 }

        hwPDU8000DualMod3Branch2L2outputactiveelectricenergy OBJECT-TYPE
            SYNTAX Integer32 (0..21474836)
            MAX-ACCESS read-only
            STATUS current
            DESCRIPTION
                "Branch 2 L2 output active electric energy. Unit:KWh. Multi:100"
            ::= { hwPDU8000DualMode3_4Entry 6 }

        hwPDU8000DualMod3Branch2L3outputactiveelectricenergy OBJECT-TYPE
            SYNTAX Integer32 (0..21474836)
            MAX-ACCESS read-only
            STATUS current
            DESCRIPTION
                "Branch 2 L3 output active electric energy. Unit:KWh. Multi:100"
            ::= { hwPDU8000DualMode3_4Entry 7 }

        hwPDU8000DualMod3Branch3L1outputactiveelectricenergy OBJECT-TYPE
            SYNTAX Integer32 (0..21474836)
            MAX-ACCESS read-only
            STATUS current
            DESCRIPTION
                "Branch 3 L1 output active electric energy. Unit:KWh. Multi:100"
            ::= { hwPDU8000DualMode3_4Entry 8 }

        hwPDU8000DualMod3Branch3L2outputactiveelectricenergy OBJECT-TYPE
            SYNTAX Integer32 (0..21474836)
            MAX-ACCESS read-only
            STATUS current
            DESCRIPTION
                "Branch 3 L2 output active electric energy. Unit:KWh. Multi:100"
            ::= { hwPDU8000DualMode3_4Entry 9 }

        hwPDU8000DualMod3Branch3L3outputactiveelectricenergy OBJECT-TYPE
            SYNTAX Integer32 (0..21474836)
            MAX-ACCESS read-only
            STATUS current
            DESCRIPTION
                "Branch 3 L3 output active electric energy. Unit:KWh. Multi:100"
            ::= { hwPDU8000DualMode3_4Entry 10 }

        hwPDU8000DualMod3Branch4L1outputactiveelectricenergy OBJECT-TYPE
            SYNTAX Integer32 (0..21474836)
            MAX-ACCESS read-only
            STATUS current
            DESCRIPTION
                "Branch 4 L1 output active electric energy. Unit:KWh. Multi:100"
            ::= { hwPDU8000DualMode3_4Entry 11 }

        hwPDU8000DualMod3Branch4L2outputactiveelectricenergy OBJECT-TYPE
            SYNTAX Integer32 (0..21474836)
            MAX-ACCESS read-only
            STATUS current
            DESCRIPTION
                "Branch 4 L2 output active electric energy. Unit:KWh. Multi:100"
            ::= { hwPDU8000DualMode3_4Entry 12 }

        hwPDU8000DualMod3Branch4L3outputactiveelectricenergy OBJECT-TYPE
            SYNTAX Integer32 (0..21474836)
            MAX-ACCESS read-only
            STATUS current
            DESCRIPTION
                "Branch 4 L3 output active electric energy. Unit:KWh. Multi:100"
            ::= { hwPDU8000DualMode3_4Entry 13 }

        hwPDU8000DualMod3Branch5L1outputactiveelectricenergy OBJECT-TYPE
            SYNTAX Integer32 (0..21474836)
            MAX-ACCESS read-only
            STATUS current
            DESCRIPTION
                "Branch 5 L1 output active electric energy. Unit:KWh. Multi:100"
            ::= { hwPDU8000DualMode3_4Entry 14 }

        hwPDU8000DualMod3Branch5L2outputactiveelectricenergy OBJECT-TYPE
            SYNTAX Integer32 (0..21474836)
            MAX-ACCESS read-only
            STATUS current
            DESCRIPTION
                "Branch 5 L2 output active electric energy. Unit:KWh. Multi:100"
            ::= { hwPDU8000DualMode3_4Entry 15 }

        hwPDU8000DualMod3Branch5L3outputactiveelectricenergy OBJECT-TYPE
            SYNTAX Integer32 (0..21474836)
            MAX-ACCESS read-only
            STATUS current
            DESCRIPTION
                "Branch 5 L3 output active electric energy. Unit:KWh. Multi:100"
            ::= { hwPDU8000DualMode3_4Entry 16 }

        hwPDU8000DualMod3Branch6L1outputactiveelectricenergy OBJECT-TYPE
            SYNTAX Integer32 (0..21474836)
            MAX-ACCESS read-only
            STATUS current
            DESCRIPTION
                "Branch 6 L1 output active electric energy. Unit:KWh. Multi:100"
            ::= { hwPDU8000DualMode3_4Entry 17 }

        hwPDU8000DualMod3Branch6L2outputactiveelectricenergy OBJECT-TYPE
            SYNTAX Integer32 (0..21474836)
            MAX-ACCESS read-only
            STATUS current
            DESCRIPTION
                "Branch 6 L2 output active electric energy. Unit:KWh. Multi:100"
            ::= { hwPDU8000DualMode3_4Entry 18 }

        hwPDU8000DualMod3Branch6L3outputactiveelectricenergy OBJECT-TYPE
            SYNTAX Integer32 (0..21474836)
            MAX-ACCESS read-only
            STATUS current
            DESCRIPTION
                "Branch 6 L3 output active electric energy. Unit:KWh. Multi:100"
            ::= { hwPDU8000DualMode3_4Entry 19 }

        hwPDU8000DualMod3Branch7L1outputactiveelectricenergy OBJECT-TYPE
            SYNTAX Integer32 (0..21474836)
            MAX-ACCESS read-only
            STATUS current
            DESCRIPTION
                "Branch 7 L1 output active electric energy. Unit:KWh. Multi:100"
            ::= { hwPDU8000DualMode3_4Entry 20 }

        hwPDU8000DualMod3Branch7L2outputactiveelectricenergy OBJECT-TYPE
            SYNTAX Integer32 (0..21474836)
            MAX-ACCESS read-only
            STATUS current
            DESCRIPTION
                "Branch 7 L2 output active electric energy. Unit:KWh. Multi:100"
            ::= { hwPDU8000DualMode3_4Entry 21 }

        hwPDU8000DualMod3Branch7L3outputactiveelectricenergy OBJECT-TYPE
            SYNTAX Integer32 (0..21474836)
            MAX-ACCESS read-only
            STATUS current
            DESCRIPTION
                "Branch 7 L3 output active electric energy. Unit:KWh. Multi:100"
            ::= { hwPDU8000DualMode3_4Entry 22 }

        hwPDU8000DualMod3Branch8L1outputactiveelectricenergy OBJECT-TYPE
            SYNTAX Integer32 (0..21474836)
            MAX-ACCESS read-only
            STATUS current
            DESCRIPTION
                "Branch 8 L1 output active electric energy. Unit:KWh. Multi:100"
            ::= { hwPDU8000DualMode3_4Entry 23 }

        hwPDU8000DualMod3Branch8L2outputactiveelectricenergy OBJECT-TYPE
            SYNTAX Integer32 (0..21474836)
            MAX-ACCESS read-only
            STATUS current
            DESCRIPTION
                "Branch 8 L2 output active electric energy. Unit:KWh. Multi:100"
            ::= { hwPDU8000DualMode3_4Entry 24 }

        hwPDU8000DualMod3Branch8L3outputactiveelectricenergy OBJECT-TYPE
            SYNTAX Integer32 (0..21474836)
            MAX-ACCESS read-only
            STATUS current
            DESCRIPTION
                "Branch 8 L3 output active electric energy. Unit:KWh. Multi:100"
            ::= { hwPDU8000DualMode3_4Entry 25 }

        hwPDU8000DualMod3Branch9L1outputactiveelectricenergy OBJECT-TYPE
            SYNTAX Integer32 (0..21474836)
            MAX-ACCESS read-only
            STATUS current
            DESCRIPTION
                "Branch 9 L1 output active electric energy. Unit:KWh. Multi:100"
            ::= { hwPDU8000DualMode3_4Entry 26 }

        hwPDU8000DualMod3Branch9L2outputactiveelectricenergy OBJECT-TYPE
            SYNTAX Integer32 (0..21474836)
            MAX-ACCESS read-only
            STATUS current
            DESCRIPTION
                "Branch 9 L2 output active electric energy. Unit:KWh. Multi:100"
            ::= { hwPDU8000DualMode3_4Entry 27 }

        hwPDU8000DualMod3Branch9L3outputactiveelectricenergy OBJECT-TYPE
            SYNTAX Integer32 (0..21474836)
            MAX-ACCESS read-only
            STATUS current
            DESCRIPTION
                "Branch 9 L3 output active electric energy. Unit:KWh. Multi:100"
            ::= { hwPDU8000DualMode3_4Entry 28 }

        hwPDU8000DualMod3Branch10L1outputactiveelectricenergy OBJECT-TYPE
            SYNTAX Integer32 (0..21474836)
            MAX-ACCESS read-only
            STATUS current
            DESCRIPTION
                "Branch 10 L1 output active electric energy. Unit:KWh. Multi:100"
            ::= { hwPDU8000DualMode3_4Entry 29 }

        hwPDU8000DualMod3Branch10L2outputactiveelectricenergy OBJECT-TYPE
            SYNTAX Integer32 (0..21474836)
            MAX-ACCESS read-only
            STATUS current
            DESCRIPTION
                "Branch 10 L2 output active electric energy. Unit:KWh. Multi:100"
            ::= { hwPDU8000DualMode3_4Entry 30 }

        hwPDU8000DualMod3Branch10L3outputactiveelectricenergy OBJECT-TYPE
            SYNTAX Integer32 (0..21474836)
            MAX-ACCESS read-only
            STATUS current
            DESCRIPTION
                "Branch 10 L3 output active electric energy. Unit:KWh. Multi:100"
            ::= { hwPDU8000DualMode3_4Entry 31 }

        hwPDU8000DualMod3Branch11L1outputactiveelectricenergy OBJECT-TYPE
            SYNTAX Integer32 (0..21474836)
            MAX-ACCESS read-only
            STATUS current
            DESCRIPTION
                "Branch 11 L1 output active electric energy. Unit:KWh. Multi:100"
            ::= { hwPDU8000DualMode3_4Entry 32 }

        hwPDU8000DualMod3Branch11L2outputactiveelectricenergy OBJECT-TYPE
            SYNTAX Integer32 (0..21474836)
            MAX-ACCESS read-only
            STATUS current
            DESCRIPTION
                "Branch 11 L2 output active electric energy. Unit:KWh. Multi:100"
            ::= { hwPDU8000DualMode3_4Entry 33 }

        hwPDU8000DualMod3Branch11L3outputactiveelectricenergy OBJECT-TYPE
            SYNTAX Integer32 (0..21474836)
            MAX-ACCESS read-only
            STATUS current
            DESCRIPTION
                "Branch 11 L3 output active electric energy. Unit:KWh. Multi:100"
            ::= { hwPDU8000DualMode3_4Entry 34 }

        hwPDU8000DualMod3Branch12L1outputactiveelectricenergy OBJECT-TYPE
            SYNTAX Integer32 (0..21474836)
            MAX-ACCESS read-only
            STATUS current
            DESCRIPTION
                "Branch 12 L1 output active electric energy. Unit:KWh. Multi:100"
            ::= { hwPDU8000DualMode3_4Entry 35 }

        hwPDU8000DualMod3Branch12L2outputactiveelectricenergy OBJECT-TYPE
            SYNTAX Integer32 (0..21474836)
            MAX-ACCESS read-only
            STATUS current
            DESCRIPTION
                "Branch 12 L2 output active electric energy. Unit:KWh. Multi:100"
            ::= { hwPDU8000DualMode3_4Entry 36 }

        hwPDU8000DualMod3Branch12L3outputactiveelectricenergy OBJECT-TYPE
            SYNTAX Integer32 (0..21474836)
            MAX-ACCESS read-only
            STATUS current
            DESCRIPTION
                "Branch 12 L3 output active electric energy. Unit:KWh. Multi:100"
            ::= { hwPDU8000DualMode3_4Entry 37 }

        hwPDU8000DualMod4Branch1L1outputactiveelectricenergy OBJECT-TYPE
            SYNTAX Integer32 (0..21474836)
            MAX-ACCESS read-only
            STATUS current
            DESCRIPTION
                "Branch 1 L1 output active electric energy. Unit:KWh. Multi:100"
            ::= { hwPDU8000DualMode3_4Entry 38 }

        hwPDU8000DualMod4Branch1L2outputactiveelectricenergy OBJECT-TYPE
            SYNTAX Integer32 (0..21474836)
            MAX-ACCESS read-only
            STATUS current
            DESCRIPTION
                "Branch 1 L2 output active electric energy. Unit:KWh. Multi:100"
            ::= { hwPDU8000DualMode3_4Entry 39 }

        hwPDU8000DualMod4Branch1L3outputactiveelectricenergy OBJECT-TYPE
            SYNTAX Integer32 (0..21474836)
            MAX-ACCESS read-only
            STATUS current
            DESCRIPTION
                "Branch 1 L3 output active electric energy. Unit:KWh. Multi:100"
            ::= { hwPDU8000DualMode3_4Entry 40 }

        hwPDU8000DualMod4Branch2L1outputactiveelectricenergy OBJECT-TYPE
            SYNTAX Integer32 (0..21474836)
            MAX-ACCESS read-only
            STATUS current
            DESCRIPTION
                "Branch 2 L1 output active electric energy. Unit:KWh. Multi:100"
            ::= { hwPDU8000DualMode3_4Entry 41 }

        hwPDU8000DualMod4Branch2L2outputactiveelectricenergy OBJECT-TYPE
            SYNTAX Integer32 (0..21474836)
            MAX-ACCESS read-only
            STATUS current
            DESCRIPTION
                "Branch 2 L2 output active electric energy. Unit:KWh. Multi:100"
            ::= { hwPDU8000DualMode3_4Entry 42 }

        hwPDU8000DualMod4Branch2L3outputactiveelectricenergy OBJECT-TYPE
            SYNTAX Integer32 (0..21474836)
            MAX-ACCESS read-only
            STATUS current
            DESCRIPTION
                "Branch 2 L3 output active electric energy. Unit:KWh. Multi:100"
            ::= { hwPDU8000DualMode3_4Entry 43 }

        hwPDU8000DualMod4Branch3L1outputactiveelectricenergy OBJECT-TYPE
            SYNTAX Integer32 (0..21474836)
            MAX-ACCESS read-only
            STATUS current
            DESCRIPTION
                "Branch 3 L1 output active electric energy. Unit:KWh. Multi:100"
            ::= { hwPDU8000DualMode3_4Entry 44 }

        hwPDU8000DualMod4Branch3L2outputactiveelectricenergy OBJECT-TYPE
            SYNTAX Integer32 (0..21474836)
            MAX-ACCESS read-only
            STATUS current
            DESCRIPTION
                "Branch 3 L2 output active electric energy. Unit:KWh. Multi:100"
            ::= { hwPDU8000DualMode3_4Entry 45 }

        hwPDU8000DualMod4Branch3L3outputactiveelectricenergy OBJECT-TYPE
            SYNTAX Integer32 (0..21474836)
            MAX-ACCESS read-only
            STATUS current
            DESCRIPTION
                "Branch 3 L3 output active electric energy. Unit:KWh. Multi:100"
            ::= { hwPDU8000DualMode3_4Entry 46 }

        hwPDU8000DualMod4Branch4L1outputactiveelectricenergy OBJECT-TYPE
            SYNTAX Integer32 (0..21474836)
            MAX-ACCESS read-only
            STATUS current
            DESCRIPTION
                "Branch 4 L1 output active electric energy. Unit:KWh. Multi:100"
            ::= { hwPDU8000DualMode3_4Entry 47 }

        hwPDU8000DualMod4Branch4L2outputactiveelectricenergy OBJECT-TYPE
            SYNTAX Integer32 (0..21474836)
            MAX-ACCESS read-only
            STATUS current
            DESCRIPTION
                "Branch 4 L2 output active electric energy. Unit:KWh. Multi:100"
            ::= { hwPDU8000DualMode3_4Entry 48 }

        hwPDU8000DualMod4Branch4L3outputactiveelectricenergy OBJECT-TYPE
            SYNTAX Integer32 (0..21474836)
            MAX-ACCESS read-only
            STATUS current
            DESCRIPTION
                "Branch 4 L3 output active electric energy. Unit:KWh. Multi:100"
            ::= { hwPDU8000DualMode3_4Entry 49 }

        hwPDU8000DualMod4Branch5L1outputactiveelectricenergy OBJECT-TYPE
            SYNTAX Integer32 (0..21474836)
            MAX-ACCESS read-only
            STATUS current
            DESCRIPTION
                "Branch 5 L1 output active electric energy. Unit:KWh. Multi:100"
            ::= { hwPDU8000DualMode3_4Entry 50 }

        hwPDU8000DualMod4Branch5L2outputactiveelectricenergy OBJECT-TYPE
            SYNTAX Integer32 (0..21474836)
            MAX-ACCESS read-only
            STATUS current
            DESCRIPTION
                "Branch 5 L2 output active electric energy. Unit:KWh. Multi:100"
            ::= { hwPDU8000DualMode3_4Entry 51 }

        hwPDU8000DualMod4Branch5L3outputactiveelectricenergy OBJECT-TYPE
            SYNTAX Integer32 (0..21474836)
            MAX-ACCESS read-only
            STATUS current
            DESCRIPTION
                "Branch 5 L3 output active electric energy. Unit:KWh. Multi:100"
            ::= { hwPDU8000DualMode3_4Entry 52 }

        hwPDU8000DualMod4Branch6L1outputactiveelectricenergy OBJECT-TYPE
            SYNTAX Integer32 (0..21474836)
            MAX-ACCESS read-only
            STATUS current
            DESCRIPTION
                "Branch 6 L1 output active electric energy. Unit:KWh. Multi:100"
            ::= { hwPDU8000DualMode3_4Entry 53 }

        hwPDU8000DualMod4Branch6L2outputactiveelectricenergy OBJECT-TYPE
            SYNTAX Integer32 (0..21474836)
            MAX-ACCESS read-only
            STATUS current
            DESCRIPTION
                "Branch 6 L2 output active electric energy. Unit:KWh. Multi:100"
            ::= { hwPDU8000DualMode3_4Entry 54 }

        hwPDU8000DualMod4Branch6L3outputactiveelectricenergy OBJECT-TYPE
            SYNTAX Integer32 (0..21474836)
            MAX-ACCESS read-only
            STATUS current
            DESCRIPTION
                "Branch 6 L3 output active electric energy. Unit:KWh. Multi:100"
            ::= { hwPDU8000DualMode3_4Entry 55 }

        hwPDU8000DualMod4Branch7L1outputactiveelectricenergy OBJECT-TYPE
            SYNTAX Integer32 (0..21474836)
            MAX-ACCESS read-only
            STATUS current
            DESCRIPTION
                "Branch 7 L1 output active electric energy. Unit:KWh. Multi:100"
            ::= { hwPDU8000DualMode3_4Entry 56 }

        hwPDU8000DualMod4Branch7L2outputactiveelectricenergy OBJECT-TYPE
            SYNTAX Integer32 (0..21474836)
            MAX-ACCESS read-only
            STATUS current
            DESCRIPTION
                "Branch 7 L2 output active electric energy. Unit:KWh. Multi:100"
            ::= { hwPDU8000DualMode3_4Entry 57 }

        hwPDU8000DualMod4Branch7L3outputactiveelectricenergy OBJECT-TYPE
            SYNTAX Integer32 (0..21474836)
            MAX-ACCESS read-only
            STATUS current
            DESCRIPTION
                "Branch 7 L3 output active electric energy. Unit:KWh. Multi:100"
            ::= { hwPDU8000DualMode3_4Entry 58 }

        hwPDU8000DualMod4Branch8L1outputactiveelectricenergy OBJECT-TYPE
            SYNTAX Integer32 (0..21474836)
            MAX-ACCESS read-only
            STATUS current
            DESCRIPTION
                "Branch 8 L1 output active electric energy. Unit:KWh. Multi:100"
            ::= { hwPDU8000DualMode3_4Entry 59 }

        hwPDU8000DualMod4Branch8L2outputactiveelectricenergy OBJECT-TYPE
            SYNTAX Integer32 (0..21474836)
            MAX-ACCESS read-only
            STATUS current
            DESCRIPTION
                "Branch 8 L2 output active electric energy. Unit:KWh. Multi:100"
            ::= { hwPDU8000DualMode3_4Entry 60 }

        hwPDU8000DualMod4Branch8L3outputactiveelectricenergy OBJECT-TYPE
            SYNTAX Integer32 (0..21474836)
            MAX-ACCESS read-only
            STATUS current
            DESCRIPTION
                "Branch 8 L3 output active electric energy. Unit:KWh. Multi:100"
            ::= { hwPDU8000DualMode3_4Entry 61 }

        hwPDU8000DualMod4Branch9L1outputactiveelectricenergy OBJECT-TYPE
            SYNTAX Integer32 (0..21474836)
            MAX-ACCESS read-only
            STATUS current
            DESCRIPTION
                "Branch 9 L1 output active electric energy. Unit:KWh. Multi:100"
            ::= { hwPDU8000DualMode3_4Entry 62 }

        hwPDU8000DualMod4Branch9L2outputactiveelectricenergy OBJECT-TYPE
            SYNTAX Integer32 (0..21474836)
            MAX-ACCESS read-only
            STATUS current
            DESCRIPTION
                "Branch 9 L2 output active electric energy. Unit:KWh. Multi:100"
            ::= { hwPDU8000DualMode3_4Entry 63 }

        hwPDU8000DualMod4Branch9L3outputactiveelectricenergy OBJECT-TYPE
            SYNTAX Integer32 (0..21474836)
            MAX-ACCESS read-only
            STATUS current
            DESCRIPTION
                "Branch 9 L3 output active electric energy. Unit:KWh. Multi:100"
            ::= { hwPDU8000DualMode3_4Entry 64 }

        hwPDU8000DualMod4Branch10L1outputactiveelectricenergy OBJECT-TYPE
            SYNTAX Integer32 (0..21474836)
            MAX-ACCESS read-only
            STATUS current
            DESCRIPTION
                "Branch 10 L1 output active electric energy. Unit:KWh. Multi:100"
            ::= { hwPDU8000DualMode3_4Entry 65 }

        hwPDU8000DualMod4Branch10L2outputactiveelectricenergy OBJECT-TYPE
            SYNTAX Integer32 (0..21474836)
            MAX-ACCESS read-only
            STATUS current
            DESCRIPTION
                "Branch 10 L2 output active electric energy. Unit:KWh. Multi:100"
            ::= { hwPDU8000DualMode3_4Entry 66 }

        hwPDU8000DualMod4Branch10L3outputactiveelectricenergy OBJECT-TYPE
            SYNTAX Integer32 (0..21474836)
            MAX-ACCESS read-only
            STATUS current
            DESCRIPTION
                "Branch 10 L3 output active electric energy. Unit:KWh. Multi:100"
            ::= { hwPDU8000DualMode3_4Entry 67 }

        hwPDU8000DualMod4Branch11L1outputactiveelectricenergy OBJECT-TYPE
            SYNTAX Integer32 (0..21474836)
            MAX-ACCESS read-only
            STATUS current
            DESCRIPTION
                "Branch 11 L1 output active electric energy. Unit:KWh. Multi:100"
            ::= { hwPDU8000DualMode3_4Entry 68 }

        hwPDU8000DualMod4Branch11L2outputactiveelectricenergy OBJECT-TYPE
            SYNTAX Integer32 (0..21474836)
            MAX-ACCESS read-only
            STATUS current
            DESCRIPTION
                "Branch 11 L2 output active electric energy. Unit:KWh. Multi:100"
            ::= { hwPDU8000DualMode3_4Entry 69 }

        hwPDU8000DualMod4Branch11L3outputactiveelectricenergy OBJECT-TYPE
            SYNTAX Integer32 (0..21474836)
            MAX-ACCESS read-only
            STATUS current
            DESCRIPTION
                "Branch 11 L3 output active electric energy. Unit:KWh. Multi:100"
            ::= { hwPDU8000DualMode3_4Entry 70 }

        hwPDU8000DualMod4Branch12L1outputactiveelectricenergy OBJECT-TYPE
            SYNTAX Integer32 (0..21474836)
            MAX-ACCESS read-only
            STATUS current
            DESCRIPTION
                "Branch 12 L1 output active electric energy. Unit:KWh. Multi:100"
            ::= { hwPDU8000DualMode3_4Entry 71 }

        hwPDU8000DualMod4Branch12L2outputactiveelectricenergy OBJECT-TYPE
            SYNTAX Integer32 (0..21474836)
            MAX-ACCESS read-only
            STATUS current
            DESCRIPTION
                "Branch 12 L2 output active electric energy. Unit:KWh. Multi:100"
            ::= { hwPDU8000DualMode3_4Entry 72 }

        hwPDU8000DualMod4Branch12L3outputactiveelectricenergy OBJECT-TYPE
            SYNTAX Integer32 (0..21474836)
            MAX-ACCESS read-only
            STATUS current
            DESCRIPTION
                "Branch 12 L3 output active electric energy. Unit:KWh. Multi:100"
            ::= { hwPDU8000DualMode3_4Entry 73 }

        hwPDU8000DualMode3_4RowStatus OBJECT-TYPE
            SYNTAX RowStatus
            MAX-ACCESS read-create
            STATUS current
            DESCRIPTION
                "The row status of Deviece."
            ::= { hwPDU8000DualMode3_4Entry 100 }

        hwPDU8000Transformer OBJECT IDENTIFIER ::= { hwIDCPDU 3 }

        hwPDU8000TransTable OBJECT-TYPE
            SYNTAX SEQUENCE OF HwPDU8000TransEntry
            MAX-ACCESS not-accessible
             STATUS current
             DESCRIPTION
                "The Equipment list of PDU8000 Transformer."
            ::= { hwPDU8000Transformer 1 }

        hwPDU8000TransEntry OBJECT-TYPE
                        SYNTAX HwPDU8000TransEntry
            MAX-ACCESS not-accessible
             STATUS current
             DESCRIPTION
                "The Equipment list of PDU8000 Transformer."
            INDEX { hwPDU8000TransIndex }
            ::= { hwPDU8000TransTable 1 }

        HwPDU8000TransEntry            ::= SEQUENCE {
                hwPDU8000TransIndex
                    Unsigned32,
                hwPDU8000TransName
                    OCTET STRING,
                hwPDU8000TransCommunicationStatus
                    INTEGER,
                hwPDU8000TransSlotNo
                    Unsigned32,
                hwPDU8000TransPortNo
                    Unsigned32,
                hwPDU8000TransModbusAddr
                    Unsigned32,
                hwPDU8000TransSoftwareVersion
                    OCTET STRING,
                hwPDU8000TransESN
                    OCTET STRING,
                hwPDU8000TransInputMode
                    INTEGER,
                hwPDU8000TransL1inputphasevoltage
                    Integer32,
                hwPDU8000TransL2inputphasevoltage
                    Integer32,
                hwPDU8000TransL3inputphasevoltage
                    Integer32,
                hwPDU8000TransL1inputphasecurrent
                    Integer32,
                hwPDU8000TransL2inputphasecurrent
                    Integer32,
                hwPDU8000TransL3inputphasecurrent
                    Integer32,
                hwPDU8000TransTotalinputactivepower
                    Integer32,
                hwPDU8000TransOutputL1phasevoltage
                    Integer32,
                hwPDU8000TransOutputL2phasevoltage
                    Integer32,
                hwPDU8000TransOutputL3phasevoltage
                    Integer32,
                hwPDU8000TransOutputL1-L2linevoltage
                    Integer32,
                hwPDU8000TransOutputL2-L3linevoltage
                    Integer32,
                hwPDU8000TransOutputL1-L3linevoltage
                    Integer32,
                hwPDU8000TransOutputL1phasecurrent
                    Integer32,
                hwPDU8000TransOutputL2phasecurrent
                    Integer32,
                hwPDU8000TransOutputL3phasecurrent
                    Integer32,
                hwPDU8000TransOutputfrequency
                    Integer32,
                hwPDU8000TransOutputL1activepower
                    Integer32,
                hwPDU8000TransOutputL2activepower
                    Integer32,
                hwPDU8000TransOutputL3activepower
                    Integer32,
                hwPDU8000TransOutputL1apparentpower
                    Integer32,
                hwPDU8000TransOutputL2apparentpower
                    Integer32,
                hwPDU8000TransOutputL3apparentpower
                    Integer32,
                hwPDU8000TransOutputL1reactivepower
                    Integer32,
                hwPDU8000TransOutputL2reactivepower
                    Integer32,
                hwPDU8000TransOutputL3reactivepower
                    Integer32,
                hwPDU8000TransOutputL1powerfactor
                    Integer32,
                hwPDU8000TransOutputL2powerfactor
                    Integer32,
                hwPDU8000TransOutputL3powerfactor
                    Integer32,
                hwPDU8000TransOutputactiveelectricenergy
                    Integer32,
                hwPDU8000TransOutputL1powerloadrate
                    Unsigned32,
                hwPDU8000TransOutputL2powerloadrate
                    Unsigned32,
                hwPDU8000TransOutputL3powerloadrate
                    Unsigned32,
                hwPDU8000TransOutputNwirecurrent
                    Integer32,
                hwPDU8000TransOutputL1THD-urate
                    Integer32,
                hwPDU8000TransOutputL2THD-urate
                    Integer32,
                hwPDU8000TransOutputL3THD-urate
                    Integer32,
                hwPDU8000TransOutputL1THD-irate
                    Integer32,
                hwPDU8000TransOutputL2THD-irate
                    Integer32,
                hwPDU8000TransOutputL3THD-irate
                    Integer32,
                hwPDU8000TransOutputtotalactivepower
                    Integer32,
                hwPDU8000TransOutputtotalapparentpower
                    Integer32,
                hwPDU8000TransOutputtotalreactivepower
                    Integer32,
                hwPDU8000TransRawstatus
                    RowStatus
            }

        hwPDU8000TransIndex OBJECT-TYPE
            SYNTAX Unsigned32
            MAX-ACCESS read-only
            STATUS current
            DESCRIPTION
                "The id of PDU8000 Transformer."
            ::= { hwPDU8000TransEntry 1 }

        hwPDU8000TransName OBJECT-TYPE
            SYNTAX OCTET STRING (SIZE (0..50))
            MAX-ACCESS read-only
            STATUS current
            DESCRIPTION
                "The name of PDU8000 Transformer."
            ::= { hwPDU8000TransEntry 2 }

        hwPDU8000TransCommunicationStatus OBJECT-TYPE
            SYNTAX INTEGER
                {
                ok(1),
                fail(2),
                unknown(255)
                }
            MAX-ACCESS read-only
            STATUS current
            DESCRIPTION
                "Communication Status."
            ::= { hwPDU8000TransEntry 3 }

        hwPDU8000TransSlotNo OBJECT-TYPE
            SYNTAX Unsigned32 (0..6)
            MAX-ACCESS read-only
            STATUS current
            DESCRIPTION
                "Slot No."
            ::= { hwPDU8000TransEntry 4 }

        hwPDU8000TransPortNo OBJECT-TYPE
            SYNTAX Unsigned32 (1..5)
            MAX-ACCESS read-only
            STATUS current
            DESCRIPTION
                "Port No."
            ::= { hwPDU8000TransEntry 5 }

        hwPDU8000TransModbusAddr OBJECT-TYPE
            SYNTAX Unsigned32 (0..247)
            MAX-ACCESS read-only
            STATUS current
            DESCRIPTION
                "Modbus Addr."
            ::= { hwPDU8000TransEntry 6 }

        hwPDU8000TransSoftwareVersion OBJECT-TYPE
            SYNTAX OCTET STRING (SIZE (0..32))
            MAX-ACCESS read-only
            STATUS current
            DESCRIPTION
                "Software Version."
            ::= { hwPDU8000TransEntry 7 }

        hwPDU8000TransESN OBJECT-TYPE
            SYNTAX OCTET STRING (SIZE (0..20))
            MAX-ACCESS read-only
            STATUS current
            DESCRIPTION
                "ESN. A string of characters."
            ::= { hwPDU8000TransEntry 8 }

        hwPDU8000TransInputMode OBJECT-TYPE
            SYNTAX INTEGER
                {
                SingleMode(1),
                DualMode(2),
                Dual1Way(3),
                Dual2Way(4),
                from380to380Transformer(5),
                from480to208Transformer(6),
                unkown(255)
                }
            MAX-ACCESS read-only
            STATUS current
            DESCRIPTION
                "Input Mode. "
            ::= { hwPDU8000TransEntry 9 }

        hwPDU8000TransL1inputphasevoltage OBJECT-TYPE
            SYNTAX Integer32 (0..1000)
            MAX-ACCESS read-only
            STATUS current
            DESCRIPTION
                "L1 input phase voltage. Unit: V. Multi: 10."
            ::= { hwPDU8000TransEntry 10 }

        hwPDU8000TransL2inputphasevoltage OBJECT-TYPE
            SYNTAX Integer32 (0..1000)
            MAX-ACCESS read-only
            STATUS current
            DESCRIPTION
                "L2 input phase voltage. Unit: V. Multi: 10."
            ::= { hwPDU8000TransEntry 11 }

        hwPDU8000TransL3inputphasevoltage OBJECT-TYPE
            SYNTAX Integer32 (0..1000)
            MAX-ACCESS read-only
            STATUS current
            DESCRIPTION
                "L3 input phase voltage. Unit: V. Multi: 10."
            ::= { hwPDU8000TransEntry 12 }

        hwPDU8000TransL1inputphasecurrent OBJECT-TYPE
            SYNTAX Integer32 (0..800)
            MAX-ACCESS read-only
            STATUS current
            DESCRIPTION
                "L1 input phase current. Unit: A. Multi: 10."
            ::= { hwPDU8000TransEntry 13 }

        hwPDU8000TransL2inputphasecurrent OBJECT-TYPE
            SYNTAX Integer32 (0..800)
            MAX-ACCESS read-only
            STATUS current
            DESCRIPTION
                "L2 input phase current. Unit: A. Multi: 10."
            ::= { hwPDU8000TransEntry 14 }

        hwPDU8000TransL3inputphasecurrent OBJECT-TYPE
            SYNTAX Integer32 (0..800)
            MAX-ACCESS read-only
            STATUS current
            DESCRIPTION
                "L3 input phase current. Unit: A. Multi: 10."
            ::= { hwPDU8000TransEntry 15 }

        hwPDU8000TransTotalinputactivepower OBJECT-TYPE
            SYNTAX Integer32 (-750..750)
            MAX-ACCESS read-only
            STATUS current
            DESCRIPTION
                "Total input active power. Unit: kW. Multi: 10."
            ::= { hwPDU8000TransEntry 16 }

        hwPDU8000TransOutputL1phasevoltage OBJECT-TYPE
            SYNTAX Integer32 (0..1000)
            MAX-ACCESS read-only
            STATUS current
            DESCRIPTION
                "Output L1  phase voltage. Unit: V. Multi: 10."
            ::= { hwPDU8000TransEntry 17 }

        hwPDU8000TransOutputL2phasevoltage OBJECT-TYPE
            SYNTAX Integer32 (0..1000)
            MAX-ACCESS read-only
            STATUS current
            DESCRIPTION
                "Output L2  phase voltage. Unit: V. Multi: 10."
            ::= { hwPDU8000TransEntry 18 }

        hwPDU8000TransOutputL3phasevoltage OBJECT-TYPE
            SYNTAX Integer32 (0..1000)
            MAX-ACCESS read-only
            STATUS current
            DESCRIPTION
                "Output L3  phase voltage. Unit: V. Multi: 10."
            ::= { hwPDU8000TransEntry 19 }

        hwPDU8000TransOutputL1-L2linevoltage OBJECT-TYPE
            SYNTAX Integer32 (0..1000)
            MAX-ACCESS read-only
            STATUS current
            DESCRIPTION
                "Output L1-L2  line voltage. Unit: V. Multi: 10."
            ::= { hwPDU8000TransEntry 20 }

        hwPDU8000TransOutputL2-L3linevoltage OBJECT-TYPE
            SYNTAX Integer32 (0..1000)
            MAX-ACCESS read-only
            STATUS current
            DESCRIPTION
                "Output L2-L3  line voltage. Unit: V. Multi: 10."
            ::= { hwPDU8000TransEntry 21 }

        hwPDU8000TransOutputL1-L3linevoltage OBJECT-TYPE
            SYNTAX Integer32 (0..1000)
            MAX-ACCESS read-only
            STATUS current
            DESCRIPTION
                "Output L1-L3  line voltage. Unit: V. Multi: 10."
            ::= { hwPDU8000TransEntry 22 }

        hwPDU8000TransOutputL1phasecurrent OBJECT-TYPE
            SYNTAX Integer32 (0..800)
            MAX-ACCESS read-only
            STATUS current
            DESCRIPTION
                "Output L1  phase current. Unit: A. Multi: 10."
            ::= { hwPDU8000TransEntry 23 }

        hwPDU8000TransOutputL2phasecurrent OBJECT-TYPE
            SYNTAX Integer32 (0..800)
            MAX-ACCESS read-only
            STATUS current
            DESCRIPTION
                "Output L2  phase current. Unit: A. Multi: 10."
            ::= { hwPDU8000TransEntry 24 }

        hwPDU8000TransOutputL3phasecurrent OBJECT-TYPE
            SYNTAX Integer32 (0..800)
            MAX-ACCESS read-only
            STATUS current
            DESCRIPTION
                "Output L3  phase current. Unit: A. Multi: 10."
            ::= { hwPDU8000TransEntry 25 }

        hwPDU8000TransOutputfrequency OBJECT-TYPE
            SYNTAX Integer32 (0..100)
            MAX-ACCESS read-only
            STATUS current
            DESCRIPTION
                "Output frequency. Unit: Hz. Multi: 100."
            ::= { hwPDU8000TransEntry 26 }

        hwPDU8000TransOutputL1activepower OBJECT-TYPE
            SYNTAX Integer32 (-250..250)
            MAX-ACCESS read-only
            STATUS current
            DESCRIPTION
                "Output L1  active power. Unit: kW. Multi: 10."
            ::= { hwPDU8000TransEntry 27 }

        hwPDU8000TransOutputL2activepower OBJECT-TYPE
            SYNTAX Integer32 (-250..250)
            MAX-ACCESS read-only
            STATUS current
            DESCRIPTION
                "Output L2  active power. Unit: kW. Multi: 10."
            ::= { hwPDU8000TransEntry 28 }

        hwPDU8000TransOutputL3activepower OBJECT-TYPE
            SYNTAX Integer32 (-250..250)
            MAX-ACCESS read-only
            STATUS current
            DESCRIPTION
                "Output L3  active power. Unit: kW. Multi: 10."
            ::= { hwPDU8000TransEntry 29 }

        hwPDU8000TransOutputL1apparentpower OBJECT-TYPE
            SYNTAX Integer32 (-250..250)
            MAX-ACCESS read-only
            STATUS current
            DESCRIPTION
                "Output L1  apparent power. Unit: kVA. Multi: 10."
            ::= { hwPDU8000TransEntry 30 }

        hwPDU8000TransOutputL2apparentpower OBJECT-TYPE
            SYNTAX Integer32 (-250..250)
            MAX-ACCESS read-only
            STATUS current
            DESCRIPTION
                "Output L2  apparent power. Unit: kVA. Multi: 10."
            ::= { hwPDU8000TransEntry 31 }

        hwPDU8000TransOutputL3apparentpower OBJECT-TYPE
            SYNTAX Integer32 (-250..250)
            MAX-ACCESS read-only
            STATUS current
            DESCRIPTION
                "Output L3  apparent power. Unit: kVA. Multi: 10."
            ::= { hwPDU8000TransEntry 32 }

        hwPDU8000TransOutputL1reactivepower OBJECT-TYPE
            SYNTAX Integer32 (-250..250)
            MAX-ACCESS read-only
            STATUS current
            DESCRIPTION
                "Output L1  reactive power. Unit: kVAR. Multi: 10."
            ::= { hwPDU8000TransEntry 33 }

        hwPDU8000TransOutputL2reactivepower OBJECT-TYPE
            SYNTAX Integer32 (-250..250)
            MAX-ACCESS read-only
            STATUS current
            DESCRIPTION
                "Output L2  reactive power. Unit: kVAR. Multi: 10."
            ::= { hwPDU8000TransEntry 34 }

        hwPDU8000TransOutputL3reactivepower OBJECT-TYPE
            SYNTAX Integer32 (-250..250)
            MAX-ACCESS read-only
            STATUS current
            DESCRIPTION
                "Output L3  reactive power. Unit: kVAR. Multi: 10."
            ::= { hwPDU8000TransEntry 35 }

        hwPDU8000TransOutputL1powerfactor OBJECT-TYPE
            SYNTAX Integer32 (-1..1)
            MAX-ACCESS read-only
            STATUS current
            DESCRIPTION
                "Output L1  power factor. Multi: 100."
            ::= { hwPDU8000TransEntry 36 }

        hwPDU8000TransOutputL2powerfactor OBJECT-TYPE
            SYNTAX Integer32 (-1..1)
            MAX-ACCESS read-only
            STATUS current
            DESCRIPTION
                "Output L2  power factor. Multi: 100."
            ::= { hwPDU8000TransEntry 37 }

        hwPDU8000TransOutputL3powerfactor OBJECT-TYPE
            SYNTAX Integer32 (-1..1)
            MAX-ACCESS read-only
            STATUS current
            DESCRIPTION
                "Output L3  power factor. Multi: 100."
            ::= { hwPDU8000TransEntry 38 }

        hwPDU8000TransOutputactiveelectricenergy OBJECT-TYPE
            SYNTAX Integer32 (0..21474836)
            MAX-ACCESS read-only
            STATUS current
            DESCRIPTION
                "Output active electric energy. Unit: kWh. Multi: 100."
            ::= { hwPDU8000TransEntry 39 }

        hwPDU8000TransOutputL1powerloadrate OBJECT-TYPE
            SYNTAX Unsigned32 (0..150)
            MAX-ACCESS read-only
            STATUS current
            DESCRIPTION
                "Output L1  power load rate. Unit: %. Multi: 1."
            ::= { hwPDU8000TransEntry 40 }

        hwPDU8000TransOutputL2powerloadrate OBJECT-TYPE
            SYNTAX Unsigned32 (0..150)
            MAX-ACCESS read-only
            STATUS current
            DESCRIPTION
                "Output L2  power load rate. Unit: %. Multi: 1."
            ::= { hwPDU8000TransEntry 41 }

        hwPDU8000TransOutputL3powerloadrate OBJECT-TYPE
            SYNTAX Unsigned32 (0..150)
            MAX-ACCESS read-only
            STATUS current
            DESCRIPTION
                "Output L3  power load rate. Unit: %. Multi: 1."
            ::= { hwPDU8000TransEntry 42 }

        hwPDU8000TransOutputNwirecurrent OBJECT-TYPE
            SYNTAX Integer32 (0..1000)
            MAX-ACCESS read-only
            STATUS current
            DESCRIPTION
                "Output N wire current. Unit: A. Multi: 10."
            ::= { hwPDU8000TransEntry 43 }

        hwPDU8000TransOutputL1THD-urate OBJECT-TYPE
            SYNTAX Integer32 (0..100)
            MAX-ACCESS read-only
            STATUS current
            DESCRIPTION
                "Output L1 THD-u rate. Unit: %. Multi: 100."
            ::= { hwPDU8000TransEntry 44 }

        hwPDU8000TransOutputL2THD-urate OBJECT-TYPE
            SYNTAX Integer32 (0..100)
            MAX-ACCESS read-only
            STATUS current
            DESCRIPTION
                "Output L2 THD-u rate. Unit: %. Multi: 100."
            ::= { hwPDU8000TransEntry 45 }

        hwPDU8000TransOutputL3THD-urate OBJECT-TYPE
            SYNTAX Integer32 (0..100)
            MAX-ACCESS read-only
            STATUS current
            DESCRIPTION
                "Output L3 THD-u rate. Unit: %. Multi: 100."
            ::= { hwPDU8000TransEntry 46 }

        hwPDU8000TransOutputL1THD-irate OBJECT-TYPE
            SYNTAX Integer32 (0..100)
            MAX-ACCESS read-only
            STATUS current
            DESCRIPTION
                "Output L1 THD-i rate. Unit: %. Multi: 100."
            ::= { hwPDU8000TransEntry 47 }

        hwPDU8000TransOutputL2THD-irate OBJECT-TYPE
            SYNTAX Integer32 (0..100)
            MAX-ACCESS read-only
            STATUS current
            DESCRIPTION
                "Output L2 THD-i rate. Unit: %. Multi: 100."
            ::= { hwPDU8000TransEntry 48 }

        hwPDU8000TransOutputL3THD-irate OBJECT-TYPE
            SYNTAX Integer32 (0..100)
            MAX-ACCESS read-only
            STATUS current
            DESCRIPTION
                "Output L3 THD-i rate. Unit: %. Multi: 100."
            ::= { hwPDU8000TransEntry 49 }

        hwPDU8000TransOutputtotalactivepower OBJECT-TYPE
            SYNTAX Integer32 (-750..750)
            MAX-ACCESS read-only
            STATUS current
            DESCRIPTION
                "Output total  active power. Unit: kW. Multi: 10."
            ::= { hwPDU8000TransEntry 50 }

        hwPDU8000TransOutputtotalapparentpower OBJECT-TYPE
            SYNTAX Integer32 (-750..750)
            MAX-ACCESS read-only
            STATUS current
            DESCRIPTION
                "Output total  apparent power. Unit: kVA. Multi: 10."
            ::= { hwPDU8000TransEntry 51 }

        hwPDU8000TransOutputtotalreactivepower OBJECT-TYPE
            SYNTAX Integer32 (-750..750)
            MAX-ACCESS read-only
            STATUS current
            DESCRIPTION
                "Output total  reactive power. Unit: kVAR. Multi: 10."
            ::= { hwPDU8000TransEntry 52 }

        hwPDU8000TransRawstatus OBJECT-TYPE
            SYNTAX RowStatus
            MAX-ACCESS read-create
            STATUS current
            DESCRIPTION
                "The RowStatus of PDU8000 Transformer."
            ::= { hwPDU8000TransEntry 100 }

        hwPDU8000TransMode1_2Table OBJECT-TYPE
            SYNTAX SEQUENCE OF HwPDU8000TransMode1_2Entry
            MAX-ACCESS not-accessible
             STATUS current
             DESCRIPTION
                "The table of PDU8000 Trans Module 1 and 2."
            ::= { hwPDU8000Transformer 2 }

        hwPDU8000TransMode1_2Entry OBJECT-TYPE
                        SYNTAX HwPDU8000TransMode1_2Entry
            MAX-ACCESS not-accessible
             STATUS current
             DESCRIPTION
                "The table of PDU8000 Trans Module 1 and 2."
            INDEX { hwPDU8000TransMode1_2Index }
            ::= { hwPDU8000TransMode1_2Table 1 }

        HwPDU8000TransMode1_2Entry            ::= SEQUENCE {
                hwPDU8000TransMode1_2Index
                    Unsigned32,
                hwPDU8000TransMod1Branch1L1outputactiveelectricenergy
                    Integer32,
                hwPDU8000TransMod1Branch1L2outputactiveelectricenergy
                    Integer32,
                hwPDU8000TransMod1Branch1L3outputactiveelectricenergy
                    Integer32,
                hwPDU8000TransMod1Branch2L1outputactiveelectricenergy
                    Integer32,
                hwPDU8000TransMod1Branch2L2outputactiveelectricenergy
                    Integer32,
                hwPDU8000TransMod1Branch2L3outputactiveelectricenergy
                    Integer32,
                hwPDU8000TransMod1Branch3L1outputactiveelectricenergy
                    Integer32,
                hwPDU8000TransMod1Branch3L2outputactiveelectricenergy
                    Integer32,
                hwPDU8000TransMod1Branch3L3outputactiveelectricenergy
                    Integer32,
                hwPDU8000TransMod1Branch4L1outputactiveelectricenergy
                    Integer32,
                hwPDU8000TransMod1Branch4L2outputactiveelectricenergy
                    Integer32,
                hwPDU8000TransMod1Branch4L3outputactiveelectricenergy
                    Integer32,
                hwPDU8000TransMod1Branch5L1outputactiveelectricenergy
                    Integer32,
                hwPDU8000TransMod1Branch5L2outputactiveelectricenergy
                    Integer32,
                hwPDU8000TransMod1Branch5L3outputactiveelectricenergy
                    Integer32,
                hwPDU8000TransMod1Branch6L1outputactiveelectricenergy
                    Integer32,
                hwPDU8000TransMod1Branch6L2outputactiveelectricenergy
                    Integer32,
                hwPDU8000TransMod1Branch6L3outputactiveelectricenergy
                    Integer32,
                hwPDU8000TransMod1Branch7L1outputactiveelectricenergy
                    Integer32,
                hwPDU8000TransMod1Branch7L2outputactiveelectricenergy
                    Integer32,
                hwPDU8000TransMod1Branch7L3outputactiveelectricenergy
                    Integer32,
                hwPDU8000TransMod1Branch8L1outputactiveelectricenergy
                    Integer32,
                hwPDU8000TransMod1Branch8L2outputactiveelectricenergy
                    Integer32,
                hwPDU8000TransMod1Branch8L3outputactiveelectricenergy
                    Integer32,
                hwPDU8000TransMod1Branch9L1outputactiveelectricenergy
                    Integer32,
                hwPDU8000TransMod1Branch9L2outputactiveelectricenergy
                    Integer32,
                hwPDU8000TransMod1Branch9L3outputactiveelectricenergy
                    Integer32,
                hwPDU8000TransMod1Branch10L1outputactiveelectricenergy
                    Integer32,
                hwPDU8000TransMod1Branch10L2outputactiveelectricenergy
                    Integer32,
                hwPDU8000TransMod1Branch10L3outputactiveelectricenergy
                    Integer32,
                hwPDU8000TransMod1Branch11L1outputactiveelectricenergy
                    Integer32,
                hwPDU8000TransMod1Branch11L2outputactiveelectricenergy
                    Integer32,
                hwPDU8000TransMod1Branch11L3outputactiveelectricenergy
                    Integer32,
                hwPDU8000TransMod1Branch12L1outputactiveelectricenergy
                    Integer32,
                hwPDU8000TransMod1Branch12L2outputactiveelectricenergy
                    Integer32,
                hwPDU8000TransMod1Branch12L3outputactiveelectricenergy
                    Integer32,
                hwPDU8000TransMod2Branch1L1outputactiveelectricenergy
                    Integer32,
                hwPDU8000TransMod2Branch1L2outputactiveelectricenergy
                    Integer32,
                hwPDU8000TransMod2Branch1L3outputactiveelectricenergy
                    Integer32,
                hwPDU8000TransMod2Branch2L1outputactiveelectricenergy
                    Integer32,
                hwPDU8000TransMod2Branch2L2outputactiveelectricenergy
                    Integer32,
                hwPDU8000TransMod2Branch2L3outputactiveelectricenergy
                    Integer32,
                hwPDU8000TransMod2Branch3L1outputactiveelectricenergy
                    Integer32,
                hwPDU8000TransMod2Branch3L2outputactiveelectricenergy
                    Integer32,
                hwPDU8000TransMod2Branch3L3outputactiveelectricenergy
                    Integer32,
                hwPDU8000TransMod2Branch4L1outputactiveelectricenergy
                    Integer32,
                hwPDU8000TransMod2Branch4L2outputactiveelectricenergy
                    Integer32,
                hwPDU8000TransMod2Branch4L3outputactiveelectricenergy
                    Integer32,
                hwPDU8000TransMod2Branch5L1outputactiveelectricenergy
                    Integer32,
                hwPDU8000TransMod2Branch5L2outputactiveelectricenergy
                    Integer32,
                hwPDU8000TransMod2Branch5L3outputactiveelectricenergy
                    Integer32,
                hwPDU8000TransMod2Branch6L1outputactiveelectricenergy
                    Integer32,
                hwPDU8000TransMod2Branch6L2outputactiveelectricenergy
                    Integer32,
                hwPDU8000TransMod2Branch6L3outputactiveelectricenergy
                    Integer32,
                hwPDU8000TransMod2Branch7L1outputactiveelectricenergy
                    Integer32,
                hwPDU8000TransMod2Branch7L2outputactiveelectricenergy
                    Integer32,
                hwPDU8000TransMod2Branch7L3outputactiveelectricenergy
                    Integer32,
                hwPDU8000TransMod2Branch8L1outputactiveelectricenergy
                    Integer32,
                hwPDU8000TransMod2Branch8L2outputactiveelectricenergy
                    Integer32,
                hwPDU8000TransMod2Branch8L3outputactiveelectricenergy
                    Integer32,
                hwPDU8000TransMod2Branch9L1outputactiveelectricenergy
                    Integer32,
                hwPDU8000TransMod2Branch9L2outputactiveelectricenergy
                    Integer32,
                hwPDU8000TransMod2Branch9L3outputactiveelectricenergy
                    Integer32,
                hwPDU8000TransMod2Branch10L1outputactiveelectricenergy
                    Integer32,
                hwPDU8000TransMod2Branch10L2outputactiveelectricenergy
                    Integer32,
                hwPDU8000TransMod2Branch10L3outputactiveelectricenergy
                    Integer32,
                hwPDU8000TransMod2Branch11L1outputactiveelectricenergy
                    Integer32,
                hwPDU8000TransMod2Branch11L2outputactiveelectricenergy
                    Integer32,
                hwPDU8000TransMod2Branch11L3outputactiveelectricenergy
                    Integer32,
                hwPDU8000TransMod2Branch12L1outputactiveelectricenergy
                    Integer32,
                hwPDU8000TransMod2Branch12L2outputactiveelectricenergy
                    Integer32,
                hwPDU8000TransMod2Branch12L3outputactiveelectricenergy
                    Integer32,
                hwPDU8000TransMode1_2RowStatus
                    RowStatus
            }

        hwPDU8000TransMode1_2Index OBJECT-TYPE
            SYNTAX Unsigned32
            MAX-ACCESS read-only
            STATUS current
            DESCRIPTION
                "The index of PDU8000 Trans Module 1 and 2."
            ::= { hwPDU8000TransMode1_2Entry 1 }

        hwPDU8000TransMod1Branch1L1outputactiveelectricenergy OBJECT-TYPE
            SYNTAX Integer32 (0..21474836)
            MAX-ACCESS read-only
            STATUS current
            DESCRIPTION
                "Branch 1 L1 output active electric energy. Unit: KWh. Multi: 100."
            ::= { hwPDU8000TransMode1_2Entry 2 }

        hwPDU8000TransMod1Branch1L2outputactiveelectricenergy OBJECT-TYPE
            SYNTAX Integer32 (0..21474836)
            MAX-ACCESS read-only
            STATUS current
            DESCRIPTION
                "Branch 1 L2 output active electric energy. Unit: KWh. Multi: 100."
            ::= { hwPDU8000TransMode1_2Entry 3 }

        hwPDU8000TransMod1Branch1L3outputactiveelectricenergy OBJECT-TYPE
            SYNTAX Integer32 (0..21474836)
            MAX-ACCESS read-only
            STATUS current
            DESCRIPTION
                "Branch 1 L3 output active electric energy. Unit: KWh. Multi: 100."
            ::= { hwPDU8000TransMode1_2Entry 4 }

        hwPDU8000TransMod1Branch2L1outputactiveelectricenergy OBJECT-TYPE
            SYNTAX Integer32 (0..21474836)
            MAX-ACCESS read-only
            STATUS current
            DESCRIPTION
                "Branch 2 L1 output active electric energy. Unit: KWh. Multi: 100."
            ::= { hwPDU8000TransMode1_2Entry 5 }

        hwPDU8000TransMod1Branch2L2outputactiveelectricenergy OBJECT-TYPE
            SYNTAX Integer32 (0..21474836)
            MAX-ACCESS read-only
            STATUS current
            DESCRIPTION
                "Branch 2 L2 output active electric energy. Unit: KWh. Multi: 100."
            ::= { hwPDU8000TransMode1_2Entry 6 }

        hwPDU8000TransMod1Branch2L3outputactiveelectricenergy OBJECT-TYPE
            SYNTAX Integer32 (0..21474836)
            MAX-ACCESS read-only
            STATUS current
            DESCRIPTION
                "Branch 2 L3 output active electric energy. Unit: KWh. Multi: 100."
            ::= { hwPDU8000TransMode1_2Entry 7 }

        hwPDU8000TransMod1Branch3L1outputactiveelectricenergy OBJECT-TYPE
            SYNTAX Integer32 (0..21474836)
            MAX-ACCESS read-only
            STATUS current
            DESCRIPTION
                "Branch 3 L1 output active electric energy. Unit: KWh. Multi: 100."
            ::= { hwPDU8000TransMode1_2Entry 8 }

        hwPDU8000TransMod1Branch3L2outputactiveelectricenergy OBJECT-TYPE
            SYNTAX Integer32 (0..21474836)
            MAX-ACCESS read-only
            STATUS current
            DESCRIPTION
                "Branch 3 L2 output active electric energy. Unit: KWh. Multi: 100."
            ::= { hwPDU8000TransMode1_2Entry 9 }

        hwPDU8000TransMod1Branch3L3outputactiveelectricenergy OBJECT-TYPE
            SYNTAX Integer32 (0..21474836)
            MAX-ACCESS read-only
            STATUS current
            DESCRIPTION
                "Branch 3 L3 output active electric energy. Unit: KWh. Multi: 100."
            ::= { hwPDU8000TransMode1_2Entry 10 }

        hwPDU8000TransMod1Branch4L1outputactiveelectricenergy OBJECT-TYPE
            SYNTAX Integer32 (0..21474836)
            MAX-ACCESS read-only
            STATUS current
            DESCRIPTION
                "Branch 4 L1 output active electric energy. Unit: KWh. Multi: 100."
            ::= { hwPDU8000TransMode1_2Entry 11 }

        hwPDU8000TransMod1Branch4L2outputactiveelectricenergy OBJECT-TYPE
            SYNTAX Integer32 (0..21474836)
            MAX-ACCESS read-only
            STATUS current
            DESCRIPTION
                "Branch 4 L2 output active electric energy. Unit: KWh. Multi: 100."
            ::= { hwPDU8000TransMode1_2Entry 12 }

        hwPDU8000TransMod1Branch4L3outputactiveelectricenergy OBJECT-TYPE
            SYNTAX Integer32 (0..21474836)
            MAX-ACCESS read-only
            STATUS current
            DESCRIPTION
                "Branch 4 L3 output active electric energy. Unit: KWh. Multi: 100."
            ::= { hwPDU8000TransMode1_2Entry 13 }

        hwPDU8000TransMod1Branch5L1outputactiveelectricenergy OBJECT-TYPE
            SYNTAX Integer32 (0..21474836)
            MAX-ACCESS read-only
            STATUS current
            DESCRIPTION
                "Branch 5 L1 output active electric energy. Unit: KWh. Multi: 100."
            ::= { hwPDU8000TransMode1_2Entry 14 }

        hwPDU8000TransMod1Branch5L2outputactiveelectricenergy OBJECT-TYPE
            SYNTAX Integer32 (0..21474836)
            MAX-ACCESS read-only
            STATUS current
            DESCRIPTION
                "Branch 5 L2 output active electric energy. Unit: KWh. Multi: 100."
            ::= { hwPDU8000TransMode1_2Entry 15 }

        hwPDU8000TransMod1Branch5L3outputactiveelectricenergy OBJECT-TYPE
            SYNTAX Integer32 (0..21474836)
            MAX-ACCESS read-only
            STATUS current
            DESCRIPTION
                "Branch 5 L3 output active electric energy. Unit: KWh. Multi: 100."
            ::= { hwPDU8000TransMode1_2Entry 16 }

        hwPDU8000TransMod1Branch6L1outputactiveelectricenergy OBJECT-TYPE
            SYNTAX Integer32 (0..21474836)
            MAX-ACCESS read-only
            STATUS current
            DESCRIPTION
                "Branch 6 L1 output active electric energy. Unit: KWh. Multi: 100."
            ::= { hwPDU8000TransMode1_2Entry 17 }

        hwPDU8000TransMod1Branch6L2outputactiveelectricenergy OBJECT-TYPE
            SYNTAX Integer32 (0..21474836)
            MAX-ACCESS read-only
            STATUS current
            DESCRIPTION
                "Branch 6 L2 output active electric energy. Unit: KWh. Multi: 100."
            ::= { hwPDU8000TransMode1_2Entry 18 }

        hwPDU8000TransMod1Branch6L3outputactiveelectricenergy OBJECT-TYPE
            SYNTAX Integer32 (0..21474836)
            MAX-ACCESS read-only
            STATUS current
            DESCRIPTION
                "Branch 6 L3 output active electric energy. Unit: KWh. Multi: 100."
            ::= { hwPDU8000TransMode1_2Entry 19 }

        hwPDU8000TransMod1Branch7L1outputactiveelectricenergy OBJECT-TYPE
            SYNTAX Integer32 (0..21474836)
            MAX-ACCESS read-only
            STATUS current
            DESCRIPTION
                "Branch 7 L1 output active electric energy. Unit: KWh. Multi: 100."
            ::= { hwPDU8000TransMode1_2Entry 20 }

        hwPDU8000TransMod1Branch7L2outputactiveelectricenergy OBJECT-TYPE
            SYNTAX Integer32 (0..21474836)
            MAX-ACCESS read-only
            STATUS current
            DESCRIPTION
                "Branch 7 L2 output active electric energy. Unit: KWh. Multi: 100."
            ::= { hwPDU8000TransMode1_2Entry 21 }

        hwPDU8000TransMod1Branch7L3outputactiveelectricenergy OBJECT-TYPE
            SYNTAX Integer32 (0..21474836)
            MAX-ACCESS read-only
            STATUS current
            DESCRIPTION
                "Branch 7 L3 output active electric energy. Unit: KWh. Multi: 100."
            ::= { hwPDU8000TransMode1_2Entry 22 }

        hwPDU8000TransMod1Branch8L1outputactiveelectricenergy OBJECT-TYPE
            SYNTAX Integer32 (0..21474836)
            MAX-ACCESS read-only
            STATUS current
            DESCRIPTION
                "Branch 8 L1 output active electric energy. Unit: KWh. Multi: 100."
            ::= { hwPDU8000TransMode1_2Entry 23 }

        hwPDU8000TransMod1Branch8L2outputactiveelectricenergy OBJECT-TYPE
            SYNTAX Integer32 (0..21474836)
            MAX-ACCESS read-only
            STATUS current
            DESCRIPTION
                "Branch 8 L2 output active electric energy. Unit: KWh. Multi: 100."
            ::= { hwPDU8000TransMode1_2Entry 24 }

        hwPDU8000TransMod1Branch8L3outputactiveelectricenergy OBJECT-TYPE
            SYNTAX Integer32 (0..21474836)
            MAX-ACCESS read-only
            STATUS current
            DESCRIPTION
                "Branch 8 L3 output active electric energy. Unit: KWh. Multi: 100."
            ::= { hwPDU8000TransMode1_2Entry 25 }

        hwPDU8000TransMod1Branch9L1outputactiveelectricenergy OBJECT-TYPE
            SYNTAX Integer32 (0..21474836)
            MAX-ACCESS read-only
            STATUS current
            DESCRIPTION
                "Branch 9 L1 output active electric energy. Unit: KWh. Multi: 100."
            ::= { hwPDU8000TransMode1_2Entry 26 }

        hwPDU8000TransMod1Branch9L2outputactiveelectricenergy OBJECT-TYPE
            SYNTAX Integer32 (0..21474836)
            MAX-ACCESS read-only
            STATUS current
            DESCRIPTION
                "Branch 9 L2 output active electric energy. Unit: KWh. Multi: 100."
            ::= { hwPDU8000TransMode1_2Entry 27 }

        hwPDU8000TransMod1Branch9L3outputactiveelectricenergy OBJECT-TYPE
            SYNTAX Integer32 (0..21474836)
            MAX-ACCESS read-only
            STATUS current
            DESCRIPTION
                "Branch 9 L3 output active electric energy. Unit: KWh. Multi: 100."
            ::= { hwPDU8000TransMode1_2Entry 28 }

        hwPDU8000TransMod1Branch10L1outputactiveelectricenergy OBJECT-TYPE
            SYNTAX Integer32 (0..21474836)
            MAX-ACCESS read-only
            STATUS current
            DESCRIPTION
                "Branch 10 L1 output active electric energy. Unit: KWh. Multi: 100."
            ::= { hwPDU8000TransMode1_2Entry 29 }

        hwPDU8000TransMod1Branch10L2outputactiveelectricenergy OBJECT-TYPE
            SYNTAX Integer32 (0..21474836)
            MAX-ACCESS read-only
            STATUS current
            DESCRIPTION
                "Branch 10 L2 output active electric energy. Unit: KWh. Multi: 100."
            ::= { hwPDU8000TransMode1_2Entry 30 }

        hwPDU8000TransMod1Branch10L3outputactiveelectricenergy OBJECT-TYPE
            SYNTAX Integer32 (0..21474836)
            MAX-ACCESS read-only
            STATUS current
            DESCRIPTION
                "Branch 10 L3 output active electric energy. Unit: KWh. Multi: 100."
            ::= { hwPDU8000TransMode1_2Entry 31 }

        hwPDU8000TransMod1Branch11L1outputactiveelectricenergy OBJECT-TYPE
            SYNTAX Integer32 (0..21474836)
            MAX-ACCESS read-only
            STATUS current
            DESCRIPTION
                "Branch 11 L1 output active electric energy. Unit: KWh. Multi: 100."
            ::= { hwPDU8000TransMode1_2Entry 32 }

        hwPDU8000TransMod1Branch11L2outputactiveelectricenergy OBJECT-TYPE
            SYNTAX Integer32 (0..21474836)
            MAX-ACCESS read-only
            STATUS current
            DESCRIPTION
                "Branch 11 L2 output active electric energy. Unit: KWh. Multi: 100."
            ::= { hwPDU8000TransMode1_2Entry 33 }

        hwPDU8000TransMod1Branch11L3outputactiveelectricenergy OBJECT-TYPE
            SYNTAX Integer32 (0..21474836)
            MAX-ACCESS read-only
            STATUS current
            DESCRIPTION
                "Branch 11 L3 output active electric energy. Unit: KWh. Multi: 100."
            ::= { hwPDU8000TransMode1_2Entry 34 }

        hwPDU8000TransMod1Branch12L1outputactiveelectricenergy OBJECT-TYPE
            SYNTAX Integer32 (0..21474836)
            MAX-ACCESS read-only
            STATUS current
            DESCRIPTION
                "Branch 12 L1 output active electric energy. Unit: KWh. Multi: 100."
            ::= { hwPDU8000TransMode1_2Entry 35 }

        hwPDU8000TransMod1Branch12L2outputactiveelectricenergy OBJECT-TYPE
            SYNTAX Integer32 (0..21474836)
            MAX-ACCESS read-only
            STATUS current
            DESCRIPTION
                "Branch 12 L2 output active electric energy. Unit: KWh. Multi: 100."
            ::= { hwPDU8000TransMode1_2Entry 36 }

        hwPDU8000TransMod1Branch12L3outputactiveelectricenergy OBJECT-TYPE
            SYNTAX Integer32 (0..21474836)
            MAX-ACCESS read-only
            STATUS current
            DESCRIPTION
                "Branch 12 L3 output active electric energy. Unit: KWh. Multi: 100."
            ::= { hwPDU8000TransMode1_2Entry 37 }

        hwPDU8000TransMod2Branch1L1outputactiveelectricenergy OBJECT-TYPE
            SYNTAX Integer32 (0..21474836)
            MAX-ACCESS read-only
            STATUS current
            DESCRIPTION
                "Branch 1 L1 output active electric energy. Unit: KWh. Multi: 100."
            ::= { hwPDU8000TransMode1_2Entry 38 }

        hwPDU8000TransMod2Branch1L2outputactiveelectricenergy OBJECT-TYPE
            SYNTAX Integer32 (0..21474836)
            MAX-ACCESS read-only
            STATUS current
            DESCRIPTION
                "Branch 1 L2 output active electric energy. Unit: KWh. Multi: 100."
            ::= { hwPDU8000TransMode1_2Entry 39 }

        hwPDU8000TransMod2Branch1L3outputactiveelectricenergy OBJECT-TYPE
            SYNTAX Integer32 (0..21474836)
            MAX-ACCESS read-only
            STATUS current
            DESCRIPTION
                "Branch 1 L3 output active electric energy. Unit: KWh. Multi: 100."
            ::= { hwPDU8000TransMode1_2Entry 40 }

        hwPDU8000TransMod2Branch2L1outputactiveelectricenergy OBJECT-TYPE
            SYNTAX Integer32 (0..21474836)
            MAX-ACCESS read-only
            STATUS current
            DESCRIPTION
                "Branch 2 L1 output active electric energy. Unit: KWh. Multi: 100."
            ::= { hwPDU8000TransMode1_2Entry 41 }

        hwPDU8000TransMod2Branch2L2outputactiveelectricenergy OBJECT-TYPE
            SYNTAX Integer32 (0..21474836)
            MAX-ACCESS read-only
            STATUS current
            DESCRIPTION
                "Branch 2 L2 output active electric energy. Unit: KWh. Multi: 100."
            ::= { hwPDU8000TransMode1_2Entry 42 }

        hwPDU8000TransMod2Branch2L3outputactiveelectricenergy OBJECT-TYPE
            SYNTAX Integer32 (0..21474836)
            MAX-ACCESS read-only
            STATUS current
            DESCRIPTION
                "Branch 2 L3 output active electric energy. Unit: KWh. Multi: 100."
            ::= { hwPDU8000TransMode1_2Entry 43 }

        hwPDU8000TransMod2Branch3L1outputactiveelectricenergy OBJECT-TYPE
            SYNTAX Integer32 (0..21474836)
            MAX-ACCESS read-only
            STATUS current
            DESCRIPTION
                "Branch 3 L1 output active electric energy. Unit: KWh. Multi: 100."
            ::= { hwPDU8000TransMode1_2Entry 44 }

        hwPDU8000TransMod2Branch3L2outputactiveelectricenergy OBJECT-TYPE
            SYNTAX Integer32 (0..21474836)
            MAX-ACCESS read-only
            STATUS current
            DESCRIPTION
                "Branch 3 L2 output active electric energy. Unit: KWh. Multi: 100."
            ::= { hwPDU8000TransMode1_2Entry 45 }

        hwPDU8000TransMod2Branch3L3outputactiveelectricenergy OBJECT-TYPE
            SYNTAX Integer32 (0..21474836)
            MAX-ACCESS read-only
            STATUS current
            DESCRIPTION
                "Branch 3 L3 output active electric energy. Unit: KWh. Multi: 100."
            ::= { hwPDU8000TransMode1_2Entry 46 }

        hwPDU8000TransMod2Branch4L1outputactiveelectricenergy OBJECT-TYPE
            SYNTAX Integer32 (0..21474836)
            MAX-ACCESS read-only
            STATUS current
            DESCRIPTION
                "Branch 4 L1 output active electric energy. Unit: KWh. Multi: 100."
            ::= { hwPDU8000TransMode1_2Entry 47 }

        hwPDU8000TransMod2Branch4L2outputactiveelectricenergy OBJECT-TYPE
            SYNTAX Integer32 (0..21474836)
            MAX-ACCESS read-only
            STATUS current
            DESCRIPTION
                "Branch 4 L2 output active electric energy. Unit: KWh. Multi: 100."
            ::= { hwPDU8000TransMode1_2Entry 48 }

        hwPDU8000TransMod2Branch4L3outputactiveelectricenergy OBJECT-TYPE
            SYNTAX Integer32 (0..21474836)
            MAX-ACCESS read-only
            STATUS current
            DESCRIPTION
                "Branch 4 L3 output active electric energy. Unit: KWh. Multi: 100."
            ::= { hwPDU8000TransMode1_2Entry 49 }

        hwPDU8000TransMod2Branch5L1outputactiveelectricenergy OBJECT-TYPE
            SYNTAX Integer32 (0..21474836)
            MAX-ACCESS read-only
            STATUS current
            DESCRIPTION
                "Branch 5 L1 output active electric energy. Unit: KWh. Multi: 100."
            ::= { hwPDU8000TransMode1_2Entry 50 }

        hwPDU8000TransMod2Branch5L2outputactiveelectricenergy OBJECT-TYPE
            SYNTAX Integer32 (0..21474836)
            MAX-ACCESS read-only
            STATUS current
            DESCRIPTION
                "Branch 5 L2 output active electric energy. Unit: KWh. Multi: 100."
            ::= { hwPDU8000TransMode1_2Entry 51 }

        hwPDU8000TransMod2Branch5L3outputactiveelectricenergy OBJECT-TYPE
            SYNTAX Integer32 (0..21474836)
            MAX-ACCESS read-only
            STATUS current
            DESCRIPTION
                "Branch 5 L3 output active electric energy. Unit: KWh. Multi: 100."
            ::= { hwPDU8000TransMode1_2Entry 52 }

        hwPDU8000TransMod2Branch6L1outputactiveelectricenergy OBJECT-TYPE
            SYNTAX Integer32 (0..21474836)
            MAX-ACCESS read-only
            STATUS current
            DESCRIPTION
                "Branch 6 L1 output active electric energy. Unit: KWh. Multi: 100."
            ::= { hwPDU8000TransMode1_2Entry 53 }

        hwPDU8000TransMod2Branch6L2outputactiveelectricenergy OBJECT-TYPE
            SYNTAX Integer32 (0..21474836)
            MAX-ACCESS read-only
            STATUS current
            DESCRIPTION
                "Branch 6 L2 output active electric energy. Unit: KWh. Multi: 100."
            ::= { hwPDU8000TransMode1_2Entry 54 }

        hwPDU8000TransMod2Branch6L3outputactiveelectricenergy OBJECT-TYPE
            SYNTAX Integer32 (0..21474836)
            MAX-ACCESS read-only
            STATUS current
            DESCRIPTION
                "Branch 6 L3 output active electric energy. Unit: KWh. Multi: 100."
            ::= { hwPDU8000TransMode1_2Entry 55 }

        hwPDU8000TransMod2Branch7L1outputactiveelectricenergy OBJECT-TYPE
            SYNTAX Integer32 (0..21474836)
            MAX-ACCESS read-only
            STATUS current
            DESCRIPTION
                "Branch 7 L1 output active electric energy. Unit: KWh. Multi: 100."
            ::= { hwPDU8000TransMode1_2Entry 56 }

        hwPDU8000TransMod2Branch7L2outputactiveelectricenergy OBJECT-TYPE
            SYNTAX Integer32 (0..21474836)
            MAX-ACCESS read-only
            STATUS current
            DESCRIPTION
                "Branch 7 L2 output active electric energy. Unit: KWh. Multi: 100."
            ::= { hwPDU8000TransMode1_2Entry 57 }

        hwPDU8000TransMod2Branch7L3outputactiveelectricenergy OBJECT-TYPE
            SYNTAX Integer32 (0..21474836)
            MAX-ACCESS read-only
            STATUS current
            DESCRIPTION
                "Branch 7 L3 output active electric energy. Unit: KWh. Multi: 100."
            ::= { hwPDU8000TransMode1_2Entry 58 }

        hwPDU8000TransMod2Branch8L1outputactiveelectricenergy OBJECT-TYPE
            SYNTAX Integer32 (0..21474836)
            MAX-ACCESS read-only
            STATUS current
            DESCRIPTION
                "Branch 8 L1 output active electric energy. Unit: KWh. Multi: 100."
            ::= { hwPDU8000TransMode1_2Entry 59 }

        hwPDU8000TransMod2Branch8L2outputactiveelectricenergy OBJECT-TYPE
            SYNTAX Integer32 (0..21474836)
            MAX-ACCESS read-only
            STATUS current
            DESCRIPTION
                "Branch 8 L2 output active electric energy. Unit: KWh. Multi: 100."
            ::= { hwPDU8000TransMode1_2Entry 60 }

        hwPDU8000TransMod2Branch8L3outputactiveelectricenergy OBJECT-TYPE
            SYNTAX Integer32 (0..21474836)
            MAX-ACCESS read-only
            STATUS current
            DESCRIPTION
                "Branch 8 L3 output active electric energy. Unit: KWh. Multi: 100."
            ::= { hwPDU8000TransMode1_2Entry 61 }

        hwPDU8000TransMod2Branch9L1outputactiveelectricenergy OBJECT-TYPE
            SYNTAX Integer32 (0..21474836)
            MAX-ACCESS read-only
            STATUS current
            DESCRIPTION
                "Branch 9 L1 output active electric energy. Unit: KWh. Multi: 100."
            ::= { hwPDU8000TransMode1_2Entry 62 }

        hwPDU8000TransMod2Branch9L2outputactiveelectricenergy OBJECT-TYPE
            SYNTAX Integer32 (0..21474836)
            MAX-ACCESS read-only
            STATUS current
            DESCRIPTION
                "Branch 9 L2 output active electric energy. Unit: KWh. Multi: 100."
            ::= { hwPDU8000TransMode1_2Entry 63 }

        hwPDU8000TransMod2Branch9L3outputactiveelectricenergy OBJECT-TYPE
            SYNTAX Integer32 (0..21474836)
            MAX-ACCESS read-only
            STATUS current
            DESCRIPTION
                "Branch 9 L3 output active electric energy. Unit: KWh. Multi: 100."
            ::= { hwPDU8000TransMode1_2Entry 64 }

        hwPDU8000TransMod2Branch10L1outputactiveelectricenergy OBJECT-TYPE
            SYNTAX Integer32 (0..21474836)
            MAX-ACCESS read-only
            STATUS current
            DESCRIPTION
                "Branch 10 L1 output active electric energy. Unit: KWh. Multi: 100."
            ::= { hwPDU8000TransMode1_2Entry 65 }

        hwPDU8000TransMod2Branch10L2outputactiveelectricenergy OBJECT-TYPE
            SYNTAX Integer32 (0..21474836)
            MAX-ACCESS read-only
            STATUS current
            DESCRIPTION
                "Branch 10 L2 output active electric energy. Unit: KWh. Multi: 100."
            ::= { hwPDU8000TransMode1_2Entry 66 }

        hwPDU8000TransMod2Branch10L3outputactiveelectricenergy OBJECT-TYPE
            SYNTAX Integer32 (0..21474836)
            MAX-ACCESS read-only
            STATUS current
            DESCRIPTION
                "Branch 10 L3 output active electric energy. Unit: KWh. Multi: 100."
            ::= { hwPDU8000TransMode1_2Entry 67 }

        hwPDU8000TransMod2Branch11L1outputactiveelectricenergy OBJECT-TYPE
            SYNTAX Integer32 (0..21474836)
            MAX-ACCESS read-only
            STATUS current
            DESCRIPTION
                "Branch 11 L1 output active electric energy. Unit: KWh. Multi: 100."
            ::= { hwPDU8000TransMode1_2Entry 68 }

        hwPDU8000TransMod2Branch11L2outputactiveelectricenergy OBJECT-TYPE
            SYNTAX Integer32 (0..21474836)
            MAX-ACCESS read-only
            STATUS current
            DESCRIPTION
                "Branch 11 L2 output active electric energy. Unit: KWh. Multi: 100."
            ::= { hwPDU8000TransMode1_2Entry 69 }

        hwPDU8000TransMod2Branch11L3outputactiveelectricenergy OBJECT-TYPE
            SYNTAX Integer32 (0..21474836)
            MAX-ACCESS read-only
            STATUS current
            DESCRIPTION
                "Branch 11 L3 output active electric energy. Unit: KWh. Multi: 100."
            ::= { hwPDU8000TransMode1_2Entry 70 }

        hwPDU8000TransMod2Branch12L1outputactiveelectricenergy OBJECT-TYPE
            SYNTAX Integer32 (0..21474836)
            MAX-ACCESS read-only
            STATUS current
            DESCRIPTION
                "Branch 12 L1 output active electric energy. Unit: KWh. Multi: 100."
            ::= { hwPDU8000TransMode1_2Entry 71 }

        hwPDU8000TransMod2Branch12L2outputactiveelectricenergy OBJECT-TYPE
            SYNTAX Integer32 (0..21474836)
            MAX-ACCESS read-only
            STATUS current
            DESCRIPTION
                "Branch 12 L2 output active electric energy. Unit: KWh. Multi: 100."
            ::= { hwPDU8000TransMode1_2Entry 72 }

        hwPDU8000TransMod2Branch12L3outputactiveelectricenergy OBJECT-TYPE
            SYNTAX Integer32 (0..21474836)
            MAX-ACCESS read-only
            STATUS current
            DESCRIPTION
                "Branch 12 L3 output active electric energy. Unit: KWh. Multi: 100."
            ::= { hwPDU8000TransMode1_2Entry 73 }

        hwPDU8000TransMode1_2RowStatus OBJECT-TYPE
            SYNTAX RowStatus
            MAX-ACCESS read-create
            STATUS current
            DESCRIPTION
                "The row status of Deviece."
            ::= { hwPDU8000TransMode1_2Entry 100 }

        hwPDU8000TransMode3_4Table OBJECT-TYPE
            SYNTAX SEQUENCE OF HwPDU8000TransMode3_4Entry
            MAX-ACCESS not-accessible
             STATUS current
             DESCRIPTION
                "The table of PDU8000 Trans Module 3 and 4."
            ::= { hwPDU8000Transformer 3 }

        hwPDU8000TransMode3_4Entry OBJECT-TYPE
                        SYNTAX HwPDU8000TransMode3_4Entry
            MAX-ACCESS not-accessible
             STATUS current
             DESCRIPTION
                "The table of PDU8000 Trans Module 3 and 4."
            INDEX { hwPDU8000TransMode3_4Index }
            ::= { hwPDU8000TransMode3_4Table 1 }

        HwPDU8000TransMode3_4Entry            ::= SEQUENCE {
                hwPDU8000TransMode3_4Index
                    Unsigned32,
                hwPDU8000TransMod3Branch1L1outputactiveelectricenergy
                    Integer32,
                hwPDU8000TransMod3Branch1L2outputactiveelectricenergy
                    Integer32,
                hwPDU8000TransMod3Branch1L3outputactiveelectricenergy
                    Integer32,
                hwPDU8000TransMod3Branch2L1outputactiveelectricenergy
                    Integer32,
                hwPDU8000TransMod3Branch2L2outputactiveelectricenergy
                    Integer32,
                hwPDU8000TransMod3Branch2L3outputactiveelectricenergy
                    Integer32,
                hwPDU8000TransMod3Branch3L1outputactiveelectricenergy
                    Integer32,
                hwPDU8000TransMod3Branch3L2outputactiveelectricenergy
                    Integer32,
                hwPDU8000TransMod3Branch3L3outputactiveelectricenergy
                    Integer32,
                hwPDU8000TransMod3Branch4L1outputactiveelectricenergy
                    Integer32,
                hwPDU8000TransMod3Branch4L2outputactiveelectricenergy
                    Integer32,
                hwPDU8000TransMod3Branch4L3outputactiveelectricenergy
                    Integer32,
                hwPDU8000TransMod3Branch5L1outputactiveelectricenergy
                    Integer32,
                hwPDU8000TransMod3Branch5L2outputactiveelectricenergy
                    Integer32,
                hwPDU8000TransMod3Branch5L3outputactiveelectricenergy
                    Integer32,
                hwPDU8000TransMod3Branch6L1outputactiveelectricenergy
                    Integer32,
                hwPDU8000TransMod3Branch6L2outputactiveelectricenergy
                    Integer32,
                hwPDU8000TransMod3Branch6L3outputactiveelectricenergy
                    Integer32,
                hwPDU8000TransMod3Branch7L1outputactiveelectricenergy
                    Integer32,
                hwPDU8000TransMod3Branch7L2outputactiveelectricenergy
                    Integer32,
                hwPDU8000TransMod3Branch7L3outputactiveelectricenergy
                    Integer32,
                hwPDU8000TransMod3Branch8L1outputactiveelectricenergy
                    Integer32,
                hwPDU8000TransMod3Branch8L2outputactiveelectricenergy
                    Integer32,
                hwPDU8000TransMod3Branch8L3outputactiveelectricenergy
                    Integer32,
                hwPDU8000TransMod3Branch9L1outputactiveelectricenergy
                    Integer32,
                hwPDU8000TransMod3Branch9L2outputactiveelectricenergy
                    Integer32,
                hwPDU8000TransMod3Branch9L3outputactiveelectricenergy
                    Integer32,
                hwPDU8000TransMod3Branch10L1outputactiveelectricenergy
                    Integer32,
                hwPDU8000TransMod3Branch10L2outputactiveelectricenergy
                    Integer32,
                hwPDU8000TransMod3Branch10L3outputactiveelectricenergy
                    Integer32,
                hwPDU8000TransMod3Branch11L1outputactiveelectricenergy
                    Integer32,
                hwPDU8000TransMod3Branch11L2outputactiveelectricenergy
                    Integer32,
                hwPDU8000TransMod3Branch11L3outputactiveelectricenergy
                    Integer32,
                hwPDU8000TransMod3Branch12L1outputactiveelectricenergy
                    Integer32,
                hwPDU8000TransMod3Branch12L2outputactiveelectricenergy
                    Integer32,
                hwPDU8000TransMod3Branch12L3outputactiveelectricenergy
                    Integer32,
                hwPDU8000TransMod4Branch1L1outputactiveelectricenergy
                    Integer32,
                hwPDU8000TransMod4Branch1L2outputactiveelectricenergy
                    Integer32,
                hwPDU8000TransMod4Branch1L3outputactiveelectricenergy
                    Integer32,
                hwPDU8000TransMod4Branch2L1outputactiveelectricenergy
                    Integer32,
                hwPDU8000TransMod4Branch2L2outputactiveelectricenergy
                    Integer32,
                hwPDU8000TransMod4Branch2L3outputactiveelectricenergy
                    Integer32,
                hwPDU8000TransMod4Branch3L1outputactiveelectricenergy
                    Integer32,
                hwPDU8000TransMod4Branch3L2outputactiveelectricenergy
                    Integer32,
                hwPDU8000TransMod4Branch3L3outputactiveelectricenergy
                    Integer32,
                hwPDU8000TransMod4Branch4L1outputactiveelectricenergy
                    Integer32,
                hwPDU8000TransMod4Branch4L2outputactiveelectricenergy
                    Integer32,
                hwPDU8000TransMod4Branch4L3outputactiveelectricenergy
                    Integer32,
                hwPDU8000TransMod4Branch5L1outputactiveelectricenergy
                    Integer32,
                hwPDU8000TransMod4Branch5L2outputactiveelectricenergy
                    Integer32,
                hwPDU8000TransMod4Branch5L3outputactiveelectricenergy
                    Integer32,
                hwPDU8000TransMod4Branch6L1outputactiveelectricenergy
                    Integer32,
                hwPDU8000TransMod4Branch6L2outputactiveelectricenergy
                    Integer32,
                hwPDU8000TransMod4Branch6L3outputactiveelectricenergy
                    Integer32,
                hwPDU8000TransMod4Branch7L1outputactiveelectricenergy
                    Integer32,
                hwPDU8000TransMod4Branch7L2outputactiveelectricenergy
                    Integer32,
                hwPDU8000TransMod4Branch7L3outputactiveelectricenergy
                    Integer32,
                hwPDU8000TransMod4Branch8L1outputactiveelectricenergy
                    Integer32,
                hwPDU8000TransMod4Branch8L2outputactiveelectricenergy
                    Integer32,
                hwPDU8000TransMod4Branch8L3outputactiveelectricenergy
                    Integer32,
                hwPDU8000TransMod4Branch9L1outputactiveelectricenergy
                    Integer32,
                hwPDU8000TransMod4Branch9L2outputactiveelectricenergy
                    Integer32,
                hwPDU8000TransMod4Branch9L3outputactiveelectricenergy
                    Integer32,
                hwPDU8000TransMod4Branch10L1outputactiveelectricenergy
                    Integer32,
                hwPDU8000TransMod4Branch10L2outputactiveelectricenergy
                    Integer32,
                hwPDU8000TransMod4Branch10L3outputactiveelectricenergy
                    Integer32,
                hwPDU8000TransMod4Branch11L1outputactiveelectricenergy
                    Integer32,
                hwPDU8000TransMod4Branch11L2outputactiveelectricenergy
                    Integer32,
                hwPDU8000TransMod4Branch11L3outputactiveelectricenergy
                    Integer32,
                hwPDU8000TransMod4Branch12L1outputactiveelectricenergy
                    Integer32,
                hwPDU8000TransMod4Branch12L2outputactiveelectricenergy
                    Integer32,
                hwPDU8000TransMod4Branch12L3outputactiveelectricenergy
                    Integer32,
                hwPDU8000TransMode3_2RowStatus
                    RowStatus
            }

        hwPDU8000TransMode3_4Index OBJECT-TYPE
            SYNTAX Unsigned32
            MAX-ACCESS read-only
            STATUS current
            DESCRIPTION
                "The index of PDU8000 Trans Module 3 and 4."
            ::= { hwPDU8000TransMode3_4Entry 1 }

        hwPDU8000TransMod3Branch1L1outputactiveelectricenergy OBJECT-TYPE
            SYNTAX Integer32 (0..21474836)
            MAX-ACCESS read-only
            STATUS current
            DESCRIPTION
                "Branch 1 L1 output active electric energy. Unit: KWh. Multi: 100."
            ::= { hwPDU8000TransMode3_4Entry 2 }

        hwPDU8000TransMod3Branch1L2outputactiveelectricenergy OBJECT-TYPE
            SYNTAX Integer32 (0..21474836)
            MAX-ACCESS read-only
            STATUS current
            DESCRIPTION
                "Branch 1 L2 output active electric energy. Unit: KWh. Multi: 100."
            ::= { hwPDU8000TransMode3_4Entry 3 }

        hwPDU8000TransMod3Branch1L3outputactiveelectricenergy OBJECT-TYPE
            SYNTAX Integer32 (0..21474836)
            MAX-ACCESS read-only
            STATUS current
            DESCRIPTION
                "Branch 1 L3 output active electric energy. Unit: KWh. Multi: 100."
            ::= { hwPDU8000TransMode3_4Entry 4 }

        hwPDU8000TransMod3Branch2L1outputactiveelectricenergy OBJECT-TYPE
            SYNTAX Integer32 (0..21474836)
            MAX-ACCESS read-only
            STATUS current
            DESCRIPTION
                "Branch 2 L1 output active electric energy. Unit: KWh. Multi: 100."
            ::= { hwPDU8000TransMode3_4Entry 5 }

        hwPDU8000TransMod3Branch2L2outputactiveelectricenergy OBJECT-TYPE
            SYNTAX Integer32 (0..21474836)
            MAX-ACCESS read-only
            STATUS current
            DESCRIPTION
                "Branch 2 L2 output active electric energy. Unit: KWh. Multi: 100."
            ::= { hwPDU8000TransMode3_4Entry 6 }

        hwPDU8000TransMod3Branch2L3outputactiveelectricenergy OBJECT-TYPE
            SYNTAX Integer32 (0..21474836)
            MAX-ACCESS read-only
            STATUS current
            DESCRIPTION
                "Branch 2 L3 output active electric energy. Unit: KWh. Multi: 100."
            ::= { hwPDU8000TransMode3_4Entry 7 }

        hwPDU8000TransMod3Branch3L1outputactiveelectricenergy OBJECT-TYPE
            SYNTAX Integer32 (0..21474836)
            MAX-ACCESS read-only
            STATUS current
            DESCRIPTION
                "Branch 3 L1 output active electric energy. Unit: KWh. Multi: 100."
            ::= { hwPDU8000TransMode3_4Entry 8 }

        hwPDU8000TransMod3Branch3L2outputactiveelectricenergy OBJECT-TYPE
            SYNTAX Integer32 (0..21474836)
            MAX-ACCESS read-only
            STATUS current
            DESCRIPTION
                "Branch 3 L2 output active electric energy. Unit: KWh. Multi: 100."
            ::= { hwPDU8000TransMode3_4Entry 9 }

        hwPDU8000TransMod3Branch3L3outputactiveelectricenergy OBJECT-TYPE
            SYNTAX Integer32 (0..21474836)
            MAX-ACCESS read-only
            STATUS current
            DESCRIPTION
                "Branch 3 L3 output active electric energy. Unit: KWh. Multi: 100."
            ::= { hwPDU8000TransMode3_4Entry 10 }

        hwPDU8000TransMod3Branch4L1outputactiveelectricenergy OBJECT-TYPE
            SYNTAX Integer32 (0..21474836)
            MAX-ACCESS read-only
            STATUS current
            DESCRIPTION
                "Branch 4 L1 output active electric energy. Unit: KWh. Multi: 100."
            ::= { hwPDU8000TransMode3_4Entry 11 }

        hwPDU8000TransMod3Branch4L2outputactiveelectricenergy OBJECT-TYPE
            SYNTAX Integer32 (0..21474836)
            MAX-ACCESS read-only
            STATUS current
            DESCRIPTION
                "Branch 4 L2 output active electric energy. Unit: KWh. Multi: 100."
            ::= { hwPDU8000TransMode3_4Entry 12 }

        hwPDU8000TransMod3Branch4L3outputactiveelectricenergy OBJECT-TYPE
            SYNTAX Integer32 (0..21474836)
            MAX-ACCESS read-only
            STATUS current
            DESCRIPTION
                "Branch 4 L3 output active electric energy. Unit: KWh. Multi: 100."
            ::= { hwPDU8000TransMode3_4Entry 13 }

        hwPDU8000TransMod3Branch5L1outputactiveelectricenergy OBJECT-TYPE
            SYNTAX Integer32 (0..21474836)
            MAX-ACCESS read-only
            STATUS current
            DESCRIPTION
                "Branch 5 L1 output active electric energy. Unit: KWh. Multi: 100."
            ::= { hwPDU8000TransMode3_4Entry 14 }

        hwPDU8000TransMod3Branch5L2outputactiveelectricenergy OBJECT-TYPE
            SYNTAX Integer32 (0..21474836)
            MAX-ACCESS read-only
            STATUS current
            DESCRIPTION
                "Branch 5 L2 output active electric energy. Unit: KWh. Multi: 100."
            ::= { hwPDU8000TransMode3_4Entry 15 }

        hwPDU8000TransMod3Branch5L3outputactiveelectricenergy OBJECT-TYPE
            SYNTAX Integer32 (0..21474836)
            MAX-ACCESS read-only
            STATUS current
            DESCRIPTION
                "Branch 5 L3 output active electric energy. Unit: KWh. Multi: 100."
            ::= { hwPDU8000TransMode3_4Entry 16 }

        hwPDU8000TransMod3Branch6L1outputactiveelectricenergy OBJECT-TYPE
            SYNTAX Integer32 (0..21474836)
            MAX-ACCESS read-only
            STATUS current
            DESCRIPTION
                "Branch 6 L1 output active electric energy. Unit: KWh. Multi: 100."
            ::= { hwPDU8000TransMode3_4Entry 17 }

        hwPDU8000TransMod3Branch6L2outputactiveelectricenergy OBJECT-TYPE
            SYNTAX Integer32 (0..21474836)
            MAX-ACCESS read-only
            STATUS current
            DESCRIPTION
                "Branch 6 L2 output active electric energy. Unit: KWh. Multi: 100."
            ::= { hwPDU8000TransMode3_4Entry 18 }

        hwPDU8000TransMod3Branch6L3outputactiveelectricenergy OBJECT-TYPE
            SYNTAX Integer32 (0..21474836)
            MAX-ACCESS read-only
            STATUS current
            DESCRIPTION
                "Branch 6 L3 output active electric energy. Unit: KWh. Multi: 100."
            ::= { hwPDU8000TransMode3_4Entry 19 }

        hwPDU8000TransMod3Branch7L1outputactiveelectricenergy OBJECT-TYPE
            SYNTAX Integer32 (0..21474836)
            MAX-ACCESS read-only
            STATUS current
            DESCRIPTION
                "Branch 7 L1 output active electric energy. Unit: KWh. Multi: 100."
            ::= { hwPDU8000TransMode3_4Entry 20 }

        hwPDU8000TransMod3Branch7L2outputactiveelectricenergy OBJECT-TYPE
            SYNTAX Integer32 (0..21474836)
            MAX-ACCESS read-only
            STATUS current
            DESCRIPTION
                "Branch 7 L2 output active electric energy. Unit: KWh. Multi: 100."
            ::= { hwPDU8000TransMode3_4Entry 21 }

        hwPDU8000TransMod3Branch7L3outputactiveelectricenergy OBJECT-TYPE
            SYNTAX Integer32 (0..21474836)
            MAX-ACCESS read-only
            STATUS current
            DESCRIPTION
                "Branch 7 L3 output active electric energy. Unit: KWh. Multi: 100."
            ::= { hwPDU8000TransMode3_4Entry 22 }

        hwPDU8000TransMod3Branch8L1outputactiveelectricenergy OBJECT-TYPE
            SYNTAX Integer32 (0..21474836)
            MAX-ACCESS read-only
            STATUS current
            DESCRIPTION
                "Branch 8 L1 output active electric energy. Unit: KWh. Multi: 100."
            ::= { hwPDU8000TransMode3_4Entry 23 }

        hwPDU8000TransMod3Branch8L2outputactiveelectricenergy OBJECT-TYPE
            SYNTAX Integer32 (0..21474836)
            MAX-ACCESS read-only
            STATUS current
            DESCRIPTION
                "Branch 8 L2 output active electric energy. Unit: KWh. Multi: 100."
            ::= { hwPDU8000TransMode3_4Entry 24 }

        hwPDU8000TransMod3Branch8L3outputactiveelectricenergy OBJECT-TYPE
            SYNTAX Integer32 (0..21474836)
            MAX-ACCESS read-only
            STATUS current
            DESCRIPTION
                "Branch 8 L3 output active electric energy. Unit: KWh. Multi: 100."
            ::= { hwPDU8000TransMode3_4Entry 25 }

        hwPDU8000TransMod3Branch9L1outputactiveelectricenergy OBJECT-TYPE
            SYNTAX Integer32 (0..21474836)
            MAX-ACCESS read-only
            STATUS current
            DESCRIPTION
                "Branch 9 L1 output active electric energy. Unit: KWh. Multi: 100."
            ::= { hwPDU8000TransMode3_4Entry 26 }

        hwPDU8000TransMod3Branch9L2outputactiveelectricenergy OBJECT-TYPE
            SYNTAX Integer32 (0..21474836)
            MAX-ACCESS read-only
            STATUS current
            DESCRIPTION
                "Branch 9 L2 output active electric energy. Unit: KWh. Multi: 100."
            ::= { hwPDU8000TransMode3_4Entry 27 }

        hwPDU8000TransMod3Branch9L3outputactiveelectricenergy OBJECT-TYPE
            SYNTAX Integer32 (0..21474836)
            MAX-ACCESS read-only
            STATUS current
            DESCRIPTION
                "Branch 9 L3 output active electric energy. Unit: KWh. Multi: 100."
            ::= { hwPDU8000TransMode3_4Entry 28 }

        hwPDU8000TransMod3Branch10L1outputactiveelectricenergy OBJECT-TYPE
            SYNTAX Integer32 (0..21474836)
            MAX-ACCESS read-only
            STATUS current
            DESCRIPTION
                "Branch 10 L1 output active electric energy. Unit: KWh. Multi: 100."
            ::= { hwPDU8000TransMode3_4Entry 29 }

        hwPDU8000TransMod3Branch10L2outputactiveelectricenergy OBJECT-TYPE
            SYNTAX Integer32 (0..21474836)
            MAX-ACCESS read-only
            STATUS current
            DESCRIPTION
                "Branch 10 L2 output active electric energy. Unit: KWh. Multi: 100."
            ::= { hwPDU8000TransMode3_4Entry 30 }

        hwPDU8000TransMod3Branch10L3outputactiveelectricenergy OBJECT-TYPE
            SYNTAX Integer32 (0..21474836)
            MAX-ACCESS read-only
            STATUS current
            DESCRIPTION
                "Branch 10 L3 output active electric energy. Unit: KWh. Multi: 100."
            ::= { hwPDU8000TransMode3_4Entry 31 }

        hwPDU8000TransMod3Branch11L1outputactiveelectricenergy OBJECT-TYPE
            SYNTAX Integer32 (0..21474836)
            MAX-ACCESS read-only
            STATUS current
            DESCRIPTION
                "Branch 11 L1 output active electric energy. Unit: KWh. Multi: 100."
            ::= { hwPDU8000TransMode3_4Entry 32 }

        hwPDU8000TransMod3Branch11L2outputactiveelectricenergy OBJECT-TYPE
            SYNTAX Integer32 (0..21474836)
            MAX-ACCESS read-only
            STATUS current
            DESCRIPTION
                "Branch 11 L2 output active electric energy. Unit: KWh. Multi: 100."
            ::= { hwPDU8000TransMode3_4Entry 33 }

        hwPDU8000TransMod3Branch11L3outputactiveelectricenergy OBJECT-TYPE
            SYNTAX Integer32 (0..21474836)
            MAX-ACCESS read-only
            STATUS current
            DESCRIPTION
                "Branch 11 L3 output active electric energy. Unit: KWh. Multi: 100."
            ::= { hwPDU8000TransMode3_4Entry 34 }

        hwPDU8000TransMod3Branch12L1outputactiveelectricenergy OBJECT-TYPE
            SYNTAX Integer32 (0..21474836)
            MAX-ACCESS read-only
            STATUS current
            DESCRIPTION
                "Branch 12 L1 output active electric energy. Unit: KWh. Multi: 100."
            ::= { hwPDU8000TransMode3_4Entry 35 }

        hwPDU8000TransMod3Branch12L2outputactiveelectricenergy OBJECT-TYPE
            SYNTAX Integer32 (0..21474836)
            MAX-ACCESS read-only
            STATUS current
            DESCRIPTION
                "Branch 12 L2 output active electric energy. Unit: KWh. Multi: 100."
            ::= { hwPDU8000TransMode3_4Entry 36 }

        hwPDU8000TransMod3Branch12L3outputactiveelectricenergy OBJECT-TYPE
            SYNTAX Integer32 (0..21474836)
            MAX-ACCESS read-only
            STATUS current
            DESCRIPTION
                "Branch 12 L3 output active electric energy. Unit: KWh. Multi: 100."
            ::= { hwPDU8000TransMode3_4Entry 37 }

        hwPDU8000TransMod4Branch1L1outputactiveelectricenergy OBJECT-TYPE
            SYNTAX Integer32 (0..21474836)
            MAX-ACCESS read-only
            STATUS current
            DESCRIPTION
                "Branch 1 L1 output active electric energy. Unit: KWh. Multi: 100."
            ::= { hwPDU8000TransMode3_4Entry 38 }

        hwPDU8000TransMod4Branch1L2outputactiveelectricenergy OBJECT-TYPE
            SYNTAX Integer32 (0..21474836)
            MAX-ACCESS read-only
            STATUS current
            DESCRIPTION
                "Branch 1 L2 output active electric energy. Unit: KWh. Multi: 100."
            ::= { hwPDU8000TransMode3_4Entry 39 }

        hwPDU8000TransMod4Branch1L3outputactiveelectricenergy OBJECT-TYPE
            SYNTAX Integer32 (0..21474836)
            MAX-ACCESS read-only
            STATUS current
            DESCRIPTION
                "Branch 1 L3 output active electric energy. Unit: KWh. Multi: 100."
            ::= { hwPDU8000TransMode3_4Entry 40 }

        hwPDU8000TransMod4Branch2L1outputactiveelectricenergy OBJECT-TYPE
            SYNTAX Integer32 (0..21474836)
            MAX-ACCESS read-only
            STATUS current
            DESCRIPTION
                "Branch 2 L1 output active electric energy. Unit: KWh. Multi: 100."
            ::= { hwPDU8000TransMode3_4Entry 41 }

        hwPDU8000TransMod4Branch2L2outputactiveelectricenergy OBJECT-TYPE
            SYNTAX Integer32 (0..21474836)
            MAX-ACCESS read-only
            STATUS current
            DESCRIPTION
                "Branch 2 L2 output active electric energy. Unit: KWh. Multi: 100."
            ::= { hwPDU8000TransMode3_4Entry 42 }

        hwPDU8000TransMod4Branch2L3outputactiveelectricenergy OBJECT-TYPE
            SYNTAX Integer32 (0..21474836)
            MAX-ACCESS read-only
            STATUS current
            DESCRIPTION
                "Branch 2 L3 output active electric energy. Unit: KWh. Multi: 100."
            ::= { hwPDU8000TransMode3_4Entry 43 }

        hwPDU8000TransMod4Branch3L1outputactiveelectricenergy OBJECT-TYPE
            SYNTAX Integer32 (0..21474836)
            MAX-ACCESS read-only
            STATUS current
            DESCRIPTION
                "Branch 3 L1 output active electric energy. Unit: KWh. Multi: 100."
            ::= { hwPDU8000TransMode3_4Entry 44 }

        hwPDU8000TransMod4Branch3L2outputactiveelectricenergy OBJECT-TYPE
            SYNTAX Integer32 (0..21474836)
            MAX-ACCESS read-only
            STATUS current
            DESCRIPTION
                "Branch 3 L2 output active electric energy. Unit: KWh. Multi: 100."
            ::= { hwPDU8000TransMode3_4Entry 45 }

        hwPDU8000TransMod4Branch3L3outputactiveelectricenergy OBJECT-TYPE
            SYNTAX Integer32 (0..21474836)
            MAX-ACCESS read-only
            STATUS current
            DESCRIPTION
                "Branch 3 L3 output active electric energy. Unit: KWh. Multi: 100."
            ::= { hwPDU8000TransMode3_4Entry 46 }

        hwPDU8000TransMod4Branch4L1outputactiveelectricenergy OBJECT-TYPE
            SYNTAX Integer32 (0..21474836)
            MAX-ACCESS read-only
            STATUS current
            DESCRIPTION
                "Branch 4 L1 output active electric energy. Unit: KWh. Multi: 100."
            ::= { hwPDU8000TransMode3_4Entry 47 }

        hwPDU8000TransMod4Branch4L2outputactiveelectricenergy OBJECT-TYPE
            SYNTAX Integer32 (0..21474836)
            MAX-ACCESS read-only
            STATUS current
            DESCRIPTION
                "Branch 4 L2 output active electric energy. Unit: KWh. Multi: 100."
            ::= { hwPDU8000TransMode3_4Entry 48 }

        hwPDU8000TransMod4Branch4L3outputactiveelectricenergy OBJECT-TYPE
            SYNTAX Integer32 (0..21474836)
            MAX-ACCESS read-only
            STATUS current
            DESCRIPTION
                "Branch 4 L3 output active electric energy. Unit: KWh. Multi: 100."
            ::= { hwPDU8000TransMode3_4Entry 49 }

        hwPDU8000TransMod4Branch5L1outputactiveelectricenergy OBJECT-TYPE
            SYNTAX Integer32 (0..21474836)
            MAX-ACCESS read-only
            STATUS current
            DESCRIPTION
                "Branch 5 L1 output active electric energy. Unit: KWh. Multi: 100."
            ::= { hwPDU8000TransMode3_4Entry 50 }

        hwPDU8000TransMod4Branch5L2outputactiveelectricenergy OBJECT-TYPE
            SYNTAX Integer32 (0..21474836)
            MAX-ACCESS read-only
            STATUS current
            DESCRIPTION
                "Branch 5 L2 output active electric energy. Unit: KWh. Multi: 100."
            ::= { hwPDU8000TransMode3_4Entry 51 }

        hwPDU8000TransMod4Branch5L3outputactiveelectricenergy OBJECT-TYPE
            SYNTAX Integer32 (0..21474836)
            MAX-ACCESS read-only
            STATUS current
            DESCRIPTION
                "Branch 5 L3 output active electric energy. Unit: KWh. Multi: 100."
            ::= { hwPDU8000TransMode3_4Entry 52 }

        hwPDU8000TransMod4Branch6L1outputactiveelectricenergy OBJECT-TYPE
            SYNTAX Integer32 (0..21474836)
            MAX-ACCESS read-only
            STATUS current
            DESCRIPTION
                "Branch 6 L1 output active electric energy. Unit: KWh. Multi: 100."
            ::= { hwPDU8000TransMode3_4Entry 53 }

        hwPDU8000TransMod4Branch6L2outputactiveelectricenergy OBJECT-TYPE
            SYNTAX Integer32 (0..21474836)
            MAX-ACCESS read-only
            STATUS current
            DESCRIPTION
                "Branch 6 L2 output active electric energy. Unit: KWh. Multi: 100."
            ::= { hwPDU8000TransMode3_4Entry 54 }

        hwPDU8000TransMod4Branch6L3outputactiveelectricenergy OBJECT-TYPE
            SYNTAX Integer32 (0..21474836)
            MAX-ACCESS read-only
            STATUS current
            DESCRIPTION
                "Branch 6 L3 output active electric energy. Unit: KWh. Multi: 100."
            ::= { hwPDU8000TransMode3_4Entry 55 }

        hwPDU8000TransMod4Branch7L1outputactiveelectricenergy OBJECT-TYPE
            SYNTAX Integer32 (0..21474836)
            MAX-ACCESS read-only
            STATUS current
            DESCRIPTION
                "Branch 7 L1 output active electric energy. Unit: KWh. Multi: 100."
            ::= { hwPDU8000TransMode3_4Entry 56 }

        hwPDU8000TransMod4Branch7L2outputactiveelectricenergy OBJECT-TYPE
            SYNTAX Integer32 (0..21474836)
            MAX-ACCESS read-only
            STATUS current
            DESCRIPTION
                "Branch 7 L2 output active electric energy. Unit: KWh. Multi: 100."
            ::= { hwPDU8000TransMode3_4Entry 57 }

        hwPDU8000TransMod4Branch7L3outputactiveelectricenergy OBJECT-TYPE
            SYNTAX Integer32 (0..21474836)
            MAX-ACCESS read-only
            STATUS current
            DESCRIPTION
                "Branch 7 L3 output active electric energy. Unit: KWh. Multi: 100."
            ::= { hwPDU8000TransMode3_4Entry 58 }

        hwPDU8000TransMod4Branch8L1outputactiveelectricenergy OBJECT-TYPE
            SYNTAX Integer32 (0..21474836)
            MAX-ACCESS read-only
            STATUS current
            DESCRIPTION
                "Branch 8 L1 output active electric energy. Unit: KWh. Multi: 100."
            ::= { hwPDU8000TransMode3_4Entry 59 }

        hwPDU8000TransMod4Branch8L2outputactiveelectricenergy OBJECT-TYPE
            SYNTAX Integer32 (0..21474836)
            MAX-ACCESS read-only
            STATUS current
            DESCRIPTION
                "Branch 8 L2 output active electric energy. Unit: KWh. Multi: 100."
            ::= { hwPDU8000TransMode3_4Entry 60 }

        hwPDU8000TransMod4Branch8L3outputactiveelectricenergy OBJECT-TYPE
            SYNTAX Integer32 (0..21474836)
            MAX-ACCESS read-only
            STATUS current
            DESCRIPTION
                "Branch 8 L3 output active electric energy. Unit: KWh. Multi: 100."
            ::= { hwPDU8000TransMode3_4Entry 61 }

        hwPDU8000TransMod4Branch9L1outputactiveelectricenergy OBJECT-TYPE
            SYNTAX Integer32 (0..21474836)
            MAX-ACCESS read-only
            STATUS current
            DESCRIPTION
                "Branch 9 L1 output active electric energy. Unit: KWh. Multi: 100."
            ::= { hwPDU8000TransMode3_4Entry 62 }

        hwPDU8000TransMod4Branch9L2outputactiveelectricenergy OBJECT-TYPE
            SYNTAX Integer32 (0..21474836)
            MAX-ACCESS read-only
            STATUS current
            DESCRIPTION
                "Branch 9 L2 output active electric energy. Unit: KWh. Multi: 100."
            ::= { hwPDU8000TransMode3_4Entry 63 }

        hwPDU8000TransMod4Branch9L3outputactiveelectricenergy OBJECT-TYPE
            SYNTAX Integer32 (0..21474836)
            MAX-ACCESS read-only
            STATUS current
            DESCRIPTION
                "Branch 9 L3 output active electric energy. Unit: KWh. Multi: 100."
            ::= { hwPDU8000TransMode3_4Entry 64 }

        hwPDU8000TransMod4Branch10L1outputactiveelectricenergy OBJECT-TYPE
            SYNTAX Integer32 (0..21474836)
            MAX-ACCESS read-only
            STATUS current
            DESCRIPTION
                "Branch 10 L1 output active electric energy. Unit: KWh. Multi: 100."
            ::= { hwPDU8000TransMode3_4Entry 65 }

        hwPDU8000TransMod4Branch10L2outputactiveelectricenergy OBJECT-TYPE
            SYNTAX Integer32 (0..21474836)
            MAX-ACCESS read-only
            STATUS current
            DESCRIPTION
                "Branch 10 L2 output active electric energy. Unit: KWh. Multi: 100."
            ::= { hwPDU8000TransMode3_4Entry 66 }

        hwPDU8000TransMod4Branch10L3outputactiveelectricenergy OBJECT-TYPE
            SYNTAX Integer32 (0..21474836)
            MAX-ACCESS read-only
            STATUS current
            DESCRIPTION
                "Branch 10 L3 output active electric energy. Unit: KWh. Multi: 100."
            ::= { hwPDU8000TransMode3_4Entry 67 }

        hwPDU8000TransMod4Branch11L1outputactiveelectricenergy OBJECT-TYPE
            SYNTAX Integer32 (0..21474836)
            MAX-ACCESS read-only
            STATUS current
            DESCRIPTION
                "Branch 11 L1 output active electric energy. Unit: KWh. Multi: 100."
            ::= { hwPDU8000TransMode3_4Entry 68 }

        hwPDU8000TransMod4Branch11L2outputactiveelectricenergy OBJECT-TYPE
            SYNTAX Integer32 (0..21474836)
            MAX-ACCESS read-only
            STATUS current
            DESCRIPTION
                "Branch 11 L2 output active electric energy. Unit: KWh. Multi: 100."
            ::= { hwPDU8000TransMode3_4Entry 69 }

        hwPDU8000TransMod4Branch11L3outputactiveelectricenergy OBJECT-TYPE
            SYNTAX Integer32 (0..21474836)
            MAX-ACCESS read-only
            STATUS current
            DESCRIPTION
                "Branch 11 L3 output active electric energy. Unit: KWh. Multi: 100."
            ::= { hwPDU8000TransMode3_4Entry 70 }

        hwPDU8000TransMod4Branch12L1outputactiveelectricenergy OBJECT-TYPE
            SYNTAX Integer32 (0..21474836)
            MAX-ACCESS read-only
            STATUS current
            DESCRIPTION
                "Branch 12 L1 output active electric energy. Unit: KWh. Multi: 100."
            ::= { hwPDU8000TransMode3_4Entry 71 }

        hwPDU8000TransMod4Branch12L2outputactiveelectricenergy OBJECT-TYPE
            SYNTAX Integer32 (0..21474836)
            MAX-ACCESS read-only
            STATUS current
            DESCRIPTION
                "Branch 12 L2 output active electric energy. Unit: KWh. Multi: 100."
            ::= { hwPDU8000TransMode3_4Entry 72 }

        hwPDU8000TransMod4Branch12L3outputactiveelectricenergy OBJECT-TYPE
            SYNTAX Integer32 (0..21474836)
            MAX-ACCESS read-only
            STATUS current
            DESCRIPTION
                "Branch 12 L3 output active electric energy. Unit: KWh. Multi: 100."
            ::= { hwPDU8000TransMode3_4Entry 73 }

        hwPDU8000TransMode3_2RowStatus OBJECT-TYPE
            SYNTAX RowStatus
            MAX-ACCESS read-create
            STATUS current
            DESCRIPTION
                "The row status of Deviece."
            ::= { hwPDU8000TransMode3_4Entry 100 }

        hwIDCACC OBJECT IDENTIFIER ::= { hwIDCMonitorMIBObjects 10 }

        hwNetCol OBJECT IDENTIFIER ::= { hwIDCACC 1 }

        hwNetColTable OBJECT-TYPE
            SYNTAX SEQUENCE OF HwNetColEntry
            MAX-ACCESS not-accessible
             STATUS current
             DESCRIPTION
                "The table of NetCol."
            ::= { hwNetCol 1 }

        hwNetColEntry OBJECT-TYPE
                        SYNTAX HwNetColEntry
            MAX-ACCESS not-accessible
             STATUS current
             DESCRIPTION
                "The table of NetCol."
            INDEX { hwNetColIndex }
            ::= { hwNetColTable 1 }

        HwNetColEntry            ::= SEQUENCE {
                hwNetColIndex
                    Unsigned32,
                hwNetColName
                    OCTET STRING,
                hwNetColCommStatus
                    INTEGER,
                hwNetColSlot
                    Unsigned32,
                hwNetColPort
                    Unsigned32,
                hwNetColModbusAddr
                    Unsigned32,
                hwNetColNetColModel
                    INTEGER,
                hwNetColNetColPower
                    INTEGER,
                hwNetColUnitonoffstatus
                    INTEGER,
                hwNetColOnoffstatusonremote
                    INTEGER,
                hwNetColCooloutp
                    Unsigned32,
                hwNetColFanoutp
                    Unsigned32,
                hwNetColHumidoutp
                    Unsigned32,
                hwNetColHeatoutp
                    Unsigned32,
                hwNetColTeamworkstatus
                    INTEGER,
                hwNetColTHcontroltype
                    INTEGER,
                hwNetColCurrenttemp
                    Integer32,
                hwNetColCurrenthumid
                    Integer32,
                hwNetColSupplyairavgtemp
                    Integer32,
                hwNetColReturnairavgtemp
                    Integer32,
                hwNetColColdaisleavgtemp
                    Integer32,
                hwNetColHotaisleavgtemp
                    Integer32,
                hwNetColSupplyairavghumid
                    Integer32,
                hwNetColReturnairavghumid
                    Integer32,
                hwNetColColdaisleavghumid
                    Integer32,
                hwNetColHot-aisleavghumid
                    Integer32,
                hwNetColSupplyair1temp
                    Integer32,
                hwNetColSupplyair2temp
                    Integer32,
                hwNetColSupplyair3temp
                    Integer32,
                hwNetColReturnair1temp
                    Integer32,
                hwNetColReturnair2temp
                    Integer32,
                hwNetColReturnair3temp
                    Integer32,
                hwNetColReturnair2humid
                    Integer32,
                hwNetColReturnair3humid
                    Integer32,
                hwNetColColdaisle1temp
                    Integer32,
                hwNetColColdaisle2temp
                    Integer32,
                hwNetColColdaisle3temp
                    Integer32,
                hwNetColColdaisle1humid
                    Integer32,
                hwNetColColdaisle2humid
                    Integer32,
                hwNetColColdaisle3humid
                    Integer32,
                hwNetColHotaisle1temp
                    Integer32,
                hwNetColHotaisle2temp
                    Integer32,
                hwNetColHotaisle3temp
                    Integer32,
                hwNetColHotaisle1humid
                    Integer32,
                hwNetColHotaisle2humid
                    Integer32,
                hwNetColHot-aisle3humid
                    Integer32,
                hwNetColComprunstatus
                    Unsigned32,
                hwNetColCompctrlstatus
                    INTEGER,
                hwNetColLiquidsolenoidvalve
                    INTEGER,
                hwNetColIndoorfanctrlstatus
                    INTEGER,
                hwNetColIndoorfan1ctrlstatus
                    Unsigned32,
                hwNetColIndoorfan2ctrlstatus
                    Unsigned32,
                hwNetColIndoorfan1runstatus
                    Unsigned32,
                hwNetColIndoorfan2runstatus
                    Unsigned32,
                hwNetColIndoorfan3runstatus
                    Unsigned32,
                hwNetColIndoorfan4runstatus
                    Unsigned32,
                hwNetColIndoorfan5runstatus
                    Unsigned32,
                hwNetColIndoorfan6runstatus
                    Unsigned32,
                hwNetColIndoorfan7runstatus
                    Unsigned32,
                hwNetColIndoorfan8runstatus
                    Unsigned32,
                hwNetColOutdoorfanctrlstatus
                    INTEGER,
                hwNetColHumidifierctrlstatus
                    Unsigned32,
                hwNetColElecheaterctrlstatus
                    INTEGER,
                hwNetColCondpump1ctrlstatus
                    INTEGER,
                hwNetColCondpump2ctrlstatus
                    INTEGER,
                hwNetColCondpumpctrlstatus
                    INTEGER,
                hwNetColReturnairtemp
                    Integer32,
                hwNetColReturnairhumid
                    Integer32,
                hwNetColHumidifierswitchctrlstatus
                    INTEGER,
                hwNetCol8000A50KIndoorfanctrlstatus
                    INTEGER,
                hwNetColDryOnoffstatusonremote
                    INTEGER,
                hwNetColRowStatus
                    RowStatus
            }

        hwNetColIndex OBJECT-TYPE
            SYNTAX Unsigned32
            MAX-ACCESS read-only
            STATUS current
            DESCRIPTION
                "The Index of NetCol."
            ::= { hwNetColEntry 1 }

        hwNetColName OBJECT-TYPE
            SYNTAX OCTET STRING (SIZE (0..50))
            MAX-ACCESS read-only
            STATUS current
            DESCRIPTION
                "The Name of NetCol."
            ::= { hwNetColEntry 2 }

        hwNetColCommStatus OBJECT-TYPE
            SYNTAX INTEGER
                {
                ok(1),
                fail(2),
                unknown(255)
                }
            MAX-ACCESS read-only
            STATUS current
            DESCRIPTION
                "Communication Status
                    Value 1 indicates noraml.
                    Value 2 indicates fail."
            ::= { hwNetColEntry 3 }

        hwNetColSlot OBJECT-TYPE
            SYNTAX Unsigned32 (0..6)
            MAX-ACCESS read-only
            STATUS current
            DESCRIPTION
                "The Slot of Device."
            ::= { hwNetColEntry 4 }

        hwNetColPort OBJECT-TYPE
            SYNTAX Unsigned32 (1..5)
            MAX-ACCESS read-only
            STATUS current
            DESCRIPTION
                "The Port No. of Device."
            ::= { hwNetColEntry 5 }

        hwNetColModbusAddr OBJECT-TYPE
            SYNTAX Unsigned32 (1.247)
            MAX-ACCESS read-only
            STATUS current
            DESCRIPTION
                "The modbus Address of the device."
            ::= { hwNetColEntry 6 }

        hwNetColNetColModel OBJECT-TYPE
            SYNTAX INTEGER
                {
                netcol5000A(1),
                netcol5000C(2),
                netcol8000A(3),
                unknown(255)
                }
            MAX-ACCESS read-only
            STATUS current
            DESCRIPTION
                "NetCol Model.
                    Value 1 indicates 5000A.
                    Value 2 indicates 5000C.
                    Value 3 indicates 8000A."
            ::= { hwNetColEntry 7 }

        hwNetColNetColPower OBJECT-TYPE
            SYNTAX INTEGER
                {
                p20kW(1),
                p25kW(2),
                p30kW(3),
                p35kW(4),
                p50kW(5),
                unknown(255)
                }
            MAX-ACCESS read-only
            STATUS current
            DESCRIPTION
                "NetCol Power.
                    Value 1 indicates 20kW.
                    Value 2 indicates 25kW.
                    Value 3 indicates 30kW.
                    Value 4 indicates 35kW.
                    Value 5 indicates 50kW."
            ::= { hwNetColEntry 8 }

        hwNetColUnitonoffstatus OBJECT-TYPE
            SYNTAX INTEGER
                {
                off(1),
                on(2),
                unknown(255)
                }
            MAX-ACCESS read-only
            STATUS current
            DESCRIPTION
                "Unit on/off status.
                    Value 1 indicates On.
                    Value 2 indicates Off."
            ::= { hwNetColEntry 9 }

        hwNetColOnoffstatusonremote OBJECT-TYPE
            SYNTAX INTEGER
                {
                off(1),
                on(2),
                unknown(255)
                }
            MAX-ACCESS read-only
            STATUS current
            DESCRIPTION
                "On/off status on remote.
                    Value 1 indicates On.
                    Value 2 indicates Off."
            ::= { hwNetColEntry 10 }

        hwNetColCooloutp OBJECT-TYPE
            SYNTAX Unsigned32 (0..100)
            MAX-ACCESS read-only
            STATUS current
            DESCRIPTION
                "Cool outp. Unit: %. Multi: 1."
            ::= { hwNetColEntry 11 }

        hwNetColFanoutp OBJECT-TYPE
            SYNTAX Unsigned32 (0..100)
            MAX-ACCESS read-only
            STATUS current
            DESCRIPTION
                "Fan outp. Unit: %. Multi: 1."
            ::= { hwNetColEntry 12 }

        hwNetColHumidoutp OBJECT-TYPE
            SYNTAX Unsigned32 (0..100)
            MAX-ACCESS read-only
            STATUS current
            DESCRIPTION
                "Humid outp. Unit: %. Multi: 1."
            ::= { hwNetColEntry 13 }

        hwNetColHeatoutp OBJECT-TYPE
            SYNTAX Unsigned32 (0..100)
            MAX-ACCESS read-only
            STATUS current
            DESCRIPTION
                "Heat outp. Unit: %. Multi: 1."
            ::= { hwNetColEntry 14 }

        hwNetColTeamworkstatus OBJECT-TYPE
            SYNTAX INTEGER
                {
                Invalid(1),
                Cool(2),
                Heat(3),
                Dehumid(4),
                Humid(5),
                Cool_humid(6),
                Heat_dehumid(7),
                Heat_humid(8),
                Cool_dehumid(9),
                unknown(255)
                }
            MAX-ACCESS read-only
            STATUS current
            DESCRIPTION
                "Teamwork status.
                    Value 1 indicates Invalid.
                    Value 2 indicates Cool.
                    Value 3 indicates Heat.
                    Value 4 indicates Dehumid.
                    Value 5 indicates Humid.
                    Value 6 indicates Cool & humid.
                    Value 7 indicates Heat & dehumid.
                    Value 8 indicates Heat & humid.
                    Value 9 indicates Cool & dehumid."
            ::= { hwNetColEntry 15 }

        hwNetColTHcontroltype OBJECT-TYPE
            SYNTAX INTEGER
                {
                Return-air(1),
                Supply-air(2),
                Cold-aisle(3),
                Hot-aisle(4),
                unknown(255)
                }
            MAX-ACCESS read-only
            STATUS current
            DESCRIPTION
                "T/H control type.
                    Value 1 indicates Return-air.
                    Value 2 indicates Supply-air.
                    Value 3 indicates Cold-aisle.
                    Value 4 indicates Hot-aisle."
            ::= { hwNetColEntry 16 }

        hwNetColCurrenttemp OBJECT-TYPE
            SYNTAX Integer32 (-50..150)
            MAX-ACCESS read-only
            STATUS current
            DESCRIPTION
                "Current temp. Unit: degC. Multi: 10."
            ::= { hwNetColEntry 17 }

        hwNetColCurrenthumid OBJECT-TYPE
            SYNTAX Integer32 (0..100)
            MAX-ACCESS read-only
            STATUS current
            DESCRIPTION
                "Current humid. Unit: %. Multi: 10."
            ::= { hwNetColEntry 18 }

        hwNetColSupplyairavgtemp OBJECT-TYPE
            SYNTAX Integer32 (-50..150)
            MAX-ACCESS read-only
            STATUS current
            DESCRIPTION
                "Supply-air avg temp. Unit: degC. Multi: 10."
            ::= { hwNetColEntry 19 }

        hwNetColReturnairavgtemp OBJECT-TYPE
            SYNTAX Integer32 (-50..150)
            MAX-ACCESS read-only
            STATUS current
            DESCRIPTION
                "Return-air avg temp. Unit: degC. Multi: 10."
            ::= { hwNetColEntry 20 }

        hwNetColColdaisleavgtemp OBJECT-TYPE
            SYNTAX Integer32 (-50..150)
            MAX-ACCESS read-only
            STATUS current
            DESCRIPTION
                "Cold-aisle avg temp. Unit: degC. Multi: 10."
            ::= { hwNetColEntry 21 }

        hwNetColHotaisleavgtemp OBJECT-TYPE
            SYNTAX Integer32 (-50..150)
            MAX-ACCESS read-only
            STATUS current
            DESCRIPTION
                "Hot-aisle avg temp. Unit: degC. Multi: 10."
            ::= { hwNetColEntry 22 }

        hwNetColSupplyairavghumid OBJECT-TYPE
            SYNTAX Integer32 (0..100)
            MAX-ACCESS read-only
            STATUS current
            DESCRIPTION
                "Supply-air avg humid. Unit: %. Multi: 10."
            ::= { hwNetColEntry 23 }

        hwNetColReturnairavghumid OBJECT-TYPE
            SYNTAX Integer32 (0..100)
            MAX-ACCESS read-only
            STATUS current
            DESCRIPTION
                "Return-air avg humid. Unit: %. Multi: 10."
            ::= { hwNetColEntry 24 }

        hwNetColColdaisleavghumid OBJECT-TYPE
            SYNTAX Integer32 (0..100)
            MAX-ACCESS read-only
            STATUS current
            DESCRIPTION
                "Cold-aisle avg humid. Unit: %. Multi: 10."
            ::= { hwNetColEntry 25 }

        hwNetColHot-aisleavghumid OBJECT-TYPE
            SYNTAX Integer32 (0..100)
            MAX-ACCESS read-only
            STATUS current
            DESCRIPTION
                "Hot-aisle avg humid. Unit: %. Multi: 10."
            ::= { hwNetColEntry 26 }

        hwNetColSupplyair1temp OBJECT-TYPE
            SYNTAX Integer32 (-50..150)
            MAX-ACCESS read-only
            STATUS current
            DESCRIPTION
                "Supply-air 1 temp. Unit: degC. Multi: 10."
            ::= { hwNetColEntry 27 }

        hwNetColSupplyair2temp OBJECT-TYPE
            SYNTAX Integer32 (-50..150)
            MAX-ACCESS read-only
            STATUS current
            DESCRIPTION
                "Supply-air 2 temp. Unit: degC. Multi: 10."
            ::= { hwNetColEntry 28 }

        hwNetColSupplyair3temp OBJECT-TYPE
            SYNTAX Integer32 (-50..150)
            MAX-ACCESS read-only
            STATUS current
            DESCRIPTION
                "Supply-air 3 temp. Unit: degC. Multi: 10."
            ::= { hwNetColEntry 29 }

        hwNetColReturnair1temp OBJECT-TYPE
            SYNTAX Integer32 (-50..150)
            MAX-ACCESS read-only
            STATUS current
            DESCRIPTION
                "Return-air 1 temp. Unit: degC. Multi: 10."
            ::= { hwNetColEntry 30 }

        hwNetColReturnair2temp OBJECT-TYPE
            SYNTAX Integer32 (-50..150)
            MAX-ACCESS read-only
            STATUS current
            DESCRIPTION
                "Return-air 2 temp. Unit: degC. Multi: 10."
            ::= { hwNetColEntry 31 }

        hwNetColReturnair3temp OBJECT-TYPE
            SYNTAX Integer32 (-50..150)
            MAX-ACCESS read-only
            STATUS current
            DESCRIPTION
                "Return-air 3 temp. Unit: degC. Multi: 10."
            ::= { hwNetColEntry 32 }

        hwNetColReturnair2humid OBJECT-TYPE
            SYNTAX Integer32 (0..100)
            MAX-ACCESS read-only
            STATUS current
            DESCRIPTION
                "Return-air 2 humid. Unit: %. Multi: 10."
            ::= { hwNetColEntry 33 }

        hwNetColReturnair3humid OBJECT-TYPE
            SYNTAX Integer32 (0..100)
            MAX-ACCESS read-only
            STATUS current
            DESCRIPTION
                "Return-air 3 humid. Unit: %. Multi: 10."
            ::= { hwNetColEntry 34 }

        hwNetColColdaisle1temp OBJECT-TYPE
            SYNTAX Integer32 (-50..150)
            MAX-ACCESS read-only
            STATUS current
            DESCRIPTION
                "Cold-aisle 1 temp. Unit: degC. Multi: 10."
            ::= { hwNetColEntry 35 }

        hwNetColColdaisle2temp OBJECT-TYPE
            SYNTAX Integer32 (-50..150)
            MAX-ACCESS read-only
            STATUS current
            DESCRIPTION
                "Cold-aisle 2 temp. Unit: degC. Multi: 10."
            ::= { hwNetColEntry 36 }

        hwNetColColdaisle3temp OBJECT-TYPE
            SYNTAX Integer32 (-50..150)
            MAX-ACCESS read-only
            STATUS current
            DESCRIPTION
                "Cold-aisle 3 temp. Unit: degC. Multi: 10."
            ::= { hwNetColEntry 37 }

        hwNetColColdaisle1humid OBJECT-TYPE
            SYNTAX Integer32 (0..100)
            MAX-ACCESS read-only
            STATUS current
            DESCRIPTION
                "Cold-aisle 1 humid. Unit: %. Multi: 10."
            ::= { hwNetColEntry 38 }

        hwNetColColdaisle2humid OBJECT-TYPE
            SYNTAX Integer32 (0..100)
            MAX-ACCESS read-only
            STATUS current
            DESCRIPTION
                "Cold-aisle 2 humid. Unit: %. Multi: 10."
            ::= { hwNetColEntry 39 }

        hwNetColColdaisle3humid OBJECT-TYPE
            SYNTAX Integer32 (0..100)
            MAX-ACCESS read-only
            STATUS current
            DESCRIPTION
                "Cold-aisle 3 humid. Unit: %. Multi: 10."
            ::= { hwNetColEntry 40 }

        hwNetColHotaisle1temp OBJECT-TYPE
            SYNTAX Integer32 (-50..150)
            MAX-ACCESS read-only
            STATUS current
            DESCRIPTION
                "Hot-aisle 1 temp. Unit: degC. Multi: 10."
            ::= { hwNetColEntry 41 }

        hwNetColHotaisle2temp OBJECT-TYPE
            SYNTAX Integer32 (-50..150)
            MAX-ACCESS read-only
            STATUS current
            DESCRIPTION
                "Hot-aisle 2 temp. Unit: degC. Multi: 10."
            ::= { hwNetColEntry 42 }

        hwNetColHotaisle3temp OBJECT-TYPE
            SYNTAX Integer32 (-50..150)
            MAX-ACCESS read-only
            STATUS current
            DESCRIPTION
                "Hot-aisle 3 temp. Unit: degC. Multi: 10."
            ::= { hwNetColEntry 43 }

        hwNetColHotaisle1humid OBJECT-TYPE
            SYNTAX Integer32 (0..100)
            MAX-ACCESS read-only
            STATUS current
            DESCRIPTION
                "Hot-aisle 1 humid. Unit: %. Multi: 10."
            ::= { hwNetColEntry 44 }

        hwNetColHotaisle2humid OBJECT-TYPE
            SYNTAX Integer32 (0..100)
            MAX-ACCESS read-only
            STATUS current
            DESCRIPTION
                "Hot-aisle 2 humid. Unit: %. Multi: 10."
            ::= { hwNetColEntry 45 }

        hwNetColHot-aisle3humid OBJECT-TYPE
            SYNTAX Integer32 (0..100)
            MAX-ACCESS read-only
            STATUS current
            DESCRIPTION
                "Hot-aisle 3 humid. Unit: %. Multi: 10."
            ::= { hwNetColEntry 46 }

        hwNetColComprunstatus OBJECT-TYPE
            SYNTAX Unsigned32 (0..10000)
            MAX-ACCESS read-only
            STATUS current
            DESCRIPTION
                "Comp run status. Unit: RPM. Multi: 1."
            ::= { hwNetColEntry 47 }

        hwNetColCompctrlstatus OBJECT-TYPE
            SYNTAX INTEGER
                {
                Off(1),
                On(2),
                unknown(255)
                }
            MAX-ACCESS read-only
            STATUS current
            DESCRIPTION
                "Comp ctrl status.
                    Value 1 indicates Off.
                    Value 2 indicates On."
            ::= { hwNetColEntry 48 }

        hwNetColLiquidsolenoidvalve OBJECT-TYPE
            SYNTAX INTEGER
                {
                Off(1),
                On(2),
                unknown(255)
                }
            MAX-ACCESS read-only
            STATUS current
            DESCRIPTION
                "Liquid solenoid valve.
                    Value 1 indicates Off.
                    Value 2 indicates On."
            ::= { hwNetColEntry 49 }

        hwNetColIndoorfanctrlstatus OBJECT-TYPE
            SYNTAX INTEGER
                {
                Off(1),
                On(2),
                unknown(255)
                }
            MAX-ACCESS read-only
            STATUS current
            DESCRIPTION
                "Indoor fan ctrl status.
                    Value 1 indicates Off.
                    Value 2 indicates On."
            ::= { hwNetColEntry 50 }

        hwNetColIndoorfan1ctrlstatus OBJECT-TYPE
            SYNTAX Unsigned32 (0..100)
            MAX-ACCESS read-only
            STATUS current
            DESCRIPTION
                "Indoor fan 1 ctrl status. Unit: %. Multi: 1."
            ::= { hwNetColEntry 51 }

        hwNetColIndoorfan2ctrlstatus OBJECT-TYPE
            SYNTAX Unsigned32 (0..100)
            MAX-ACCESS read-only
            STATUS current
            DESCRIPTION
                "Indoor fan 2 ctrl status. Unit: %. Multi: 1."
            ::= { hwNetColEntry 52 }

        hwNetColIndoorfan1runstatus OBJECT-TYPE
            SYNTAX Unsigned32 (0..10000)
            MAX-ACCESS read-only
            STATUS current
            DESCRIPTION
                "Indoor fan 1 run status. Unit: RPM. Multi: 1."
            ::= { hwNetColEntry 53 }

        hwNetColIndoorfan2runstatus OBJECT-TYPE
            SYNTAX Unsigned32 (0..10000)
            MAX-ACCESS read-only
            STATUS current
            DESCRIPTION
                "Indoor fan 2 run status. Unit: RPM. Multi: 1."
            ::= { hwNetColEntry 54 }

        hwNetColIndoorfan3runstatus OBJECT-TYPE
            SYNTAX Unsigned32 (0..10000)
            MAX-ACCESS read-only
            STATUS current
            DESCRIPTION
                "Indoor fan 3 run status. Unit: RPM. Multi: 1."
            ::= { hwNetColEntry 55 }

        hwNetColIndoorfan4runstatus OBJECT-TYPE
            SYNTAX Unsigned32 (0..10000)
            MAX-ACCESS read-only
            STATUS current
            DESCRIPTION
                "Indoor fan 4 run status. Unit: RPM. Multi: 1."
            ::= { hwNetColEntry 56 }

        hwNetColIndoorfan5runstatus OBJECT-TYPE
            SYNTAX Unsigned32 (0..10000)
            MAX-ACCESS read-only
            STATUS current
            DESCRIPTION
                "Indoor fan 5 run status. Unit: RPM. Multi: 1."
            ::= { hwNetColEntry 57 }

        hwNetColIndoorfan6runstatus OBJECT-TYPE
            SYNTAX Unsigned32 (0..10000)
            MAX-ACCESS read-only
            STATUS current
            DESCRIPTION
                "Indoor fan 6 run status. Unit: RPM. Multi: 1."
            ::= { hwNetColEntry 58 }

        hwNetColIndoorfan7runstatus OBJECT-TYPE
            SYNTAX Unsigned32 (0..10000)
            MAX-ACCESS read-only
            STATUS current
            DESCRIPTION
                "Indoor fan 7 run status. Unit: RPM. Multi: 1."
            ::= { hwNetColEntry 59 }

        hwNetColIndoorfan8runstatus OBJECT-TYPE
            SYNTAX Unsigned32 (0..10000)
            MAX-ACCESS read-only
            STATUS current
            DESCRIPTION
                "Indoor fan 8 run status. Unit: RPM. Multi: 1."
            ::= { hwNetColEntry 60 }

        hwNetColOutdoorfanctrlstatus OBJECT-TYPE
            SYNTAX INTEGER
                {
                Off(1),
                On(2),
                unknown(255)
                }
            MAX-ACCESS read-only
            STATUS current
            DESCRIPTION
                "Outdoor fan ctrl status.
                    Value 1 indicates Off.
                    Value 2 indicates On."
            ::= { hwNetColEntry 61 }

        hwNetColHumidifierctrlstatus OBJECT-TYPE
            SYNTAX Unsigned32 (0..100)
            MAX-ACCESS read-only
            STATUS current
            DESCRIPTION
                "Humidifier ctrl status. Unit: %. Multi: 1."
            ::= { hwNetColEntry 62 }

        hwNetColElecheaterctrlstatus OBJECT-TYPE
            SYNTAX INTEGER
                {
                Off(1),
                On(2),
                unknown(255)
                }
            MAX-ACCESS read-only
            STATUS current
            DESCRIPTION
                "Elec heater ctrl status.
                    Value 1 indicates Off.
                    Value 2 indicates On."
            ::= { hwNetColEntry 63 }

        hwNetColCondpump1ctrlstatus OBJECT-TYPE
            SYNTAX INTEGER
                {
                Off(1),
                On(2),
                unknown(255)
                }
            MAX-ACCESS read-only
            STATUS current
            DESCRIPTION
                "Cond pump 1 ctrl status.
                    Value 1 indicates Off.
                    Value 2 indicates On."
            ::= { hwNetColEntry 64 }

        hwNetColCondpump2ctrlstatus OBJECT-TYPE
            SYNTAX INTEGER
                {
                Off(1),
                On(2),
                unknown(255)
                }
            MAX-ACCESS read-only
            STATUS current
            DESCRIPTION
                "Cond pump 2 ctrl status.
                    Value 1 indicates Off.
                    Value 2 indicates On."
            ::= { hwNetColEntry 65 }

        hwNetColCondpumpctrlstatus OBJECT-TYPE
            SYNTAX INTEGER
                {
                Off(1),
                On(2),
                unknown(255)
                }
            MAX-ACCESS read-only
            STATUS current
            DESCRIPTION
                "Cond pump ctrl status.
                    Value 1 indicates Off.
                    Value 2 indicates On."
            ::= { hwNetColEntry 66 }

        hwNetColReturnairtemp OBJECT-TYPE
            SYNTAX Integer32 (-50..150)
            MAX-ACCESS read-only
            STATUS current
            DESCRIPTION
                "8000A 50Kw Return-air temp. Unit: degC. Multi: 10."
            ::= { hwNetColEntry 67 }

        hwNetColReturnairhumid OBJECT-TYPE
            SYNTAX Integer32 (0..100)
            MAX-ACCESS read-only
            STATUS current
            DESCRIPTION
                "8000A 50Kw Return-air humid. Unit: %. Multi: 10."
            ::= { hwNetColEntry 68 }

        hwNetColHumidifierswitchctrlstatus OBJECT-TYPE
            SYNTAX INTEGER
                {
                Off(1),
                On(2),
                unknown(255)
                }
            MAX-ACCESS read-only
            STATUS current
            DESCRIPTION
                "Humidifier switch ctrl status.
                    Value 1 indicates Off.
                    Value 2 indicates On."
            ::= { hwNetColEntry 69 }

        hwNetCol8000A50KIndoorfanctrlstatus OBJECT-TYPE
            SYNTAX INTEGER
                {
                Off(1),
                lowspeed(2),
                highspeed(3),
                unknown(255)
                }
            MAX-ACCESS read-only
            STATUS current
            DESCRIPTION
                "8000A 50Kw Indoor fan ctrl status.
                    Value 1 indicates Off.
                    Value 2 indicates Low speed.
                    Value 3 indicates High speed."
            ::= { hwNetColEntry 70 }

        hwNetColDryOnoffstatusonremote OBJECT-TYPE
            SYNTAX INTEGER
                {
                off(1),
                on(2),
                unknown(255)
                }
            MAX-ACCESS read-only
            STATUS current
            DESCRIPTION
                "On/off status on remote.
                    Value 1 indicates On.
                    Value 2 indicates Off."
            ::= { hwNetColEntry 71 }

        hwNetColRowStatus OBJECT-TYPE
            SYNTAX RowStatus
            MAX-ACCESS read-create
            STATUS current
            DESCRIPTION
                "The row status of Deviece."
            ::= { hwNetColEntry 100 }

        hwSystemInfo OBJECT IDENTIFIER ::= { hwIDCMonitorMIBObjects 11 }

        hwSystemPUE OBJECT-TYPE
            SYNTAX OCTET STRING (SIZE (1..20))
            MAX-ACCESS read-only
            STATUS current
            DESCRIPTION
                "The PUE of all system.Multi 10."
            ::= { hwSystemInfo 0 }

        hwPD510 OBJECT IDENTIFIER ::= { hwIDCMonitorMIBObjects 12 }

        hwPD510RunningTable OBJECT-TYPE
            SYNTAX SEQUENCE OF HwPD510RunningEntry
            MAX-ACCESS not-accessible
             STATUS current
             DESCRIPTION
                "The running table of Huawei PD510 Equipment."
            ::= { hwPD510 1 }

        hwPD510RunningEntry OBJECT-TYPE
                        SYNTAX HwPD510RunningEntry
            MAX-ACCESS not-accessible
             STATUS current
             DESCRIPTION
                "The running table of Huawei PD510 Equipment."
            INDEX { hwPD510RunningIndex }
            ::= { hwPD510RunningTable 1 }

        HwPD510RunningEntry            ::= SEQUENCE {
                hwPD510RunningIndex
                    Unsigned32,
                hwPD510Name
                    OCTET STRING,
                hwPD510CommStatus
                    INTEGER,
                hwPD510CommSlotNo
                    Unsigned32,
                hwPD510CommPortNo
                    Unsigned32,
                hwPD510ModbusAddress
                    Unsigned32,
                hwPD510VoltageWiringType
                    INTEGER,
                hwPD510CurrentWiringType
                    INTEGER,
                hwPD510LoadType
                    INTEGER,
                hwPD510UnblanceDegreeOfVoltage
                    Integer32,
                hwPD510UnblanceDegreeOfCurrent
                    Integer32,
                hwPD510DeviceRunningTime
                    Integer32,
                hwPD510Frequence
                    Integer32,
                hwPD510PhaseVoltageV1
                    Integer32,
                hwPD510PhaseVoltageV2
                    Integer32,
                hwPD510PhaseVoltageV3
                    Integer32,
                hwPD510AveragePhaseVoltage
                    Integer32,
                hwPD510LineVoltageV12
                    Integer32,
                hwPD510LineVoltageV23
                    Integer32,
                hwPD510LineVoltageV31
                    Integer32,
                hwPD510AverageLineVoltage
                    Integer32,
                hwPD510CurrentI1
                    Integer32,
                hwPD510CurrentI2
                    Integer32,
                hwPD510CurrentI3
                    Integer32,
                hwPD510AverageCurrent
                    Integer32,
                hwPD510NeutralLineCurrentIn
                    Integer32,
                hwPD510PhaseActivePowerP1
                    Integer32,
                hwPD510PhaseActivePowerP2
                    Integer32,
                hwPD510PhaseActivePowerP3
                    Integer32,
                hwPD510SystemActivePower
                    Integer32,
                hwPD510PhaseReactivePowerQ1
                    Integer32,
                hwPD510PhaseReactivePowerQ2
                    Integer32,
                hwPD510PhaseReactivePowerQ3
                    Integer32,
                hwPD510SystemReactivePower
                    Integer32,
                hwPD510PhaseApparentPowerS1
                    Integer32,
                hwPD510PhaseApparentPowerS2
                    Integer32,
                hwPD510PhaseApparentPowerS3
                    Integer32,
                hwPD510SystemApparentPower
                    Integer32,
                hwPD510PhasePowerFactorPF1
                    Integer32,
                hwPD510PhasePowerFactorPF2
                    Integer32,
                hwPD510PhasePowerFactorPF3
                    Integer32,
                hwPD510SystemPowerFactor
                    Integer32,
                hwPD510InputActiveEnergy
                    Integer32,
                hwPD510OutputActiveEnergy
                    Integer32,
                hwPD510InductiveReactiveEnergy
                    Integer32,
                hwPD510CapacitiveeactiveEnergy
                    Integer32,
                hwPD510TotalActiveEnergy
                    Integer32,
                hwPD510NetActiveEnergy
                    Integer32,
                hwPD510TotalReactiveEnergy
                    Integer32,
                hwPD510NetReactiveEnergy
                    Integer32,
                hwPD510ApparentEnergy
                    Integer32,
                hwPD510RowStatus
                    RowStatus
            }

        hwPD510RunningIndex OBJECT-TYPE
            SYNTAX Unsigned32
            MAX-ACCESS read-only
            STATUS current
            DESCRIPTION
                "Index of the device running table for the PD510."
            ::= { hwPD510RunningEntry 1 }

        hwPD510Name OBJECT-TYPE
            SYNTAX OCTET STRING (SIZE (0..50))
            MAX-ACCESS read-only
            STATUS current
            DESCRIPTION
                "Name of the device running table for the PD510."
            ::= { hwPD510RunningEntry 2 }

        hwPD510CommStatus OBJECT-TYPE
            SYNTAX INTEGER
                {
                ok(1),
                fail(2),
                unknown(255)
                }
            MAX-ACCESS read-only
            STATUS current
            DESCRIPTION
                "Communication Status
                    Value 1 indicates noraml.
                    Value 2 indicates fail."
            ::= { hwPD510RunningEntry 3 }

        hwPD510CommSlotNo OBJECT-TYPE
            SYNTAX Unsigned32 (0..6)
            MAX-ACCESS read-only
            STATUS current
            DESCRIPTION
                "the Slot No. of Device."
            ::= { hwPD510RunningEntry 4 }

        hwPD510CommPortNo OBJECT-TYPE
            SYNTAX Unsigned32 (1..5)
            MAX-ACCESS read-only
            STATUS current
            DESCRIPTION
                "the Port No. of Device."
            ::= { hwPD510RunningEntry 5 }

        hwPD510ModbusAddress OBJECT-TYPE
            SYNTAX Unsigned32 (1..247)
            MAX-ACCESS read-only
            STATUS current
            DESCRIPTION
                "ModbusAddress of the device running table for the PD510."
            ::= { hwPD510RunningEntry 6 }

        hwPD510VoltageWiringType OBJECT-TYPE
            SYNTAX INTEGER
                {
                threeLN(1),                                                                    twoLN(2),                                                                  twoLL(3),                                                      unknown(255)                     
                }
            MAX-ACCESS read-only
            STATUS current
            DESCRIPTION
                "VoltageWiringType of the device running table for the PD510.
                Value 1 indicates threeLN.
                Value 2 indicates twoLN.
                Value 3 indicates twoLL."
            ::= { hwPD510RunningEntry 7 }

        hwPD510CurrentWiringType OBJECT-TYPE
            SYNTAX INTEGER
                {
                threeCT(1),
                twoCT(2),                                                                   oneCT(3),                                          
                unknown(255)
                }
            MAX-ACCESS read-only
            STATUS current
            DESCRIPTION
                "CurrentWiringType  of the device running table for the PD510.
                Value 1 indicates threeCT.
                Value 2 indicates twoCT.
                Value 3 indicates oneCT."
            ::= { hwPD510RunningEntry 8 }

        hwPD510LoadType OBJECT-TYPE
            SYNTAX INTEGER
                {
                Resistive(1),
                Inductive(2),                                                                Capacitive(3),
                unknown(255)
                }
            MAX-ACCESS read-only
            STATUS current
            DESCRIPTION
                "Load Type of the device running table for the PD510.
                Value 1 indicates Resistive.
                Value 2 indicates Inductive.
                Value 3 indicates Capacitive."
            ::= { hwPD510RunningEntry 9 }

        hwPD510UnblanceDegreeOfVoltage OBJECT-TYPE
            SYNTAX Integer32 (0..100)
            MAX-ACCESS read-only
            STATUS current
            DESCRIPTION
                "UnblanceDegreeOfVoltage of the device running table for the PD510.Unit:%. Multiple 10."
            ::= { hwPD510RunningEntry 10 }

        hwPD510UnblanceDegreeOfCurrent OBJECT-TYPE
            SYNTAX Integer32 (0..100)
            MAX-ACCESS read-only
            STATUS current
            DESCRIPTION
                "UnblanceDegreeOfCurrent of the device running table for the PD510.Unit:%. Multiple 10."
            ::= { hwPD510RunningEntry 11 }

        hwPD510DeviceRunningTime OBJECT-TYPE
            SYNTAX Integer32 (0..9999999)
            MAX-ACCESS read-only
            STATUS current
            DESCRIPTION
                "DeviceRunningTime of the device running table for the PD510.Unit:%. Multiple 10."
            ::= { hwPD510RunningEntry 12 }

        hwPD510Frequence OBJECT-TYPE
            SYNTAX Integer32 (45..65)
            MAX-ACCESS read-only
            STATUS current
            DESCRIPTION
                "Frequence of the device running table for the PD510.Unit:Hz. Multiple 10."
            ::= { hwPD510RunningEntry 13 }

        hwPD510PhaseVoltageV1 OBJECT-TYPE
            SYNTAX Integer32 (0..65535)
            MAX-ACCESS read-only
            STATUS current
            DESCRIPTION
                "PhaseVoltage V1 of the device running table for the PD510.Unit:V . Multiple 10."
            ::= { hwPD510RunningEntry 14 }

        hwPD510PhaseVoltageV2 OBJECT-TYPE
            SYNTAX Integer32 (0..65535)
            MAX-ACCESS read-only
            STATUS current
            DESCRIPTION
                "PhaseVoltage V2 of the device running table for the PD510..Unit:V . Multiple 10."
            ::= { hwPD510RunningEntry 15 }

        hwPD510PhaseVoltageV3 OBJECT-TYPE
            SYNTAX Integer32 (0..65535)
            MAX-ACCESS read-only
            STATUS current
            DESCRIPTION
                "PhaseVoltage V3 of the device running table for the PD510..Unit:V . Multiple 10."
            ::= { hwPD510RunningEntry 16 }

        hwPD510AveragePhaseVoltage OBJECT-TYPE
            SYNTAX Integer32 (0..65535)
            MAX-ACCESS read-only
            STATUS current
            DESCRIPTION
                "AveragePhaseVoltage of the device running table for the PD510.Unit:V . Multiple 10."
            ::= { hwPD510RunningEntry 17 }

        hwPD510LineVoltageV12 OBJECT-TYPE
            SYNTAX Integer32 (0..65535)
            MAX-ACCESS read-only
            STATUS current
            DESCRIPTION
                "LineVoltageV12 of the device running table for the PD510.Unit:V . Multiple 10."
            ::= { hwPD510RunningEntry 18 }

        hwPD510LineVoltageV23 OBJECT-TYPE
            SYNTAX Integer32 (0..65535)
            MAX-ACCESS read-only
            STATUS current
            DESCRIPTION
                "LineVoltageV23 of the device running table for the PD510.Unit:V . Multiple 10."
            ::= { hwPD510RunningEntry 19 }

        hwPD510LineVoltageV31 OBJECT-TYPE
            SYNTAX Integer32 (0..65535)
            MAX-ACCESS read-only
            STATUS current
            DESCRIPTION
                "LineVoltage31 of the device running table for the PD510.Unit:V . Multiple 10."
            ::= { hwPD510RunningEntry 20 }

        hwPD510AverageLineVoltage OBJECT-TYPE
            SYNTAX Integer32 (0..65535)
            MAX-ACCESS read-only
            STATUS current
            DESCRIPTION
                "AverageLineVoltage of the device running table for the PD510.Unit:V . Multiple 10."
            ::= { hwPD510RunningEntry 21 }

        hwPD510CurrentI1 OBJECT-TYPE
            SYNTAX Integer32 (0..65535)
            MAX-ACCESS read-only
            STATUS current
            DESCRIPTION
                "CurrentI1 of the device running table for the PD510.Unit:A . Multiple 10."
            ::= { hwPD510RunningEntry 22 }

        hwPD510CurrentI2 OBJECT-TYPE
            SYNTAX Integer32 (0..65535)
            MAX-ACCESS read-only
            STATUS current
            DESCRIPTION
                "CurrentI2 of the device running table for the PD510.Unit:A . Multiple 10."
            ::= { hwPD510RunningEntry 23 }

        hwPD510CurrentI3 OBJECT-TYPE
            SYNTAX Integer32 (0..65535)
            MAX-ACCESS read-only
            STATUS current
            DESCRIPTION
                "CurrentI3 of the device running table for the PD510.Unit:A . Multiple 10."
            ::= { hwPD510RunningEntry 24 }

        hwPD510AverageCurrent OBJECT-TYPE
            SYNTAX Integer32 (0..65535)
            MAX-ACCESS read-only
            STATUS current
            DESCRIPTION
                "AverageCurrent of the device running table for the PD510.Unit:A . Multiple 10."
            ::= { hwPD510RunningEntry 25 }

        hwPD510NeutralLineCurrentIn OBJECT-TYPE
            SYNTAX Integer32 (0..65535)
            MAX-ACCESS read-only
            STATUS current
            DESCRIPTION
                "NeutralLineCurrentIn of the device running table for the PD510.Unit:A . Multiple 10."
            ::= { hwPD510RunningEntry 26 }

        hwPD510PhaseActivePowerP1 OBJECT-TYPE
            SYNTAX Integer32 ( -32768..32767)
            MAX-ACCESS read-only
            STATUS current
            DESCRIPTION
                "PhaseActivePowerP1 of the device running table for the PD510.Unit:W . Multiple 10."
            ::= { hwPD510RunningEntry 27 }

        hwPD510PhaseActivePowerP2 OBJECT-TYPE
            SYNTAX Integer32 ( -32768..32767)
            MAX-ACCESS read-only
            STATUS current
            DESCRIPTION
                "PhaseActivePowerP2 of the device running table for the PD510.Unit:W . Multiple 10."
            ::= { hwPD510RunningEntry 28 }

        hwPD510PhaseActivePowerP3 OBJECT-TYPE
            SYNTAX Integer32 ( -32768..32767)
            MAX-ACCESS read-only
            STATUS current
            DESCRIPTION
                "PhaseActivePowerP3 of the device running table for the PD510.Unit:W . Multiple 10."
            ::= { hwPD510RunningEntry 29 }

        hwPD510SystemActivePower OBJECT-TYPE
            SYNTAX Integer32 ( -32768..32767)
            MAX-ACCESS read-only
            STATUS current
            DESCRIPTION
                "SystemActivePower of the device running table for the PD510.Unit:W . Multiple 10."
            ::= { hwPD510RunningEntry 30 }

        hwPD510PhaseReactivePowerQ1 OBJECT-TYPE
            SYNTAX Integer32 ( -32768..32767)
            MAX-ACCESS read-only
            STATUS current
            DESCRIPTION
                "PhaseReactivePowerP1 of the device running table for the PD510.Unit:Var . Multiple 10."
            ::= { hwPD510RunningEntry 31 }

        hwPD510PhaseReactivePowerQ2 OBJECT-TYPE
            SYNTAX Integer32 ( -32768..32767)
            MAX-ACCESS read-only
            STATUS current
            DESCRIPTION
                "PhaseReactivePowerP2 of the device running table for the PD510.Unit:Var . Multiple 10."
            ::= { hwPD510RunningEntry 32 }

        hwPD510PhaseReactivePowerQ3 OBJECT-TYPE
            SYNTAX Integer32 ( -32768..32767)
            MAX-ACCESS read-only
            STATUS current
            DESCRIPTION
                "PhaseReactivePowerP3 of the device running table for the PD510.Unit:Var . Multiple 10."
            ::= { hwPD510RunningEntry 33 }

        hwPD510SystemReactivePower OBJECT-TYPE
            SYNTAX Integer32 ( -32768..32767)
            MAX-ACCESS read-only
            STATUS current
            DESCRIPTION
                "SystemReactivePower of the device running table for the PD510.Unit:Var . Multiple 10."
            ::= { hwPD510RunningEntry 34 }

        hwPD510PhaseApparentPowerS1 OBJECT-TYPE
            SYNTAX Integer32 (0..66535)
            MAX-ACCESS read-only
            STATUS current
            DESCRIPTION
                "PhaseApparentPowerS1 of the device running table for the PD510.Unit:VA. Multiple 10."
            ::= { hwPD510RunningEntry 35 }

        hwPD510PhaseApparentPowerS2 OBJECT-TYPE
            SYNTAX Integer32 (0..66535)
            MAX-ACCESS read-only
            STATUS current
            DESCRIPTION
                "PhaseApparentPowerS2 of the device running table for the PD510.Unit:VA. Multiple 10."
            ::= { hwPD510RunningEntry 36 }

        hwPD510PhaseApparentPowerS3 OBJECT-TYPE
            SYNTAX Integer32 (0..66535)
            MAX-ACCESS read-only
            STATUS current
            DESCRIPTION
                "PhaseApparentPowerS3 of the device running table for the PD510.Unit:VA. Multiple 10."
            ::= { hwPD510RunningEntry 37 }

        hwPD510SystemApparentPower OBJECT-TYPE
            SYNTAX Integer32 (0..66535)
            MAX-ACCESS read-only
            STATUS current
            DESCRIPTION
                "SystemApparentPower  of the device running table for the PD510.Unit:VA. Multiple 10."
            ::= { hwPD510RunningEntry 38 }

        hwPD510PhasePowerFactorPF1 OBJECT-TYPE
            SYNTAX Integer32 ( -1..1)
            MAX-ACCESS read-only
            STATUS current
            DESCRIPTION
                "PhasePowerFactorPF1  of the device running table for the PD510.Unit:NA. Multiple 10."
            ::= { hwPD510RunningEntry 39 }

        hwPD510PhasePowerFactorPF2 OBJECT-TYPE
            SYNTAX Integer32 ( -1..1)
            MAX-ACCESS read-only
            STATUS current
            DESCRIPTION
                "PhasePowerFactorPF2  of the device running table for the PD510.Unit:NA. Multiple 10."
            ::= { hwPD510RunningEntry 40 }

        hwPD510PhasePowerFactorPF3 OBJECT-TYPE
            SYNTAX Integer32 ( -1..1)
            MAX-ACCESS read-only
            STATUS current
            DESCRIPTION
                "PhasePowerFactorPF3  of the device running table for the PD510.Unit:NA. Multiple 10."
            ::= { hwPD510RunningEntry 41 }

        hwPD510SystemPowerFactor OBJECT-TYPE
            SYNTAX Integer32 ( -1..1)
            MAX-ACCESS read-only
            STATUS current
            DESCRIPTION
                "SystemPowerFactor of the device running table for the PD510.Unit:NA. Multiple 10."
            ::= { hwPD510RunningEntry 42 }

        hwPD510InputActiveEnergy OBJECT-TYPE
            SYNTAX Integer32 (0..99999999)
            MAX-ACCESS read-only
            STATUS current
            DESCRIPTION
                "InputActiveEnergy of the device running table for the PD510.Unit:Kwh. Multiple 10."
            ::= { hwPD510RunningEntry 43 }

        hwPD510OutputActiveEnergy OBJECT-TYPE
            SYNTAX Integer32 (0..99999999)
            MAX-ACCESS read-only
            STATUS current
            DESCRIPTION
                "OutputActiveEnergy of the device running table for the PD510.Unit:Kwh. Multiple 10."
            ::= { hwPD510RunningEntry 44 }

        hwPD510InductiveReactiveEnergy OBJECT-TYPE
            SYNTAX Integer32 (0..99999999)
            MAX-ACCESS read-only
            STATUS current
            DESCRIPTION
                "InductiveReactiveEnergy  of the device running table for the PD510.Unit:Kvarh. Multiple 10."
            ::= { hwPD510RunningEntry 45 }

        hwPD510CapacitiveeactiveEnergy OBJECT-TYPE
            SYNTAX Integer32 (0..99999999)
            MAX-ACCESS read-only
            STATUS current
            DESCRIPTION
                "CapacitiveeactiveEnergy  of the device running table for the PD510.Unit:Kvarh. Multiple 10."
            ::= { hwPD510RunningEntry 46 }

        hwPD510TotalActiveEnergy OBJECT-TYPE
            SYNTAX Integer32 (0..99999999)
            MAX-ACCESS read-only
            STATUS current
            DESCRIPTION
                "TotalActiveEnergy of the device running table for the PD510.Unit:Kwh. Multiple 10."
            ::= { hwPD510RunningEntry 47 }

        hwPD510NetActiveEnergy OBJECT-TYPE
            SYNTAX Integer32 (0..99999999)
            MAX-ACCESS read-only
            STATUS current
            DESCRIPTION
                "NetActiveEnergy  of the device running table for the PD510.Unit:Kwh. Multiple 10."
            ::= { hwPD510RunningEntry 48 }

        hwPD510TotalReactiveEnergy OBJECT-TYPE
            SYNTAX Integer32 (0..99999999)
            MAX-ACCESS read-only
            STATUS current
            DESCRIPTION
                "TotalReactiveEnergy of the device running table for the PD510.Unit:Kvarh. Multiple 10."
            ::= { hwPD510RunningEntry 49 }

        hwPD510NetReactiveEnergy OBJECT-TYPE
            SYNTAX Integer32 (0..99999999)
            MAX-ACCESS read-only
            STATUS current
            DESCRIPTION
                "NetReactiveEnergy  of the device running table for the PD510.Unit:Kvarh. Multiple 10."
            ::= { hwPD510RunningEntry 50 }

        hwPD510ApparentEnergy OBJECT-TYPE
            SYNTAX Integer32 (0..99999999)
            MAX-ACCESS read-only
            STATUS current
            DESCRIPTION
                "ApparentEnergyModbusAddress of the device running table for the PD510.Unit:KVAh. Multiple 10."
            ::= { hwPD510RunningEntry 51 }

        hwPD510RowStatus OBJECT-TYPE
            SYNTAX RowStatus
            MAX-ACCESS read-create
            STATUS current
            DESCRIPTION
                "RowStatus  of the device running table for the PD510."
            ::= { hwPD510RunningEntry 100 }

        hwPD510ConfigTable OBJECT-TYPE
            SYNTAX SEQUENCE OF HwPD510ConfigEntry
            MAX-ACCESS not-accessible
             STATUS current
             DESCRIPTION
                "The Config Table of PD510 Equipment."
            ::= { hwPD510 2 }

        hwPD510ConfigEntry OBJECT-TYPE
                        SYNTAX HwPD510ConfigEntry
            MAX-ACCESS not-accessible
             STATUS current
             DESCRIPTION
                "The Config Table of PD510 Equipment."
            INDEX { hwPD510ConfigIndex }
            ::= { hwPD510ConfigTable 1 }

        HwPD510ConfigEntry            ::= SEQUENCE {
                hwPD510ConfigIndex
                    Unsigned32,
                hwPD510FrequenceHighAlarmPoint
                    Integer32,
                hwPD510FrequenceLowAlarmPoint
                    Integer32,
                hwPD510PhaseVoltageV1HighAlarmPoint
                    Integer32,
                hwPD510PhaseVoltageV1LowAlarmPoint
                    Integer32,
                hwPD510PhaseVoltageV2HighAlarmPoint
                    Integer32,
                hwPD510PhaseVoltageV2LowAlarmPoint
                    Integer32,
                hwPD510PhaseVoltageV3HighAlarmPoint
                    Integer32,
                hwPD510PhaseVoltageV3LowAlarmPoint
                    Integer32,
                hwPD510LineVoltageV12HighAlarmPoint
                    Integer32,
                hwPD510LineVoltageV12LowAlarmPoint
                    Integer32,
                hwPD510LineVoltageV23HighAlarmPoint
                    Integer32,
                hwPD510LineVoltageV23LowAlarmPoint
                    Integer32,
                hwPD510LineVoltageV31HighAlarmPoint
                    Integer32,
                hwPD510LineVoltageV31LowAlarmPoint
                    Integer32,
                hwPD510CurrentI1HighAlarmPoint
                    Integer32,
                hwPD510CurrentI1LowAlarmPoint
                    Integer32,
                hwPD510CurrentI2HighAlarmPoint
                    Integer32,
                hwPD510CurrentI2LowAlarmPoint
                    Integer32,
                hwPD510CurrentI3HighAlarmPoint
                    Integer32,
                hwPD510CurrentI3LowAlarmPoint
                    Integer32,
                hwPD510NeutralLineCurrentInHighAlarmPoint
                    Integer32,
                hwPD510NeutralLineCurrentInLowAlarmPoint
                    Integer32,
                hwPD510ConfigRowStatus
                    RowStatus
            }

        hwPD510ConfigIndex OBJECT-TYPE
            SYNTAX Unsigned32
            MAX-ACCESS read-only
            STATUS current
            DESCRIPTION
                "Index of the device config table for the PD510."
            ::= { hwPD510ConfigEntry 1 }

        hwPD510FrequenceHighAlarmPoint OBJECT-TYPE
            SYNTAX Integer32 (45..65)
            MAX-ACCESS read-write
            STATUS current
            DESCRIPTION
                "Frequence High Alarm Point. The value ranges from 45 to 65. The unit is Hz. Multiple 10."
            ::= { hwPD510ConfigEntry 2 }

        hwPD510FrequenceLowAlarmPoint OBJECT-TYPE
            SYNTAX Integer32 (45..65)
            MAX-ACCESS read-write
            STATUS current
            DESCRIPTION
                "Frequence Low Alarm Point. The value ranges from 45 to 65. The unit is Hz. Multiple 10."
            ::= { hwPD510ConfigEntry 3 }

        hwPD510PhaseVoltageV1HighAlarmPoint OBJECT-TYPE
            SYNTAX Integer32 (0..65535)
            MAX-ACCESS read-write
            STATUS current
            DESCRIPTION
                "Phase Voltage V1 High Alarm Point. The value ranges from 0 to 65535. The unit is V. Multiple 10."
            ::= { hwPD510ConfigEntry 4 }

        hwPD510PhaseVoltageV1LowAlarmPoint OBJECT-TYPE
            SYNTAX Integer32 (0..65535)
            MAX-ACCESS read-write
            STATUS current
            DESCRIPTION
                "Phase Voltage V1 Low Alarm Point. The value ranges from 0 to 65535. The unit is V. Multiple 10."
            ::= { hwPD510ConfigEntry 5 }

        hwPD510PhaseVoltageV2HighAlarmPoint OBJECT-TYPE
            SYNTAX Integer32 (0..65535)
            MAX-ACCESS read-write
            STATUS current
            DESCRIPTION
                "Phase Voltage V2 High Alarm Point. The value ranges from 0 to 65535. The unit is V. Multiple 10."
            ::= { hwPD510ConfigEntry 6 }

        hwPD510PhaseVoltageV2LowAlarmPoint OBJECT-TYPE
            SYNTAX Integer32 (0..65535)
            MAX-ACCESS read-write
            STATUS current
            DESCRIPTION
                "Phase Voltage V2 Low Alarm Point. The value ranges from 0 to 65535. The unit is V. Multiple 10."
            ::= { hwPD510ConfigEntry 7 }

        hwPD510PhaseVoltageV3HighAlarmPoint OBJECT-TYPE
            SYNTAX Integer32 (0..65535)
            MAX-ACCESS read-write
            STATUS current
            DESCRIPTION
                "Phase Voltage V3 High Alarm Point. The value ranges from 0 to 65535. The unit is V. Multiple 10."
            ::= { hwPD510ConfigEntry 8 }

        hwPD510PhaseVoltageV3LowAlarmPoint OBJECT-TYPE
            SYNTAX Integer32 (0..65535)
            MAX-ACCESS read-write
            STATUS current
            DESCRIPTION
                "Phase Voltage V3 Low Alarm Point. The value ranges from 0 to 65535. The unit is V. Multiple 10."
            ::= { hwPD510ConfigEntry 9 }

        hwPD510LineVoltageV12HighAlarmPoint OBJECT-TYPE
            SYNTAX Integer32 (0..65535)
            MAX-ACCESS read-write
            STATUS current
            DESCRIPTION
                "Line Voltage V12 High Alarm Point. The value ranges from 0 to 65535. The unit is V. Multiple 10."
            ::= { hwPD510ConfigEntry 10 }

        hwPD510LineVoltageV12LowAlarmPoint OBJECT-TYPE
            SYNTAX Integer32 (0..65535)
            MAX-ACCESS read-write
            STATUS current
            DESCRIPTION
                "Line Voltage V12 Low Alarm Point. The value ranges from 0 to 65535. The unit is V. Multiple 10."
            ::= { hwPD510ConfigEntry 11 }

        hwPD510LineVoltageV23HighAlarmPoint OBJECT-TYPE
            SYNTAX Integer32 (0..65535)
            MAX-ACCESS read-write
            STATUS current
            DESCRIPTION
                "Line Voltage V23 High Alarm Point. The value ranges from 0 to 65535. The unit is V. Multiple 10."
            ::= { hwPD510ConfigEntry 12 }

        hwPD510LineVoltageV23LowAlarmPoint OBJECT-TYPE
            SYNTAX Integer32 (0..65535)
            MAX-ACCESS read-write
            STATUS current
            DESCRIPTION
                "Line Voltage V23 Low Alarm Point. The value ranges from 0 to 65535. The unit is V. Multiple 10."
            ::= { hwPD510ConfigEntry 13 }

        hwPD510LineVoltageV31HighAlarmPoint OBJECT-TYPE
            SYNTAX Integer32 (0..65535)
            MAX-ACCESS read-write
            STATUS current
            DESCRIPTION
                "Line Voltage V31 High Alarm Point. The value ranges from 0 to 65535. The unit is V. Multiple 10."
            ::= { hwPD510ConfigEntry 14 }

        hwPD510LineVoltageV31LowAlarmPoint OBJECT-TYPE
            SYNTAX Integer32 (0..65535)
            MAX-ACCESS read-write
            STATUS current
            DESCRIPTION
                "Line Voltage V31 Low Alarm Point. The value ranges from 0 to 65535. The unit is V. Multiple 10."
            ::= { hwPD510ConfigEntry 15 }

        hwPD510CurrentI1HighAlarmPoint OBJECT-TYPE
            SYNTAX Integer32 (0..65535)
            MAX-ACCESS read-write
            STATUS current
            DESCRIPTION
                "Current I1 High Alarm Point. The value ranges from 0 to 65535. The unit is A. Multiple 10."
            ::= { hwPD510ConfigEntry 16 }

        hwPD510CurrentI1LowAlarmPoint OBJECT-TYPE
            SYNTAX Integer32 (0..65535)
            MAX-ACCESS read-write
            STATUS current
            DESCRIPTION
                "Current I1 Low Alarm Point. The value ranges from 0 to 65535. The unit is A. Multiple 10."
            ::= { hwPD510ConfigEntry 17 }

        hwPD510CurrentI2HighAlarmPoint OBJECT-TYPE
            SYNTAX Integer32 (0..65535)
            MAX-ACCESS read-write
            STATUS current
            DESCRIPTION
                "Current I2 High Alarm Point. The value ranges from 0 to 65535. The unit is A. Multiple 10."
            ::= { hwPD510ConfigEntry 18 }

        hwPD510CurrentI2LowAlarmPoint OBJECT-TYPE
            SYNTAX Integer32 (0..65535)
            MAX-ACCESS read-write
            STATUS current
            DESCRIPTION
                "Current I2 Low Alarm Point. The value ranges from 0 to 65535. The unit is A. Multiple 10."
            ::= { hwPD510ConfigEntry 19 }

        hwPD510CurrentI3HighAlarmPoint OBJECT-TYPE
            SYNTAX Integer32 (0..65535)
            MAX-ACCESS read-write
            STATUS current
            DESCRIPTION
                "Current I3 High Alarm Point. The value ranges from 0 to 65535. The unit is A. Multiple 10."
            ::= { hwPD510ConfigEntry 20 }

        hwPD510CurrentI3LowAlarmPoint OBJECT-TYPE
            SYNTAX Integer32 (0..65535)
            MAX-ACCESS read-write
            STATUS current
            DESCRIPTION
                "Current I3 Low Alarm Point. The value ranges from 0 to 65535. The unit is A. Multiple 10."
            ::= { hwPD510ConfigEntry 21 }

        hwPD510NeutralLineCurrentInHighAlarmPoint OBJECT-TYPE
            SYNTAX Integer32 (0..65535)
            MAX-ACCESS read-write
            STATUS current
            DESCRIPTION
                "Neutral Line Current In High Alarm Point. The value ranges from 0 to 65535. The unit is A. Multiple 10."
            ::= { hwPD510ConfigEntry 22 }

        hwPD510NeutralLineCurrentInLowAlarmPoint OBJECT-TYPE
            SYNTAX Integer32 (0..65535)
            MAX-ACCESS read-write
            STATUS current
            DESCRIPTION
                "Neutral Line Current In Low Alarm Point. The value ranges from 0 to 65535. The unit is A. Multiple 10."
            ::= { hwPD510ConfigEntry 23 }

        hwPD510ConfigRowStatus OBJECT-TYPE
            SYNTAX RowStatus
            MAX-ACCESS read-create
            STATUS current
            DESCRIPTION
                "The config rowstatus of huawei temphum equipment."
            ::= { hwPD510ConfigEntry 100 }

        hwEA800 OBJECT IDENTIFIER ::= { hwIDCMonitorMIBObjects 13 }

        hwEA800RunningTable OBJECT-TYPE
            SYNTAX SEQUENCE OF HwEA800RunningEntry
            MAX-ACCESS not-accessible
             STATUS current
             DESCRIPTION
                "The running table of Huawei EA800 Equipment."
            ::= { hwEA800 1 }

        hwEA800RunningEntry OBJECT-TYPE
                        SYNTAX HwEA800RunningEntry
            MAX-ACCESS not-accessible
             STATUS current
             DESCRIPTION
                "The running table of Huawei EA800 Equipment."
            INDEX { hwEA800RunningIndex }
            ::= { hwEA800RunningTable 1 }

        HwEA800RunningEntry            ::= SEQUENCE {
                hwEA800RunningIndex
                    Unsigned32,
                hwEA800Name
                    OCTET STRING,
                hwEA800CommStatus
                    INTEGER,
                hwEA800CommSlotNo
                    Unsigned32,
                hwEA800CommPortNo
                    Unsigned32,
                hwEA800SoftwareVersion
                    OCTET STRING,
                hwEA800BypassStatus
                    INTEGER,
                hwEA800On-offStatus
                    INTEGER,
                hwEA800WorkingStatus
                    INTEGER,
                hwEA800WorkingModel
                    INTEGER,
                hwEA800InputVoltage
                    Integer32,
                hwEA800OutputVoltage
                    Integer32,
                hwEA800OutputCurrentPercent
                    Integer32,
                hwEA800InputFrequency
                    Integer32,
                hwEA800SingleBatteryVoltage
                    Integer32,
                hwEA800InnerTemperature
                    Integer32,
                hwEA800RatedInputVoltage
                    Integer32,
                hwEA800RatedOutputCurrentPercent
                    Integer32,
                hwEA800RatedBatteryVoltage
                    Integer32,
                hwEA800RatedInputFrequency
                    Integer32,
                hwEA800RowStatus
                    RowStatus
            }

        hwEA800RunningIndex OBJECT-TYPE
            SYNTAX Unsigned32
            MAX-ACCESS read-only
            STATUS current
            DESCRIPTION
                "Index of the device running table for the EA800."
            ::= { hwEA800RunningEntry 1 }

        hwEA800Name OBJECT-TYPE
            SYNTAX OCTET STRING (SIZE (0..50))
            MAX-ACCESS read-only
            STATUS current
            DESCRIPTION
                "Name of the device running table for the EA800."
            ::= { hwEA800RunningEntry 2 }

        hwEA800CommStatus OBJECT-TYPE
            SYNTAX INTEGER
                {
                ok(1),
                fail(2),
                unknown(255)
                }
            MAX-ACCESS read-only
            STATUS current
            DESCRIPTION
                "Communication Status
                    Value 1 indicates noraml.
                    Value 2 indicates fail."
            ::= { hwEA800RunningEntry 3 }

        hwEA800CommSlotNo OBJECT-TYPE
            SYNTAX Unsigned32 (1..6)
            MAX-ACCESS read-only
            STATUS current
            DESCRIPTION
                "the Slot No. of Device."
            ::= { hwEA800RunningEntry 4 }

        hwEA800CommPortNo OBJECT-TYPE
            SYNTAX Unsigned32 (1..5)
            MAX-ACCESS read-only
            STATUS current
            DESCRIPTION
                "the Port No. of Device."
            ::= { hwEA800RunningEntry 5 }

        hwEA800SoftwareVersion OBJECT-TYPE
            SYNTAX OCTET STRING (SIZE (0..32     ))
            MAX-ACCESS read-only
            STATUS current
            DESCRIPTION
                "The software version of EA800 equipment."
            ::= { hwEA800RunningEntry 7 }

        hwEA800BypassStatus OBJECT-TYPE
            SYNTAX INTEGER
                {
                no(1),
                yes(2),                                                                                                         
                unknown(255)
                }
            MAX-ACCESS read-only
            STATUS current
            DESCRIPTION
                "Bypass Status  of the device running table for the EA800.
                Value 1 indicates No.
                Value 2 indicates Yes."
            ::= { hwEA800RunningEntry 8 }

        hwEA800On-offStatus OBJECT-TYPE
            SYNTAX INTEGER
                {
                on(1),
                off(2),                                                                
                unknown(255)
                }
            MAX-ACCESS read-only
            STATUS current
            DESCRIPTION
                "On-off Status of the device running table for the EA800.
                Value 1 indicates On.
                Value 2 indicates Off."
            ::= { hwEA800RunningEntry 9 }

        hwEA800WorkingStatus OBJECT-TYPE
            SYNTAX INTEGER
                {
                normal(1),
                test(2),                                                                                                         
                unknown(255)
                }
            MAX-ACCESS read-only
            STATUS current
            DESCRIPTION
                "Working Status  of the device running table for the EA800.
                Value 1 indicates normal.
                Value 2 indicates test."
            ::= { hwEA800RunningEntry 10 }

        hwEA800WorkingModel OBJECT-TYPE
            SYNTAX INTEGER
                {
                online(1),
                backup(2),                                                                
                unknown(255)
                }
            MAX-ACCESS read-only
            STATUS current
            DESCRIPTION
                "On-off Status of the device running table for the EA800.
                Value 1 indicates online.
                Value 2 indicates backup."
            ::= { hwEA800RunningEntry 11 }

        hwEA800InputVoltage OBJECT-TYPE
            SYNTAX Integer32 (0..1000)
            MAX-ACCESS read-only
            STATUS current
            DESCRIPTION
                "InputVoltage of the device running table for the EA800.Unit:V Multiple 10."
            ::= { hwEA800RunningEntry 12 }

        hwEA800OutputVoltage OBJECT-TYPE
            SYNTAX Integer32 (0..1000)
            MAX-ACCESS read-only
            STATUS current
            DESCRIPTION
                "OutputVoltage of the device running table for the EA800.Unit:V Multiple 10."
            ::= { hwEA800RunningEntry 13 }

        hwEA800OutputCurrentPercent OBJECT-TYPE
            SYNTAX Integer32 (0..1000)
            MAX-ACCESS read-only
            STATUS current
            DESCRIPTION
                "OutputCurrentPercent of the device running table for the EA800.Unit:% Multiple 0."
            ::= { hwEA800RunningEntry 14 }

        hwEA800InputFrequency OBJECT-TYPE
            SYNTAX Integer32 (0..100)
            MAX-ACCESS read-only
            STATUS current
            DESCRIPTION
                "InputFrequency of the device running table for the EA800.Unit:Hz Multiple 10."
            ::= { hwEA800RunningEntry 15 }

        hwEA800SingleBatteryVoltage OBJECT-TYPE
            SYNTAX Integer32 (0..10)
            MAX-ACCESS read-only
            STATUS current
            DESCRIPTION
                "SingleBatteryVoltage of the device running table for the EA800.Unit:V Multiple 100."
            ::= { hwEA800RunningEntry 16 }

        hwEA800InnerTemperature OBJECT-TYPE
            SYNTAX Integer32 (0..100)
            MAX-ACCESS read-only
            STATUS current
            DESCRIPTION
                "InnerTemperature of the device running table for the EA800.Unit:degC Multiple 10."
            ::= { hwEA800RunningEntry 17 }

        hwEA800RatedInputVoltage OBJECT-TYPE
            SYNTAX Integer32 (0..1000)
            MAX-ACCESS read-only
            STATUS current
            DESCRIPTION
                "RatedInputVoltage of the device running table for the EA800.Unit:V Multiple 10."
            ::= { hwEA800RunningEntry 18 }

        hwEA800RatedOutputCurrentPercent OBJECT-TYPE
            SYNTAX Integer32 (0..100)
            MAX-ACCESS read-only
            STATUS current
            DESCRIPTION
                "RatedOutputCurrentPercent of the device running table for the EA800.Unit:% Multiple 0."
            ::= { hwEA800RunningEntry 19 }

        hwEA800RatedBatteryVoltage OBJECT-TYPE
            SYNTAX Integer32 (0..1000)
            MAX-ACCESS read-only
            STATUS current
            DESCRIPTION
                "RatedBatteryVoltage of the device running table for the EA800.Unit:V Multiple 10."
            ::= { hwEA800RunningEntry 20 }

        hwEA800RatedInputFrequency OBJECT-TYPE
            SYNTAX Integer32 (0..100)
            MAX-ACCESS read-only
            STATUS current
            DESCRIPTION
                "RatedInputFrequency of the device running table for the EA800.Unit:Hz Multiple 10."
            ::= { hwEA800RunningEntry 21 }

        hwEA800RowStatus OBJECT-TYPE
            SYNTAX RowStatus
            MAX-ACCESS read-create
            STATUS current
            DESCRIPTION
                "RowStatus  of the device running table for the EA800."
            ::= { hwEA800RunningEntry 100 }

        hwUL33 OBJECT IDENTIFIER ::= { hwIDCMonitorMIBObjects 14 }

        hwUL33RunningTable OBJECT-TYPE
            SYNTAX SEQUENCE OF HwUL33RunningEntry
            MAX-ACCESS not-accessible
             STATUS current
             DESCRIPTION
                "The running table of Huawei UL33 Equipment."
            ::= { hwUL33 1 }

        hwUL33RunningEntry OBJECT-TYPE
                        SYNTAX HwUL33RunningEntry
            MAX-ACCESS not-accessible
             STATUS current
             DESCRIPTION
                "The running table of Huawei UL33 Equipment."
            INDEX { hwUL33RunningIndex }
            ::= { hwUL33RunningTable 1 }

        HwUL33RunningEntry            ::= SEQUENCE {
                hwUL33RunningIndex
                    Unsigned32,
                hwUL33Name
                    OCTET STRING,
                hwUL33CommStatus
                    INTEGER,
                hwUL33CommSlotNo
                    Unsigned32,
                hwUL33CommPortNo
                    Unsigned32,
                hwUL33ModbusAddress
                    Unsigned32,
                hwUl33PowerMode
                    INTEGER,
                hwUl33BatteryStatus
                    INTEGER,
                hwUl33On-offStatus
                    INTEGER,
                hwUl33SoftwareVersion
                    OCTET STRING,
                hwUl33A-PhaseOutputVoltage
                    Integer32,
                hwUl33B-PhaseOutputVoltage
                    Integer32,
                hwUl33C-PhaseOutputVoltage
                    Integer32,
                hwUl33A-PhaseOutputCurrent
                    Integer32,
                hwUl33B-PhaseOutputCurrent
                    Integer32,
                hwUl33C-PhaseOutputCurrent
                    Integer32,
                hwUl33DCInputVoltage
                    Integer32,
                hwUl33ABInputLineVoltage
                    Integer32,
                hwUl33BCInputLineVoltage
                    Integer32,
                hwUl33CAInputLineVoltage
                    Integer32,
                hwUl33InputFrequency
                    Integer32,
                hwUl33A-PhaseBypassVoltage
                    Integer32,
                hwUl33B-PhaseBypassVoltage
                    Integer32,
                hwUl33C-PhaseBypassVoltage
                    Integer32,
                hwUl33BatteryCurrent
                    Integer32,
                hwUl33Backuptime
                    Unsigned32,
                hwUl33A-PhaseLoadRatio
                    Integer32,
                hwUl33B-PhaseLoadRatio
                    Integer32,
                hwUl33C-PhaseLoadRatio
                    Integer32,
                hwUl33RowStatus
                    RowStatus
            }

        hwUL33RunningIndex OBJECT-TYPE
            SYNTAX Unsigned32
            MAX-ACCESS read-only
            STATUS current
            DESCRIPTION
                "Index of the device running table for the UL33."
            ::= { hwUL33RunningEntry 1 }

        hwUL33Name OBJECT-TYPE
            SYNTAX OCTET STRING (SIZE (0..50))
            MAX-ACCESS read-only
            STATUS current
            DESCRIPTION
                "Name of the device running table for the UL33."
            ::= { hwUL33RunningEntry 2 }

        hwUL33CommStatus OBJECT-TYPE
            SYNTAX INTEGER
                {
                ok(1),
                fail(2),
                unknown(255)
                }
            MAX-ACCESS read-only
            STATUS current
            DESCRIPTION
                "Communication Status
                    Value 1 indicates noraml.
                    Value 2 indicates fail."
            ::= { hwUL33RunningEntry 3 }

        hwUL33CommSlotNo OBJECT-TYPE
            SYNTAX Unsigned32 (1..6)
            MAX-ACCESS read-only
            STATUS current
            DESCRIPTION
                "the Slot No. of Device."
            ::= { hwUL33RunningEntry 4 }

        hwUL33CommPortNo OBJECT-TYPE
            SYNTAX Unsigned32 (1..5)
            MAX-ACCESS read-only
            STATUS current
            DESCRIPTION
                "the Port No. of Device."
            ::= { hwUL33RunningEntry 5 }

        hwUL33ModbusAddress OBJECT-TYPE
            SYNTAX Unsigned32 (1..247)
            MAX-ACCESS read-only
            STATUS current
            DESCRIPTION
                "ModbusAddress of the device running table for the UL33."
            ::= { hwUL33RunningEntry 6 }

        hwUl33PowerMode OBJECT-TYPE
            SYNTAX INTEGER
                {
                upsMode(1),
                bypassMode(2),
                noPowerSupply(3),
                unknown(255)
                }
            MAX-ACCESS read-only
            STATUS current
            DESCRIPTION
                "Power mode of UL33 equipment.
                Value 1 indicates upsMode.
                Value 2 indicates  bypassMode.
                Value 3 indicates  noPowerSupply."
            ::= { hwUL33RunningEntry 7 }

        hwUl33BatteryStatus OBJECT-TYPE
            SYNTAX INTEGER
                {
                floatCharging(1),
                equalizedCharging(2), 
                noCharging(3),                                                                                                        
                unknown(255)
                }
            MAX-ACCESS read-only
            STATUS current
            DESCRIPTION
                "Battery Status  of the device running table for the UL33.
                Value 1 indicates floatCharging.
                Value 2 indicates equalizedCharging. 
                Value 3 indicates noCharging."
            ::= { hwUL33RunningEntry 8 }

        hwUl33On-offStatus OBJECT-TYPE
            SYNTAX INTEGER
                {
                on(1),
                off(2),                                                                
                unknown(255)
                }
            MAX-ACCESS read-only
            STATUS current
            DESCRIPTION
                "On-off Status of the device running table for the UL33.
                Value 1 indicates On.
                Value 2 indicates Off."
            ::= { hwUL33RunningEntry 9 }

        hwUl33SoftwareVersion OBJECT-TYPE
            SYNTAX OCTET STRING (SIZE (0..32     ))
            MAX-ACCESS read-only
            STATUS current
            DESCRIPTION
                "The software version of UL33 equipment."
            ::= { hwUL33RunningEntry 10 }

        hwUl33A-PhaseOutputVoltage OBJECT-TYPE
            SYNTAX Integer32 (0..1000)
            MAX-ACCESS read-only
            STATUS current
            DESCRIPTION
                "A-PhaseOutputVoltage of the device running table for the UL33.Unit:V."
            ::= { hwUL33RunningEntry 11 }

        hwUl33B-PhaseOutputVoltage OBJECT-TYPE
            SYNTAX Integer32 (0..1000)
            MAX-ACCESS read-only
            STATUS current
            DESCRIPTION
                "B-PhaseOutputVoltage of the device running table for the UL33.Unit:V."
            ::= { hwUL33RunningEntry 12 }

        hwUl33C-PhaseOutputVoltage OBJECT-TYPE
            SYNTAX Integer32 (0..1000)
            MAX-ACCESS read-only
            STATUS current
            DESCRIPTION
                "C-PhaseOutputVoltage of the device running table for the UL33.Unit:V."
            ::= { hwUL33RunningEntry 13 }

        hwUl33A-PhaseOutputCurrent OBJECT-TYPE
            SYNTAX Integer32 (0..1000)
            MAX-ACCESS read-only
            STATUS current
            DESCRIPTION
                "A-PhaseOutputCurrent of the device running table for the UL33.Unit:A Multiple 100."
            ::= { hwUL33RunningEntry 14 }

        hwUl33B-PhaseOutputCurrent OBJECT-TYPE
            SYNTAX Integer32 (0..1000)
            MAX-ACCESS read-only
            STATUS current
            DESCRIPTION
                "B-PhaseOutputCurrent of the device running table for the UL33.Unit:A Multiple 100."
            ::= { hwUL33RunningEntry 15 }

        hwUl33C-PhaseOutputCurrent OBJECT-TYPE
            SYNTAX Integer32 (0..1000)
            MAX-ACCESS read-only
            STATUS current
            DESCRIPTION
                "C-PhaseOutputCurrent of the device running table for the UL33.Unit:A Multiple 100."
            ::= { hwUL33RunningEntry 16 }

        hwUl33DCInputVoltage OBJECT-TYPE
            SYNTAX Integer32 (0..2000)
            MAX-ACCESS read-only
            STATUS current
            DESCRIPTION
                "DCInputVoltage of the device running table for the UL33.Unit:V."
            ::= { hwUL33RunningEntry 17 }

        hwUl33ABInputLineVoltage OBJECT-TYPE
            SYNTAX Integer32 (0..1000)
            MAX-ACCESS read-only
            STATUS current
            DESCRIPTION
                "ABInputLineVoltage of the device running table for the UL33.Unit:V."
            ::= { hwUL33RunningEntry 18 }

        hwUl33BCInputLineVoltage OBJECT-TYPE
            SYNTAX Integer32 (0..1000)
            MAX-ACCESS read-only
            STATUS current
            DESCRIPTION
                "BCInputLineVoltage of the device running table for the UL33.Unit:V."
            ::= { hwUL33RunningEntry 19 }

        hwUl33CAInputLineVoltage OBJECT-TYPE
            SYNTAX Integer32 (0..1000)
            MAX-ACCESS read-only
            STATUS current
            DESCRIPTION
                "CAInputLineVoltage of the device running table for the UL33.Unit:V."
            ::= { hwUL33RunningEntry 20 }

        hwUl33InputFrequency OBJECT-TYPE
            SYNTAX Integer32 (0..100)
            MAX-ACCESS read-only
            STATUS current
            DESCRIPTION
                "InputFrequency of the device running table for the UL33.Unit:Hz Multiple 10."
            ::= { hwUL33RunningEntry 21 }

        hwUl33A-PhaseBypassVoltage OBJECT-TYPE
            SYNTAX Integer32 (0..1000)
            MAX-ACCESS read-only
            STATUS current
            DESCRIPTION
                "A-PhaseBypassVoltage of the device running table for the UL33.Unit:V."
            ::= { hwUL33RunningEntry 22 }

        hwUl33B-PhaseBypassVoltage OBJECT-TYPE
            SYNTAX Integer32 (0..1000)
            MAX-ACCESS read-only
            STATUS current
            DESCRIPTION
                "B-PhaseBypassVoltage of the device running table for the UL33.Unit:V."
            ::= { hwUL33RunningEntry 23 }

        hwUl33C-PhaseBypassVoltage OBJECT-TYPE
            SYNTAX Integer32 (0..1000)
            MAX-ACCESS read-only
            STATUS current
            DESCRIPTION
                "C-PhaseBypassVoltage of the device running table for the UL33.Unit:V."
            ::= { hwUL33RunningEntry 24 }

        hwUl33BatteryCurrent OBJECT-TYPE
            SYNTAX Integer32 ( -3000..3000)
            MAX-ACCESS read-only
            STATUS current
            DESCRIPTION
                "BatteryCurrent of the device running table for the UL33.Unit:A Multiple 100."
            ::= { hwUL33RunningEntry 25 }

        hwUl33Backuptime OBJECT-TYPE
            SYNTAX Unsigned32 (0..2880)
            MAX-ACCESS read-only
            STATUS current
            DESCRIPTION
                "Backuptime of the device running table for the UL33.Unit:Min Multiple 10."
            ::= { hwUL33RunningEntry 26 }

        hwUl33A-PhaseLoadRatio OBJECT-TYPE
            SYNTAX Integer32 (0..500)
            MAX-ACCESS read-only
            STATUS current
            DESCRIPTION
                "A-PhaseLoadRatio of the device running table for the UL33.Unit:%."
            ::= { hwUL33RunningEntry 27 }

        hwUl33B-PhaseLoadRatio OBJECT-TYPE
            SYNTAX Integer32 (0..500)
            MAX-ACCESS read-only
            STATUS current
            DESCRIPTION
                "B-PhaseLoadRatio of the device running table for the UL33.Unit:%."
            ::= { hwUL33RunningEntry 28 }

        hwUl33C-PhaseLoadRatio OBJECT-TYPE
            SYNTAX Integer32 (0..500)
            MAX-ACCESS read-only
            STATUS current
            DESCRIPTION
                "C-PhaseLoadRatio of the device running table for the UL33.Unit:%."
            ::= { hwUL33RunningEntry 29 }

        hwUl33RowStatus OBJECT-TYPE
            SYNTAX RowStatus
            MAX-ACCESS read-create
            STATUS current
            DESCRIPTION
                "RowStatus  of the device running table for the UL33."
            ::= { hwUL33RunningEntry 100 }

        hwMonitorMIBTraps OBJECT IDENTIFIER ::= { hwMonitor 2 }

        hwMonitorAlarmTraps OBJECT IDENTIFIER ::= { hwMonitorMIBTraps 1 }

        hwMonitorAlarmTrapsPrefix OBJECT IDENTIFIER ::= { hwMonitorAlarmTraps 0 }

        hwMUS02AAlarmTraps OBJECT IDENTIFIER ::= { hwMonitorAlarmTrapsPrefix 1 }

        hwMUS02AExistAlarmTraps NOTIFICATION-TYPE
            OBJECTS { hwAlarmTrapOrdinalNumber,hwAlarmText,hwAlarmLevel,hwAlarmSigDesc,hwMUS02AEquipId,hwMUS02AEquipName,hwMUS02APresenceStatus            }
            STATUS current
            DESCRIPTION
                "This trap is sent to NMS when RS485 communication card is not detected,which was detected yet."
            ::= { hwMUS02AAlarmTraps 1 }

        hwMUS02AExistAlarmResumeTraps NOTIFICATION-TYPE
            OBJECTS { hwAlarmTrapOrdinalNumber,hwAlarmText,hwAlarmLevel,hwAlarmSigDesc,hwMUS02AEquipId,hwMUS02AEquipName,hwMUS02APresenceStatus            }
            STATUS current
            DESCRIPTION
                "This trap is sent to NMS when RS485 communication card is detected,which was not detected yet."
            ::= { hwMUS02AAlarmTraps 2 }

        hwMUS02ACom4VoltageLowAlarmTraps NOTIFICATION-TYPE
            OBJECTS { hwAlarmTrapOrdinalNumber,hwAlarmText,hwAlarmLevel,hwAlarmSigDesc,hwMUS02AEquipId,hwMUS02AEquipName,hwMUS02ACom4PowerOutputStatus,hwMUS02ACom4PowerOutputAlarmStatus            }
            STATUS current
            DESCRIPTION
                "This trap is sent to NMS when COM4/12V Volt. Low alarm occur"
            ::= { hwMUS02AAlarmTraps 3 }

        hwMUS02ACom4VoltageLowAlarmResumeTraps NOTIFICATION-TYPE
            OBJECTS { hwAlarmTrapOrdinalNumber,hwAlarmText,hwAlarmLevel,hwAlarmSigDesc,hwMUS02AEquipId,hwMUS02AEquipName,hwMUS02ACom4PowerOutputStatus,hwMUS02ACom4PowerOutputAlarmStatus            }
            STATUS current
            DESCRIPTION
                "This trap is sent to NMS when COM4/12V Volt. Low alarm resume"
            ::= { hwMUS02AAlarmTraps 4 }

        hwMUS02ACom5VoltageLowAlarmTraps NOTIFICATION-TYPE
            OBJECTS { hwAlarmTrapOrdinalNumber,hwAlarmText,hwAlarmLevel,hwAlarmSigDesc,hwMUS02AEquipId,hwMUS02AEquipName,hwMUS02ACom5PowerOutputStatus,hwMUS02ACom5PowerOutputAlarmStatus            }
            STATUS current
            DESCRIPTION
                "This trap is sent to NMS when COM5/12V Volt. Low alarm occur"
            ::= { hwMUS02AAlarmTraps 5 }

        hwMUS02ACom5VoltageLowAlarmResumeTraps NOTIFICATION-TYPE
            OBJECTS { hwAlarmTrapOrdinalNumber,hwAlarmText,hwAlarmLevel,hwAlarmSigDesc,hwMUS02AEquipId,hwMUS02AEquipName,hwMUS02ACom5PowerOutputStatus,hwMUS02ACom5PowerOutputAlarmStatus            }
            STATUS current
            DESCRIPTION
                "This trap is sent to NMS when COM5/12V Volt. Low alarm resume"
            ::= { hwMUS02AAlarmTraps 6 }

        hwMUE05AAlarmTraps OBJECT IDENTIFIER ::= { hwMonitorAlarmTrapsPrefix 2 }

        hwMUE05AExistAlarmTraps NOTIFICATION-TYPE
            OBJECTS { hwAlarmTrapOrdinalNumber,hwAlarmText,hwAlarmLevel,hwAlarmSigDesc,hwMUE05AEquipId,hwMUE05AEquipName,hwMUE05APresenceStatus            }
            STATUS current
            DESCRIPTION
                "This trap is sent to NMS when AI and DI Extension Card is not detected,which was detected yet."
            ::= { hwMUE05AAlarmTraps 1 }

        hwMUE05AExistAlarmResumeTraps NOTIFICATION-TYPE
            OBJECTS { hwAlarmTrapOrdinalNumber,hwAlarmText,hwAlarmLevel,hwAlarmSigDesc,hwMUE05AEquipId,hwMUE05AEquipName,hwMUE05APresenceStatus            }
            STATUS current
            DESCRIPTION
                "This trap is sent to NMS when AI and DI Extension Card is detected,which was not detected yet."
            ::= { hwMUE05AAlarmTraps 2 }

        hwMUE05ACh1DiAlarmTraps NOTIFICATION-TYPE
            OBJECTS { hwAlarmTrapOrdinalNumber,hwAlarmText,hwAlarmLevel,hwAlarmSigDesc,hwMUE05AEquipId,hwMUE05AEquipName,hwMUE05ACh1DiStatus            }
            STATUS current
            DESCRIPTION
                "This trap is sent to NMS when AI/DI_1 DI Alarm occur"
            ::= { hwMUE05AAlarmTraps 3 }

        hwMUE05ACh1DiAlarmResumeTraps NOTIFICATION-TYPE
            OBJECTS { hwAlarmTrapOrdinalNumber,hwAlarmText,hwAlarmLevel,hwAlarmSigDesc,hwMUE05AEquipId,hwMUE05AEquipName,hwMUE05ACh1DiStatus            }
            STATUS current
            DESCRIPTION
                "This trap is sent to NMS when AI/DI_1 DI Alarm resume"
            ::= { hwMUE05AAlarmTraps 4 }

        hwMUE05ACh1SensorFailureAlarmTraps NOTIFICATION-TYPE
            OBJECTS { hwAlarmTrapOrdinalNumber,hwAlarmText,hwAlarmLevel,hwAlarmSigDesc,hwMUE05AEquipId,hwMUE05AEquipName,hwMUE05ACh1SensorStatus            }
            STATUS current
            DESCRIPTION
                "This trap is sent to NMS when AI/DI_1 Sensor Fail. alarm occur"
            ::= { hwMUE05AAlarmTraps 5 }

        hwMUE05ACh1SensorFailureAlarmResumeTraps NOTIFICATION-TYPE
            OBJECTS { hwAlarmTrapOrdinalNumber,hwAlarmText,hwAlarmLevel,hwAlarmSigDesc,hwMUE05AEquipId,hwMUE05AEquipName,hwMUE05ACh1SensorStatus            }
            STATUS current
            DESCRIPTION
                "This trap is sent to NMS when AI/DI_1 Sensor Fail. alarm resume"
            ::= { hwMUE05AAlarmTraps 6 }

        hwMUE05ACh1HighAlarmTraps NOTIFICATION-TYPE
            OBJECTS { hwAlarmTrapOrdinalNumber,hwAlarmText,hwAlarmLevel,hwAlarmSigDesc,hwMUE05AEquipId,hwMUE05AEquipName,hwMUE05ACh1AiValue            }
            STATUS current
            DESCRIPTION
                "This trap is sent to NMS when  AI/DI_1 High Alarm occur"
            ::= { hwMUE05AAlarmTraps 7 }

        hwMUE05ACh1HighAlarmResumeTraps NOTIFICATION-TYPE
            OBJECTS { hwAlarmTrapOrdinalNumber,hwAlarmText,hwAlarmLevel,hwAlarmSigDesc,hwMUE05AEquipId,hwMUE05AEquipName,hwMUE05ACh1AiValue            }
            STATUS current
            DESCRIPTION
                "This trap is sent to NMS when  AI/DI_1 High Alarm resume"
            ::= { hwMUE05AAlarmTraps 8 }

        hwMUE05ACh1LowAlarmTraps NOTIFICATION-TYPE
            OBJECTS { hwAlarmTrapOrdinalNumber,hwAlarmText,hwAlarmLevel,hwAlarmSigDesc,hwMUE05AEquipId,hwMUE05AEquipName,hwMUE05ACh1AiValue            }
            STATUS current
            DESCRIPTION
                "This trap is sent to NMS when AI/DI_1 Low Alarm occur"
            ::= { hwMUE05AAlarmTraps 9 }

        hwMUE05ACh1LowAlarmResumeTraps NOTIFICATION-TYPE
            OBJECTS { hwAlarmTrapOrdinalNumber,hwAlarmText,hwAlarmLevel,hwAlarmSigDesc,hwMUE05AEquipId,hwMUE05AEquipName,hwMUE05ACh1AiValue            }
            STATUS current
            DESCRIPTION
                "This trap is sent to NMS when AI/DI_1 Low Alarm resume"
            ::= { hwMUE05AAlarmTraps 10 }

        hwMUE05ACh2DiAlarmTraps NOTIFICATION-TYPE
            OBJECTS { hwAlarmTrapOrdinalNumber,hwAlarmText,hwAlarmLevel,hwAlarmSigDesc,hwMUE05AEquipId,hwMUE05AEquipName,hwMUE05ACh2DiStatus            }
            STATUS current
            DESCRIPTION
                "This trap is sent to NMS when AI/DI_2 DI Alarm occur"
            ::= { hwMUE05AAlarmTraps 11 }

        hwMUE05ACh2DiAlarmResumeTraps NOTIFICATION-TYPE
            OBJECTS { hwAlarmTrapOrdinalNumber,hwAlarmText,hwAlarmLevel,hwAlarmSigDesc,hwMUE05AEquipId,hwMUE05AEquipName,hwMUE05ACh2DiStatus            }
            STATUS current
            DESCRIPTION
                "This trap is sent to NMS when AI/DI_2 DI Alarm resume"
            ::= { hwMUE05AAlarmTraps 12 }

        hwMUE05ACh2SensorFailureAlarmTraps NOTIFICATION-TYPE
            OBJECTS { hwAlarmTrapOrdinalNumber,hwAlarmText,hwAlarmLevel,hwAlarmSigDesc,hwMUE05AEquipId,hwMUE05AEquipName,hwMUE05ACh2SensorStatus            }
            STATUS current
            DESCRIPTION
                "This trap is sent to NMS when AI/DI_2 Sensor Fail. alarm occur"
            ::= { hwMUE05AAlarmTraps 13 }

        hwMUE05ACh2SensorFailureAlarmResumeTraps NOTIFICATION-TYPE
            OBJECTS { hwAlarmTrapOrdinalNumber,hwAlarmText,hwAlarmLevel,hwAlarmSigDesc,hwMUE05AEquipId,hwMUE05AEquipName,hwMUE05ACh2SensorStatus            }
            STATUS current
            DESCRIPTION
                "This trap is sent to NMS when AI/DI_2 Sensor Fail. alarm resume"
            ::= { hwMUE05AAlarmTraps 14 }

        hwMUE05ACh2HighAlarmTraps NOTIFICATION-TYPE
            OBJECTS { hwAlarmTrapOrdinalNumber,hwAlarmText,hwAlarmLevel,hwAlarmSigDesc,hwMUE05AEquipId,hwMUE05AEquipName,hwMUE05ACh2AiValue            }
            STATUS current
            DESCRIPTION
                "This trap is sent to NMS when  AI/DI_2 High Alarm occur"
            ::= { hwMUE05AAlarmTraps 15 }

        hwMUE05ACh2HighAlarmResumeTraps NOTIFICATION-TYPE
            OBJECTS { hwAlarmTrapOrdinalNumber,hwAlarmText,hwAlarmLevel,hwAlarmSigDesc,hwMUE05AEquipId,hwMUE05AEquipName,hwMUE05ACh2AiValue            }
            STATUS current
            DESCRIPTION
                "This trap is sent to NMS when  AI/DI_2 High Alarm resume"
            ::= { hwMUE05AAlarmTraps 16 }

        hwMUE05ACh2LowAlarmTraps NOTIFICATION-TYPE
            OBJECTS { hwAlarmTrapOrdinalNumber,hwAlarmText,hwAlarmLevel,hwAlarmSigDesc,hwMUE05AEquipId,hwMUE05AEquipName,hwMUE05ACh2AiValue            }
            STATUS current
            DESCRIPTION
                "This trap is sent to NMS when AI/DI_2 Low Alarm occur"
            ::= { hwMUE05AAlarmTraps 17 }

        hwMUE05ACh2LowAlarmResumeTraps NOTIFICATION-TYPE
            OBJECTS { hwAlarmTrapOrdinalNumber,hwAlarmText,hwAlarmLevel,hwAlarmSigDesc,hwMUE05AEquipId,hwMUE05AEquipName,hwMUE05ACh2AiValue            }
            STATUS current
            DESCRIPTION
                "This trap is sent to NMS when AI/DI_2 Low Alarm resume"
            ::= { hwMUE05AAlarmTraps 18 }

        hwMUE05ACh3DiAlarmTraps NOTIFICATION-TYPE
            OBJECTS { hwAlarmTrapOrdinalNumber,hwAlarmText,hwAlarmLevel,hwAlarmSigDesc,hwMUE05AEquipId,hwMUE05AEquipName,hwMUE05ACh3DiStatus            }
            STATUS current
            DESCRIPTION
                "This trap is sent to NMS when AI/DI_3 DI Alarm occur"
            ::= { hwMUE05AAlarmTraps 19 }

        hwMUE05ACh3DiAlarmResumeTraps NOTIFICATION-TYPE
            OBJECTS { hwAlarmTrapOrdinalNumber,hwAlarmText,hwAlarmLevel,hwAlarmSigDesc,hwMUE05AEquipId,hwMUE05AEquipName,hwMUE05ACh3DiStatus            }
            STATUS current
            DESCRIPTION
                "This trap is sent to NMS when AI/DI_3 DI Alarm resume"
            ::= { hwMUE05AAlarmTraps 20 }

        hwMUE05ACh3SensorFailureAlarmTraps NOTIFICATION-TYPE
            OBJECTS { hwAlarmTrapOrdinalNumber,hwAlarmText,hwAlarmLevel,hwAlarmSigDesc,hwMUE05AEquipId,hwMUE05AEquipName,hwMUE05ACh3SensorStatus            }
            STATUS current
            DESCRIPTION
                "This trap is sent to NMS when AI/DI_3 Sensor Fail. alarm occur"
            ::= { hwMUE05AAlarmTraps 21 }

        hwMUE05ACh3SensorFailureAlarmResumeTraps NOTIFICATION-TYPE
            OBJECTS { hwAlarmTrapOrdinalNumber,hwAlarmText,hwAlarmLevel,hwAlarmSigDesc,hwMUE05AEquipId,hwMUE05AEquipName,hwMUE05ACh3SensorStatus            }
            STATUS current
            DESCRIPTION
                "This trap is sent to NMS when AI/DI_3 Sensor Fail. alarm resume"
            ::= { hwMUE05AAlarmTraps 22 }

        hwMUE05ACh3HighAlarmTraps NOTIFICATION-TYPE
            OBJECTS { hwAlarmTrapOrdinalNumber,hwAlarmText,hwAlarmLevel,hwAlarmSigDesc,hwMUE05AEquipId,hwMUE05AEquipName,hwMUE05ACh3AiValue            }
            STATUS current
            DESCRIPTION
                "This trap is sent to NMS when  AI/DI_3 High Alarm occur"
            ::= { hwMUE05AAlarmTraps 23 }

        hwMUE05ACh3HighAlarmResumeTraps NOTIFICATION-TYPE
            OBJECTS { hwAlarmTrapOrdinalNumber,hwAlarmText,hwAlarmLevel,hwAlarmSigDesc,hwMUE05AEquipId,hwMUE05AEquipName,hwMUE05ACh3AiValue            }
            STATUS current
            DESCRIPTION
                "This trap is sent to NMS when  AI/DI_3 High Alarm resume"
            ::= { hwMUE05AAlarmTraps 24 }

        hwMUE05ACh3LowAlarmTraps NOTIFICATION-TYPE
            OBJECTS { hwAlarmTrapOrdinalNumber,hwAlarmText,hwAlarmLevel,hwAlarmSigDesc,hwMUE05AEquipId,hwMUE05AEquipName,hwMUE05ACh3AiValue            }
            STATUS current
            DESCRIPTION
                "This trap is sent to NMS when AI/DI_3 Low Alarm occur"
            ::= { hwMUE05AAlarmTraps 25 }

        hwMUE05ACh3LowAlarmResumeTraps NOTIFICATION-TYPE
            OBJECTS { hwAlarmTrapOrdinalNumber,hwAlarmText,hwAlarmLevel,hwAlarmSigDesc,hwMUE05AEquipId,hwMUE05AEquipName,hwMUE05ACh3AiValue            }
            STATUS current
            DESCRIPTION
                "This trap is sent to NMS when AI/DI_3 Low Alarm resume"
            ::= { hwMUE05AAlarmTraps 26 }

        hwMUE05ACh4DiAlarmTraps NOTIFICATION-TYPE
            OBJECTS { hwAlarmTrapOrdinalNumber,hwAlarmText,hwAlarmLevel,hwAlarmSigDesc,hwMUE05AEquipId,hwMUE05AEquipName,hwMUE05ACh4DiStatus            }
            STATUS current
            DESCRIPTION
                "This trap is sent to NMS when AI/DI_4 DI Alarm occur"
            ::= { hwMUE05AAlarmTraps 27 }

        hwMUE05ACh4DiAlarmResumeTraps NOTIFICATION-TYPE
            OBJECTS { hwAlarmTrapOrdinalNumber,hwAlarmText,hwAlarmLevel,hwAlarmSigDesc,hwMUE05AEquipId,hwMUE05AEquipName,hwMUE05ACh4DiStatus            }
            STATUS current
            DESCRIPTION
                "This trap is sent to NMS when AI/DI_4 DI Alarm resume"
            ::= { hwMUE05AAlarmTraps 28 }

        hwMUE05ACh4SensorFailureAlarmTraps NOTIFICATION-TYPE
            OBJECTS { hwAlarmTrapOrdinalNumber,hwAlarmText,hwAlarmLevel,hwAlarmSigDesc,hwMUE05AEquipId,hwMUE05AEquipName,hwMUE05ACh4SensorStatus            }
            STATUS current
            DESCRIPTION
                "This trap is sent to NMS when AI/DI_4 Sensor Fail. alarm occur"
            ::= { hwMUE05AAlarmTraps 29 }

        hwMUE05ACh4SensorFailureAlarmResumeTraps NOTIFICATION-TYPE
            OBJECTS { hwAlarmTrapOrdinalNumber,hwAlarmText,hwAlarmLevel,hwAlarmSigDesc,hwMUE05AEquipId,hwMUE05AEquipName,hwMUE05ACh4SensorStatus            }
            STATUS current
            DESCRIPTION
                "This trap is sent to NMS when AI/DI_4 Sensor Fail. alarm resume"
            ::= { hwMUE05AAlarmTraps 30 }

        hwMUE05ACh4HighAlarmTraps NOTIFICATION-TYPE
            OBJECTS { hwAlarmTrapOrdinalNumber,hwAlarmText,hwAlarmLevel,hwAlarmSigDesc,hwMUE05AEquipId,hwMUE05AEquipName,hwMUE05ACh4AiValue            }
            STATUS current
            DESCRIPTION
                "This trap is sent to NMS when  AI/DI_4 High Alarm occur"
            ::= { hwMUE05AAlarmTraps 31 }

        hwMUE05ACh4HighAlarmResumeTraps NOTIFICATION-TYPE
            OBJECTS { hwAlarmTrapOrdinalNumber,hwAlarmText,hwAlarmLevel,hwAlarmSigDesc,hwMUE05AEquipId,hwMUE05AEquipName,hwMUE05ACh4AiValue            }
            STATUS current
            DESCRIPTION
                "This trap is sent to NMS when  AI/DI_4 High Alarm resume"
            ::= { hwMUE05AAlarmTraps 32 }

        hwMUE05ACh4LowAlarmTraps NOTIFICATION-TYPE
            OBJECTS { hwAlarmTrapOrdinalNumber,hwAlarmText,hwAlarmLevel,hwAlarmSigDesc,hwMUE05AEquipId,hwMUE05AEquipName,hwMUE05ACh4AiValue            }
            STATUS current
            DESCRIPTION
                "This trap is sent to NMS when AI/DI_4 Low Alarm occur"
            ::= { hwMUE05AAlarmTraps 33 }

        hwMUE05ACh4LowAlarmResumeTraps NOTIFICATION-TYPE
            OBJECTS { hwAlarmTrapOrdinalNumber,hwAlarmText,hwAlarmLevel,hwAlarmSigDesc,hwMUE05AEquipId,hwMUE05AEquipName,hwMUE05ACh4AiValue            }
            STATUS current
            DESCRIPTION
                "This trap is sent to NMS when AI/DI_4 Low Alarm resume"
            ::= { hwMUE05AAlarmTraps 34 }

        hwMUE05ACh1VoltageLowAlarmTraps NOTIFICATION-TYPE
            OBJECTS { hwAlarmTrapOrdinalNumber,hwAlarmText,hwAlarmLevel,hwAlarmSigDesc,hwMUE05AEquipId,hwMUE05AEquipName,hwMUE05ACh1PowerOutputStatus,hwMUE05ACh1PowerOutputAlarmStatus            }
            STATUS current
            DESCRIPTION
                "This trap is sent to NMS when AI/DI_1 Volt. Low alarm occur"
            ::= { hwMUE05AAlarmTraps 35 }

        hwMUE05ACh1VoltageLowAlarmResumeTraps NOTIFICATION-TYPE
            OBJECTS { hwAlarmTrapOrdinalNumber,hwAlarmText,hwAlarmLevel,hwAlarmSigDesc,hwMUE05AEquipId,hwMUE05AEquipName,hwMUE05ACh1PowerOutputStatus,hwMUE05ACh1PowerOutputAlarmStatus            }
            STATUS current
            DESCRIPTION
                "This trap is sent to NMS when AI/DI_1 Volt. Low alarm resume"
            ::= { hwMUE05AAlarmTraps 36 }

        hwMUE05ACh2VoltageLowAlarmTraps NOTIFICATION-TYPE
            OBJECTS { hwAlarmTrapOrdinalNumber,hwAlarmText,hwAlarmLevel,hwAlarmSigDesc,hwMUE05AEquipId,hwMUE05AEquipName,hwMUE05ACh2PowerOutputStatus,hwMUE05ACh2PowerOutputAlarmStatus            }
            STATUS current
            DESCRIPTION
                "This trap is sent to NMS when AI/DI_2 Volt. Low alarm occur"
            ::= { hwMUE05AAlarmTraps 37 }

        hwMUE05ACh2VoltageLowAlarmResumeTraps NOTIFICATION-TYPE
            OBJECTS { hwAlarmTrapOrdinalNumber,hwAlarmText,hwAlarmLevel,hwAlarmSigDesc,hwMUE05AEquipId,hwMUE05AEquipName,hwMUE05ACh2PowerOutputStatus,hwMUE05ACh2PowerOutputAlarmStatus            }
            STATUS current
            DESCRIPTION
                "This trap is sent to NMS when AI/DI_2 Volt. Low alarm resume"
            ::= { hwMUE05AAlarmTraps 38 }

        hwMUE05ACh3VoltageLowAlarmTraps NOTIFICATION-TYPE
            OBJECTS { hwAlarmTrapOrdinalNumber,hwAlarmText,hwAlarmLevel,hwAlarmSigDesc,hwMUE05AEquipId,hwMUE05AEquipName,hwMUE05ACh3PowerOutputStatus,hwMUE05ACh3PowerOutputAlarmStatus            }
            STATUS current
            DESCRIPTION
                "This trap is sent to NMS when AI/DI_3 Volt. Low alarm occur"
            ::= { hwMUE05AAlarmTraps 39 }

        hwMUE05ACh3VoltageLowAlarmResumeTraps NOTIFICATION-TYPE
            OBJECTS { hwAlarmTrapOrdinalNumber,hwAlarmText,hwAlarmLevel,hwAlarmSigDesc,hwMUE05AEquipId,hwMUE05AEquipName,hwMUE05ACh3PowerOutputStatus,hwMUE05ACh3PowerOutputAlarmStatus            }
            STATUS current
            DESCRIPTION
                "This trap is sent to NMS when AI/DI_3 Volt. Low alarm resume"
            ::= { hwMUE05AAlarmTraps 40 }

        hwMUE05ACh4VoltageLowAlarmTraps NOTIFICATION-TYPE
            OBJECTS { hwAlarmTrapOrdinalNumber,hwAlarmText,hwAlarmLevel,hwAlarmSigDesc,hwMUE05AEquipId,hwMUE05AEquipName,hwMUE05ACh4PowerOutputStatus,hwMUE05ACh4PowerOutputAlarmStatus            }
            STATUS current
            DESCRIPTION
                "This trap is sent to NMS when AI/DI_4 Volt. Low alarm occur"
            ::= { hwMUE05AAlarmTraps 41 }

        hwMUE05ACh4VoltageLowAlarmResumeTraps NOTIFICATION-TYPE
            OBJECTS { hwAlarmTrapOrdinalNumber,hwAlarmText,hwAlarmLevel,hwAlarmSigDesc,hwMUE05AEquipId,hwMUE05AEquipName,hwMUE05ACh4PowerOutputStatus,hwMUE05ACh4PowerOutputAlarmStatus            }
            STATUS current
            DESCRIPTION
                "This trap is sent to NMS when AI/DI_4 Volt. Low alarm resume"
            ::= { hwMUE05AAlarmTraps 42 }

        hwMUE05ACh1SensorWiringErrorAlarmTraps NOTIFICATION-TYPE
            OBJECTS { hwAlarmTrapOrdinalNumber,hwAlarmText,hwAlarmLevel,hwAlarmSigDesc,hwMUE05AEquipId,hwMUE05AEquipName            }
            STATUS current
            DESCRIPTION
                "This trap is sent to NMS when AI/DI_1 Wiring Error alarm occur"
            ::= { hwMUE05AAlarmTraps 43 }

        hwMUE05ACh1SensorWiringErrorAlarmResumeTraps NOTIFICATION-TYPE
            OBJECTS { hwAlarmTrapOrdinalNumber,hwAlarmText,hwAlarmLevel,hwAlarmSigDesc,hwMUE05AEquipId,hwMUE05AEquipName            }
            STATUS current
            DESCRIPTION
                "This trap is sent to NMS when AI/DI_1 Wiring Error alarm resume"
            ::= { hwMUE05AAlarmTraps 44 }

        hwMUE05ACh2SensorWiringErrorAlarmTraps NOTIFICATION-TYPE
            OBJECTS { hwAlarmTrapOrdinalNumber,hwAlarmText,hwAlarmLevel,hwAlarmSigDesc,hwMUE05AEquipId,hwMUE05AEquipName            }
            STATUS current
            DESCRIPTION
                "This trap is sent to NMS when AI/DI_2 Wiring Error alarm occur"
            ::= { hwMUE05AAlarmTraps 45 }

        hwMUE05ACh2SensorWiringErrorAlarmResumeTraps NOTIFICATION-TYPE
            OBJECTS { hwAlarmTrapOrdinalNumber,hwAlarmText,hwAlarmLevel,hwAlarmSigDesc,hwMUE05AEquipId,hwMUE05AEquipName            }
            STATUS current
            DESCRIPTION
                "This trap is sent to NMS when AI/DI_2 Wiring Error alarm resume"
            ::= { hwMUE05AAlarmTraps 46 }

        hwMUE05ACh3SensorWiringErrorAlarmTraps NOTIFICATION-TYPE
            OBJECTS { hwAlarmTrapOrdinalNumber,hwAlarmText,hwAlarmLevel,hwAlarmSigDesc,hwMUE05AEquipId,hwMUE05AEquipName            }
            STATUS current
            DESCRIPTION
                "This trap is sent to NMS when AI/DI_3 Wiring Error alarm occur"
            ::= { hwMUE05AAlarmTraps 47 }

        hwMUE05ACh3SensorWiringErrorAlarmResumeTraps NOTIFICATION-TYPE
            OBJECTS { hwAlarmTrapOrdinalNumber,hwAlarmText,hwAlarmLevel,hwAlarmSigDesc,hwMUE05AEquipId,hwMUE05AEquipName            }
            STATUS current
            DESCRIPTION
                "This trap is sent to NMS when AI/DI_3 Wiring Error alarm resume"
            ::= { hwMUE05AAlarmTraps 48 }

        hwMUE05ACh4SensorWiringErrorAlarmTraps NOTIFICATION-TYPE
            OBJECTS { hwAlarmTrapOrdinalNumber,hwAlarmText,hwAlarmLevel,hwAlarmSigDesc,hwMUE05AEquipId,hwMUE05AEquipName            }
            STATUS current
            DESCRIPTION
                "This trap is sent to NMS when AI/DI_4 Wiring Error alarm occur"
            ::= { hwMUE05AAlarmTraps 49 }

        hwMUE05ACh4SensorWiringErrorAlarmResumeTraps NOTIFICATION-TYPE
            OBJECTS { hwAlarmTrapOrdinalNumber,hwAlarmText,hwAlarmLevel,hwAlarmSigDesc,hwMUE05AEquipId,hwMUE05AEquipName            }
            STATUS current
            DESCRIPTION
                "This trap is sent to NMS when AI/DI_4 Wiring Error alarm resume"
            ::= { hwMUE05AAlarmTraps 50 }

        hwMUE06AAlarmTraps OBJECT IDENTIFIER ::= { hwMonitorAlarmTrapsPrefix 3 }

        hwMUE06AExistAlarmTraps NOTIFICATION-TYPE
            OBJECTS { hwAlarmTrapOrdinalNumber,hwAlarmText,hwAlarmLevel,hwAlarmSigDesc,hwMUE06AEquipId,hwMUE06AEquipName,hwMUE06APresenceStatus            }
            STATUS current
            DESCRIPTION
                "This trap is sent to NMS when Independent Deployment AI and DI Board is not detected,which was detected yet."
            ::= { hwMUE06AAlarmTraps 1 }

        hwMUE06AExistAlarmResumeTraps NOTIFICATION-TYPE
            OBJECTS { hwAlarmTrapOrdinalNumber,hwAlarmText,hwAlarmLevel,hwAlarmSigDesc,hwMUE06AEquipId,hwMUE06AEquipName,hwMUE06APresenceStatus            }
            STATUS current
            DESCRIPTION
                "This trap is sent to NMS when Independent Deployment AI and DI Board is detected,which was not detected yet."
            ::= { hwMUE06AAlarmTraps 2 }

        hwMUE06ACh1DiAlarmTraps NOTIFICATION-TYPE
            OBJECTS { hwAlarmTrapOrdinalNumber,hwAlarmText,hwAlarmLevel,hwAlarmSigDesc,hwMUE06AEquipId,hwMUE06AEquipName,hwMUE06ACh1DiStatus            }
            STATUS current
            DESCRIPTION
                "This trap is sent to NMS when AI/DI_1 DI Alarm occur"
            ::= { hwMUE06AAlarmTraps 3 }

        hwMUE06ACh1DiAlarmResumeTraps NOTIFICATION-TYPE
            OBJECTS { hwAlarmTrapOrdinalNumber,hwAlarmText,hwAlarmLevel,hwAlarmSigDesc,hwMUE06AEquipId,hwMUE06AEquipName,hwMUE06ACh1DiStatus            }
            STATUS current
            DESCRIPTION
                "This trap is sent to NMS when AI/DI_1 DI Alarm resume"
            ::= { hwMUE06AAlarmTraps 4 }

        hwMUE06ACh1SensorFailureAlarmTraps NOTIFICATION-TYPE
            OBJECTS { hwAlarmTrapOrdinalNumber,hwAlarmText,hwAlarmLevel,hwAlarmSigDesc,hwMUE06AEquipId,hwMUE06AEquipName,hwMUE06ACh1SensorStatus            }
            STATUS current
            DESCRIPTION
                "This trap is sent to NMS when AI/DI_1 Sensor Fail. alarm occur"
            ::= { hwMUE06AAlarmTraps 5 }

        hwMUE06ACh1SensorFailureAlarmResumeTraps NOTIFICATION-TYPE
            OBJECTS { hwAlarmTrapOrdinalNumber,hwAlarmText,hwAlarmLevel,hwAlarmSigDesc,hwMUE06AEquipId,hwMUE06AEquipName,hwMUE06ACh1SensorStatus            }
            STATUS current
            DESCRIPTION
                "This trap is sent to NMS when AI/DI_1 Sensor Fail. alarm resume"
            ::= { hwMUE06AAlarmTraps 6 }

        hwMUE06ACh1HighAlarmTraps NOTIFICATION-TYPE
            OBJECTS { hwAlarmTrapOrdinalNumber,hwAlarmText,hwAlarmLevel,hwAlarmSigDesc,hwMUE06AEquipId,hwMUE06AEquipName,hwMUE06ACh1AiValue            }
            STATUS current
            DESCRIPTION
                "This trap is sent to NMS when  AI/DI_1 High Alarm occur"
            ::= { hwMUE06AAlarmTraps 7 }

        hwMUE06ACh1HighAlarmResumeTraps NOTIFICATION-TYPE
            OBJECTS { hwAlarmTrapOrdinalNumber,hwAlarmText,hwAlarmLevel,hwAlarmSigDesc,hwMUE06AEquipId,hwMUE06AEquipName,hwMUE06ACh1AiValue            }
            STATUS current
            DESCRIPTION
                "This trap is sent to NMS when  AI/DI_1 High Alarm resume"
            ::= { hwMUE06AAlarmTraps 8 }

        hwMUE06ACh1LowAlarmTraps NOTIFICATION-TYPE
            OBJECTS { hwAlarmTrapOrdinalNumber,hwAlarmText,hwAlarmLevel,hwAlarmSigDesc,hwMUE06AEquipId,hwMUE06AEquipName,hwMUE06ACh1AiValue            }
            STATUS current
            DESCRIPTION
                "This trap is sent to NMS when AI/DI_1 Low Alarm occur"
            ::= { hwMUE06AAlarmTraps 9 }

        hwMUE06ACh1LowAlarmResumeTraps NOTIFICATION-TYPE
            OBJECTS { hwAlarmTrapOrdinalNumber,hwAlarmText,hwAlarmLevel,hwAlarmSigDesc,hwMUE06AEquipId,hwMUE06AEquipName,hwMUE06ACh1AiValue            }
            STATUS current
            DESCRIPTION
                "This trap is sent to NMS when AI/DI_1 Low Alarm resume"
            ::= { hwMUE06AAlarmTraps 10 }

        hwMUE06ACh2DiAlarmTraps NOTIFICATION-TYPE
            OBJECTS { hwAlarmTrapOrdinalNumber,hwAlarmText,hwAlarmLevel,hwAlarmSigDesc,hwMUE06AEquipId,hwMUE06AEquipName,hwMUE06ACh2DiStatus            }
            STATUS current
            DESCRIPTION
                "This trap is sent to NMS when AI/DI_2 DI Alarm occur"
            ::= { hwMUE06AAlarmTraps 11 }

        hwMUE06ACh2DiAlarmResumeTraps NOTIFICATION-TYPE
            OBJECTS { hwAlarmTrapOrdinalNumber,hwAlarmText,hwAlarmLevel,hwAlarmSigDesc,hwMUE06AEquipId,hwMUE06AEquipName,hwMUE06ACh2DiStatus            }
            STATUS current
            DESCRIPTION
                "This trap is sent to NMS when AI/DI_2 DI Alarm resume"
            ::= { hwMUE06AAlarmTraps 12 }

        hwMUE06ACh2SensorFailureAlarmTraps NOTIFICATION-TYPE
            OBJECTS { hwAlarmTrapOrdinalNumber,hwAlarmText,hwAlarmLevel,hwAlarmSigDesc,hwMUE06AEquipId,hwMUE06AEquipName,hwMUE06ACh2SensorStatus            }
            STATUS current
            DESCRIPTION
                "This trap is sent to NMS when AI/DI_2 Sensor Fail. alarm occur"
            ::= { hwMUE06AAlarmTraps 13 }

        hwMUE06ACh2SensorFailureAlarmResumeTraps NOTIFICATION-TYPE
            OBJECTS { hwAlarmTrapOrdinalNumber,hwAlarmText,hwAlarmLevel,hwAlarmSigDesc,hwMUE06AEquipId,hwMUE06AEquipName,hwMUE06ACh2SensorStatus            }
            STATUS current
            DESCRIPTION
                "This trap is sent to NMS when AI/DI_2 Sensor Fail. alarm resume"
            ::= { hwMUE06AAlarmTraps 14 }

        hwMUE06ACh2HighAlarmTraps NOTIFICATION-TYPE
            OBJECTS { hwAlarmTrapOrdinalNumber,hwAlarmText,hwAlarmLevel,hwAlarmSigDesc,hwMUE06AEquipId,hwMUE06AEquipName,hwMUE06ACh2AiValue            }
            STATUS current
            DESCRIPTION
                "This trap is sent to NMS when AI/DI_2 High Alarm occur"
            ::= { hwMUE06AAlarmTraps 15 }

        hwMUE06ACh2HighAlarmResumeTraps NOTIFICATION-TYPE
            OBJECTS { hwAlarmTrapOrdinalNumber,hwAlarmText,hwAlarmLevel,hwAlarmSigDesc,hwMUE06AEquipId,hwMUE06AEquipName,hwMUE06ACh2AiValue            }
            STATUS current
            DESCRIPTION
                "This trap is sent to NMS when AI/DI_2 High Alarm resume"
            ::= { hwMUE06AAlarmTraps 16 }

        hwMUE06ACh2LowAlarmTraps NOTIFICATION-TYPE
            OBJECTS { hwAlarmTrapOrdinalNumber,hwAlarmText,hwAlarmLevel,hwAlarmSigDesc,hwMUE06AEquipId,hwMUE06AEquipName,hwMUE06ACh2AiValue            }
            STATUS current
            DESCRIPTION
                "This trap is sent to NMS when AI/DI_2 Low Alarm occur"
            ::= { hwMUE06AAlarmTraps 17 }

        hwMUE06ACh2LowAlarmResumeTraps NOTIFICATION-TYPE
            OBJECTS { hwAlarmTrapOrdinalNumber,hwAlarmText,hwAlarmLevel,hwAlarmSigDesc,hwMUE06AEquipId,hwMUE06AEquipName,hwMUE06ACh2AiValue            }
            STATUS current
            DESCRIPTION
                "This trap is sent to NMS when AI/DI_2 Low Alarm resume"
            ::= { hwMUE06AAlarmTraps 18 }

        hwMUE06ACh3DiAlarmTraps NOTIFICATION-TYPE
            OBJECTS { hwAlarmTrapOrdinalNumber,hwAlarmText,hwAlarmLevel,hwAlarmSigDesc,hwMUE06AEquipId,hwMUE06AEquipName,hwMUE06ACh3DiStatus            }
            STATUS current
            DESCRIPTION
                "This trap is sent to NMS when AI/DI_3 DI Alarm occur"
            ::= { hwMUE06AAlarmTraps 19 }

        hwMUE06ACh3DiAlarmResumeTraps NOTIFICATION-TYPE
            OBJECTS { hwAlarmTrapOrdinalNumber,hwAlarmText,hwAlarmLevel,hwAlarmSigDesc,hwMUE06AEquipId,hwMUE06AEquipName,hwMUE06ACh3DiStatus            }
            STATUS current
            DESCRIPTION
                "This trap is sent to NMS when AI/DI_3 DI Alarm resume"
            ::= { hwMUE06AAlarmTraps 20 }

        hwMUE06ACh3SensorFailureAlarmTraps NOTIFICATION-TYPE
            OBJECTS { hwAlarmTrapOrdinalNumber,hwAlarmText,hwAlarmLevel,hwAlarmSigDesc,hwMUE06AEquipId,hwMUE06AEquipName,hwMUE06ACh3SensorStatus            }
            STATUS current
            DESCRIPTION
                "This trap is sent to NMS when AI/DI_3 Sensor Fail. alarm occur"
            ::= { hwMUE06AAlarmTraps 21 }

        hwMUE06ACh3SensorFailureAlarmResumeTraps NOTIFICATION-TYPE
            OBJECTS { hwAlarmTrapOrdinalNumber,hwAlarmText,hwAlarmLevel,hwAlarmSigDesc,hwMUE06AEquipId,hwMUE06AEquipName,hwMUE06ACh3SensorStatus            }
            STATUS current
            DESCRIPTION
                "This trap is sent to NMS when AI/DI_3 Sensor Fail. alarm resume"
            ::= { hwMUE06AAlarmTraps 22 }

        hwMUE06ACh3HighAlarmTraps NOTIFICATION-TYPE
            OBJECTS { hwAlarmTrapOrdinalNumber,hwAlarmText,hwAlarmLevel,hwAlarmSigDesc,hwMUE06AEquipId,hwMUE06AEquipName,hwMUE06ACh3AiValue            }
            STATUS current
            DESCRIPTION
                "This trap is sent to NMS when AI/DI_3 High Alarm occur"
            ::= { hwMUE06AAlarmTraps 23 }

        hwMUE06ACh3HighAlarmResumeTraps NOTIFICATION-TYPE
            OBJECTS { hwAlarmTrapOrdinalNumber,hwAlarmText,hwAlarmLevel,hwAlarmSigDesc,hwMUE06AEquipId,hwMUE06AEquipName,hwMUE06ACh3AiValue            }
            STATUS current
            DESCRIPTION
                "This trap is sent to NMS when AI/DI_3 High Alarm resume"
            ::= { hwMUE06AAlarmTraps 24 }

        hwMUE06ACh3LowAlarmTraps NOTIFICATION-TYPE
            OBJECTS { hwAlarmTrapOrdinalNumber,hwAlarmText,hwAlarmLevel,hwAlarmSigDesc,hwMUE06AEquipId,hwMUE06AEquipName,hwMUE06ACh3AiValue            }
            STATUS current
            DESCRIPTION
                "This trap is sent to NMS when AI/DI_3 Low Alarm occur"
            ::= { hwMUE06AAlarmTraps 25 }

        hwMUE06ACh3LowAlarmResumeTraps NOTIFICATION-TYPE
            OBJECTS { hwAlarmTrapOrdinalNumber,hwAlarmText,hwAlarmLevel,hwAlarmSigDesc,hwMUE06AEquipId,hwMUE06AEquipName,hwMUE06ACh3AiValue            }
            STATUS current
            DESCRIPTION
                "This trap is sent to NMS when AI/DI_3 Low Alarm resume"
            ::= { hwMUE06AAlarmTraps 26 }

        hwMUE06ACh4DiAlarmTraps NOTIFICATION-TYPE
            OBJECTS { hwAlarmTrapOrdinalNumber,hwAlarmText,hwAlarmLevel,hwAlarmSigDesc,hwMUE06AEquipId,hwMUE06AEquipName,hwMUE06ACh4DiStatus            }
            STATUS current
            DESCRIPTION
                "This trap is sent to NMS when AI/DI_4 DI Alarm occur"
            ::= { hwMUE06AAlarmTraps 27 }

        hwMUE06ACh4DiAlarmResumeTraps NOTIFICATION-TYPE
            OBJECTS { hwAlarmTrapOrdinalNumber,hwAlarmText,hwAlarmLevel,hwAlarmSigDesc,hwMUE06AEquipId,hwMUE06AEquipName,hwMUE06ACh4DiStatus            }
            STATUS current
            DESCRIPTION
                "This trap is sent to NMS when AI/DI_4 DI Alarm resume"
            ::= { hwMUE06AAlarmTraps 28 }

        hwMUE06ACh4SensorFailureAlarmTraps NOTIFICATION-TYPE
            OBJECTS { hwAlarmTrapOrdinalNumber,hwAlarmText,hwAlarmLevel,hwAlarmSigDesc,hwMUE06AEquipId,hwMUE06AEquipName,hwMUE06ACh4SensorStatus            }
            STATUS current
            DESCRIPTION
                "This trap is sent to NMS when AI/DI_4 Sensor Fail. alarm occur"
            ::= { hwMUE06AAlarmTraps 29 }

        hwMUE06ACh4SensorFailureAlarmResumeTraps NOTIFICATION-TYPE
            OBJECTS { hwAlarmTrapOrdinalNumber,hwAlarmText,hwAlarmLevel,hwAlarmSigDesc,hwMUE06AEquipId,hwMUE06AEquipName,hwMUE06ACh4SensorStatus            }
            STATUS current
            DESCRIPTION
                "This trap is sent to NMS when AI/DI_4 Sensor Fail. alarm resume"
            ::= { hwMUE06AAlarmTraps 30 }

        hwMUE06ACh4HighAlarmTraps NOTIFICATION-TYPE
            OBJECTS { hwAlarmTrapOrdinalNumber,hwAlarmText,hwAlarmLevel,hwAlarmSigDesc,hwMUE06AEquipId,hwMUE06AEquipName,hwMUE06ACh4AiValue            }
            STATUS current
            DESCRIPTION
                "This trap is sent to NMS when AI/DI_4 High Alarm occur"
            ::= { hwMUE06AAlarmTraps 31 }

        hwMUE06ACh4HighAlarmResumeTraps NOTIFICATION-TYPE
            OBJECTS { hwAlarmTrapOrdinalNumber,hwAlarmText,hwAlarmLevel,hwAlarmSigDesc,hwMUE06AEquipId,hwMUE06AEquipName,hwMUE06ACh4AiValue            }
            STATUS current
            DESCRIPTION
                "This trap is sent to NMS when AI/DI_4 High Alarm resume"
            ::= { hwMUE06AAlarmTraps 32 }

        hwMUE06ACh4LowAlarmTraps NOTIFICATION-TYPE
            OBJECTS { hwAlarmTrapOrdinalNumber,hwAlarmText,hwAlarmLevel,hwAlarmSigDesc,hwMUE06AEquipId,hwMUE06AEquipName,hwMUE06ACh4AiValue            }
            STATUS current
            DESCRIPTION
                "This trap is sent to NMS when AI/DI_4 Low Alarm occur"
            ::= { hwMUE06AAlarmTraps 33 }

        hwMUE06ACh4LowAlarmResumeTraps NOTIFICATION-TYPE
            OBJECTS { hwAlarmTrapOrdinalNumber,hwAlarmText,hwAlarmLevel,hwAlarmSigDesc,hwMUE06AEquipId,hwMUE06AEquipName,hwMUE06ACh4AiValue            }
            STATUS current
            DESCRIPTION
                "This trap is sent to NMS when AI/DI_4 Low Alarm resume"
            ::= { hwMUE06AAlarmTraps 34 }

        hwMUE06ACh5DiAlarmTraps NOTIFICATION-TYPE
            OBJECTS { hwAlarmTrapOrdinalNumber,hwAlarmText,hwAlarmLevel,hwAlarmSigDesc,hwMUE06AEquipId,hwMUE06AEquipName,hwMUE06ACh5DiStatus            }
            STATUS current
            DESCRIPTION
                "This trap is sent to NMS when AI/DI_5 DI Alarm occur"
            ::= { hwMUE06AAlarmTraps 35 }

        hwMUE06ACh5DiAlarmResumeTraps NOTIFICATION-TYPE
            OBJECTS { hwAlarmTrapOrdinalNumber,hwAlarmText,hwAlarmLevel,hwAlarmSigDesc,hwMUE06AEquipId,hwMUE06AEquipName,hwMUE06ACh5DiStatus            }
            STATUS current
            DESCRIPTION
                "This trap is sent to NMS when AI/DI_5 DI Alarm resume"
            ::= { hwMUE06AAlarmTraps 36 }

        hwMUE06ACh5SensorFailureAlarmTraps NOTIFICATION-TYPE
            OBJECTS { hwAlarmTrapOrdinalNumber,hwAlarmText,hwAlarmLevel,hwAlarmSigDesc,hwMUE06AEquipId,hwMUE06AEquipName,hwMUE06ACh5SensorStatus            }
            STATUS current
            DESCRIPTION
                "This trap is sent to NMS when AI/DI_5 Sensor Fail. alarm occur"
            ::= { hwMUE06AAlarmTraps 37 }

        hwMUE06ACh5SensorFailureAlarmResumeTraps NOTIFICATION-TYPE
            OBJECTS { hwAlarmTrapOrdinalNumber,hwAlarmText,hwAlarmLevel,hwAlarmSigDesc,hwMUE06AEquipId,hwMUE06AEquipName,hwMUE06ACh5SensorStatus            }
            STATUS current
            DESCRIPTION
                "This trap is sent to NMS when AI/DI_5 Sensor Fail. alarm resume"
            ::= { hwMUE06AAlarmTraps 38 }

        hwMUE06ACh5HighAlarmTraps NOTIFICATION-TYPE
            OBJECTS { hwAlarmTrapOrdinalNumber,hwAlarmText,hwAlarmLevel,hwAlarmSigDesc,hwMUE06AEquipId,hwMUE06AEquipName,hwMUE06ACh5AiValue            }
            STATUS current
            DESCRIPTION
                "This trap is sent to NMS when AI/DI_5 High Alarm occur"
            ::= { hwMUE06AAlarmTraps 39 }

        hwMUE06ACh5HighAlarmResumeTraps NOTIFICATION-TYPE
            OBJECTS { hwAlarmTrapOrdinalNumber,hwAlarmText,hwAlarmLevel,hwAlarmSigDesc,hwMUE06AEquipId,hwMUE06AEquipName,hwMUE06ACh5AiValue            }
            STATUS current
            DESCRIPTION
                "This trap is sent to NMS when AI/DI_5 High Alarm resume"
            ::= { hwMUE06AAlarmTraps 40 }

        hwMUE06ACh5LowAlarmTraps NOTIFICATION-TYPE
            OBJECTS { hwAlarmTrapOrdinalNumber,hwAlarmText,hwAlarmLevel,hwAlarmSigDesc,hwMUE06AEquipId,hwMUE06AEquipName,hwMUE06ACh5AiValue            }
            STATUS current
            DESCRIPTION
                "This trap is sent to NMS when AI/DI_5 Low Alarm occur"
            ::= { hwMUE06AAlarmTraps 41 }

        hwMUE06ACh5LowAlarmResumeTraps NOTIFICATION-TYPE
            OBJECTS { hwAlarmTrapOrdinalNumber,hwAlarmText,hwAlarmLevel,hwAlarmSigDesc,hwMUE06AEquipId,hwMUE06AEquipName,hwMUE06ACh5AiValue            }
            STATUS current
            DESCRIPTION
                "This trap is sent to NMS when AI/DI_5 Low Alarm resume"
            ::= { hwMUE06AAlarmTraps 42 }

        hwMUE06ACh6DiAlarmTraps NOTIFICATION-TYPE
            OBJECTS { hwAlarmTrapOrdinalNumber,hwAlarmText,hwAlarmLevel,hwAlarmSigDesc,hwMUE06AEquipId,hwMUE06AEquipName,hwMUE06ACh6DiStatus            }
            STATUS current
            DESCRIPTION
                "This trap is sent to NMS when AI/DI_6 DI Alarm occur"
            ::= { hwMUE06AAlarmTraps 43 }

        hwMUE06ACh6DiAlarmResumeTraps NOTIFICATION-TYPE
            OBJECTS { hwAlarmTrapOrdinalNumber,hwAlarmText,hwAlarmLevel,hwAlarmSigDesc,hwMUE06AEquipId,hwMUE06AEquipName,hwMUE06ACh6DiStatus            }
            STATUS current
            DESCRIPTION
                "This trap is sent to NMS when AI/DI_6 DI Alarm resume"
            ::= { hwMUE06AAlarmTraps 44 }

        hwMUE06ACh6SensorFailureAlarmTraps NOTIFICATION-TYPE
            OBJECTS { hwAlarmTrapOrdinalNumber,hwAlarmText,hwAlarmLevel,hwAlarmSigDesc,hwMUE06AEquipId,hwMUE06AEquipName,hwMUE06ACh6SensorStatus            }
            STATUS current
            DESCRIPTION
                "This trap is sent to NMS when AI/DI_6 Sensor Fail. alarm occur"
            ::= { hwMUE06AAlarmTraps 45 }

        hwMUE06ACh6SensorFailureAlarmResumeTraps NOTIFICATION-TYPE
            OBJECTS { hwAlarmTrapOrdinalNumber,hwAlarmText,hwAlarmLevel,hwAlarmSigDesc,hwMUE06AEquipId,hwMUE06AEquipName,hwMUE06ACh6SensorStatus            }
            STATUS current
            DESCRIPTION
                "This trap is sent to NMS when AI/DI_6 Sensor Fail. alarm resume"
            ::= { hwMUE06AAlarmTraps 46 }

        hwMUE06ACh6HighAlarmTraps NOTIFICATION-TYPE
            OBJECTS { hwAlarmTrapOrdinalNumber,hwAlarmText,hwAlarmLevel,hwAlarmSigDesc,hwMUE06AEquipId,hwMUE06AEquipName,hwMUE06ACh6AiValue            }
            STATUS current
            DESCRIPTION
                "This trap is sent to NMS when AI/DI_6 High Alarm occur"
            ::= { hwMUE06AAlarmTraps 47 }

        hwMUE06ACh6HighAlarmResumeTraps NOTIFICATION-TYPE
            OBJECTS { hwAlarmTrapOrdinalNumber,hwAlarmText,hwAlarmLevel,hwAlarmSigDesc,hwMUE06AEquipId,hwMUE06AEquipName,hwMUE06ACh6AiValue            }
            STATUS current
            DESCRIPTION
                "This trap is sent to NMS when AI/DI_6 High Alarm resume"
            ::= { hwMUE06AAlarmTraps 48 }

        hwMUE06ACh6LowAlarmTraps NOTIFICATION-TYPE
            OBJECTS { hwAlarmTrapOrdinalNumber,hwAlarmText,hwAlarmLevel,hwAlarmSigDesc,hwMUE06AEquipId,hwMUE06AEquipName,hwMUE06ACh6AiValue            }
            STATUS current
            DESCRIPTION
                "This trap is sent to NMS when AI/DI_6 Low Alarm occur"
            ::= { hwMUE06AAlarmTraps 49 }

        hwMUE06ACh6LowAlarmResumeTraps NOTIFICATION-TYPE
            OBJECTS { hwAlarmTrapOrdinalNumber,hwAlarmText,hwAlarmLevel,hwAlarmSigDesc,hwMUE06AEquipId,hwMUE06AEquipName,hwMUE06ACh6AiValue            }
            STATUS current
            DESCRIPTION
                "This trap is sent to NMS when AI/DI_6 Low Alarm resume"
            ::= { hwMUE06AAlarmTraps 50 }

        hwMUE06ACh7DiAlarmTraps NOTIFICATION-TYPE
            OBJECTS { hwAlarmTrapOrdinalNumber,hwAlarmText,hwAlarmLevel,hwAlarmSigDesc,hwMUE06AEquipId,hwMUE06AEquipName,hwMUE06ACh7DiStatus            }
            STATUS current
            DESCRIPTION
                "This trap is sent to NMS when AI/DI_7 DI Alarm occur"
            ::= { hwMUE06AAlarmTraps 51 }

        hwMUE06ACh7DiAlarmResumeTraps NOTIFICATION-TYPE
            OBJECTS { hwAlarmTrapOrdinalNumber,hwAlarmText,hwAlarmLevel,hwAlarmSigDesc,hwMUE06AEquipId,hwMUE06AEquipName,hwMUE06ACh7DiStatus            }
            STATUS current
            DESCRIPTION
                "This trap is sent to NMS when AI/DI_7 DI Alarm resume"
            ::= { hwMUE06AAlarmTraps 52 }

        hwMUE06ACh7SensorFailureAlarmTraps NOTIFICATION-TYPE
            OBJECTS { hwAlarmTrapOrdinalNumber,hwAlarmText,hwAlarmLevel,hwAlarmSigDesc,hwMUE06AEquipId,hwMUE06AEquipName,hwMUE06ACh7SensorStatus            }
            STATUS current
            DESCRIPTION
                "This trap is sent to NMS when AI/DI_7 Sensor Fail. alarm occur"
            ::= { hwMUE06AAlarmTraps 53 }

        hwMUE06ACh7SensorFailureAlarmResumeTraps NOTIFICATION-TYPE
            OBJECTS { hwAlarmTrapOrdinalNumber,hwAlarmText,hwAlarmLevel,hwAlarmSigDesc,hwMUE06AEquipId,hwMUE06AEquipName,hwMUE06ACh7SensorStatus            }
            STATUS current
            DESCRIPTION
                "This trap is sent to NMS when AI/DI_7 Sensor Fail. alarm resume"
            ::= { hwMUE06AAlarmTraps 54 }

        hwMUE06ACh7HighAlarmTraps NOTIFICATION-TYPE
            OBJECTS { hwAlarmTrapOrdinalNumber,hwAlarmText,hwAlarmLevel,hwAlarmSigDesc,hwMUE06AEquipId,hwMUE06AEquipName,hwMUE06ACh7AiValue            }
            STATUS current
            DESCRIPTION
                "This trap is sent to NMS when AI/DI_7 High Alarm occur"
            ::= { hwMUE06AAlarmTraps 55 }

        hwMUE06ACh7HighAlarmResumeTraps NOTIFICATION-TYPE
            OBJECTS { hwAlarmTrapOrdinalNumber,hwAlarmText,hwAlarmLevel,hwAlarmSigDesc,hwMUE06AEquipId,hwMUE06AEquipName,hwMUE06ACh7AiValue            }
            STATUS current
            DESCRIPTION
                "This trap is sent to NMS when AI/DI_7 High Alarm resume"
            ::= { hwMUE06AAlarmTraps 56 }

        hwMUE06ACh7LowAlarmTraps NOTIFICATION-TYPE
            OBJECTS { hwAlarmTrapOrdinalNumber,hwAlarmText,hwAlarmLevel,hwAlarmSigDesc,hwMUE06AEquipId,hwMUE06AEquipName,hwMUE06ACh7AiValue            }
            STATUS current
            DESCRIPTION
                "This trap is sent to NMS when AI/DI_7 Low Alarm occur"
            ::= { hwMUE06AAlarmTraps 57 }

        hwMUE06ACh7LowAlarmResumeTraps NOTIFICATION-TYPE
            OBJECTS { hwAlarmTrapOrdinalNumber,hwAlarmText,hwAlarmLevel,hwAlarmSigDesc,hwMUE06AEquipId,hwMUE06AEquipName,hwMUE06ACh7AiValue            }
            STATUS current
            DESCRIPTION
                "This trap is sent to NMS when AI/DI_7 Low Alarm resume"
            ::= { hwMUE06AAlarmTraps 58 }

        hwMUE06ACh8DiAlarmTraps NOTIFICATION-TYPE
            OBJECTS { hwAlarmTrapOrdinalNumber,hwAlarmText,hwAlarmLevel,hwAlarmSigDesc,hwMUE06AEquipId,hwMUE06AEquipName,hwMUE06ACh8DiStatus            }
            STATUS current
            DESCRIPTION
                "This trap is sent to NMS when AI/DI_8 DI Alarm occur"
            ::= { hwMUE06AAlarmTraps 59 }

        hwMUE06ACh8DiAlarmResumeTraps NOTIFICATION-TYPE
            OBJECTS { hwAlarmTrapOrdinalNumber,hwAlarmText,hwAlarmLevel,hwAlarmSigDesc,hwMUE06AEquipId,hwMUE06AEquipName,hwMUE06ACh8DiStatus            }
            STATUS current
            DESCRIPTION
                "This trap is sent to NMS when AI/DI_8 DI Alarm resume"
            ::= { hwMUE06AAlarmTraps 60 }

        hwMUE06ACh8SensorFailureAlarmTraps NOTIFICATION-TYPE
            OBJECTS { hwAlarmTrapOrdinalNumber,hwAlarmText,hwAlarmLevel,hwAlarmSigDesc,hwMUE06AEquipId,hwMUE06AEquipName,hwMUE06ACh8SensorStatus            }
            STATUS current
            DESCRIPTION
                "This trap is sent to NMS when AI/DI_8 Sensor Fail. alarm occur"
            ::= { hwMUE06AAlarmTraps 61 }

        hwMUE06ACh8SensorFailureAlarmResumeTraps NOTIFICATION-TYPE
            OBJECTS { hwAlarmTrapOrdinalNumber,hwAlarmText,hwAlarmLevel,hwAlarmSigDesc,hwMUE06AEquipId,hwMUE06AEquipName,hwMUE06ACh8SensorStatus            }
            STATUS current
            DESCRIPTION
                "This trap is sent to NMS when AI/DI_8 Sensor Fail. alarm resume"
            ::= { hwMUE06AAlarmTraps 62 }

        hwMUE06ACh8HighAlarmTraps NOTIFICATION-TYPE
            OBJECTS { hwAlarmTrapOrdinalNumber,hwAlarmText,hwAlarmLevel,hwAlarmSigDesc,hwMUE06AEquipId,hwMUE06AEquipName,hwMUE06ACh8AiValue            }
            STATUS current
            DESCRIPTION
                "This trap is sent to NMS when AI/DI_8 High Alarm occur"
            ::= { hwMUE06AAlarmTraps 63 }

        hwMUE06ACh8HighAlarmResumeTraps NOTIFICATION-TYPE
            OBJECTS { hwAlarmTrapOrdinalNumber,hwAlarmText,hwAlarmLevel,hwAlarmSigDesc,hwMUE06AEquipId,hwMUE06AEquipName,hwMUE06ACh8AiValue            }
            STATUS current
            DESCRIPTION
                "This trap is sent to NMS when AI/DI_8 High Alarm resume"
            ::= { hwMUE06AAlarmTraps 64 }

        hwMUE06ACh8LowAlarmTraps NOTIFICATION-TYPE
            OBJECTS { hwAlarmTrapOrdinalNumber,hwAlarmText,hwAlarmLevel,hwAlarmSigDesc,hwMUE06AEquipId,hwMUE06AEquipName,hwMUE06ACh8AiValue            }
            STATUS current
            DESCRIPTION
                "This trap is sent to NMS when AI/DI_8 Low Alarm occur"
            ::= { hwMUE06AAlarmTraps 65 }

        hwMUE06ACh8LowAlarmResumeTraps NOTIFICATION-TYPE
            OBJECTS { hwAlarmTrapOrdinalNumber,hwAlarmText,hwAlarmLevel,hwAlarmSigDesc,hwMUE06AEquipId,hwMUE06AEquipName,hwMUE06ACh8AiValue            }
            STATUS current
            DESCRIPTION
                "This trap is sent to NMS when AI/DI_8 Low Alarm resume"
            ::= { hwMUE06AAlarmTraps 66 }

        hwMUE06ACh1VoltageLowAlarmTraps NOTIFICATION-TYPE
            OBJECTS { hwAlarmTrapOrdinalNumber,hwAlarmText,hwAlarmLevel,hwAlarmSigDesc,hwMUE06AEquipId,hwMUE06AEquipName,hwMUE06ACh1PowerOutputStatus,hwMUE06ACh1PowerOutputAlarmStatus            }
            STATUS current
            DESCRIPTION
                "This trap is sent to NMS when AI/DI_1 Volt. Low alarm occur"
            ::= { hwMUE06AAlarmTraps 67 }

        hwMUE06ACh1VoltageLowAlarmResumeTraps NOTIFICATION-TYPE
            OBJECTS { hwAlarmTrapOrdinalNumber,hwAlarmText,hwAlarmLevel,hwAlarmSigDesc,hwMUE06AEquipId,hwMUE06AEquipName,hwMUE06ACh1PowerOutputStatus,hwMUE06ACh1PowerOutputAlarmStatus            }
            STATUS current
            DESCRIPTION
                "This trap is sent to NMS when AI/DI_1 Volt. Low alarm resume"
            ::= { hwMUE06AAlarmTraps 68 }

        hwMUE06ACh2VoltageLowAlarmTraps NOTIFICATION-TYPE
            OBJECTS { hwAlarmTrapOrdinalNumber,hwAlarmText,hwAlarmLevel,hwAlarmSigDesc,hwMUE06AEquipId,hwMUE06AEquipName,hwMUE06ACh2PowerOutputStatus,hwMUE06ACh2PowerOutputAlarmStatus            }
            STATUS current
            DESCRIPTION
                "This trap is sent to NMS when AI/DI_2 Volt. Low alarm occur"
            ::= { hwMUE06AAlarmTraps 69 }

        hwMUE06ACh2VoltageLowAlarmResumeTraps NOTIFICATION-TYPE
            OBJECTS { hwAlarmTrapOrdinalNumber,hwAlarmText,hwAlarmLevel,hwAlarmSigDesc,hwMUE06AEquipId,hwMUE06AEquipName,hwMUE06ACh2PowerOutputStatus,hwMUE06ACh2PowerOutputAlarmStatus            }
            STATUS current
            DESCRIPTION
                "This trap is sent to NMS when AI/DI_2 Volt. Low alarm resume"
            ::= { hwMUE06AAlarmTraps 70 }

        hwMUE06ACh3VoltageLowAlarmTraps NOTIFICATION-TYPE
            OBJECTS { hwAlarmTrapOrdinalNumber,hwAlarmText,hwAlarmLevel,hwAlarmSigDesc,hwMUE06AEquipId,hwMUE06AEquipName,hwMUE06ACh3PowerOutputStatus,hwMUE06ACh3PowerOutputAlarmStatus            }
            STATUS current
            DESCRIPTION
                "This trap is sent to NMS when AI/DI_3 Volt. Low alarm occur"
            ::= { hwMUE06AAlarmTraps 71 }

        hwMUE06ACh3VoltageLowAlarmResumeTraps NOTIFICATION-TYPE
            OBJECTS { hwAlarmTrapOrdinalNumber,hwAlarmText,hwAlarmLevel,hwAlarmSigDesc,hwMUE06AEquipId,hwMUE06AEquipName,hwMUE06ACh3PowerOutputStatus,hwMUE06ACh3PowerOutputAlarmStatus            }
            STATUS current
            DESCRIPTION
                "This trap is sent to NMS when AI/DI_3 Volt. Low alarm resume"
            ::= { hwMUE06AAlarmTraps 72 }

        hwMUE06ACh4VoltageLowAlarmTraps NOTIFICATION-TYPE
            OBJECTS { hwAlarmTrapOrdinalNumber,hwAlarmText,hwAlarmLevel,hwAlarmSigDesc,hwMUE06AEquipId,hwMUE06AEquipName,hwMUE06ACh4PowerOutputStatus,hwMUE06ACh4PowerOutputAlarmStatus            }
            STATUS current
            DESCRIPTION
                "This trap is sent to NMS when AI/DI_4 Volt. Low alarm occur"
            ::= { hwMUE06AAlarmTraps 73 }

        hwMUE06ACh4VoltageLowAlarmResumeTraps NOTIFICATION-TYPE
            OBJECTS { hwAlarmTrapOrdinalNumber,hwAlarmText,hwAlarmLevel,hwAlarmSigDesc,hwMUE06AEquipId,hwMUE06AEquipName,hwMUE06ACh4PowerOutputStatus,hwMUE06ACh4PowerOutputAlarmStatus            }
            STATUS current
            DESCRIPTION
                "This trap is sent to NMS when AI/DI_4 Volt. Low alarm resume"
            ::= { hwMUE06AAlarmTraps 74 }

        hwMUE06ACh5VoltageLowAlarmTraps NOTIFICATION-TYPE
            OBJECTS { hwAlarmTrapOrdinalNumber,hwAlarmText,hwAlarmLevel,hwAlarmSigDesc,hwMUE06AEquipId,hwMUE06AEquipName,hwMUE06ACh5PowerOutputStatus,hwMUE06ACh5PowerOutputAlarmStatus            }
            STATUS current
            DESCRIPTION
                "This trap is sent to NMS when AI/DI_5 Volt. Low alarm occur"
            ::= { hwMUE06AAlarmTraps 75 }

        hwMUE06ACh5VoltageLowAlarmResumeTraps NOTIFICATION-TYPE
            OBJECTS { hwAlarmTrapOrdinalNumber,hwAlarmText,hwAlarmLevel,hwAlarmSigDesc,hwMUE06AEquipId,hwMUE06AEquipName,hwMUE06ACh5PowerOutputStatus,hwMUE06ACh5PowerOutputAlarmStatus            }
            STATUS current
            DESCRIPTION
                "This trap is sent to NMS when AI/DI_5 Volt. Low alarm resume"
            ::= { hwMUE06AAlarmTraps 76 }

        hwMUE06ACh6VoltageLowAlarmTraps NOTIFICATION-TYPE
            OBJECTS { hwAlarmTrapOrdinalNumber,hwAlarmText,hwAlarmLevel,hwAlarmSigDesc,hwMUE06AEquipId,hwMUE06AEquipName,hwMUE06ACh6PowerOutputStatus,hwMUE06ACh6PowerOutputAlarmStatus            }
            STATUS current
            DESCRIPTION
                "This trap is sent to NMS when AI/DI_6 Volt. Low alarm occur"
            ::= { hwMUE06AAlarmTraps 77 }

        hwMUE06ACh6VoltageLowAlarmResumeTraps NOTIFICATION-TYPE
            OBJECTS { hwAlarmTrapOrdinalNumber,hwAlarmText,hwAlarmLevel,hwAlarmSigDesc,hwMUE06AEquipId,hwMUE06AEquipName,hwMUE06ACh6PowerOutputStatus,hwMUE06ACh6PowerOutputAlarmStatus            }
            STATUS current
            DESCRIPTION
                "This trap is sent to NMS when AI/DI_6 Volt. Low alarm resume"
            ::= { hwMUE06AAlarmTraps 78 }

        hwMUE06ACh7VoltageLowAlarmTraps NOTIFICATION-TYPE
            OBJECTS { hwAlarmTrapOrdinalNumber,hwAlarmText,hwAlarmLevel,hwAlarmSigDesc,hwMUE06AEquipId,hwMUE06AEquipName,hwMUE06ACh7PowerOutputStatus,hwMUE06ACh7PowerOutputAlarmStatus            }
            STATUS current
            DESCRIPTION
                "This trap is sent to NMS when AI/DI_7 Volt. Low alarm occur"
            ::= { hwMUE06AAlarmTraps 79 }

        hwMUE06ACh7VoltageLowAlarmResumeTraps NOTIFICATION-TYPE
            OBJECTS { hwAlarmTrapOrdinalNumber,hwAlarmText,hwAlarmLevel,hwAlarmSigDesc,hwMUE06AEquipId,hwMUE06AEquipName,hwMUE06ACh7PowerOutputStatus,hwMUE06ACh7PowerOutputAlarmStatus            }
            STATUS current
            DESCRIPTION
                "This trap is sent to NMS when AI/DI_7 Volt. Low alarm resume"
            ::= { hwMUE06AAlarmTraps 80 }

        hwMUE06ACh8VoltageLowAlarmTraps NOTIFICATION-TYPE
            OBJECTS { hwAlarmTrapOrdinalNumber,hwAlarmText,hwAlarmLevel,hwAlarmSigDesc,hwMUE06AEquipId,hwMUE06AEquipName,hwMUE06ACh8PowerOutputStatus,hwMUE06ACh8PowerOutputAlarmStatus            }
            STATUS current
            DESCRIPTION
                "This trap is sent to NMS when AI/DI_8 Volt. Low alarm occur"
            ::= { hwMUE06AAlarmTraps 81 }

        hwMUE06ACh8VoltageLowAlarmResumeTraps NOTIFICATION-TYPE
            OBJECTS { hwAlarmTrapOrdinalNumber,hwAlarmText,hwAlarmLevel,hwAlarmSigDesc,hwMUE06AEquipId,hwMUE06AEquipName,hwMUE06ACh8PowerOutputStatus,hwMUE06ACh8PowerOutputAlarmStatus            }
            STATUS current
            DESCRIPTION
                "This trap is sent to NMS when AI/DI_8 Volt. Low alarm resume"
            ::= { hwMUE06AAlarmTraps 82 }

        hwMUE06APowerVotageLowAlarmTraps NOTIFICATION-TYPE
            OBJECTS { hwAlarmTrapOrdinalNumber,hwAlarmText,hwAlarmLevel,hwAlarmSigDesc,hwMUE06AEquipId,hwMUE06AEquipName,hwMUE06APowerVoltageLowAlarmStatus            }
            STATUS current
            DESCRIPTION
                "This trap is sent to NMS when Power Volt. Low alarm occur"
            ::= { hwMUE06AAlarmTraps 83 }

        hwMUE06APowerVotageLowAlarmResumeTraps NOTIFICATION-TYPE
            OBJECTS { hwAlarmTrapOrdinalNumber,hwAlarmText,hwAlarmLevel,hwAlarmSigDesc,hwMUE06AEquipId,hwMUE06AEquipName,hwMUE06APowerVoltageLowAlarmStatus            }
            STATUS current
            DESCRIPTION
                "This trap is sent to NMS when Power Volt. Low alarm resume"
            ::= { hwMUE06AAlarmTraps 84 }

        hwMUE06ACh1SensorWiringErrorAlarmTraps NOTIFICATION-TYPE
            OBJECTS { hwAlarmTrapOrdinalNumber,hwAlarmText,hwAlarmLevel,hwAlarmSigDesc,hwMUE06AEquipId,hwMUE06AEquipName            }
            STATUS current
            DESCRIPTION
                "This trap is sent to NMS when AI/DI_1 Wiring Error alarm occur"
            ::= { hwMUE06AAlarmTraps 85 }

        hwMUE06ACh1SensorWiringErrorAlarmResumeTraps NOTIFICATION-TYPE
            OBJECTS { hwAlarmTrapOrdinalNumber,hwAlarmText,hwAlarmLevel,hwAlarmSigDesc,hwMUE06AEquipId,hwMUE06AEquipName            }
            STATUS current
            DESCRIPTION
                "This trap is sent to NMS when AI/DI_1 Wiring Error alarm resume"
            ::= { hwMUE06AAlarmTraps 86 }

        hwMUE06ACh2SensorWiringErrorAlarmTraps NOTIFICATION-TYPE
            OBJECTS { hwAlarmTrapOrdinalNumber,hwAlarmText,hwAlarmLevel,hwAlarmSigDesc,hwMUE06AEquipId,hwMUE06AEquipName            }
            STATUS current
            DESCRIPTION
                "This trap is sent to NMS when AI/DI_2 Wiring Error alarm occur"
            ::= { hwMUE06AAlarmTraps 87 }

        hwMUE06ACh2SensorWiringErrorAlarmResumeTraps NOTIFICATION-TYPE
            OBJECTS { hwAlarmTrapOrdinalNumber,hwAlarmText,hwAlarmLevel,hwAlarmSigDesc,hwMUE06AEquipId,hwMUE06AEquipName            }
            STATUS current
            DESCRIPTION
                "This trap is sent to NMS when AI/DI_2 Wiring Error alarm resume"
            ::= { hwMUE06AAlarmTraps 88 }

        hwMUE06ACh3SensorWiringErrorAlarmTraps NOTIFICATION-TYPE
            OBJECTS { hwAlarmTrapOrdinalNumber,hwAlarmText,hwAlarmLevel,hwAlarmSigDesc,hwMUE06AEquipId,hwMUE06AEquipName            }
            STATUS current
            DESCRIPTION
                "This trap is sent to NMS when AI/DI_3 Wiring Error alarm occur"
            ::= { hwMUE06AAlarmTraps 89 }

        hwMUE06ACh3SensorWiringErrorAlarmResumeTraps NOTIFICATION-TYPE
            OBJECTS { hwAlarmTrapOrdinalNumber,hwAlarmText,hwAlarmLevel,hwAlarmSigDesc,hwMUE06AEquipId,hwMUE06AEquipName            }
            STATUS current
            DESCRIPTION
                "This trap is sent to NMS when AI/DI_3 Wiring Error alarm resume"
            ::= { hwMUE06AAlarmTraps 90 }

        hwMUE06ACh4SensorWiringErrorAlarmTraps NOTIFICATION-TYPE
            OBJECTS { hwAlarmTrapOrdinalNumber,hwAlarmText,hwAlarmLevel,hwAlarmSigDesc,hwMUE06AEquipId,hwMUE06AEquipName            }
            STATUS current
            DESCRIPTION
                "This trap is sent to NMS when AI/DI_4 Wiring Error alarm occur"
            ::= { hwMUE06AAlarmTraps 91 }

        hwMUE06ACh4SensorWiringErrorAlarmResumeTraps NOTIFICATION-TYPE
            OBJECTS { hwAlarmTrapOrdinalNumber,hwAlarmText,hwAlarmLevel,hwAlarmSigDesc,hwMUE06AEquipId,hwMUE06AEquipName            }
            STATUS current
            DESCRIPTION
                "This trap is sent to NMS when AI/DI_4 Wiring Error alarm resume"
            ::= { hwMUE06AAlarmTraps 92 }

        hwMUE06ACh5SensorWiringErrorAlarmTraps NOTIFICATION-TYPE
            OBJECTS { hwAlarmTrapOrdinalNumber,hwAlarmText,hwAlarmLevel,hwAlarmSigDesc,hwMUE06AEquipId,hwMUE06AEquipName            }
            STATUS current
            DESCRIPTION
                "This trap is sent to NMS when AI/DI_5 Wiring Error alarm occur"
            ::= { hwMUE06AAlarmTraps 93 }

        hwMUE06ACh5SensorWiringErrorAlarmResumeTraps NOTIFICATION-TYPE
            OBJECTS { hwAlarmTrapOrdinalNumber,hwAlarmText,hwAlarmLevel,hwAlarmSigDesc,hwMUE06AEquipId,hwMUE06AEquipName            }
            STATUS current
            DESCRIPTION
                "This trap is sent to NMS when AI/DI_5 Wiring Error alarm resume"
            ::= { hwMUE06AAlarmTraps 94 }

        hwMUE06ACh6SensorWiringErrorAlarmTraps NOTIFICATION-TYPE
            OBJECTS { hwAlarmTrapOrdinalNumber,hwAlarmText,hwAlarmLevel,hwAlarmSigDesc,hwMUE06AEquipId,hwMUE06AEquipName            }
            STATUS current
            DESCRIPTION
                "This trap is sent to NMS when AI/DI_6 Wiring Error alarm occur"
            ::= { hwMUE06AAlarmTraps 95 }

        hwMUE06ACh6SensorWiringErrorAlarmResumeTraps NOTIFICATION-TYPE
            OBJECTS { hwAlarmTrapOrdinalNumber,hwAlarmText,hwAlarmLevel,hwAlarmSigDesc,hwMUE06AEquipId,hwMUE06AEquipName            }
            STATUS current
            DESCRIPTION
                "This trap is sent to NMS when AI/DI_6 Wiring Error alarm resume"
            ::= { hwMUE06AAlarmTraps 96 }

        hwMUE06ACh7SensorWiringErrorAlarmTraps NOTIFICATION-TYPE
            OBJECTS { hwAlarmTrapOrdinalNumber,hwAlarmText,hwAlarmLevel,hwAlarmSigDesc,hwMUE06AEquipId,hwMUE06AEquipName            }
            STATUS current
            DESCRIPTION
                "This trap is sent to NMS when AI/DI_7 Wiring Error alarm occur"
            ::= { hwMUE06AAlarmTraps 97 }

        hwMUE06ACh7SensorWiringErrorAlarmResumeTraps NOTIFICATION-TYPE
            OBJECTS { hwAlarmTrapOrdinalNumber,hwAlarmText,hwAlarmLevel,hwAlarmSigDesc,hwMUE06AEquipId,hwMUE06AEquipName            }
            STATUS current
            DESCRIPTION
                "This trap is sent to NMS when AI/DI_7 Wiring Error alarm resume"
            ::= { hwMUE06AAlarmTraps 98 }

        hwMUE06ACh8SensorWiringErrorAlarmTraps NOTIFICATION-TYPE
            OBJECTS { hwAlarmTrapOrdinalNumber,hwAlarmText,hwAlarmLevel,hwAlarmSigDesc,hwMUE06AEquipId,hwMUE06AEquipName            }
            STATUS current
            DESCRIPTION
                "This trap is sent to NMS when AI/DI_8 Wiring Error alarm occur"
            ::= { hwMUE06AAlarmTraps 99 }

        hwMUE06ACh8SensorWiringErrorAlarmResumeTraps NOTIFICATION-TYPE
            OBJECTS { hwAlarmTrapOrdinalNumber,hwAlarmText,hwAlarmLevel,hwAlarmSigDesc,hwMUE06AEquipId,hwMUE06AEquipName            }
            STATUS current
            DESCRIPTION
                "This trap is sent to NMS when AI/DI_8 Wiring Error alarm resume"
            ::= { hwMUE06AAlarmTraps 100 }

        hwFansAlarmTraps OBJECT IDENTIFIER ::= { hwMonitorAlarmTrapsPrefix 5 }

        hwFB3000WAlarms OBJECT IDENTIFIER ::= { hwFansAlarmTraps 1 }

        hwFB3000WAlarmTraps NOTIFICATION-TYPE
            OBJECTS { hwAlarmTrapOrdinalNumber,hwAlarmText,hwAlarmLevel,hwAlarmSigDesc,hwFB3000WRunningIndex,hwFB3000WName            }
            STATUS current
            DESCRIPTION
                "This trap is sent to NMS when Fan Equip alarm occur"
            ::= { hwFB3000WAlarms 1 }

        hwFB3000WAlarmResumeTraps NOTIFICATION-TYPE
            OBJECTS { hwAlarmTrapOrdinalNumber,hwAlarmText,hwAlarmLevel,hwAlarmSigDesc,hwFB3000WRunningIndex,hwFB3000WName            }
            STATUS current
            DESCRIPTION
                "This trap is sent to NMS when Fan Equip  alarm resume"
            ::= { hwFB3000WAlarms 2 }

        hwUPSAlarmTraps OBJECT IDENTIFIER ::= { hwMonitorAlarmTrapsPrefix 4 }

        hwHuaweiUPS2000GAAlarms OBJECT IDENTIFIER ::= { hwUPSAlarmTraps 1 }

        hwHuaweiUPS2000G-AAlarmTraps NOTIFICATION-TYPE
            OBJECTS { hwAlarmTrapOrdinalNumber,hwAlarmText,hwAlarmLevel,hwAlarmSigDesc,hwHuaweiUPS2000G-AId,hwHuaweiUPS2000G-AName,hwHuaweiUPS2000G-AModbusAddress            }
            STATUS current
            DESCRIPTION
                "This trap is sent to NMS when UPS2000G-A Equipment alarm occur."
            ::= { hwHuaweiUPS2000GAAlarms 1 }

        hwHuaweiUPS2000G-AAlarmResumeTraps NOTIFICATION-TYPE
            OBJECTS { hwAlarmTrapOrdinalNumber,hwAlarmText,hwAlarmLevel,hwAlarmSigDesc,hwHuaweiUPS2000G-AId,hwHuaweiUPS2000G-AName,hwHuaweiUPS2000G-AModbusAddress            }
            STATUS current
            DESCRIPTION
                "This trap is sent to NMS when UPS2000G-A Equipment alarm resume."
            ::= { hwHuaweiUPS2000GAAlarms 2 }

        hwHuaweiUPS2000GBAlarms OBJECT IDENTIFIER ::= { hwUPSAlarmTraps 2 }

        hwUPS2000G-BAlarmTraps NOTIFICATION-TYPE
            OBJECTS { hwAlarmTrapOrdinalNumber,hwAlarmText,hwAlarmLevel,hwAlarmSigDesc,hwHuaweiUPS2000G-BRunningName,hwHuaweiUPS2000G-BRunningModBusAddr,hwHuaweiUPS2000G-BRunningESN            }
            STATUS current
            DESCRIPTION
                "This trap is sent to NMS when UPS2000G-B Equipment alarm occur."
            ::= { hwHuaweiUPS2000GBAlarms 1 }

        hwUPS2000G-BAlarmResumeTraps NOTIFICATION-TYPE
            OBJECTS { hwAlarmTrapOrdinalNumber,hwAlarmText,hwAlarmLevel,hwAlarmSigDesc,hwHuaweiUPS2000G-BRunningName,hwHuaweiUPS2000G-BRunningModBusAddr,hwHuaweiUPS2000G-BRunningESN            }
            STATUS current
            DESCRIPTION
                "This trap is sent to NMS when UPS2000G-B Equipment alarm resume."
            ::= { hwHuaweiUPS2000GBAlarms 2 }

        hwHuaweiUPS5000EAlarms OBJECT IDENTIFIER ::= { hwUPSAlarmTraps 3 }

        hwHuaweiUPS5000EOverallAlarmTraps NOTIFICATION-TYPE
            OBJECTS { hwAlarmTrapOrdinalNumber,hwAlarmText,hwAlarmLevel,hwAlarmSigDesc,hwHuaweiUPS5000ERunningIndex,hwHuaweiUPS5000ERunningName,hwUPS5000ESlot,hwUPS5000EPort,hwUPS5000EModbusAddress            }
            STATUS current
            DESCRIPTION
                "This trap is sent to NMS when UPS5000E Equipment alarm occur."
            ::= { hwHuaweiUPS5000EAlarms 1 }

        hwHuaweiUPS5000EOverallAlarmResumeTraps NOTIFICATION-TYPE
            OBJECTS { hwAlarmTrapOrdinalNumber,hwAlarmText,hwAlarmLevel,hwAlarmSigDesc,hwHuaweiUPS5000ERunningIndex,hwHuaweiUPS5000ERunningName,hwUPS5000ESlot,hwUPS5000EPort,hwUPS5000EModbusAddress            }
            STATUS current
            DESCRIPTION
                "This trap is sent to NMS when UPS5000E Equipment alarm resume."
            ::= { hwHuaweiUPS5000EAlarms 2 }

        hwHuaweiUPS5000EModuleAlarm1Traps NOTIFICATION-TYPE
            OBJECTS { hwAlarmTrapOrdinalNumber,hwAlarmText,hwAlarmLevel,hwAlarmSigDesc,hwHuaweiUPS5000ERunningIndex,hwHuaweiUPS5000ERunningName,hwUPS5000ESlot,hwUPS5000EPort,hwUPS5000EModbusAddress            }
            STATUS current
            DESCRIPTION
                "This trap is sent to NMS when UPS5000E Equipment (Module) part I alarm occur."
            ::= { hwHuaweiUPS5000EAlarms 3 }

        hwHuaweiUPS5000EModuleAlarm1ResumeTraps NOTIFICATION-TYPE
            OBJECTS { hwAlarmTrapOrdinalNumber,hwAlarmText,hwAlarmLevel,hwAlarmSigDesc,hwHuaweiUPS5000ERunningIndex,hwHuaweiUPS5000ERunningName,hwUPS5000ESlot,hwUPS5000EPort,hwUPS5000EModbusAddress            }
            STATUS current
            DESCRIPTION
                "This trap is sent to NMS when UPS5000E Equipment (Module) part I alarm resume."
            ::= { hwHuaweiUPS5000EAlarms 4 }

        hwHuaweiUPS5000EModuleAlarm2Traps NOTIFICATION-TYPE
            OBJECTS { hwAlarmTrapOrdinalNumber,hwAlarmText,hwAlarmLevel,hwAlarmSigDesc,hwHuaweiUPS5000ERunningIndex,hwHuaweiUPS5000ERunningName,hwUPS5000ESlot,hwUPS5000EPort,hwUPS5000EModbusAddress            }
            STATUS current
            DESCRIPTION
                "This trap is sent to NMS when UPS5000E Equipment (Module) part II alarm occur."
            ::= { hwHuaweiUPS5000EAlarms 5 }

        hwHuaweiUPS5000EModuleAlarm2ResumeTraps NOTIFICATION-TYPE
            OBJECTS { hwAlarmTrapOrdinalNumber,hwAlarmText,hwAlarmLevel,hwAlarmSigDesc,hwHuaweiUPS5000ERunningIndex,hwHuaweiUPS5000ERunningName,hwUPS5000ESlot,hwUPS5000EPort,hwUPS5000EModbusAddress            }
            STATUS current
            DESCRIPTION
                "This trap is sent to NMS when UPS5000E Equipment (Module) part II alarm resume."
            ::= { hwHuaweiUPS5000EAlarms 6 }

        hwHuaweiUPS5000EModuleAlarm3Traps NOTIFICATION-TYPE
            OBJECTS { hwAlarmTrapOrdinalNumber,hwAlarmText,hwAlarmLevel,hwAlarmSigDesc,hwHuaweiUPS5000ERunningIndex,hwHuaweiUPS5000ERunningName,hwUPS5000ESlot,hwUPS5000EPort,hwUPS5000EModbusAddress            }
            STATUS current
            DESCRIPTION
                "This trap is sent to NMS when UPS5000E Equipment (Module) part III alarm occur."
            ::= { hwHuaweiUPS5000EAlarms 7 }

        hwHuaweiUPS5000EModuleAlarm3ResumeTraps NOTIFICATION-TYPE
            OBJECTS { hwAlarmTrapOrdinalNumber,hwAlarmText,hwAlarmLevel,hwAlarmSigDesc,hwHuaweiUPS5000ERunningIndex,hwHuaweiUPS5000ERunningName,hwUPS5000ESlot,hwUPS5000EPort,hwUPS5000EModbusAddress            }
            STATUS current
            DESCRIPTION
                "This trap is sent to NMS when UPS5000E Equipment (Module) part III alarm resume."
            ::= { hwHuaweiUPS5000EAlarms 8 }

        hwHuaweiUPS5000EModuleAlarm4Traps NOTIFICATION-TYPE
            OBJECTS { hwAlarmTrapOrdinalNumber,hwAlarmText,hwAlarmLevel,hwAlarmSigDesc,hwHuaweiUPS5000ERunningIndex,hwHuaweiUPS5000ERunningName,hwUPS5000ESlot,hwUPS5000EPort,hwUPS5000EModbusAddress            }
            STATUS current
            DESCRIPTION
                "This trap is sent to NMS when UPS5000E Equipment (Module) part IV alarm occur."
            ::= { hwHuaweiUPS5000EAlarms 9 }

        hwHuaweiUPS5000EModuleAlarm4ResumeTraps NOTIFICATION-TYPE
            OBJECTS { hwAlarmTrapOrdinalNumber,hwAlarmText,hwAlarmLevel,hwAlarmSigDesc,hwHuaweiUPS5000ERunningIndex,hwHuaweiUPS5000ERunningName,hwUPS5000ESlot,hwUPS5000EPort,hwUPS5000EModbusAddress            }
            STATUS current
            DESCRIPTION
                "This trap is sent to NMS when UPS5000E Equipment (Module) part IV alarm resume."
            ::= { hwHuaweiUPS5000EAlarms 10 }

        hwHuaweiUPS5000EModuleAlarm5Traps NOTIFICATION-TYPE
            OBJECTS { hwAlarmTrapOrdinalNumber,hwAlarmText,hwAlarmLevel,hwAlarmSigDesc,hwHuaweiUPS5000ERunningIndex,hwHuaweiUPS5000ERunningName,hwUPS5000ESlot,hwUPS5000EPort,hwUPS5000EModbusAddress            }
            STATUS current
            DESCRIPTION
                "This trap is sent to NMS when UPS5000E Equipment (Module) part V alarm occur."
            ::= { hwHuaweiUPS5000EAlarms 11 }

        hwHuaweiUPS5000EModuleAlarm5ResumeTraps NOTIFICATION-TYPE
            OBJECTS { hwAlarmTrapOrdinalNumber,hwAlarmText,hwAlarmLevel,hwAlarmSigDesc,hwHuaweiUPS5000ERunningIndex,hwHuaweiUPS5000ERunningName,hwUPS5000ESlot,hwUPS5000EPort,hwUPS5000EModbusAddress            }
            STATUS current
            DESCRIPTION
                "This trap is sent to NMS when UPS5000E Equipment (Module) part V alarm resume."
            ::= { hwHuaweiUPS5000EAlarms 12 }

        hwHuaweiUPS5000EModuleAlarm6Traps NOTIFICATION-TYPE
            OBJECTS { hwAlarmTrapOrdinalNumber,hwAlarmText,hwAlarmLevel,hwAlarmSigDesc,hwHuaweiUPS5000ERunningIndex,hwHuaweiUPS5000ERunningName,hwUPS5000ESlot,hwUPS5000EPort,hwUPS5000EModbusAddress            }
            STATUS current
            DESCRIPTION
                "This trap is sent to NMS when UPS5000E Equipment (Module) part VI alarm occur."
            ::= { hwHuaweiUPS5000EAlarms 13 }

        hwHuaweiUPS5000EModuleAlarm6ResumeTraps NOTIFICATION-TYPE
            OBJECTS { hwAlarmTrapOrdinalNumber,hwAlarmText,hwAlarmLevel,hwAlarmSigDesc,hwHuaweiUPS5000ERunningIndex,hwHuaweiUPS5000ERunningName,hwUPS5000ESlot,hwUPS5000EPort,hwUPS5000EModbusAddress            }
            STATUS current
            DESCRIPTION
                "This trap is sent to NMS when UPS5000E Equipment (Module) part VI alarm resume."
            ::= { hwHuaweiUPS5000EAlarms 14 }

        hwHuaweiUPS5000EModuleAlarm7Traps NOTIFICATION-TYPE
            OBJECTS { hwAlarmTrapOrdinalNumber,hwAlarmText,hwAlarmLevel,hwAlarmSigDesc,hwHuaweiUPS5000ERunningIndex,hwHuaweiUPS5000ERunningName,hwUPS5000ESlot,hwUPS5000EPort,hwUPS5000EModbusAddress            }
            STATUS current
            DESCRIPTION
                "This trap is sent to NMS when UPS5000E Equipment (Module) part VII alarm occur."
            ::= { hwHuaweiUPS5000EAlarms 15 }

        hwHuaweiUPS5000EModuleAlarm7ResumeTraps NOTIFICATION-TYPE
            OBJECTS { hwAlarmTrapOrdinalNumber,hwAlarmText,hwAlarmLevel,hwAlarmSigDesc,hwHuaweiUPS5000ERunningIndex,hwHuaweiUPS5000ERunningName,hwUPS5000ESlot,hwUPS5000EPort,hwUPS5000EModbusAddress            }
            STATUS current
            DESCRIPTION
                "This trap is sent to NMS when UPS5000E Equipment (Module) part VII alarm resume."
            ::= { hwHuaweiUPS5000EAlarms 16 }

        hwHuaweiUPS5000EECUAlarmTraps NOTIFICATION-TYPE
            OBJECTS { hwAlarmTrapOrdinalNumber,hwAlarmText,hwAlarmLevel,hwAlarmSigDesc,hwHuaweiUPS5000ERunningIndex,hwHuaweiUPS5000ERunningName,hwUPS5000ESlot,hwUPS5000EPort,hwUPS5000EModbusAddress            }
            STATUS current
            DESCRIPTION
                "This trap is sent to NMS when UPS5000E Equipment (ECU 1 or 2) alarm occur."
            ::= { hwHuaweiUPS5000EAlarms 17 }

        hwHuaweiUPS5000EECUAlarmResumeTraps NOTIFICATION-TYPE
            OBJECTS { hwAlarmTrapOrdinalNumber,hwAlarmText,hwAlarmLevel,hwAlarmSigDesc,hwHuaweiUPS5000ERunningIndex,hwHuaweiUPS5000ERunningName,hwUPS5000ESlot,hwUPS5000EPort,hwUPS5000EModbusAddress            }
            STATUS current
            DESCRIPTION
                "This trap is sent to NMS when UPS5000E Equipment (ECU 1 or 2) alarm resume."
            ::= { hwHuaweiUPS5000EAlarms 18 }

        hwEnvAlarmTraps OBJECT IDENTIFIER ::= { hwMonitorAlarmTrapsPrefix 6 }

        hwEnvGPRSAlarms OBJECT IDENTIFIER ::= { hwEnvAlarmTraps 1 }

        hwEnvGPRSAlarmTraps NOTIFICATION-TYPE
            OBJECTS { hwAlarmTrapOrdinalNumber,hwAlarmText,hwAlarmLevel,hwAlarmSigDesc,hwEnvGPRSId,hwEnvGPRSName            }
            STATUS current
            DESCRIPTION
                "This trap is sent to NMS when GPRS Equipment alarm occur."
            ::= { hwEnvGPRSAlarms 1 }

        hwEnvGPRSAlarmResumeTraps NOTIFICATION-TYPE
            OBJECTS { hwAlarmTrapOrdinalNumber,hwAlarmText,hwAlarmLevel,hwAlarmSigDesc,hwEnvGPRSId,hwEnvGPRSName            }
            STATUS current
            DESCRIPTION
                "This trap is sent to NMS when GPRS Equipment alarm resume."
            ::= { hwEnvGPRSAlarms 2 }

        hwHuaweiTempHumAlarms OBJECT IDENTIFIER ::= { hwEnvAlarmTraps 2 }

        hwHuaweiTempHumAlarmTraps NOTIFICATION-TYPE
            OBJECTS { hwAlarmTrapOrdinalNumber,hwAlarmText,hwAlarmLevel,hwAlarmSigDesc,hwHuaweiTempHumSlotNo,hwHuaweiTempHumPortNo,hwHuaweiTempHumName,hwHuaweiTempHumTemperature,hwHuaweiTempHumHumidity            }
            STATUS current
            DESCRIPTION
                "This trap is sent to NMS when TempHum Equipment alarm occur."
            ::= { hwHuaweiTempHumAlarms 1 }

        hwHuaweiTempHumAlarmResumeTraps NOTIFICATION-TYPE
            OBJECTS { hwAlarmTrapOrdinalNumber,hwAlarmText,hwAlarmLevel,hwAlarmSigDesc,hwHuaweiTempHumSlotNo,hwHuaweiTempHumPortNo,hwHuaweiTempHumName,hwHuaweiTempHumTemperature,hwHuaweiTempHumHumidity            }
            STATUS current
            DESCRIPTION
                "This trap is sent to NMS when TempHum Equipment alarm resume."
            ::= { hwHuaweiTempHumAlarms 2 }

        hwPolymerTempHumAlarms OBJECT IDENTIFIER ::= { hwEnvAlarmTraps 3 }

        hwPolymerTempHumAlarmTraps NOTIFICATION-TYPE
            OBJECTS { hwAlarmTrapOrdinalNumber,hwAlarmText,hwAlarmLevel,hwAlarmSigDesc,hwPolymerTempHumRunningIndex,hwPolymerTempHumSlotNo,hwPolymerTempHumPortNo,hwPolymerTempHumModbusAddr,hwPolymerTempHumName            }
            STATUS current
            DESCRIPTION
                "This trap is sent to NMS when TempHum Equipment alarm occur."
            ::= { hwPolymerTempHumAlarms 1 }

        hwPolymerTempHumAlarmResumeTraps NOTIFICATION-TYPE
            OBJECTS { hwAlarmTrapOrdinalNumber,hwAlarmText,hwAlarmLevel,hwAlarmSigDesc,hwPolymerTempHumRunningIndex,hwPolymerTempHumSlotNo,hwPolymerTempHumPortNo,hwPolymerTempHumModbusAddr,hwPolymerTempHumName            }
            STATUS current
            DESCRIPTION
                "This trap is sent to NMS when TempHum Equipment alarm resume."
            ::= { hwPolymerTempHumAlarms 2 }

        hwNetPointAlarmTraps OBJECT IDENTIFIER ::= { hwMonitorAlarmTrapsPrefix 7 }

        hwNetPointDisconnectedAlarmTraps NOTIFICATION-TYPE
            OBJECTS { hwAlarmTrapOrdinalNumber,hwAlarmText,hwAlarmLevel,hwAlarmSigDesc,hwNetPointName            }
            STATUS current
            DESCRIPTION
                "The Alarm occur, when NetPoint disconnected."
            ::= { hwNetPointAlarmTraps 1 }

        hwNetPointDisconnectedAlarmResumeTraps NOTIFICATION-TYPE
            OBJECTS { hwAlarmTrapOrdinalNumber,hwAlarmText,hwAlarmLevel,hwAlarmSigDesc,hwNetPointName            }
            STATUS current
            DESCRIPTION
                "Resume of disconnected for Netpoint."
            ::= { hwNetPointAlarmTraps 2 }

        hwATSAlarmTraps OBJECT IDENTIFIER ::= { hwMonitorAlarmTrapsPrefix 8 }

        hwOMD800Alarms OBJECT IDENTIFIER ::= { hwATSAlarmTraps 1 }

        hwOMD800AlarmTraps NOTIFICATION-TYPE
            OBJECTS { hwAlarmTrapOrdinalNumber,hwAlarmText,hwAlarmLevel,hwAlarmSigDesc,hwOMD800RunningIndex,hwOMD800RunningName,hwOMD800RunningSlotNo,hwOMD800RunningPortNo,hwOMD800RunningModBusAddr            }
            STATUS current
            DESCRIPTION
                "This trap is sent to NMS when OMD800 Equip alarm occur"
            ::= { hwOMD800Alarms 1 }

        hwOMD800AlarmResumeTraps NOTIFICATION-TYPE
            OBJECTS { hwAlarmTrapOrdinalNumber,hwAlarmText,hwAlarmLevel,hwAlarmSigDesc,hwOMD800RunningIndex,hwOMD800RunningName,hwOMD800RunningSlotNo,hwOMD800RunningPortNo,hwOMD800RunningModBusAddr            }
            STATUS current
            DESCRIPTION
                "This trap is sent to NMS when OMD800 Equip  alarm resume"
            ::= { hwOMD800Alarms 2 }

        hwPDUAlarmTraps OBJECT IDENTIFIER ::= { hwMonitorAlarmTrapsPrefix 9 }

        hwPDU8000SingleAlarms OBJECT IDENTIFIER ::= { hwPDUAlarmTraps 1 }

        hwPDU8000SingleAlarm1Traps NOTIFICATION-TYPE
            OBJECTS { hwAlarmTrapOrdinalNumber,hwAlarmText,hwAlarmLevel,hwAlarmSigDesc,hwPDU8000SingleIndex,hwPDU8000SingleName,hwPDU8000SingleSlotNo,hwPDU8000SinglePortNo,hwPDU8000SingleModbusAddr            }
            STATUS current
            DESCRIPTION
                "When alarms occurs sent to NMS."
            ::= { hwPDU8000SingleAlarms 1 }

        hwPDU8000SingleAlarmResume1Traps NOTIFICATION-TYPE
            OBJECTS { hwAlarmTrapOrdinalNumber,hwAlarmText,hwAlarmLevel,hwAlarmSigDesc,hwPDU8000SingleIndex,hwPDU8000SingleName,hwPDU8000SingleSlotNo,hwPDU8000SinglePortNo,hwPDU8000SingleModbusAddr            }
            STATUS current
            DESCRIPTION
                "When Alarms Resume sent to NMS."
            ::= { hwPDU8000SingleAlarms 2 }

        hwPDU8000SingleAlarm2Traps NOTIFICATION-TYPE
            OBJECTS { hwAlarmTrapOrdinalNumber,hwAlarmText,hwAlarmLevel,hwAlarmSigDesc,hwPDU8000SingleIndex,hwPDU8000SingleName,hwPDU8000SingleSlotNo,hwPDU8000SinglePortNo,hwPDU8000SingleModbusAddr            }
            STATUS current
            DESCRIPTION
                "When alarms occurs sent to NMS."
            ::= { hwPDU8000SingleAlarms 3 }

        hwPDU8000SingleAlarmResume2Traps NOTIFICATION-TYPE
            OBJECTS { hwAlarmTrapOrdinalNumber,hwAlarmText,hwAlarmLevel,hwAlarmSigDesc,hwPDU8000SingleIndex,hwPDU8000SingleName,hwPDU8000SingleSlotNo,hwPDU8000SinglePortNo,hwPDU8000SingleModbusAddr            }
            STATUS current
            DESCRIPTION
                "When Alarms Resume sent to NMS."
            ::= { hwPDU8000SingleAlarms 4 }

        hwPDU8000SingleAlarm3Traps NOTIFICATION-TYPE
            OBJECTS { hwAlarmTrapOrdinalNumber,hwAlarmText,hwAlarmLevel,hwAlarmSigDesc,hwPDU8000SingleIndex,hwPDU8000SingleName,hwPDU8000SingleSlotNo,hwPDU8000SinglePortNo,hwPDU8000SingleModbusAddr            }
            STATUS current
            DESCRIPTION
                "When alarms occurs sent to NMS."
            ::= { hwPDU8000SingleAlarms 5 }

        hwPDU8000SingleAlarmResume3Traps NOTIFICATION-TYPE
            OBJECTS { hwAlarmTrapOrdinalNumber,hwAlarmText,hwAlarmLevel,hwAlarmSigDesc,hwPDU8000SingleIndex,hwPDU8000SingleName,hwPDU8000SingleSlotNo,hwPDU8000SinglePortNo,hwPDU8000SingleModbusAddr            }
            STATUS current
            DESCRIPTION
                "When Alarms Resume sent to NMS."
            ::= { hwPDU8000SingleAlarms 6 }

        hwPDU8000SingleAlarm4Traps NOTIFICATION-TYPE
            OBJECTS { hwAlarmTrapOrdinalNumber,hwAlarmText,hwAlarmLevel,hwAlarmSigDesc,hwPDU8000SingleIndex,hwPDU8000SingleName,hwPDU8000SingleSlotNo,hwPDU8000SinglePortNo,hwPDU8000SingleModbusAddr            }
            STATUS current
            DESCRIPTION
                "When alarms occurs sent to NMS."
            ::= { hwPDU8000SingleAlarms 7 }

        hwPDU8000SingleAlarmResume4Traps NOTIFICATION-TYPE
            OBJECTS { hwAlarmTrapOrdinalNumber,hwAlarmText,hwAlarmLevel,hwAlarmSigDesc,hwPDU8000SingleIndex,hwPDU8000SingleName,hwPDU8000SingleSlotNo,hwPDU8000SinglePortNo,hwPDU8000SingleModbusAddr            }
            STATUS current
            DESCRIPTION
                "When Alarms Resume sent to NMS."
            ::= { hwPDU8000SingleAlarms 8 }

        hwPDU8000DualAlarms OBJECT IDENTIFIER ::= { hwPDUAlarmTraps 2 }

        hwPDU8000DualAlarm1Traps NOTIFICATION-TYPE
            OBJECTS { hwAlarmTrapOrdinalNumber,hwAlarmText,hwAlarmLevel,hwAlarmSigDesc,hwPDU8000TableDualIndex,hwPDU8000DualName,hwPDU8000DualSlotNo,hwPDU8000DualPortNo,hwPDU8000DualModbusAddr            }
            STATUS current
            DESCRIPTION
                "When alarms occurs sent to NMS."
            ::= { hwPDU8000DualAlarms 1 }

        hwPDU8000DualAlarmResume1Traps NOTIFICATION-TYPE
            OBJECTS { hwAlarmTrapOrdinalNumber,hwAlarmText,hwAlarmLevel,hwAlarmSigDesc,hwPDU8000TableDualIndex,hwPDU8000DualName,hwPDU8000DualSlotNo,hwPDU8000DualPortNo,hwPDU8000DualModbusAddr            }
            STATUS current
            DESCRIPTION
                "When Alarms Resume sent to NMS."
            ::= { hwPDU8000DualAlarms 2 }

        hwPDU8000DualAlarm2Traps NOTIFICATION-TYPE
            OBJECTS { hwAlarmTrapOrdinalNumber,hwAlarmText,hwAlarmLevel,hwAlarmSigDesc,hwPDU8000TableDualIndex,hwPDU8000DualName,hwPDU8000DualSlotNo,hwPDU8000DualPortNo,hwPDU8000DualModbusAddr            }
            STATUS current
            DESCRIPTION
                "When alarms occurs sent to NMS."
            ::= { hwPDU8000DualAlarms 3 }

        hwPDU8000DualAlarmResume2Traps NOTIFICATION-TYPE
            OBJECTS { hwAlarmTrapOrdinalNumber,hwAlarmText,hwAlarmLevel,hwAlarmSigDesc,hwPDU8000TableDualIndex,hwPDU8000DualName,hwPDU8000DualSlotNo,hwPDU8000DualPortNo,hwPDU8000DualModbusAddr            }
            STATUS current
            DESCRIPTION
                "When Alarms Resume sent to NMS."
            ::= { hwPDU8000DualAlarms 4 }

        hwPDU8000DualAlarm3Traps NOTIFICATION-TYPE
            OBJECTS { hwAlarmTrapOrdinalNumber,hwAlarmText,hwAlarmLevel,hwAlarmSigDesc,hwPDU8000TableDualIndex,hwPDU8000DualName,hwPDU8000DualSlotNo,hwPDU8000DualPortNo,hwPDU8000DualModbusAddr            }
            STATUS current
            DESCRIPTION
                "When alarms occurs sent to NMS."
            ::= { hwPDU8000DualAlarms 5 }

        hwPDU8000DualAlarmResume3Traps NOTIFICATION-TYPE
            OBJECTS { hwAlarmTrapOrdinalNumber,hwAlarmText,hwAlarmLevel,hwAlarmSigDesc,hwPDU8000TableDualIndex,hwPDU8000DualName,hwPDU8000DualSlotNo,hwPDU8000DualPortNo,hwPDU8000DualModbusAddr            }
            STATUS current
            DESCRIPTION
                "When Alarms Resume sent to NMS."
            ::= { hwPDU8000DualAlarms 6 }

        hwPDU8000DualAlarm4Traps NOTIFICATION-TYPE
            OBJECTS { hwAlarmTrapOrdinalNumber,hwAlarmText,hwAlarmLevel,hwAlarmSigDesc,hwPDU8000TableDualIndex,hwPDU8000DualName,hwPDU8000DualSlotNo,hwPDU8000DualPortNo,hwPDU8000DualModbusAddr            }
            STATUS current
            DESCRIPTION
                "When alarms occurs sent to NMS."
            ::= { hwPDU8000DualAlarms 7 }

        hwPDU8000DualAlarmResume4Traps NOTIFICATION-TYPE
            OBJECTS { hwAlarmTrapOrdinalNumber,hwAlarmText,hwAlarmLevel,hwAlarmSigDesc,hwPDU8000TableDualIndex,hwPDU8000DualName,hwPDU8000DualSlotNo,hwPDU8000DualPortNo,hwPDU8000DualModbusAddr            }
            STATUS current
            DESCRIPTION
                "When Alarms Resume sent to NMS."
            ::= { hwPDU8000DualAlarms 8 }

        hwPDU8000TranformerAlarms OBJECT IDENTIFIER ::= { hwPDUAlarmTraps 3 }

        hwPDU8000TransAlarm1Traps NOTIFICATION-TYPE
            OBJECTS { hwAlarmTrapOrdinalNumber,hwAlarmText,hwAlarmLevel,hwAlarmSigDesc,hwPDU8000TransIndex,hwPDU8000TransName,hwPDU8000TransSlotNo,hwPDU8000TransPortNo,hwPDU8000TransModbusAddr            }
            STATUS current
            DESCRIPTION
                "When alarms occurs sent to NMS."
            ::= { hwPDU8000TranformerAlarms 1 }

        hwPDU8000TransAlarmResume1Traps NOTIFICATION-TYPE
            OBJECTS { hwAlarmTrapOrdinalNumber,hwAlarmText,hwAlarmLevel,hwAlarmSigDesc,hwPDU8000TransIndex,hwPDU8000TransName,hwPDU8000TransSlotNo,hwPDU8000TransPortNo,hwPDU8000TransModbusAddr            }
            STATUS current
            DESCRIPTION
                "When Alarms Resume sent to NMS."
            ::= { hwPDU8000TranformerAlarms 2 }

        hwPDU8000TransAlarm2Traps NOTIFICATION-TYPE
            OBJECTS { hwAlarmTrapOrdinalNumber,hwAlarmText,hwAlarmLevel,hwAlarmSigDesc,hwPDU8000TransIndex,hwPDU8000TransName,hwPDU8000TransSlotNo,hwPDU8000TransPortNo,hwPDU8000TransModbusAddr            }
            STATUS current
            DESCRIPTION
                "When alarms occurs sent to NMS."
            ::= { hwPDU8000TranformerAlarms 3 }

        hwPDU8000TransAlarmResume2Traps NOTIFICATION-TYPE
            OBJECTS { hwAlarmTrapOrdinalNumber,hwAlarmText,hwAlarmLevel,hwAlarmSigDesc,hwPDU8000TransIndex,hwPDU8000TransName,hwPDU8000TransSlotNo,hwPDU8000TransPortNo,hwPDU8000TransModbusAddr            }
            STATUS current
            DESCRIPTION
                "When Alarms Resume sent to NMS."
            ::= { hwPDU8000TranformerAlarms 4 }

        hwPDU8000TransAlarm3Traps NOTIFICATION-TYPE
            OBJECTS { hwAlarmTrapOrdinalNumber,hwAlarmText,hwAlarmLevel,hwAlarmSigDesc,hwPDU8000TransIndex,hwPDU8000TransName,hwPDU8000TransSlotNo,hwPDU8000TransPortNo,hwPDU8000TransModbusAddr            }
            STATUS current
            DESCRIPTION
                "When alarms occurs sent to NMS."
            ::= { hwPDU8000TranformerAlarms 5 }

        hwPDU8000TransAlarmResume3Traps NOTIFICATION-TYPE
            OBJECTS { hwAlarmTrapOrdinalNumber,hwAlarmText,hwAlarmLevel,hwAlarmSigDesc,hwPDU8000TransIndex,hwPDU8000TransName,hwPDU8000TransSlotNo,hwPDU8000TransPortNo,hwPDU8000TransModbusAddr            }
            STATUS current
            DESCRIPTION
                "When Alarms Resume sent to NMS."
            ::= { hwPDU8000TranformerAlarms 6 }

        hwPDU8000TransAlarm4Traps NOTIFICATION-TYPE
            OBJECTS { hwAlarmTrapOrdinalNumber,hwAlarmText,hwAlarmLevel,hwAlarmSigDesc,hwPDU8000TransIndex,hwPDU8000TransName,hwPDU8000TransSlotNo,hwPDU8000TransPortNo,hwPDU8000TransModbusAddr            }
            STATUS current
            DESCRIPTION
                "When alarms occurs sent to NMS."
            ::= { hwPDU8000TranformerAlarms 7 }

        hwPDU8000TransAlarmResume4Traps NOTIFICATION-TYPE
            OBJECTS { hwAlarmTrapOrdinalNumber,hwAlarmText,hwAlarmLevel,hwAlarmSigDesc,hwPDU8000TransIndex,hwPDU8000TransName,hwPDU8000TransSlotNo,hwPDU8000TransPortNo,hwPDU8000TransModbusAddr            }
            STATUS current
            DESCRIPTION
                "When Alarms Resume sent to NMS."
            ::= { hwPDU8000TranformerAlarms 8 }

        hwAccAlarmTraps OBJECT IDENTIFIER ::= { hwMonitorAlarmTrapsPrefix 10 }

        hwNetColAlarms OBJECT IDENTIFIER ::= { hwAccAlarmTraps 1 }

        hwNetColAlarmTraps NOTIFICATION-TYPE
            OBJECTS { hwAlarmTrapOrdinalNumber,hwAlarmText,hwAlarmLevel,hwAlarmSigDesc,hwNetColIndex,hwNetColName,hwNetColSlot,hwNetColPort,hwNetColModbusAddr            }
            STATUS current
            DESCRIPTION
                "This trap is sent to NMS when NetCol Equip alarm occur"
            ::= { hwNetColAlarms 1 }

        hwNetCol5000AAlarmResumeTraps NOTIFICATION-TYPE
            OBJECTS { hwAlarmTrapOrdinalNumber,hwAlarmText,hwAlarmLevel,hwAlarmSigDesc,hwNetColIndex,hwNetColName,hwNetColSlot,hwNetColPort,hwNetColModbusAddr            }
            STATUS current
            DESCRIPTION
                "This trap is sent to NMS when NetCol5000A Equip  alarm resume"
            ::= { hwNetColAlarms 2 }

        hwPD510AlarmTraps OBJECT IDENTIFIER ::= { hwMonitorAlarmTrapsPrefix 11 }

        hwPD510Alarms OBJECT IDENTIFIER ::= { hwPD510AlarmTraps 1 }

        hwPD510AlarmTraps NOTIFICATION-TYPE
            OBJECTS { hwAlarmTrapOrdinalNumber,hwAlarmText,hwAlarmLevel,hwAlarmSigDesc,hwPD510RunningIndex,hwPD510Name,hwPD510CommSlotNo,hwPD510CommPortNo,hwPD510ModbusAddress            }
            STATUS current
            DESCRIPTION
                "This trap is sent to NMS when PD510 Equip alarm occur"
            ::= { hwPD510Alarms 1 }

        hwPD510AlarmResumeTraps NOTIFICATION-TYPE
            OBJECTS { hwAlarmTrapOrdinalNumber,hwAlarmText,hwAlarmLevel,hwAlarmSigDesc,hwPD510RunningIndex,hwPD510Name,hwPD510CommSlotNo,hwPD510CommPortNo,hwPD510ModbusAddress            }
            STATUS current
            DESCRIPTION
                "This trap is sent to NMS when PD510 Equip  alarm resume"
            ::= { hwPD510Alarms 2 }

        hwEA800AlarmTraps OBJECT IDENTIFIER ::= { hwMonitorAlarmTrapsPrefix 12 }

        hwEA800Alarms OBJECT IDENTIFIER ::= { hwEA800AlarmTraps 1 }

        hwEA800AlarmTraps NOTIFICATION-TYPE
            OBJECTS { hwAlarmTrapOrdinalNumber,hwAlarmText,hwAlarmLevel,hwAlarmSigDesc,hwEA800RunningIndex,hwEA800Name,hwEA800CommSlotNo,hwEA800CommPortNo,hwEA800SoftwareVersion            }
            STATUS current
            DESCRIPTION
                "This trap is sent to NMS when EA800 Equip alarm occur"
            ::= { hwEA800Alarms 1 }

        hwEA800AlarmResumeTraps NOTIFICATION-TYPE
            OBJECTS { hwAlarmTrapOrdinalNumber,hwAlarmText,hwAlarmLevel,hwAlarmSigDesc,hwEA800RunningIndex,hwEA800Name,hwEA800CommSlotNo,hwEA800CommPortNo,hwEA800SoftwareVersion            }
            STATUS current
            DESCRIPTION
                "This trap is sent to NMS when EA800 Equip  alarm resume"
            ::= { hwEA800Alarms 2 }

        hwUL33AlarmTraps OBJECT IDENTIFIER ::= { hwMonitorAlarmTrapsPrefix 13 }

        hwUL33Alarms OBJECT IDENTIFIER ::= { hwUL33AlarmTraps 1 }

        hwUL33AlarmTraps NOTIFICATION-TYPE
            OBJECTS { hwAlarmTrapOrdinalNumber,hwAlarmText,hwAlarmLevel,hwAlarmSigDesc,hwUL33RunningIndex,hwUL33Name,hwUL33CommSlotNo,hwUL33CommPortNo,hwUL33ModbusAddress            }
            STATUS current
            DESCRIPTION
                "This trap is sent to NMS when UL33 Equip alarm occur"
            ::= { hwUL33Alarms 1 }

        hwUL33AlarmResumeTraps NOTIFICATION-TYPE
            OBJECTS { hwAlarmTrapOrdinalNumber,hwAlarmText,hwAlarmLevel,hwAlarmSigDesc,hwUL33RunningIndex,hwUL33Name,hwUL33CommSlotNo,hwUL33CommPortNo,hwUL33ModbusAddress            }
            STATUS current
            DESCRIPTION
                "This trap is sent to NMS when UL33 Equip  alarm resume"
            ::= { hwUL33Alarms 2 }

        hwNetPointExtendAlarmTraps OBJECT IDENTIFIER ::= { hwMonitorAlarmTrapsPrefix 14 }

        hwNetPointExtend1DisconnectedAlarmTraps NOTIFICATION-TYPE
            OBJECTS { hwAlarmTrapOrdinalNumber,hwAlarmText,hwAlarmLevel,hwAlarmSigDesc,hwNetPointExtend1Name            }
            STATUS current
            DESCRIPTION
                "The Alarm occur, when NetPoint extend1 disconnected."
            ::= { hwNetPointExtendAlarmTraps 1 }

        hwNetPointExtend1DisconnectedAlarmResumeTraps NOTIFICATION-TYPE
            OBJECTS { hwAlarmTrapOrdinalNumber,hwAlarmText,hwAlarmLevel,hwAlarmSigDesc,hwNetPointExtend1Name            }
            STATUS current
            DESCRIPTION
                "Resume of disconnected for Netpoint extend1."
            ::= { hwNetPointExtendAlarmTraps 2 }

        hwNetPointExtend2DisconnectedAlarmTraps NOTIFICATION-TYPE
            OBJECTS { hwAlarmTrapOrdinalNumber,hwAlarmText,hwAlarmLevel,hwAlarmSigDesc,hwNetPointExtend2Name            }
            STATUS current
            DESCRIPTION
                "The Alarm occur, when NetPoint extend2 disconnected."
            ::= { hwNetPointExtendAlarmTraps 3 }

        hwNetPointExtend2DisconnectedAlarmResumeTraps NOTIFICATION-TYPE
            OBJECTS { hwAlarmTrapOrdinalNumber,hwAlarmText,hwAlarmLevel,hwAlarmSigDesc,hwNetPointExtend2Name            }
            STATUS current
            DESCRIPTION
                "Resume of disconnected for Netpoint extend2."
            ::= { hwNetPointExtendAlarmTraps 4 }

        hwNetPointExtend3DisconnectedAlarmTraps NOTIFICATION-TYPE
            OBJECTS { hwAlarmTrapOrdinalNumber,hwAlarmText,hwAlarmLevel,hwAlarmSigDesc,hwNetPointExtend3Name            }
            STATUS current
            DESCRIPTION
                "The Alarm occur, when NetPoint extend3 disconnected."
            ::= { hwNetPointExtendAlarmTraps 5 }

        hwNetPointExtend3DisconnectedAlarmResumeTraps NOTIFICATION-TYPE
            OBJECTS { hwAlarmTrapOrdinalNumber,hwAlarmText,hwAlarmLevel,hwAlarmSigDesc,hwNetPointExtend3Name            }
            STATUS current
            DESCRIPTION
                "Resume of disconnected for Netpoint extend3."
            ::= { hwNetPointExtendAlarmTraps 6 }

END
