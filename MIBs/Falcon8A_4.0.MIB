--  Title:    FALCON8A.MIB
--  Version:  v4.0
--  Date:     12/06/99 09:31am
--
--  This is the MIB for the Falcon equiped with 20 analog inputs.
--
--  Copyright @ 1998 RLE Technologies.  All rights reserved worldwide.
--
--  This MIB defines objects for the RLE Falcon SNMP Agent.
--

RLE-FALCON-MIB DEFINITIONS ::= BEGIN

IMPORTS
	TruthValue, PositiveInteger
		FROM RFC1253
	DisplayString
		FROM RFC1213-MIB
	OBJECT-TYPE
		FROM RFC-1212
	Counter, enterprises
		FROM RFC1155-SMI;

RLE OBJECT IDENTIFIER ::= { enterprises  3184 }

products   OBJECT IDENTIFIER ::= { RLE  1 }

Falcon   OBJECT IDENTIFIER ::= { products  1 }

FalconMIB OBJECT IDENTIFIER ::= { Falcon 1 }

FalconIdent OBJECT IDENTIFIER ::= { FalconMIB 1 }

FalconIdentManufacturer OBJECT-TYPE
    SYNTAX  DisplayString
    ACCESS  read-only
    STATUS  mandatory
    DESCRIPTION
           "The Monitor Control Unit manufacturer."
    ::= { FalconIdent  1 }

FalconIdentModel OBJECT-TYPE
    SYNTAX  DisplayString
    ACCESS  read-only
    STATUS  mandatory
    DESCRIPTION
           "The Monitor Control Unit Model designation."
    ::= { FalconIdent  2 }

FalconIdentSoftwareVersion OBJECT-TYPE
    SYNTAX  DisplayString
    ACCESS  read-only
    STATUS  mandatory
    DESCRIPTION
           "The Falcon SNMP Agent software version."
    ::= { FalconIdent  3 }

FalconIdentSpecific OBJECT-TYPE
    SYNTAX  OBJECT IDENTIFIER
    ACCESS  read-only
    STATUS  mandatory
    DESCRIPTION
           "A reference to MIB definitions specific to the
            particular Monitor Unit being managed. This
            object is used to locate the product-specific MIB
            for this device.

            If this information is not present, its value
            should be the OBJECT IDENTIFIER { 0 0 },
            which is a syntactically valid object identifier,
            and any conformant implementation of ASN.1 and BER
            must be able to generate and recognize this value."
    ::= { FalconIdent  4 }

FalconSystem OBJECT IDENTIFIER ::= { FalconMIB 2 }

FalconClock OBJECT-TYPE
    SYNTAX  DisplayString
    ACCESS  read-write
    STATUS  mandatory
    DESCRIPTION
           "The Falcon internal clock settings.
            Displayed as MM/DD/YY HH:MM:SS"
    ::= { FalconSystem  1 }

FalconDoorAlarmBypass OBJECT-TYPE
    SYNTAX  INTEGER (-2147483648..2147483647)
    ACCESS  read-write
    STATUS  mandatory
    DESCRIPTION
           "The Falcon door alarm bypass switch.
            This allows the alarm to be bypassed upon valid keypad access.
            Zero disables this, or use 1 thru 8 for the corresponding
            Falcon input."
    ::= { FalconSystem  2 }

FalconKeypad OBJECT IDENTIFIER ::= { FalconSystem 3 }

FalconKeypadCode1 OBJECT-TYPE
    SYNTAX  DisplayString
    ACCESS  read-write
    STATUS  mandatory
    DESCRIPTION
           "The Falcon keypad access code for user #1.
            This can be up to six numberic characters."
    ::= { FalconKeypad  1 }

FalconKeypadName1 OBJECT-TYPE
    SYNTAX  DisplayString
    ACCESS  read-write
    STATUS  mandatory
    DESCRIPTION
           "The Falcon keypad access name for user #1.
            This can be up to 20 characters."
    ::= { FalconKeypad  2 }

FalconKeypadCode2 OBJECT-TYPE
    SYNTAX  DisplayString
    ACCESS  read-write
    STATUS  mandatory
    DESCRIPTION
           "The Falcon keypad access code for user #2.
            This can be up to six numberic characters."
    ::= { FalconKeypad  3 }

FalconKeypadName2 OBJECT-TYPE
    SYNTAX  DisplayString
    ACCESS  read-write
    STATUS  mandatory
    DESCRIPTION
           "The Falcon keypad access name for user #2.
            This can be up to 20 characters."
    ::= { FalconKeypad  4 }

FalconKeypadCode3 OBJECT-TYPE
    SYNTAX  DisplayString
    ACCESS  read-write
    STATUS  mandatory
    DESCRIPTION
           "The Falcon keypad access code for user #3.
            This can be up to six numberic characters."
    ::= { FalconKeypad  5 }

FalconKeypadName3 OBJECT-TYPE
    SYNTAX  DisplayString
    ACCESS  read-write
    STATUS  mandatory
    DESCRIPTION
           "The Falcon keypad access name for user #3.
            This can be up to 20 characters."
    ::= { FalconKeypad  6 }

FalconKeypadCode4 OBJECT-TYPE
    SYNTAX  DisplayString
    ACCESS  read-write
    STATUS  mandatory
    DESCRIPTION
           "The Falcon keypad access code for user #4.
            This can be up to six numberic characters."
    ::= { FalconKeypad  7 }

FalconKeypadName4 OBJECT-TYPE
    SYNTAX  DisplayString
    ACCESS  read-write
    STATUS  mandatory
    DESCRIPTION
           "The Falcon keypad access name for user #4.
            This can be up to 20 characters."
    ::= { FalconKeypad  8 }

FalconKeypadCode5 OBJECT-TYPE
    SYNTAX  DisplayString
    ACCESS  read-write
    STATUS  mandatory
    DESCRIPTION
           "The Falcon keypad access code for user #5.
            This can be up to six numberic characters."
    ::= { FalconKeypad  9 }

FalconKeypadName5 OBJECT-TYPE
    SYNTAX  DisplayString
    ACCESS  read-write
    STATUS  mandatory
    DESCRIPTION
           "The Falcon keypad access name for user #5.
            This can be up to 20 characters."
    ::= { FalconKeypad  10 }

FalconKeypadCode6 OBJECT-TYPE
    SYNTAX  DisplayString
    ACCESS  read-write
    STATUS  mandatory
    DESCRIPTION
           "The Falcon keypad access code for user #6.
            This can be up to six numberic characters."
    ::= { FalconKeypad  11 }

FalconKeypadName6 OBJECT-TYPE
    SYNTAX  DisplayString
    ACCESS  read-write
    STATUS  mandatory
    DESCRIPTION
           "The Falcon keypad access name for user #6.
            This can be up to 20 characters."
    ::= { FalconKeypad  12 }

FalconKeypadCode7 OBJECT-TYPE
    SYNTAX  DisplayString
    ACCESS  read-write
    STATUS  mandatory
    DESCRIPTION
           "The Falcon keypad access code for user #7.
            This can be up to six numberic characters."
    ::= { FalconKeypad  13 }

FalconKeypadName7 OBJECT-TYPE
    SYNTAX  DisplayString
    ACCESS  read-write
    STATUS  mandatory
    DESCRIPTION
           "The Falcon keypad access name for user #7.
            This can be up to 20 characters."
    ::= { FalconKeypad  14 }

FalconKeypadCode8 OBJECT-TYPE
    SYNTAX  DisplayString
    ACCESS  read-write
    STATUS  mandatory
    DESCRIPTION
           "The Falcon keypad access code for user #8.
            This can be up to six numberic characters."
    ::= { FalconKeypad  15 }

FalconKeypadName8 OBJECT-TYPE
    SYNTAX  DisplayString
    ACCESS  read-write
    STATUS  mandatory
    DESCRIPTION
           "The Falcon keypad access name for user #8.
            This can be up to 20 characters."
    ::= { FalconKeypad  16 }

FalconKeypadCode9 OBJECT-TYPE
    SYNTAX  DisplayString
    ACCESS  read-write
    STATUS  mandatory
    DESCRIPTION
           "The Falcon keypad access code for user #9.
            This can be up to six numberic characters."
    ::= { FalconKeypad  17 }

FalconKeypadName9 OBJECT-TYPE
    SYNTAX  DisplayString
    ACCESS  read-write
    STATUS  mandatory
    DESCRIPTION
           "The Falcon keypad access name for user #9.
            This can be up to 20 characters."
    ::= { FalconKeypad  18 }

FalconKeypadCode10 OBJECT-TYPE
    SYNTAX  DisplayString
    ACCESS  read-write
    STATUS  mandatory
    DESCRIPTION
           "The Falcon keypad access code for user #10.
            This can be up to six numberic characters."
    ::= { FalconKeypad  19 }

FalconKeypadName10 OBJECT-TYPE
    SYNTAX  DisplayString
    ACCESS  read-write
    STATUS  mandatory
    DESCRIPTION
           "The Falcon keypad access name for user #10.
            This can be up to 20 characters."
    ::= { FalconKeypad  20 }

FalconKeypadCode11 OBJECT-TYPE
    SYNTAX  DisplayString
    ACCESS  read-write
    STATUS  mandatory
    DESCRIPTION
           "The Falcon keypad access code for user #11.
            This can be up to six numberic characters."
    ::= { FalconKeypad  21 }

FalconKeypadName11 OBJECT-TYPE
    SYNTAX  DisplayString
    ACCESS  read-write
    STATUS  mandatory
    DESCRIPTION
           "The Falcon keypad access name for user #11.
            This can be up to 20 characters."
    ::= { FalconKeypad  22 }

FalconKeypadCode12 OBJECT-TYPE
    SYNTAX  DisplayString
    ACCESS  read-write
    STATUS  mandatory
    DESCRIPTION
           "The Falcon keypad access code for user #12.
            This can be up to six numberic characters."
    ::= { FalconKeypad  23 }

FalconKeypadName12 OBJECT-TYPE
    SYNTAX  DisplayString
    ACCESS  read-write
    STATUS  mandatory
    DESCRIPTION
           "The Falcon keypad access name for user #12.
            This can be up to 20 characters."
    ::= { FalconKeypad  24 }

FalconKeypadCode13 OBJECT-TYPE
    SYNTAX  DisplayString
    ACCESS  read-write
    STATUS  mandatory
    DESCRIPTION
           "The Falcon keypad access code for user #13.
            This can be up to six numberic characters."
    ::= { FalconKeypad  25 }

FalconKeypadName13 OBJECT-TYPE
    SYNTAX  DisplayString
    ACCESS  read-write
    STATUS  mandatory
    DESCRIPTION
           "The Falcon keypad access name for user #13.
            This can be up to 20 characters."
    ::= { FalconKeypad  26 }

FalconKeypadCode14 OBJECT-TYPE
    SYNTAX  DisplayString
    ACCESS  read-write
    STATUS  mandatory
    DESCRIPTION
           "The Falcon keypad access code for user #14.
            This can be up to six numberic characters."
    ::= { FalconKeypad  27 }

FalconKeypadName14 OBJECT-TYPE
    SYNTAX  DisplayString
    ACCESS  read-write
    STATUS  mandatory
    DESCRIPTION
           "The Falcon keypad access name for user #14.
            This can be up to 20 characters."
    ::= { FalconKeypad  28 }

FalconKeypadCode15 OBJECT-TYPE
    SYNTAX  DisplayString
    ACCESS  read-write
    STATUS  mandatory
    DESCRIPTION
           "The Falcon keypad access code for user #15.
            This can be up to six numberic characters."
    ::= { FalconKeypad  29 }

FalconKeypadName15 OBJECT-TYPE
    SYNTAX  DisplayString
    ACCESS  read-write
    STATUS  mandatory
    DESCRIPTION
           "The Falcon keypad access name for user #15.
            This can be up to 20 characters."
    ::= { FalconKeypad  30 }

FalconKeypadCode16 OBJECT-TYPE
    SYNTAX  DisplayString
    ACCESS  read-write
    STATUS  mandatory
    DESCRIPTION
           "The Falcon keypad access code for user #16.
            This can be up to six numberic characters."
    ::= { FalconKeypad  31 }

FalconKeypadName16 OBJECT-TYPE
    SYNTAX  DisplayString
    ACCESS  read-write
    STATUS  mandatory
    DESCRIPTION
           "The Falcon keypad access name for user #16.
            This can be up to 20 characters."
    ::= { FalconKeypad  32 }

FalconKeypadCode17 OBJECT-TYPE
    SYNTAX  DisplayString
    ACCESS  read-write
    STATUS  mandatory
    DESCRIPTION
           "The Falcon keypad access code for user #17.
            This can be up to six numberic characters."
    ::= { FalconKeypad  33 }

FalconKeypadName17 OBJECT-TYPE
    SYNTAX  DisplayString
    ACCESS  read-write
    STATUS  mandatory
    DESCRIPTION
           "The Falcon keypad access name for user #17.
            This can be up to 20 characters."
    ::= { FalconKeypad  34 }

FalconKeypadCode18 OBJECT-TYPE
    SYNTAX  DisplayString
    ACCESS  read-write
    STATUS  mandatory
    DESCRIPTION
           "The Falcon keypad access code for user #18.
            This can be up to six numberic characters."
    ::= { FalconKeypad  35 }

FalconKeypadName18 OBJECT-TYPE
    SYNTAX  DisplayString
    ACCESS  read-write
    STATUS  mandatory
    DESCRIPTION
           "The Falcon keypad access name for user #18.
            This can be up to 20 characters."
    ::= { FalconKeypad  36 }

FalconKeypadCode19 OBJECT-TYPE
    SYNTAX  DisplayString
    ACCESS  read-write
    STATUS  mandatory
    DESCRIPTION
           "The Falcon keypad access code for user #19.
            This can be up to six numberic characters."
    ::= { FalconKeypad  37 }

FalconKeypadName19 OBJECT-TYPE
    SYNTAX  DisplayString
    ACCESS  read-write
    STATUS  mandatory
    DESCRIPTION
           "The Falcon keypad access name for user #19.
            This can be up to 20 characters."
    ::= { FalconKeypad  38 }

FalconKeypadCode20 OBJECT-TYPE
    SYNTAX  DisplayString
    ACCESS  read-write
    STATUS  mandatory
    DESCRIPTION
           "The Falcon keypad access code for user #20.
            This can be up to six numberic characters."
    ::= { FalconKeypad  39 }

FalconKeypadName20 OBJECT-TYPE
    SYNTAX  DisplayString
    ACCESS  read-write
    STATUS  mandatory
    DESCRIPTION
           "The Falcon keypad access name for user #20.
            This can be up to 20 characters."
    ::= { FalconKeypad  40 }

FalconInputVoltage OBJECT-TYPE
    SYNTAX  INTEGER (-2147483648..2147483647)
    ACCESS  read-only
    STATUS  mandatory
    DESCRIPTION
           "The Falcon input voltage (DC Power)."
    ::= { FalconSystem  4 }

FalconOnBattery OBJECT-TYPE
    SYNTAX  INTEGER {
    notInstalled(0),
    Installed(1)
}
    ACCESS  read-write
    STATUS  mandatory
    DESCRIPTION
           "The state of use of the On Battery Alarm. When
            the State is set to installed(1), the On Battery and
            Low Battery alarms are enabled.
            This variable is stored in non-volatile memory."
    ::= { FalconSystem  5 }

FalconLowBatteryThreshold OBJECT-TYPE
    SYNTAX  INTEGER (-2147483648..2147483647)
    ACCESS  read-write
    STATUS  mandatory
    DESCRIPTION
           "The low voltage trip point for the low battery alarm.
            When the input voltage goes below this voltage, the
            Low Battery alarm is set.
            This variable is stored in non-volatile memory."
    ::= { FalconSystem  6 }

FalconAnalogAverage OBJECT-TYPE
    SYNTAX  INTEGER (0..60)
    ACCESS  read-write
    STATUS  mandatory
    DESCRIPTION
           "This is the analog averaging duration in seconds.
            The analog input readings are averaged for this time
            period before updating. This value must be set to
            1,2,3,4,5,6,10,15,20,30 or 60 seconds.
            This variable is stored in non-volatile memory."
    ::= { FalconSystem  7 }

FalconInputs OBJECT IDENTIFIER ::= { FalconMIB  3 }

FalconInput1 OBJECT IDENTIFIER ::= { FalconInputs 1 }

FalconInput1State OBJECT-TYPE
    SYNTAX  INTEGER {
    notInstalled(1),
    Analog_4to20_Installed(2),
    Digital_NO_Installed(3),
    Digital_NC_Installed(4)
}
    ACCESS  read-write
    STATUS  mandatory
    DESCRIPTION
           "The state of use of Input1. When a sensor is
            connected to Input1 set State to installed(2) to
            indicate that the value of FalconReading1 is valid.
            When no sensor is connected to Input1 set
            State to notInstalled(1) to indicate that the value of
            FalconReading1 may not be valid.
            This variable is stored in non-volatile memory."
    ::= { FalconInput1  1 }

FalconInput1Reading OBJECT-TYPE
    SYNTAX  INTEGER (-2147483648..2147483647)
    ACCESS  read-only
    STATUS  mandatory
    DESCRIPTION
           "The reading for sensor 1.
            If the input is digital, the reading will be 1 (active) or
            0 (inactive)"
    ::= { FalconInput1  2 }

FalconInput1Gain OBJECT-TYPE
    SYNTAX  INTEGER (-2147483648..2147483647)
    ACCESS  read-write
    STATUS  mandatory
    DESCRIPTION
           "A correction gain associated with the sensor variable.
            The value of gain is multiplied by the value from
            Input Sensor Number 1 to obtain the value of
            the Input1 variable. The gain variable is stored in
            non-volatile memory."
    ::= { FalconInput1  3 }

FalconInput1Offset OBJECT-TYPE
    SYNTAX  INTEGER (-2147483648..2147483647)
    ACCESS  read-write
    STATUS  mandatory
    DESCRIPTION
           "A correction Offset associated with the sensor variable.
            The value of Offset is added to the value from
            Input Sensor Number 1 to obtain the value of
            the Input1 variable. The Offset variable is stored in
            non-volatile memory."
    ::= { FalconInput1  4 }

FalconInput1Label OBJECT-TYPE
    SYNTAX  DisplayString
    ACCESS  read-write
    STATUS  mandatory
    DESCRIPTION
           "A user-defined text string associated with Input1.
            The text string is stored in non-volatile memory."
    ::= { FalconInput1  5 }

FalconInput1UOM OBJECT-TYPE
    SYNTAX  DisplayString
    ACCESS  read-write
    STATUS  mandatory
    DESCRIPTION
           "A user-defined text string associated with Input1.
            The text string is stored in non-volatile memory."
    ::= { FalconInput1  6 }

FalconInput1HighLimit2 OBJECT-TYPE
    SYNTAX  INTEGER (-2147483648..2147483647)
    ACCESS  read-write
    STATUS  mandatory
    DESCRIPTION
           "When Input1 reaches or exceeds this value a trap will
            be generated signifying a high alarm condition at
            sensor 1.
            The HighLimit2 variable is stored in non-volatile memory."
    ::= { FalconInput1  7 }

FalconInput1HighLimit OBJECT-TYPE
    SYNTAX  INTEGER (-2147483648..2147483647)
    ACCESS  read-write
    STATUS  mandatory
    DESCRIPTION
           "When Input1 reaches or exceeds this value a trap will
            be generated signifying a high alarm condition at
            sensor 1.
            The HighLimit variable is stored in non-volatile memory."
    ::= { FalconInput1  8 }

FalconInput1LowLimit OBJECT-TYPE
    SYNTAX  INTEGER (-2147483648..2147483647)
    ACCESS  read-write
    STATUS  mandatory
    DESCRIPTION
           "When Input1 reaches or goes below this value a trap will
            be generated signifying a low alarm condition at sensor 1.
            The LowLimit variable is stored in non-volatile memory."
    ::= { FalconInput1  9 }

FalconInput1LowLimit2 OBJECT-TYPE
    SYNTAX  INTEGER (-2147483648..2147483647)
    ACCESS  read-write
    STATUS  mandatory
    DESCRIPTION
           "When Input1 reaches or goes below this value a trap will
            be generated signifying a low alarm condition at sensor 1.
            The LowLimit variable is stored in non-volatile memory."
    ::= { FalconInput1  10 }

FalconInput1RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { FalconInput1  11 }

FalconInput1Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { FalconInput1  12 }

FalconInput1Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { FalconInput1  13 }

FalconInput2 OBJECT IDENTIFIER ::= { FalconInputs 2 }

FalconInput2State OBJECT-TYPE
    SYNTAX  INTEGER {
    notInstalled(1),
    Analog_4to20_Installed(2),
    Digital_NO_Installed(3),
    Digital_NC_Installed(4)
}
    ACCESS  read-write
    STATUS  mandatory
    DESCRIPTION
           "The state of use of Input2. When a sensor is
            connected to Input2 set State to installed(2) to
            indicate that the value of FalconReading2 is valid.
            When no sensor is connected to Input2 set
            State to notInstalled(1) to indicate that the value of
            FalconReading2 may not be valid.
            This variable is stored in non-volatile memory."
    ::= { FalconInput2  1 }

FalconInput2Reading OBJECT-TYPE
    SYNTAX  INTEGER (-2147483648..2147483647)
    ACCESS  read-only
    STATUS  mandatory
    DESCRIPTION
           "The reading for sensor 2.
            If the input is digital, the reading will be 1 (active) or
            0 (inactive)"
    ::= { FalconInput2  2 }

FalconInput2Gain OBJECT-TYPE
    SYNTAX  INTEGER (-2147483648..2147483647)
    ACCESS  read-write
    STATUS  mandatory
    DESCRIPTION
           "A correction gain associated with the sensor variable.
            The value of gain is multiplied by the value from
            Input Sensor Number 2 to obtain the value of
            the Input2 variable. The gain variable is stored in
            non-volatile memory."
    ::= { FalconInput2  3 }

FalconInput2Offset OBJECT-TYPE
    SYNTAX  INTEGER (-2147483648..2147483647)
    ACCESS  read-write
    STATUS  mandatory
    DESCRIPTION
           "A correction Offset associated with the sensor variable.
            The value of Offset is added to the value from
            Input Sensor Number 2 to obtain the value of
            the Input2 variable. The Offset variable is stored in
            non-volatile memory."
    ::= { FalconInput2  4 }

FalconInput2Label OBJECT-TYPE
    SYNTAX  DisplayString
    ACCESS  read-write
    STATUS  mandatory
    DESCRIPTION
           "A user-defined text string associated with Input2.
            The text string is stored in non-volatile memory."
    ::= { FalconInput2  5 }

FalconInput2UOM OBJECT-TYPE
    SYNTAX  DisplayString
    ACCESS  read-write
    STATUS  mandatory
    DESCRIPTION
           "A user-defined text string associated with Input2.
            The text string is stored in non-volatile memory."
    ::= { FalconInput2  6 }

FalconInput2HighLimit2 OBJECT-TYPE
    SYNTAX  INTEGER (-2147483648..2147483647)
    ACCESS  read-write
    STATUS  mandatory
    DESCRIPTION
           "When input 2 reaches or exceeds this value a trap will
            be generated signifying a high alarm condition at
            sensor 2.
            The HighLimit variable is stored in non-volatile memory."
    ::= { FalconInput2  7 }

FalconInput2HighLimit OBJECT-TYPE
    SYNTAX  INTEGER (-2147483648..2147483647)
    ACCESS  read-write
    STATUS  mandatory
    DESCRIPTION
           "When input 2 reaches or exceeds this value a trap will
            be generated signifying a high alarm condition at
            sensor 2.
            The HighLimit variable is stored in non-volatile memory."
    ::= { FalconInput2  8 }

FalconInput2LowLimit OBJECT-TYPE
    SYNTAX  INTEGER (-2147483648..2147483647)
    ACCESS  read-write
    STATUS  mandatory
    DESCRIPTION
           "When input 2 reaches or goes below this value a trap will
            be generated signifying a low alarm condition at sensor 2.
            The LowLimit variable is stored in non-volatile memory."
    ::= { FalconInput2  9 }

FalconInput2LowLimit2 OBJECT-TYPE
    SYNTAX  INTEGER (-2147483648..2147483647)
    ACCESS  read-write
    STATUS  mandatory
    DESCRIPTION
           "When input 2 reaches or goes below this value a trap will
            be generated signifying a low alarm condition at sensor 2.
            The LowLimit variable is stored in non-volatile memory."
    ::= { FalconInput2  10 }

FalconInput2RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { FalconInput2  11 }

FalconInput2Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { FalconInput2  12 }

FalconInput2Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { FalconInput2  13 }

FalconInput3 OBJECT IDENTIFIER ::= { FalconInputs 3 }

FalconInput3State OBJECT-TYPE
    SYNTAX  INTEGER {
    notInstalled(1),
    Analog_4to20_Installed(2),
    Digital_NO_Installed(3),
    Digital_NC_Installed(4)
}
    ACCESS  read-write
    STATUS  mandatory
    DESCRIPTION
           "The state of use of Input3. When a sensor is
            connected to Input3 set State to installed(2) to
            indicate that the value of FalconReading3 is valid.
            When no sensor is connected to Input3 set
            State to notInstalled(1) to indicate that the value of
            FalconReading3 may not be valid.
            This variable is stored in non-volatile memory."
    ::= { FalconInput3  1 }

FalconInput3Reading OBJECT-TYPE
    SYNTAX  INTEGER (-2147483648..2147483647)
    ACCESS  read-only
    STATUS  mandatory
    DESCRIPTION
           "The reading for sensor 3.
            If the input is digital, the reading will be 1 (active) or
            0 (inactive)"
    ::= { FalconInput3  2 }

FalconInput3Gain OBJECT-TYPE
    SYNTAX  INTEGER (-2147483648..2147483647)
    ACCESS  read-write
    STATUS  mandatory
    DESCRIPTION
           "A correction gain associated with the sensor variable.
            The value of gain is multiplied by the value from
            Input Sensor Number 3 to obtain the value of
            the Input3 variable. The gain variable is stored in
            non-volatile memory."
    ::= { FalconInput3  3 }

FalconInput3Offset OBJECT-TYPE
    SYNTAX  INTEGER (-2147483648..2147483647)
    ACCESS  read-write
    STATUS  mandatory
    DESCRIPTION
           "A correction Offset associated with the sensor variable.
            The value of Offset is added to the value from
            Input Sensor Number 3 to obtain the value of
            the Input3 variable. The Offset variable is stored in
            non-volatile memory."
    ::= { FalconInput3  4 }

FalconInput3Label OBJECT-TYPE
    SYNTAX  DisplayString
    ACCESS  read-write
    STATUS  mandatory
    DESCRIPTION
           "A user-defined text string associated with Input3.
            The text string is stored in non-volatile memory."
    ::= { FalconInput3  5 }

FalconInput3UOM OBJECT-TYPE
    SYNTAX  DisplayString
    ACCESS  read-write
    STATUS  mandatory
    DESCRIPTION
           "A user-defined text string associated with Input3.
            The text string is stored in non-volatile memory."
    ::= { FalconInput3  6 }

FalconInput3HighLimit2 OBJECT-TYPE
    SYNTAX  INTEGER (-2147483648..2147483647)
    ACCESS  read-write
    STATUS  mandatory
    DESCRIPTION
           "When input 3 reaches or exceeds this value a trap will
            be generated signifying a high alarm condition at
            sensor 3.
            The HighLimit variable is stored in non-volatile memory."
    ::= { FalconInput3  7 }

FalconInput3HighLimit OBJECT-TYPE
    SYNTAX  INTEGER (-2147483648..2147483647)
    ACCESS  read-write
    STATUS  mandatory
    DESCRIPTION
           "When input 3 reaches or exceeds this value a trap will
            be generated signifying a high alarm condition at
            sensor 3.
            The HighLimit variable is stored in non-volatile memory."
    ::= { FalconInput3  8 }

FalconInput3LowLimit OBJECT-TYPE
    SYNTAX  INTEGER (-2147483648..2147483647)
    ACCESS  read-write
    STATUS  mandatory
    DESCRIPTION
           "When input 3 reaches or goes below this value a trap will
            be generated signifying a low alarm condition at sensor 3.
            The LowLimit variable is stored in non-volatile memory."
    ::= { FalconInput3  9 }

FalconInput3LowLimit2 OBJECT-TYPE
    SYNTAX  INTEGER (-2147483648..2147483647)
    ACCESS  read-write
    STATUS  mandatory
    DESCRIPTION
           "When input 3 reaches or goes below this value a trap will
            be generated signifying a low alarm condition at sensor 3.
            The LowLimit variable is stored in non-volatile memory."
    ::= { FalconInput3  10 }

FalconInput3RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { FalconInput3  11 }

FalconInput3Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { FalconInput3  12 }

FalconInput3Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { FalconInput3  13 }

FalconInput4 OBJECT IDENTIFIER ::= { FalconInputs 4 }

FalconInput4State OBJECT-TYPE
    SYNTAX  INTEGER {
    notInstalled(1),
    Analog_4to20_Installed(2),
    Digital_NO_Installed(3),
    Digital_NC_Installed(4)
}
    ACCESS  read-write
    STATUS  mandatory
    DESCRIPTION
           "The state of use of Input4. When a sensor is
            connected to Input4 set State to installed(2) to
            indicate that the value of FalconReading4 is valid.
            When no sensor is connected to Input4 set
            State to notInstalled(1) to indicate that the value of
            FalconReading4 may not be valid.
            This variable is stored in non-volatile memory."
    ::= { FalconInput4  1 }

FalconInput4Reading OBJECT-TYPE
    SYNTAX  INTEGER (-2147483648..2147483647)
    ACCESS  read-only
    STATUS  mandatory
    DESCRIPTION
           "The reading for sensor 4.
            If the input is digital, the reading will be 1 (active) or
            0 (inactive)"
    ::= { FalconInput4  2 }

FalconInput4Gain OBJECT-TYPE
    SYNTAX  INTEGER (-2147483648..2147483647)
    ACCESS  read-write
    STATUS  mandatory
    DESCRIPTION
           "A correction gain associated with the sensor variable.
            The value of gain is multiplied by the value from
            Input Sensor Number 4 to obtain the value of
            the Input4 variable. The gain variable is stored in
            non-volatile memory."
    ::= { FalconInput4  3 }

FalconInput4Offset OBJECT-TYPE
    SYNTAX  INTEGER (-2147483648..2147483647)
    ACCESS  read-write
    STATUS  mandatory
    DESCRIPTION
           "A correction Offset associated with the sensor variable.
            The value of Offset is added to the value from
            Input Sensor Number 4 to obtain the value of
            the Input4 variable. The Offset variable is stored in
            non-volatile memory."
    ::= { FalconInput4  4 }

FalconInput4Label OBJECT-TYPE
    SYNTAX  DisplayString
    ACCESS  read-write
    STATUS  mandatory
    DESCRIPTION
           "A user-defined text string associated with Input4.
            The text string is stored in non-volatile memory."
    ::= { FalconInput4  5 }

FalconInput4UOM OBJECT-TYPE
    SYNTAX  DisplayString
    ACCESS  read-write
    STATUS  mandatory
    DESCRIPTION
           "A user-defined text string associated with Input4.
            The text string is stored in non-volatile memory."
    ::= { FalconInput4  6 }

FalconInput4HighLimit2 OBJECT-TYPE
    SYNTAX  INTEGER (-2147483648..2147483647)
    ACCESS  read-write
    STATUS  mandatory
    DESCRIPTION
           "When input 4 reaches or exceeds this value a trap will
            be generated signifying a high alarm condition at
            sensor 4.
            The HighLimit variable is stored in non-volatile memory."
    ::= { FalconInput4  7 }

FalconInput4HighLimit OBJECT-TYPE
    SYNTAX  INTEGER (-2147483648..2147483647)
    ACCESS  read-write
    STATUS  mandatory
    DESCRIPTION
           "When input 4 reaches or exceeds this value a trap will
            be generated signifying a high alarm condition at
            sensor 4.
            The HighLimit variable is stored in non-volatile memory."
    ::= { FalconInput4  8 }

FalconInput4LowLimit OBJECT-TYPE
    SYNTAX  INTEGER (-2147483648..2147483647)
    ACCESS  read-write
    STATUS  mandatory
    DESCRIPTION
           "When input 4 reaches or goes below this value a trap will
            be generated signifying a low alarm condition at sensor 4.
            The LowLimit variable is stored in non-volatile memory."
    ::= { FalconInput4  9 }

FalconInput4LowLimit2 OBJECT-TYPE
    SYNTAX  INTEGER (-2147483648..2147483647)
    ACCESS  read-write
    STATUS  mandatory
    DESCRIPTION
           "When input 4 reaches or goes below this value a trap will
            be generated signifying a low alarm condition at sensor 4.
            The LowLimit variable is stored in non-volatile memory."
    ::= { FalconInput4  10 }

FalconInput4RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { FalconInput4  11 }

FalconInput4Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { FalconInput4  12 }

FalconInput4Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { FalconInput4  13 }

FalconInput5 OBJECT IDENTIFIER ::= { FalconInputs 5 }

FalconInput5State OBJECT-TYPE
    SYNTAX  INTEGER {
    notInstalled(1),
    Analog_4to20_Installed(2),
    Digital_NO_Installed(3),
    Digital_NC_Installed(4)
}
    ACCESS  read-write
    STATUS  mandatory
    DESCRIPTION
           "The state of use of Input5. When a sensor is
            connected to Input5 set State to installed(2) to
            indicate that the value of FalconReading4 is valid.
            When no sensor is connected to Input5 set
            State to notInstalled(1) to indicate that the value of
            FalconReading5 may not be valid.
            This variable is stored in non-volatile memory."
    ::= { FalconInput5  1 }

FalconInput5Reading OBJECT-TYPE
    SYNTAX  INTEGER (-2147483648..2147483647)
    ACCESS  read-only
    STATUS  mandatory
    DESCRIPTION
           "The reading for sensor 5.
            If the input is digital, the reading will be 1 (active) or
            0 (inactive)"
    ::= { FalconInput5  2 }

FalconInput5Gain OBJECT-TYPE
    SYNTAX  INTEGER (-2147483648..2147483647)
    ACCESS  read-write
    STATUS  mandatory
    DESCRIPTION
           "A correction gain associated with the sensor variable.
            The value of gain is multiplied by the value from
            Input Sensor Number 5 to obtain the value of
            the Input5 variable. The gain variable is stored in
            non-volatile memory."
    ::= { FalconInput5  3 }

FalconInput5Offset OBJECT-TYPE
    SYNTAX  INTEGER (-2147483648..2147483647)
    ACCESS  read-write
    STATUS  mandatory
    DESCRIPTION
           "A correction Offset associated with the sensor variable.
            The value of Offset is added to the value from
            Input Sensor Number 5 to obtain the value of
            the Input5 variable. The Offset variable is stored in
            non-volatile memory."
    ::= { FalconInput5  4 }

FalconInput5Label OBJECT-TYPE
    SYNTAX  DisplayString
    ACCESS  read-write
    STATUS  mandatory
    DESCRIPTION
           "A user-defined text string associated with Input5.
            The text string is stored in non-volatile memory."
    ::= { FalconInput5  5 }

FalconInput5UOM OBJECT-TYPE
    SYNTAX  DisplayString
    ACCESS  read-write
    STATUS  mandatory
    DESCRIPTION
           "A user-defined text string associated with Input5.
            The text string is stored in non-volatile memory."
    ::= { FalconInput5  6 }

FalconInput5HighLimit2 OBJECT-TYPE
    SYNTAX  INTEGER (-2147483648..2147483647)
    ACCESS  read-write
    STATUS  mandatory
    DESCRIPTION
           "When input 5 reaches or exceeds this value a trap will
            be generated signifying a high alarm condition at
            sensor 5.
            The HighLimit variable is stored in non-volatile memory."
    ::= { FalconInput5  7 }

FalconInput5HighLimit OBJECT-TYPE
    SYNTAX  INTEGER (-2147483648..2147483647)
    ACCESS  read-write
    STATUS  mandatory
    DESCRIPTION
           "When input 5 reaches or exceeds this value a trap will
            be generated signifying a high alarm condition at
            sensor 5.
            The HighLimit variable is stored in non-volatile memory."
    ::= { FalconInput5  8 }

FalconInput5LowLimit OBJECT-TYPE
    SYNTAX  INTEGER (-2147483648..2147483647)
    ACCESS  read-write
    STATUS  mandatory
    DESCRIPTION
           "When input 5 reaches or goes below this value a trap will
            be generated signifying a low alarm condition at sensor 5.
            The LowLimit variable is stored in non-volatile memory."
    ::= { FalconInput5  9 }

FalconInput5LowLimit2 OBJECT-TYPE
    SYNTAX  INTEGER (-2147483648..2147483647)
    ACCESS  read-write
    STATUS  mandatory
    DESCRIPTION
           "When input 5 reaches or goes below this value a trap will
            be generated signifying a low alarm condition at sensor 5.
            The LowLimit variable is stored in non-volatile memory."
    ::= { FalconInput5  10 }

FalconInput5RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { FalconInput5  11 }

FalconInput5Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { FalconInput5  12 }

FalconInput5Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { FalconInput5  13 }

FalconInput6 OBJECT IDENTIFIER ::= { FalconInputs 6 }

FalconInput6State OBJECT-TYPE
    SYNTAX  INTEGER {
    notInstalled(1),
    Analog_4to20_Installed(2),
    Digital_NO_Installed(3),
    Digital_NC_Installed(4)
}
    ACCESS  read-write
    STATUS  mandatory
    DESCRIPTION
           "The state of use of Input6. When a sensor is
            connected to Input6 set State to installed(2) to
            indicate that the value of FalconReading6 is valid.
            When no sensor is connected to Input6 set
            State to notInstalled(1) to indicate that the value of
            FalconReading6 may not be valid.
            This variable is stored in non-volatile memory."
    ::= { FalconInput6  1 }

FalconInput6Reading OBJECT-TYPE
    SYNTAX  INTEGER (-2147483648..2147483647)
    ACCESS  read-only
    STATUS  mandatory
    DESCRIPTION
           "The reading for sensor 6.
            If the input is digital, the reading will be 1 (active) or
            0 (inactive)"
    ::= { FalconInput6  2 }

FalconInput6Gain OBJECT-TYPE
    SYNTAX  INTEGER (-2147483648..2147483647)
    ACCESS  read-write
    STATUS  mandatory
    DESCRIPTION
           "A correction gain associated with the sensor variable.
            The value of gain is multiplied by the value from
            Input Sensor Number 6 to obtain the value of
            the Input6 variable. The gain variable is stored in
            non-volatile memory."
    ::= { FalconInput6  3 }

FalconInput6Offset OBJECT-TYPE
    SYNTAX  INTEGER (-2147483648..2147483647)
    ACCESS  read-write
    STATUS  mandatory
    DESCRIPTION
           "A correction Offset associated with the sensor variable.
            The value of Offset is added to the value from
            Input Sensor Number 6 to obtain the value of
            the Input6 variable. The Offset variable is stored in
            non-volatile memory."
    ::= { FalconInput6  4 }

FalconInput6Label OBJECT-TYPE
    SYNTAX  DisplayString
    ACCESS  read-write
    STATUS  mandatory
    DESCRIPTION
           "A user-defined text string associated with Input6.
            The text string is stored in non-volatile memory."
    ::= { FalconInput6  5 }

FalconInput6UOM OBJECT-TYPE
    SYNTAX  DisplayString
    ACCESS  read-write
    STATUS  mandatory
    DESCRIPTION
           "A user-defined text string associated with Input6.
            The text string is stored in non-volatile memory."
    ::= { FalconInput6  6 }

FalconInput6HighLimit2 OBJECT-TYPE
    SYNTAX  INTEGER (-2147483648..2147483647)
    ACCESS  read-write
    STATUS  mandatory
    DESCRIPTION
           "When input 6 reaches or exceeds this value a trap will
            be generated signifying a high alarm condition at
            sensor 6.
            The HighLimit variable is stored in non-volatile memory."
    ::= { FalconInput6  7 }

FalconInput6HighLimit OBJECT-TYPE
    SYNTAX  INTEGER (-2147483648..2147483647)
    ACCESS  read-write
    STATUS  mandatory
    DESCRIPTION
           "When input 6 reaches or exceeds this value a trap will
            be generated signifying a high alarm condition at
            sensor 6.
            The HighLimit variable is stored in non-volatile memory."
    ::= { FalconInput6  8 }

FalconInput6LowLimit OBJECT-TYPE
    SYNTAX  INTEGER (-2147483648..2147483647)
    ACCESS  read-write
    STATUS  mandatory
    DESCRIPTION
           "When input 6 reaches or goes below this value a trap will
            be generated signifying a low alarm condition at sensor 6.
            The LowLimit variable is stored in non-volatile memory."
    ::= { FalconInput6  9 }

FalconInput6LowLimit2 OBJECT-TYPE
    SYNTAX  INTEGER (-2147483648..2147483647)
    ACCESS  read-write
    STATUS  mandatory
    DESCRIPTION
           "When input 6 reaches or goes below this value a trap will
            be generated signifying a low alarm condition at sensor 6.
            The LowLimit variable is stored in non-volatile memory."
    ::= { FalconInput6  10 }

FalconInput6RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { FalconInput6  11 }

FalconInput6Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { FalconInput6  12 }

FalconInput6Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { FalconInput6  13 }

FalconInput7 OBJECT IDENTIFIER ::= { FalconInputs 7 }

FalconInput7State OBJECT-TYPE
    SYNTAX  INTEGER {
    notInstalled(1),
    Analog_4to20_Installed(2),
    Digital_NO_Installed(3),
    Digital_NC_Installed(4)
}
    ACCESS  read-write
    STATUS  mandatory
    DESCRIPTION
           "The state of use of Input7. When a sensor is
            connected to Input7 set State to installed(2) to
            indicate that the value of FalconReading4 is valid.
            When no sensor is connected to Input7 set
            State to notInstalled(1) to indicate that the value of
            FalconReading7 may not be valid.
            This variable is stored in non-volatile memory."
    ::= { FalconInput7  1 }

FalconInput7Reading OBJECT-TYPE
    SYNTAX  INTEGER (-2147483648..2147483647)
    ACCESS  read-only
    STATUS  mandatory
    DESCRIPTION
           "The reading for sensor 7.
            If the input is digital, the reading will be 1 (active) or
            0 (inactive)"
    ::= { FalconInput7  2 }

FalconInput7Gain OBJECT-TYPE
    SYNTAX  INTEGER (-2147483648..2147483647)
    ACCESS  read-write
    STATUS  mandatory
    DESCRIPTION
           "A correction gain associated with the sensor variable.
            The value of gain is multiplied by the value from
            Input Sensor Number 7 to obtain the value of
            the Input7 variable. The gain variable is stored in
            non-volatile memory."
    ::= { FalconInput7  3 }

FalconInput7Offset OBJECT-TYPE
    SYNTAX  INTEGER (-2147483648..2147483647)
    ACCESS  read-write
    STATUS  mandatory
    DESCRIPTION
           "A correction Offset associated with the sensor variable.
            The value of Offset is added to the value from
            Input Sensor Number 7 to obtain the value of
            the Input7 variable. The Offset variable is stored in
            non-volatile memory."
    ::= { FalconInput7  4 }

FalconInput7Label OBJECT-TYPE
    SYNTAX  DisplayString
    ACCESS  read-write
    STATUS  mandatory
    DESCRIPTION
           "A user-defined text string associated with Input7.
            The text string is stored in non-volatile memory."
    ::= { FalconInput7  5 }

FalconInput7UOM OBJECT-TYPE
    SYNTAX  DisplayString
    ACCESS  read-write
    STATUS  mandatory
    DESCRIPTION
           "A user-defined text string associated with Input7.
            The text string is stored in non-volatile memory."
    ::= { FalconInput7  6 }

FalconInput7HighLimit2 OBJECT-TYPE
    SYNTAX  INTEGER (-2147483648..2147483647)
    ACCESS  read-write
    STATUS  mandatory
    DESCRIPTION
           "When input 7 reaches or exceeds this value a trap will
            be generated signifying a high alarm condition at
            sensor 7.
            The HighLimit variable is stored in non-volatile memory."
    ::= { FalconInput7  7 }

FalconInput7HighLimit OBJECT-TYPE
    SYNTAX  INTEGER (-2147483648..2147483647)
    ACCESS  read-write
    STATUS  mandatory
    DESCRIPTION
           "When input 7 reaches or exceeds this value a trap will
            be generated signifying a high alarm condition at
            sensor 7.
            The HighLimit variable is stored in non-volatile memory."
    ::= { FalconInput7  8 }

FalconInput7LowLimit OBJECT-TYPE
    SYNTAX  INTEGER (-2147483648..2147483647)
    ACCESS  read-write
    STATUS  mandatory
    DESCRIPTION
           "When input 7 reaches or goes below this value a trap will
            be generated signifying a low alarm condition at sensor 7.
            The LowLimit variable is stored in non-volatile memory."
    ::= { FalconInput7  9 }

FalconInput7LowLimit2 OBJECT-TYPE
    SYNTAX  INTEGER (-2147483648..2147483647)
    ACCESS  read-write
    STATUS  mandatory
    DESCRIPTION
           "When input 7 reaches or goes below this value a trap will
            be generated signifying a low alarm condition at sensor 7.
            The LowLimit variable is stored in non-volatile memory."
    ::= { FalconInput7  10 }

FalconInput7RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { FalconInput7  11 }

FalconInput7Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { FalconInput7  12 }

FalconInput7Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { FalconInput7  13 }

FalconInput8 OBJECT IDENTIFIER ::= { FalconInputs 8 }

FalconInput8State OBJECT-TYPE
    SYNTAX  INTEGER {
    notInstalled(1),
    Analog_4to20_Installed(2),
    Digital_NO_Installed(3),
    Digital_NC_Installed(4)
}
    ACCESS  read-write
    STATUS  mandatory
    DESCRIPTION
           "The state of use of Input8. When a sensor is
            connected to Input8 set State to installed(2) to
            indicate that the value of FalconReading8 is valid.
            When no sensor is connected to Input8 set
            State to notInstalled(1) to indicate that the value of
            FalconReading8 may not be valid.
            This variable is stored in non-volatile memory."
    ::= { FalconInput8  1 }

FalconInput8Reading OBJECT-TYPE
    SYNTAX  INTEGER (-2147483648..2147483647)
    ACCESS  read-only
    STATUS  mandatory
    DESCRIPTION
           "The reading for sensor 8.
            If the input is digital, the reading will be 1 (active) or
            0 (inactive)"
    ::= { FalconInput8  2 }

FalconInput8Gain OBJECT-TYPE
    SYNTAX  INTEGER (-2147483648..2147483647)
    ACCESS  read-write
    STATUS  mandatory
    DESCRIPTION
           "A correction gain associated with the sensor variable.
            The value of gain is multiplied by the value from
            Input Sensor Number 8 to obtain the value of
            the Input8 variable. The gain variable is stored in
            non-volatile memory."
    ::= { FalconInput8  3 }

FalconInput8Offset OBJECT-TYPE
    SYNTAX  INTEGER (-2147483648..2147483647)
    ACCESS  read-write
    STATUS  mandatory
    DESCRIPTION
           "A correction Offset associated with the sensor variable.
            The value of Offset is added to the value from
            Input Sensor Number 8 to obtain the value of
            the Input8 variable. The Offset variable is stored in
            non-volatile memory."
    ::= { FalconInput8  4 }

FalconInput8Label OBJECT-TYPE
    SYNTAX  DisplayString
    ACCESS  read-write
    STATUS  mandatory
    DESCRIPTION
           "A user-defined text string associated with Input8.
            The text string is stored in non-volatile memory."
    ::= { FalconInput8  5 }

FalconInput8UOM OBJECT-TYPE
    SYNTAX  DisplayString
    ACCESS  read-write
    STATUS  mandatory
    DESCRIPTION
           "A user-defined text string associated with Input8.
            The text string is stored in non-volatile memory."
    ::= { FalconInput8  6 }

FalconInput8HighLimit2 OBJECT-TYPE
    SYNTAX  INTEGER (-2147483648..2147483647)
    ACCESS  read-write
    STATUS  mandatory
    DESCRIPTION
           "When input 8 reaches or exceeds this value a trap will
            be generated signifying a high alarm condition at
            sensor 8.
            The HighLimit variable is stored in non-volatile memory."
    ::= { FalconInput8  7 }

FalconInput8HighLimit OBJECT-TYPE
    SYNTAX  INTEGER (-2147483648..2147483647)
    ACCESS  read-write
    STATUS  mandatory
    DESCRIPTION
           "When input 8 reaches or exceeds this value a trap will
            be generated signifying a high alarm condition at
            sensor 8.
            The HighLimit variable is stored in non-volatile memory."
    ::= { FalconInput8  8 }

FalconInput8LowLimit OBJECT-TYPE
    SYNTAX  INTEGER (-2147483648..2147483647)
    ACCESS  read-write
    STATUS  mandatory
    DESCRIPTION
           "When input 8 reaches or goes below this value a trap will
            be generated signifying a low alarm condition at sensor 8.
            The LowLimit variable is stored in non-volatile memory."
    ::= { FalconInput8  9 }

FalconInput8LowLimit2 OBJECT-TYPE
    SYNTAX  INTEGER (-2147483648..2147483647)
    ACCESS  read-write
    STATUS  mandatory
    DESCRIPTION
           "When input 8 reaches or goes below this value a trap will
            be generated signifying a low alarm condition at sensor 8.
            The LowLimit variable is stored in non-volatile memory."
    ::= { FalconInput8  10 }

FalconInput8RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { FalconInput8  11 }

FalconInput8Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { FalconInput8  12 }

FalconInput8Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { FalconInput8  13 }

FalconInput9 OBJECT IDENTIFIER ::= { FalconInputs 9 }

FalconInput9State OBJECT-TYPE
    SYNTAX  INTEGER {
    notInstalled(1),
    Analog_4to20_Installed(2),
    Digital_NO_Installed(3),
    Digital_NC_Installed(4)
}
    ACCESS  read-write
    STATUS  mandatory
    DESCRIPTION
           "The state of use of Input9. When a sensor is
            connected to Input9 set State to installed(2) to
            indicate that the value of FalconReading9 is valid.
            When no sensor is connected to Input9 set
            State to notInstalled(1) to indicate that the value of
            FalconReading9 may not be valid.
            This variable is stored in non-volatile memory."
    ::= { FalconInput9  1 }

FalconInput9Reading OBJECT-TYPE
    SYNTAX  INTEGER (-2147483648..2147483647)
    ACCESS  read-only
    STATUS  mandatory
    DESCRIPTION
           "The reading for sensor 9.
            If the input is digital, the reading will be 1 (active) or
            0 (inactive)"
    ::= { FalconInput9  2 }

FalconInput9Gain OBJECT-TYPE
    SYNTAX  INTEGER (-2147483648..2147483647)
    ACCESS  read-write
    STATUS  mandatory
    DESCRIPTION
           "A correction gain associated with the sensor variable.
            The value of gain is multiplied by the value from
            Input Sensor Number 9 to obtain the value of
            the Input9 variable. The gain variable is stored in
            non-volatile memory."
    ::= { FalconInput9  3 }

FalconInput9Offset OBJECT-TYPE
    SYNTAX  INTEGER (-2147483648..2147483647)
    ACCESS  read-write
    STATUS  mandatory
    DESCRIPTION
           "A correction Offset associated with the sensor variable.
            The value of Offset is added to the value from
            Input Sensor Number 9 to obtain the value of
            the Input9 variable. The Offset variable is stored in
            non-volatile memory."
    ::= { FalconInput9  4 }

FalconInput9Label OBJECT-TYPE
    SYNTAX  DisplayString
    ACCESS  read-write
    STATUS  mandatory
    DESCRIPTION
           "A user-defined text string associated with Input9.
            The text string is stored in non-volatile memory."
    ::= { FalconInput9  5 }

FalconInput9UOM OBJECT-TYPE
    SYNTAX  DisplayString
    ACCESS  read-write
    STATUS  mandatory
    DESCRIPTION
           "A user-defined text string associated with Input9.
            The text string is stored in non-volatile memory."
    ::= { FalconInput9  6 }

FalconInput9HighLimit2 OBJECT-TYPE
    SYNTAX  INTEGER (-2147483648..2147483647)
    ACCESS  read-write
    STATUS  mandatory
    DESCRIPTION
           "When input 9 reaches or exceeds this value a trap will
            be generated signifying a high alarm condition at
            sensor 9.
            The HighLimit variable is stored in non-volatile memory."
    ::= { FalconInput9  7 }

FalconInput9HighLimit OBJECT-TYPE
    SYNTAX  INTEGER (-2147483648..2147483647)
    ACCESS  read-write
    STATUS  mandatory
    DESCRIPTION
           "When input 9 reaches or exceeds this value a trap will
            be generated signifying a high alarm condition at
            sensor 9.
            The HighLimit variable is stored in non-volatile memory."
    ::= { FalconInput9  8 }

FalconInput9LowLimit OBJECT-TYPE
    SYNTAX  INTEGER (-2147483648..2147483647)
    ACCESS  read-write
    STATUS  mandatory
    DESCRIPTION
           "When input 9 reaches or goes below this value a trap will
            be generated signifying a low alarm condition at sensor 9.
            The LowLimit variable is stored in non-volatile memory."
    ::= { FalconInput9  9 }

FalconInput9LowLimit2 OBJECT-TYPE
    SYNTAX  INTEGER (-2147483648..2147483647)
    ACCESS  read-write
    STATUS  mandatory
    DESCRIPTION
           "When input 9 reaches or goes below this value a trap will
            be generated signifying a low alarm condition at sensor 9.
            The LowLimit variable is stored in non-volatile memory."
    ::= { FalconInput9  10 }

FalconInput9RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { FalconInput9  11 }

FalconInput9Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { FalconInput9  12 }

FalconInput9Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { FalconInput9  13 }

FalconInput10 OBJECT IDENTIFIER ::= { FalconInputs 10 }

FalconInput10State OBJECT-TYPE
    SYNTAX  INTEGER {
    notInstalled(1),
    Analog_4to20_Installed(2),
    Digital_NO_Installed(3),
    Digital_NC_Installed(4)
}
    ACCESS  read-write
    STATUS  mandatory
    DESCRIPTION
           "The state of use of Input10. When a sensor is
            connected to Input10 set State to installed(2) to
            indicate that the value of FalconReading10 is valid.
            When no sensor is connected to Input10 set
            State to notInstalled(1) to indicate that the value of
            FalconReading10 may not be valid.
            This variable is stored in non-volatile memory."
    ::= { FalconInput10  1 }

FalconInput10Reading OBJECT-TYPE
    SYNTAX  INTEGER (-2147483648..2147483647)
    ACCESS  read-only
    STATUS  mandatory
    DESCRIPTION
           "The reading for sensor 10.
            If the input is digital, the reading will be 1 (active) or
            0 (inactive)"
    ::= { FalconInput10  2 }

FalconInput10Gain OBJECT-TYPE
    SYNTAX  INTEGER (-2147483648..2147483647)
    ACCESS  read-write
    STATUS  mandatory
    DESCRIPTION
           "A correction gain associated with the sensor variable.
            The value of gain is multiplied by the value from
            Input Sensor Number 10 to obtain the value of
            the Input10 variable. The gain variable is stored in
            non-volatile memory."
    ::= { FalconInput10  3 }

FalconInput10Offset OBJECT-TYPE
    SYNTAX  INTEGER (-2147483648..2147483647)
    ACCESS  read-write
    STATUS  mandatory
    DESCRIPTION
           "A correction Offset associated with the sensor variable.
            The value of Offset is added to the value from
            Input Sensor Number 10 to obtain the value of
            the Input10 variable. The Offset variable is stored in
            non-volatile memory."
    ::= { FalconInput10  4 }

FalconInput10Label OBJECT-TYPE
    SYNTAX  DisplayString
    ACCESS  read-write
    STATUS  mandatory
    DESCRIPTION
           "A user-defined text string associated with Input10.
            The text string is stored in non-volatile memory."
    ::= { FalconInput10  5 }

FalconInput10UOM OBJECT-TYPE
    SYNTAX  DisplayString
    ACCESS  read-write
    STATUS  mandatory
    DESCRIPTION
           "A user-defined text string associated with Input10.
            The text string is stored in non-volatile memory."
    ::= { FalconInput10  6 }

FalconInput10HighLimit2 OBJECT-TYPE
    SYNTAX  INTEGER (-2147483648..2147483647)
    ACCESS  read-write
    STATUS  mandatory
    DESCRIPTION
           "When Input10 reaches or exceeds this value a trap will
            be generated signifying a high alarm condition at
            sensor 10.
            The HighLimit variable is stored in non-volatile memory."
    ::= { FalconInput10  7 }

FalconInput10HighLimit OBJECT-TYPE
    SYNTAX  INTEGER (-2147483648..2147483647)
    ACCESS  read-write
    STATUS  mandatory
    DESCRIPTION
           "When Input10 reaches or exceeds this value a trap will
            be generated signifying a high alarm condition at
            sensor 10.
            The HighLimit variable is stored in non-volatile memory."
    ::= { FalconInput10  8 }

FalconInput10LowLimit OBJECT-TYPE
    SYNTAX  INTEGER (-2147483648..2147483647)
    ACCESS  read-write
    STATUS  mandatory
    DESCRIPTION
           "When Input10 reaches or goes below this value a trap will
            be generated signifying a low alarm condition at sensor 10.
            The LowLimit variable is stored in non-volatile memory."
    ::= { FalconInput10  9 }

FalconInput10LowLimit2 OBJECT-TYPE
    SYNTAX  INTEGER (-2147483648..2147483647)
    ACCESS  read-write
    STATUS  mandatory
    DESCRIPTION
           "When Input10 reaches or goes below this value a trap will
            be generated signifying a low alarm condition at sensor 10.
            The LowLimit variable is stored in non-volatile memory."
    ::= { FalconInput10  10 }

FalconInput10RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { FalconInput10  11 }

FalconInput10Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { FalconInput10  12 }

FalconInput10Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { FalconInput10  13 }

FalconInput11 OBJECT IDENTIFIER ::= { FalconInputs 11 }

FalconInput11State OBJECT-TYPE
    SYNTAX  INTEGER {
    notInstalled(1),
    Analog_4to20_Installed(2),
    Digital_NO_Installed(3),
    Digital_NC_Installed(4)
}
    ACCESS  read-write
    STATUS  mandatory
    DESCRIPTION
           "The state of use of Input11. When a sensor is
            connected to Input11 set State to installed(2) to
            indicate that the value of FalconReading11 is valid.
            When no sensor is connected to Input11 set
            State to notInstalled(1) to indicate that the value of
            FalconReading11 may not be valid.
            This variable is stored in non-volatile memory."
    ::= { FalconInput11  1 }

FalconInput11Reading OBJECT-TYPE
    SYNTAX  INTEGER (-2147483648..2147483647)
    ACCESS  read-only
    STATUS  mandatory
    DESCRIPTION
           "The reading for sensor 11.
            If the input is digital, the reading will be 1 (active) or
            0 (inactive)"
    ::= { FalconInput11  2 }

FalconInput11Gain OBJECT-TYPE
    SYNTAX  INTEGER (-2147483648..2147483647)
    ACCESS  read-write
    STATUS  mandatory
    DESCRIPTION
           "A correction gain associated with the sensor variable.
            The value of gain is multiplied by the value from
            Input Sensor Number 11 to obtain the value of
            the Input11 variable. The gain variable is stored in
            non-volatile memory."
    ::= { FalconInput11  3 }

FalconInput11Offset OBJECT-TYPE
    SYNTAX  INTEGER (-2147483648..2147483647)
    ACCESS  read-write
    STATUS  mandatory
    DESCRIPTION
           "A correction Offset associated with the sensor variable.
            The value of Offset is added to the value from
            Input Sensor Number 11 to obtain the value of
            the Input11 variable. The Offset variable is stored in
            non-volatile memory."
    ::= { FalconInput11  4 }

FalconInput11Label OBJECT-TYPE
    SYNTAX  DisplayString
    ACCESS  read-write
    STATUS  mandatory
    DESCRIPTION
           "A user-defined text string associated with Input11.
            The text string is stored in non-volatile memory."
    ::= { FalconInput11  5 }

FalconInput11UOM OBJECT-TYPE
    SYNTAX  DisplayString
    ACCESS  read-write
    STATUS  mandatory
    DESCRIPTION
           "A user-defined text string associated with Input11.
            The text string is stored in non-volatile memory."
    ::= { FalconInput11  6 }

FalconInput11HighLimit2 OBJECT-TYPE
    SYNTAX  INTEGER (-2147483648..2147483647)
    ACCESS  read-write
    STATUS  mandatory
    DESCRIPTION
           "When Input11 reaches or exceeds this value a trap will
            be generated signifying a high alarm condition at
            sensor 11.
            The HighLimit variable is stored in non-volatile memory."
    ::= { FalconInput11  7 }

FalconInput11HighLimit OBJECT-TYPE
    SYNTAX  INTEGER (-2147483648..2147483647)
    ACCESS  read-write
    STATUS  mandatory
    DESCRIPTION
           "When Input11 reaches or exceeds this value a trap will
            be generated signifying a high alarm condition at
            sensor 11.
            The HighLimit variable is stored in non-volatile memory."
    ::= { FalconInput11  8 }

FalconInput11LowLimit OBJECT-TYPE
    SYNTAX  INTEGER (-2147483648..2147483647)
    ACCESS  read-write
    STATUS  mandatory
    DESCRIPTION
           "When Input11 reaches or goes below this value a trap will
            be generated signifying a low alarm condition at sensor 11.
            The LowLimit variable is stored in non-volatile memory."
    ::= { FalconInput11  9 }

FalconInput11LowLimit2 OBJECT-TYPE
    SYNTAX  INTEGER (-2147483648..2147483647)
    ACCESS  read-write
    STATUS  mandatory
    DESCRIPTION
           "When Input11 reaches or goes below this value a trap will
            be generated signifying a low alarm condition at sensor 11.
            The LowLimit variable is stored in non-volatile memory."
    ::= { FalconInput11  10 }

FalconInput11RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { FalconInput11  11 }

FalconInput11Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { FalconInput11  12 }

FalconInput11Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { FalconInput11  13 }

FalconInput12 OBJECT IDENTIFIER ::= { FalconInputs 12 }

FalconInput12State OBJECT-TYPE
    SYNTAX  INTEGER {
    notInstalled(1),
    Analog_4to20_Installed(2),
    Digital_NO_Installed(3),
    Digital_NC_Installed(4)
}
    ACCESS  read-write
    STATUS  mandatory
    DESCRIPTION
           "The state of use of Input12. When a sensor is
            connected to Input12 set State to installed(2) to
            indicate that the value of FalconReading12 is valid.
            When no sensor is connected to Input12 set
            State to notInstalled(1) to indicate that the value of
            FalconReading12 may not be valid.
            This variable is stored in non-volatile memory."
    ::= { FalconInput12  1 }

FalconInput12Reading OBJECT-TYPE
    SYNTAX  INTEGER (-2147483648..2147483647)
    ACCESS  read-only
    STATUS  mandatory
    DESCRIPTION
           "The reading for sensor 12.
            If the input is digital, the reading will be 1 (active) or
            0 (inactive)"
    ::= { FalconInput12  2 }

FalconInput12Gain OBJECT-TYPE
    SYNTAX  INTEGER (-2147483648..2147483647)
    ACCESS  read-write
    STATUS  mandatory
    DESCRIPTION
           "A correction gain associated with the sensor variable.
            The value of gain is multiplied by the value from
            Input Sensor Number 12 to obtain the value of
            the Input12 variable. The gain variable is stored in
            non-volatile memory."
    ::= { FalconInput12  3 }

FalconInput12Offset OBJECT-TYPE
    SYNTAX  INTEGER (-2147483648..2147483647)
    ACCESS  read-write
    STATUS  mandatory
    DESCRIPTION
           "A correction Offset associated with the sensor variable.
            The value of Offset is added to the value from
            Input Sensor Number 12 to obtain the value of
            the Input12 variable. The Offset variable is stored in
            non-volatile memory."
    ::= { FalconInput12  4 }

FalconInput12Label OBJECT-TYPE
    SYNTAX  DisplayString
    ACCESS  read-write
    STATUS  mandatory
    DESCRIPTION
           "A user-defined text string associated with Input12.
            The text string is stored in non-volatile memory."
    ::= { FalconInput12  5 }

FalconInput12UOM OBJECT-TYPE
    SYNTAX  DisplayString
    ACCESS  read-write
    STATUS  mandatory
    DESCRIPTION
           "A user-defined text string associated with Input12.
            The text string is stored in non-volatile memory."
    ::= { FalconInput12  6 }

FalconInput12HighLimit2 OBJECT-TYPE
    SYNTAX  INTEGER (-2147483648..2147483647)
    ACCESS  read-write
    STATUS  mandatory
    DESCRIPTION
           "When Input12 reaches or exceeds this value a trap will
            be generated signifying a high alarm condition at
            sensor 12.
            The HighLimit variable is stored in non-volatile memory."
    ::= { FalconInput12  7 }

FalconInput12HighLimit OBJECT-TYPE
    SYNTAX  INTEGER (-2147483648..2147483647)
    ACCESS  read-write
    STATUS  mandatory
    DESCRIPTION
           "When Input12 reaches or exceeds this value a trap will
            be generated signifying a high alarm condition at
            sensor 12.
            The HighLimit variable is stored in non-volatile memory."
    ::= { FalconInput12  8 }

FalconInput12LowLimit OBJECT-TYPE
    SYNTAX  INTEGER (-2147483648..2147483647)
    ACCESS  read-write
    STATUS  mandatory
    DESCRIPTION
           "When Input12 reaches or goes below this value a trap will
            be generated signifying a low alarm condition at sensor 12.
            The LowLimit variable is stored in non-volatile memory."
    ::= { FalconInput12  9 }

FalconInput12LowLimit2 OBJECT-TYPE
    SYNTAX  INTEGER (-2147483648..2147483647)
    ACCESS  read-write
    STATUS  mandatory
    DESCRIPTION
           "When Input12 reaches or goes below this value a trap will
            be generated signifying a low alarm condition at sensor 12.
            The LowLimit variable is stored in non-volatile memory."
    ::= { FalconInput12  10 }

FalconInput12RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { FalconInput12  11 }

FalconInput12Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { FalconInput12  12 }

FalconInput12Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { FalconInput12  13 }

FalconInput13 OBJECT IDENTIFIER ::= { FalconInputs 13 }

FalconInput13State OBJECT-TYPE
    SYNTAX  INTEGER {
    notInstalled(1),
    Analog_4to20_Installed(2),
    Digital_NO_Installed(3),
    Digital_NC_Installed(4)
}
    ACCESS  read-write
    STATUS  mandatory
    DESCRIPTION
           "The state of use of Input13. When a sensor is
            connected to Input13 set State to installed(2) to
            indicate that the value of FalconReading13 is valid.
            When no sensor is connected to Input13 set
            State to notInstalled(1) to indicate that the value of
            FalconReading13 may not be valid.
            This variable is stored in non-volatile memory."
    ::= { FalconInput13  1 }

FalconInput13Reading OBJECT-TYPE
    SYNTAX  INTEGER (-2147483648..2147483647)
    ACCESS  read-only
    STATUS  mandatory
    DESCRIPTION
           "The reading for sensor 13.
            If the input is digital, the reading will be 1 (active) or
            0 (inactive)"
    ::= { FalconInput13  2 }

FalconInput13Gain OBJECT-TYPE
    SYNTAX  INTEGER (-2147483648..2147483647)
    ACCESS  read-write
    STATUS  mandatory
    DESCRIPTION
           "A correction gain associated with the sensor variable.
            The value of gain is multiplied by the value from
            Input Sensor Number 13 to obtain the value of
            the Input13 variable. The gain variable is stored in
            non-volatile memory."
    ::= { FalconInput13  3 }

FalconInput13Offset OBJECT-TYPE
    SYNTAX  INTEGER (-2147483648..2147483647)
    ACCESS  read-write
    STATUS  mandatory
    DESCRIPTION
           "A correction Offset associated with the sensor variable.
            The value of Offset is added to the value from
            Input Sensor Number 13 to obtain the value of
            the Input13 variable. The Offset variable is stored in
            non-volatile memory."
    ::= { FalconInput13  4 }

FalconInput13Label OBJECT-TYPE
    SYNTAX  DisplayString
    ACCESS  read-write
    STATUS  mandatory
    DESCRIPTION
           "A user-defined text string associated with Input13.
            The text string is stored in non-volatile memory."
    ::= { FalconInput13  5 }

FalconInput13UOM OBJECT-TYPE
    SYNTAX  DisplayString
    ACCESS  read-write
    STATUS  mandatory
    DESCRIPTION
           "A user-defined text string associated with Input13.
            The text string is stored in non-volatile memory."
    ::= { FalconInput13  6 }

FalconInput13HighLimit2 OBJECT-TYPE
    SYNTAX  INTEGER (-2147483648..2147483647)
    ACCESS  read-write
    STATUS  mandatory
    DESCRIPTION
           "When Input13 reaches or exceeds this value a trap will
            be generated signifying a high alarm condition at
            sensor 13.
            The HighLimit variable is stored in non-volatile memory."
    ::= { FalconInput13  7 }

FalconInput13HighLimit OBJECT-TYPE
    SYNTAX  INTEGER (-2147483648..2147483647)
    ACCESS  read-write
    STATUS  mandatory
    DESCRIPTION
           "When Input13 reaches or exceeds this value a trap will
            be generated signifying a high alarm condition at
            sensor 13.
            The HighLimit variable is stored in non-volatile memory."
    ::= { FalconInput13  8 }

FalconInput13LowLimit OBJECT-TYPE
    SYNTAX  INTEGER (-2147483648..2147483647)
    ACCESS  read-write
    STATUS  mandatory
    DESCRIPTION
           "When Input13 reaches or goes below this value a trap will
            be generated signifying a low alarm condition at sensor 13.
            The LowLimit variable is stored in non-volatile memory."
    ::= { FalconInput13  9 }

FalconInput13LowLimit2 OBJECT-TYPE
    SYNTAX  INTEGER (-2147483648..2147483647)
    ACCESS  read-write
    STATUS  mandatory
    DESCRIPTION
           "When Input13 reaches or goes below this value a trap will
            be generated signifying a low alarm condition at sensor 13.
            The LowLimit variable is stored in non-volatile memory."
    ::= { FalconInput13  10 }

FalconInput13RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { FalconInput13  11 }

FalconInput13Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { FalconInput13  12 }

FalconInput13Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { FalconInput13  13 }

FalconInput14 OBJECT IDENTIFIER ::= { FalconInputs 14 }

FalconInput14State OBJECT-TYPE
    SYNTAX  INTEGER {
    notInstalled(1),
    Analog_4to20_Installed(2),
    Digital_NO_Installed(3),
    Digital_NC_Installed(4)
}
    ACCESS  read-write
    STATUS  mandatory
    DESCRIPTION
           "The state of use of Input14. When a sensor is
            connected to Input14 set State to installed(2) to
            indicate that the value of FalconReading14 is valid.
            When no sensor is connected to Input14 set
            State to notInstalled(1) to indicate that the value of
            FalconReading14 may not be valid.
            This variable is stored in non-volatile memory."
    ::= { FalconInput14  1 }

FalconInput14Reading OBJECT-TYPE
    SYNTAX  INTEGER (-2147483648..2147483647)
    ACCESS  read-only
    STATUS  mandatory
    DESCRIPTION
           "The reading for sensor 14.
            If the input is digital, the reading will be 1 (active) or
            0 (inactive)"
    ::= { FalconInput14  2 }

FalconInput14Gain OBJECT-TYPE
    SYNTAX  INTEGER (-2147483648..2147483647)
    ACCESS  read-write
    STATUS  mandatory
    DESCRIPTION
           "A correction gain associated with the sensor variable.
            The value of gain is multiplied by the value from
            Input Sensor Number 14 to obtain the value of
            the Input14 variable. The gain variable is stored in
            non-volatile memory."
    ::= { FalconInput14  3 }

FalconInput14Offset OBJECT-TYPE
    SYNTAX  INTEGER (-2147483648..2147483647)
    ACCESS  read-write
    STATUS  mandatory
    DESCRIPTION
           "A correction Offset associated with the sensor variable.
            The value of Offset is added to the value from
            Input Sensor Number 14 to obtain the value of
            the Input14 variable. The Offset variable is stored in
            non-volatile memory."
    ::= { FalconInput14  4 }

FalconInput14Label OBJECT-TYPE
    SYNTAX  DisplayString
    ACCESS  read-write
    STATUS  mandatory
    DESCRIPTION
           "A user-defined text string associated with Input14.
            The text string is stored in non-volatile memory."
    ::= { FalconInput14  5 }

FalconInput14UOM OBJECT-TYPE
    SYNTAX  DisplayString
    ACCESS  read-write
    STATUS  mandatory
    DESCRIPTION
           "A user-defined text string associated with Input14.
            The text string is stored in non-volatile memory."
    ::= { FalconInput14  6 }

FalconInput14HighLimit2 OBJECT-TYPE
    SYNTAX  INTEGER (-2147483648..2147483647)
    ACCESS  read-write
    STATUS  mandatory
    DESCRIPTION
           "When Input14 reaches or exceeds this value a trap will
            be generated signifying a high alarm condition at
            sensor 14.
            The HighLimit variable is stored in non-volatile memory."
    ::= { FalconInput14  7 }

FalconInput14HighLimit OBJECT-TYPE
    SYNTAX  INTEGER (-2147483648..2147483647)
    ACCESS  read-write
    STATUS  mandatory
    DESCRIPTION
           "When Input14 reaches or exceeds this value a trap will
            be generated signifying a high alarm condition at
            sensor 14.
            The HighLimit variable is stored in non-volatile memory."
    ::= { FalconInput14  8 }

FalconInput14LowLimit OBJECT-TYPE
    SYNTAX  INTEGER (-2147483648..2147483647)
    ACCESS  read-write
    STATUS  mandatory
    DESCRIPTION
           "When Input14 reaches or goes below this value a trap will
            be generated signifying a low alarm condition at sensor 14.
            The LowLimit variable is stored in non-volatile memory."
    ::= { FalconInput14  9 }

FalconInput14LowLimit2 OBJECT-TYPE
    SYNTAX  INTEGER (-2147483648..2147483647)
    ACCESS  read-write
    STATUS  mandatory
    DESCRIPTION
           "When Input14 reaches or goes below this value a trap will
            be generated signifying a low alarm condition at sensor 14.
            The LowLimit variable is stored in non-volatile memory."
    ::= { FalconInput14  10 }

FalconInput14RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { FalconInput14  11 }

FalconInput14Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { FalconInput14  12 }

FalconInput14Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { FalconInput14  13 }

FalconInput15 OBJECT IDENTIFIER ::= { FalconInputs 15 }

FalconInput15State OBJECT-TYPE
    SYNTAX  INTEGER {
    notInstalled(1),
    Analog_4to20_Installed(2),
    Digital_NO_Installed(3),
    Digital_NC_Installed(4)
}
    ACCESS  read-write
    STATUS  mandatory
    DESCRIPTION
           "The state of use of Input15. When a sensor is
            connected to Input15 set State to installed(2) to
            indicate that the value of FalconReading15 is valid.
            When no sensor is connected to Input15 set
            State to notInstalled(1) to indicate that the value of
            FalconReading15 may not be valid.
            This variable is stored in non-volatile memory."
    ::= { FalconInput15  1 }

FalconInput15Reading OBJECT-TYPE
    SYNTAX  INTEGER (-2147483648..2147483647)
    ACCESS  read-only
    STATUS  mandatory
    DESCRIPTION
           "The reading for sensor 15.
            If the input is digital, the reading will be 1 (active) or
            0 (inactive)"
    ::= { FalconInput15  2 }

FalconInput15Gain OBJECT-TYPE
    SYNTAX  INTEGER (-2147483648..2147483647)
    ACCESS  read-write
    STATUS  mandatory
    DESCRIPTION
           "A correction gain associated with the sensor variable.
            The value of gain is multiplied by the value from
            Input Sensor Number 15 to obtain the value of
            the Input15 variable. The gain variable is stored in
            non-volatile memory."
    ::= { FalconInput15  3 }

FalconInput15Offset OBJECT-TYPE
    SYNTAX  INTEGER (-2147483648..2147483647)
    ACCESS  read-write
    STATUS  mandatory
    DESCRIPTION
           "A correction Offset associated with the sensor variable.
            The value of Offset is added to the value from
            Input Sensor Number 15 to obtain the value of
            the Input15 variable. The Offset variable is stored in
            non-volatile memory."
    ::= { FalconInput15  4 }

FalconInput15Label OBJECT-TYPE
    SYNTAX  DisplayString
    ACCESS  read-write
    STATUS  mandatory
    DESCRIPTION
           "A user-defined text string associated with Input15.
            The text string is stored in non-volatile memory."
    ::= { FalconInput15  5 }

FalconInput15UOM OBJECT-TYPE
    SYNTAX  DisplayString
    ACCESS  read-write
    STATUS  mandatory
    DESCRIPTION
           "A user-defined text string associated with Input15.
            The text string is stored in non-volatile memory."
    ::= { FalconInput15  6 }

FalconInput15HighLimit2 OBJECT-TYPE
    SYNTAX  INTEGER (-2147483648..2147483647)
    ACCESS  read-write
    STATUS  mandatory
    DESCRIPTION
           "When Input15 reaches or exceeds this value a trap will
            be generated signifying a high alarm condition at
            sensor 15.
            The HighLimit variable is stored in non-volatile memory."
    ::= { FalconInput15  7 }

FalconInput15HighLimit OBJECT-TYPE
    SYNTAX  INTEGER (-2147483648..2147483647)
    ACCESS  read-write
    STATUS  mandatory
    DESCRIPTION
           "When Input15 reaches or exceeds this value a trap will
            be generated signifying a high alarm condition at
            sensor 15.
            The HighLimit variable is stored in non-volatile memory."
    ::= { FalconInput15  8 }

FalconInput15LowLimit OBJECT-TYPE
    SYNTAX  INTEGER (-2147483648..2147483647)
    ACCESS  read-write
    STATUS  mandatory
    DESCRIPTION
           "When Input15 reaches or goes below this value a trap will
            be generated signifying a low alarm condition at sensor 15.
            The LowLimit variable is stored in non-volatile memory."
    ::= { FalconInput15  9 }

FalconInput15LowLimit2 OBJECT-TYPE
    SYNTAX  INTEGER (-2147483648..2147483647)
    ACCESS  read-write
    STATUS  mandatory
    DESCRIPTION
           "When Input15 reaches or goes below this value a trap will
            be generated signifying a low alarm condition at sensor 15.
            The LowLimit variable is stored in non-volatile memory."
    ::= { FalconInput15  10 }

FalconInput15RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { FalconInput15  11 }

FalconInput15Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { FalconInput15  12 }

FalconInput15Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { FalconInput15  13 }

FalconInput16 OBJECT IDENTIFIER ::= { FalconInputs 16 }

FalconInput16State OBJECT-TYPE
    SYNTAX  INTEGER {
    notInstalled(1),
    Analog_4to20_Installed(2),
    Digital_NO_Installed(3),
    Digital_NC_Installed(4)
}
    ACCESS  read-write
    STATUS  mandatory
    DESCRIPTION
           "The state of use of Input16. When a sensor is
            connected to Input16 set State to installed(2) to
            indicate that the value of FalconReading16 is valid.
            When no sensor is connected to Input16 set
            State to notInstalled(1) to indicate that the value of
            FalconReading16 may not be valid.
            This variable is stored in non-volatile memory."
    ::= { FalconInput16  1 }

FalconInput16Reading OBJECT-TYPE
    SYNTAX  INTEGER (-2147483648..2147483647)
    ACCESS  read-only
    STATUS  mandatory
    DESCRIPTION
           "The reading for sensor 16.
            If the input is digital, the reading will be 1 (active) or
            0 (inactive)"
    ::= { FalconInput16  2 }

FalconInput16Gain OBJECT-TYPE
    SYNTAX  INTEGER (-2147483648..2147483647)
    ACCESS  read-write
    STATUS  mandatory
    DESCRIPTION
           "A correction gain associated with the sensor variable.
            The value of gain is multiplied by the value from
            Input Sensor Number 16 to obtain the value of
            the Input16 variable. The gain variable is stored in
            non-volatile memory."
    ::= { FalconInput16  3 }

FalconInput16Offset OBJECT-TYPE
    SYNTAX  INTEGER (-2147483648..2147483647)
    ACCESS  read-write
    STATUS  mandatory
    DESCRIPTION
           "A correction Offset associated with the sensor variable.
            The value of Offset is added to the value from
            Input Sensor Number 16 to obtain the value of
            the Input16 variable. The Offset variable is stored in
            non-volatile memory."
    ::= { FalconInput16  4 }

FalconInput16Label OBJECT-TYPE
    SYNTAX  DisplayString
    ACCESS  read-write
    STATUS  mandatory
    DESCRIPTION
           "A user-defined text string associated with Input16.
            The text string is stored in non-volatile memory."
    ::= { FalconInput16  5 }

FalconInput16UOM OBJECT-TYPE
    SYNTAX  DisplayString
    ACCESS  read-write
    STATUS  mandatory
    DESCRIPTION
           "A user-defined text string associated with Input16.
            The text string is stored in non-volatile memory."
    ::= { FalconInput16  6 }

FalconInput16HighLimit2 OBJECT-TYPE
    SYNTAX  INTEGER (-2147483648..2147483647)
    ACCESS  read-write
    STATUS  mandatory
    DESCRIPTION
           "When Input16 reaches or exceeds this value a trap will
            be generated signifying a high alarm condition at
            sensor 16.
            The HighLimit variable is stored in non-volatile memory."
    ::= { FalconInput16  7 }

FalconInput16HighLimit OBJECT-TYPE
    SYNTAX  INTEGER (-2147483648..2147483647)
    ACCESS  read-write
    STATUS  mandatory
    DESCRIPTION
           "When Input16 reaches or exceeds this value a trap will
            be generated signifying a high alarm condition at
            sensor 16.
            The HighLimit variable is stored in non-volatile memory."
    ::= { FalconInput16  8 }

FalconInput16LowLimit OBJECT-TYPE
    SYNTAX  INTEGER (-2147483648..2147483647)
    ACCESS  read-write
    STATUS  mandatory
    DESCRIPTION
           "When Input16 reaches or goes below this value a trap will
            be generated signifying a low alarm condition at sensor 16.
            The LowLimit variable is stored in non-volatile memory."
    ::= { FalconInput16  9 }

FalconInput16LowLimit2 OBJECT-TYPE
    SYNTAX  INTEGER (-2147483648..2147483647)
    ACCESS  read-write
    STATUS  mandatory
    DESCRIPTION
           "When Input16 reaches or goes below this value a trap will
            be generated signifying a low alarm condition at sensor 16.
            The LowLimit variable is stored in non-volatile memory."
    ::= { FalconInput16  10 }

FalconInput16RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { FalconInput16  11 }

FalconInput16Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { FalconInput16  12 }

FalconInput16Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { FalconInput16  13 }

FalconInput17 OBJECT IDENTIFIER ::= { FalconInputs 17 }

FalconInput17State OBJECT-TYPE
    SYNTAX  INTEGER {
    notInstalled(1),
    Analog_4to20_Installed(2),
    Digital_NO_Installed(3),
    Digital_NC_Installed(4)
}
    ACCESS  read-write
    STATUS  mandatory
    DESCRIPTION
           "The state of use of Input17. When a sensor is
            connected to Input17 set State to installed(2) to
            indicate that the value of FalconReading17 is valid.
            When no sensor is connected to Input17 set
            State to notInstalled(1) to indicate that the value of
            FalconReading17 may not be valid.
            This variable is stored in non-volatile memory."
    ::= { FalconInput17  1 }

FalconInput17Reading OBJECT-TYPE
    SYNTAX  INTEGER (-2147483648..2147483647)
    ACCESS  read-only
    STATUS  mandatory
    DESCRIPTION
           "The reading for sensor 17.
            If the input is digital, the reading will be 1 (active) or
            0 (inactive)"
    ::= { FalconInput17  2 }

FalconInput17Gain OBJECT-TYPE
    SYNTAX  INTEGER (-2147483648..2147483647)
    ACCESS  read-write
    STATUS  mandatory
    DESCRIPTION
           "A correction gain associated with the sensor variable.
            The value of gain is multiplied by the value from
            Input Sensor Number 17 to obtain the value of
            the Input17 variable. The gain variable is stored in
            non-volatile memory."
    ::= { FalconInput17  3 }

FalconInput17Offset OBJECT-TYPE
    SYNTAX  INTEGER (-2147483648..2147483647)
    ACCESS  read-write
    STATUS  mandatory
    DESCRIPTION
           "A correction Offset associated with the sensor variable.
            The value of Offset is added to the value from
            Input Sensor Number 17 to obtain the value of
            the Input17 variable. The Offset variable is stored in
            non-volatile memory."
    ::= { FalconInput17  4 }

FalconInput17Label OBJECT-TYPE
    SYNTAX  DisplayString
    ACCESS  read-write
    STATUS  mandatory
    DESCRIPTION
           "A user-defined text string associated with Input17.
            The text string is stored in non-volatile memory."
    ::= { FalconInput17  5 }

FalconInput17UOM OBJECT-TYPE
    SYNTAX  DisplayString
    ACCESS  read-write
    STATUS  mandatory
    DESCRIPTION
           "A user-defined text string associated with Input17.
            The text string is stored in non-volatile memory."
    ::= { FalconInput17  6 }

FalconInput17HighLimit2 OBJECT-TYPE
    SYNTAX  INTEGER (-2147483648..2147483647)
    ACCESS  read-write
    STATUS  mandatory
    DESCRIPTION
           "When Input17 reaches or exceeds this value a trap will
            be generated signifying a high alarm condition at
            sensor 17.
            The HighLimit variable is stored in non-volatile memory."
    ::= { FalconInput17  7 }

FalconInput17HighLimit OBJECT-TYPE
    SYNTAX  INTEGER (-2147483648..2147483647)
    ACCESS  read-write
    STATUS  mandatory
    DESCRIPTION
           "When Input17 reaches or exceeds this value a trap will
            be generated signifying a high alarm condition at
            sensor 17.
            The HighLimit variable is stored in non-volatile memory."
    ::= { FalconInput17  8 }

FalconInput17LowLimit OBJECT-TYPE
    SYNTAX  INTEGER (-2147483648..2147483647)
    ACCESS  read-write
    STATUS  mandatory
    DESCRIPTION
           "When Input17 reaches or goes below this value a trap will
            be generated signifying a low alarm condition at sensor 17.
            The LowLimit variable is stored in non-volatile memory."
    ::= { FalconInput17  9 }

FalconInput17LowLimit2 OBJECT-TYPE
    SYNTAX  INTEGER (-2147483648..2147483647)
    ACCESS  read-write
    STATUS  mandatory
    DESCRIPTION
           "When Input17 reaches or goes below this value a trap will
            be generated signifying a low alarm condition at sensor 17.
            The LowLimit variable is stored in non-volatile memory."
    ::= { FalconInput17  10 }

FalconInput17RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { FalconInput17  11 }

FalconInput17Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { FalconInput17  12 }

FalconInput17Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { FalconInput17  13 }

FalconInput18 OBJECT IDENTIFIER ::= { FalconInputs 18 }

FalconInput18State OBJECT-TYPE
    SYNTAX  INTEGER {
    notInstalled(1),
    Analog_4to20_Installed(2),
    Digital_NO_Installed(3),
    Digital_NC_Installed(4)
}
    ACCESS  read-write
    STATUS  mandatory
    DESCRIPTION
           "The state of use of Input18. When a sensor is
            connected to Input18 set State to installed(2) to
            indicate that the value of FalconReading18 is valid.
            When no sensor is connected to Input18 set
            State to notInstalled(1) to indicate that the value of
            FalconReading18 may not be valid.
            This variable is stored in non-volatile memory."
    ::= { FalconInput18  1 }

FalconInput18Reading OBJECT-TYPE
    SYNTAX  INTEGER (-2147483648..2147483647)
    ACCESS  read-only
    STATUS  mandatory
    DESCRIPTION
           "The reading for sensor 18.
            If the input is digital, the reading will be 1 (active) or
            0 (inactive)"
    ::= { FalconInput18  2 }

FalconInput18Gain OBJECT-TYPE
    SYNTAX  INTEGER (-2147483648..2147483647)
    ACCESS  read-write
    STATUS  mandatory
    DESCRIPTION
           "A correction gain associated with the sensor variable.
            The value of gain is multiplied by the value from
            Input Sensor Number 18 to obtain the value of
            the Input18 variable. The gain variable is stored in
            non-volatile memory."
    ::= { FalconInput18  3 }

FalconInput18Offset OBJECT-TYPE
    SYNTAX  INTEGER (-2147483648..2147483647)
    ACCESS  read-write
    STATUS  mandatory
    DESCRIPTION
           "A correction Offset associated with the sensor variable.
            The value of Offset is added to the value from
            Input Sensor Number 18 to obtain the value of
            the Input18 variable. The Offset variable is stored in
            non-volatile memory."
    ::= { FalconInput18  4 }

FalconInput18Label OBJECT-TYPE
    SYNTAX  DisplayString
    ACCESS  read-write
    STATUS  mandatory
    DESCRIPTION
           "A user-defined text string associated with Input18.
            The text string is stored in non-volatile memory."
    ::= { FalconInput18  5 }

FalconInput18UOM OBJECT-TYPE
    SYNTAX  DisplayString
    ACCESS  read-write
    STATUS  mandatory
    DESCRIPTION
           "A user-defined text string associated with Input18.
            The text string is stored in non-volatile memory."
    ::= { FalconInput18  6 }

FalconInput18HighLimit2 OBJECT-TYPE
    SYNTAX  INTEGER (-2147483648..2147483647)
    ACCESS  read-write
    STATUS  mandatory
    DESCRIPTION
           "When Input18 reaches or exceeds this value a trap will
            be generated signifying a high alarm condition at
            sensor 18.
            The HighLimit variable is stored in non-volatile memory."
    ::= { FalconInput18  7 }

FalconInput18HighLimit OBJECT-TYPE
    SYNTAX  INTEGER (-2147483648..2147483647)
    ACCESS  read-write
    STATUS  mandatory
    DESCRIPTION
           "When Input18 reaches or exceeds this value a trap will
            be generated signifying a high alarm condition at
            sensor 18.
            The HighLimit variable is stored in non-volatile memory."
    ::= { FalconInput18  8 }

FalconInput18LowLimit OBJECT-TYPE
    SYNTAX  INTEGER (-2147483648..2147483647)
    ACCESS  read-write
    STATUS  mandatory
    DESCRIPTION
           "When Input18 reaches or goes below this value a trap will
            be generated signifying a low alarm condition at sensor 18.
            The LowLimit variable is stored in non-volatile memory."
    ::= { FalconInput18  9 }

FalconInput18LowLimit2 OBJECT-TYPE
    SYNTAX  INTEGER (-2147483648..2147483647)
    ACCESS  read-write
    STATUS  mandatory
    DESCRIPTION
           "When Input18 reaches or goes below this value a trap will
            be generated signifying a low alarm condition at sensor 18.
            The LowLimit variable is stored in non-volatile memory."
    ::= { FalconInput18  10 }

FalconInput18RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { FalconInput18  11 }

FalconInput18Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { FalconInput18  12 }

FalconInput18Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { FalconInput18  13 }

FalconInput19 OBJECT IDENTIFIER ::= { FalconInputs 19 }

FalconInput19State OBJECT-TYPE
    SYNTAX  INTEGER {
    notInstalled(1),
    Analog_4to20_Installed(2),
    Digital_NO_Installed(3),
    Digital_NC_Installed(4)
}
    ACCESS  read-write
    STATUS  mandatory
    DESCRIPTION
           "The state of use of Input19. When a sensor is
            connected to Input19 set State to installed(2) to
            indicate that the value of FalconReading19 is valid.
            When no sensor is connected to Input19 set
            State to notInstalled(1) to indicate that the value of
            FalconReading19 may not be valid.
            This variable is stored in non-volatile memory."
    ::= { FalconInput19  1 }

FalconInput19Reading OBJECT-TYPE
    SYNTAX  INTEGER (-2147483648..2147483647)
    ACCESS  read-only
    STATUS  mandatory
    DESCRIPTION
           "The reading for sensor 19.
            If the input is digital, the reading will be 1 (active) or
            0 (inactive)"
    ::= { FalconInput19  2 }

FalconInput19Gain OBJECT-TYPE
    SYNTAX  INTEGER (-2147483648..2147483647)
    ACCESS  read-write
    STATUS  mandatory
    DESCRIPTION
           "A correction gain associated with the sensor variable.
            The value of gain is multiplied by the value from
            Input Sensor Number 19 to obtain the value of
            the Input19 variable. The gain variable is stored in
            non-volatile memory."
    ::= { FalconInput19  3 }

FalconInput19Offset OBJECT-TYPE
    SYNTAX  INTEGER (-2147483648..2147483647)
    ACCESS  read-write
    STATUS  mandatory
    DESCRIPTION
           "A correction Offset associated with the sensor variable.
            The value of Offset is added to the value from
            Input Sensor Number 19 to obtain the value of
            the Input19 variable. The Offset variable is stored in
            non-volatile memory."
    ::= { FalconInput19  4 }

FalconInput19Label OBJECT-TYPE
    SYNTAX  DisplayString
    ACCESS  read-write
    STATUS  mandatory
    DESCRIPTION
           "A user-defined text string associated with Input19.
            The text string is stored in non-volatile memory."
    ::= { FalconInput19  5 }

FalconInput19UOM OBJECT-TYPE
    SYNTAX  DisplayString
    ACCESS  read-write
    STATUS  mandatory
    DESCRIPTION
           "A user-defined text string associated with Input19.
            The text string is stored in non-volatile memory."
    ::= { FalconInput19  6 }

FalconInput19HighLimit2 OBJECT-TYPE
    SYNTAX  INTEGER (-2147483648..2147483647)
    ACCESS  read-write
    STATUS  mandatory
    DESCRIPTION
           "When Input19 reaches or exceeds this value a trap will
            be generated signifying a high alarm condition at
            sensor 19.
            The HighLimit variable is stored in non-volatile memory."
    ::= { FalconInput19  7 }

FalconInput19HighLimit OBJECT-TYPE
    SYNTAX  INTEGER (-2147483648..2147483647)
    ACCESS  read-write
    STATUS  mandatory
    DESCRIPTION
           "When Input19 reaches or exceeds this value a trap will
            be generated signifying a high alarm condition at
            sensor 19.
            The HighLimit variable is stored in non-volatile memory."
    ::= { FalconInput19  8 }

FalconInput19LowLimit OBJECT-TYPE
    SYNTAX  INTEGER (-2147483648..2147483647)
    ACCESS  read-write
    STATUS  mandatory
    DESCRIPTION
           "When Input19 reaches or goes below this value a trap will
            be generated signifying a low alarm condition at sensor 19.
            The LowLimit variable is stored in non-volatile memory."
    ::= { FalconInput19  9 }

FalconInput19LowLimit2 OBJECT-TYPE
    SYNTAX  INTEGER (-2147483648..2147483647)
    ACCESS  read-write
    STATUS  mandatory
    DESCRIPTION
           "When Input19 reaches or goes below this value a trap will
            be generated signifying a low alarm condition at sensor 19.
            The LowLimit variable is stored in non-volatile memory."
    ::= { FalconInput19  10 }

FalconInput19RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { FalconInput19  11 }

FalconInput19Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { FalconInput19  12 }

FalconInput19Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { FalconInput19  13 }

FalconInput20 OBJECT IDENTIFIER ::= { FalconInputs 20 }

FalconInput20State OBJECT-TYPE
    SYNTAX  INTEGER {
    notInstalled(1),
    Analog_4to20_Installed(2),
    Digital_NO_Installed(3),
    Digital_NC_Installed(4)
}
    ACCESS  read-write
    STATUS  mandatory
    DESCRIPTION
           "The state of use of Input20. When a sensor is
            connected to Input20 set State to installed(2) to
            indicate that the value of FalconReading20 is valid.
            When no sensor is connected to Input20 set
            State to notInstalled(1) to indicate that the value of
            FalconReading20 may not be valid.
            This variable is stored in non-volatile memory."
    ::= { FalconInput20  1 }

FalconInput20Reading OBJECT-TYPE
    SYNTAX  INTEGER (-2147483648..2147483647)
    ACCESS  read-only
    STATUS  mandatory
    DESCRIPTION
           "The reading for sensor 20.
            If the input is digital, the reading will be 1 (active) or
            0 (inactive)"
    ::= { FalconInput20  2 }

FalconInput20Gain OBJECT-TYPE
    SYNTAX  INTEGER (-2147483648..2147483647)
    ACCESS  read-write
    STATUS  mandatory
    DESCRIPTION
           "A correction gain associated with the sensor variable.
            The value of gain is multiplied by the value from
            Input Sensor Number 20 to obtain the value of
            the Input20 variable. The gain variable is stored in
            non-volatile memory."
    ::= { FalconInput20  3 }

FalconInput20Offset OBJECT-TYPE
    SYNTAX  INTEGER (-2147483648..2147483647)
    ACCESS  read-write
    STATUS  mandatory
    DESCRIPTION
           "A correction Offset associated with the sensor variable.
            The value of Offset is added to the value from
            Input Sensor Number 20 to obtain the value of
            the Input20 variable. The Offset variable is stored in
            non-volatile memory."
    ::= { FalconInput20  4 }

FalconInput20Label OBJECT-TYPE
    SYNTAX  DisplayString
    ACCESS  read-write
    STATUS  mandatory
    DESCRIPTION
           "A user-defined text string associated with Input20.
            The text string is stored in non-volatile memory."
    ::= { FalconInput20  5 }

FalconInput20UOM OBJECT-TYPE
    SYNTAX  DisplayString
    ACCESS  read-write
    STATUS  mandatory
    DESCRIPTION
           "A user-defined text string associated with Input20.
            The text string is stored in non-volatile memory."
    ::= { FalconInput20  6 }

FalconInput20HighLimit2 OBJECT-TYPE
    SYNTAX  INTEGER (-2147483648..2147483647)
    ACCESS  read-write
    STATUS  mandatory
    DESCRIPTION
           "When Input20 reaches or exceeds this value a trap will
            be generated signifying a high alarm condition at
            sensor 20.
            The HighLimit variable is stored in non-volatile memory."
    ::= { FalconInput20  7 }

FalconInput20HighLimit OBJECT-TYPE
    SYNTAX  INTEGER (-2147483648..2147483647)
    ACCESS  read-write
    STATUS  mandatory
    DESCRIPTION
           "When Input20 reaches or exceeds this value a trap will
            be generated signifying a high alarm condition at
            sensor 20.
            The HighLimit variable is stored in non-volatile memory."
    ::= { FalconInput20  8 }

FalconInput20LowLimit OBJECT-TYPE
    SYNTAX  INTEGER (-2147483648..2147483647)
    ACCESS  read-write
    STATUS  mandatory
    DESCRIPTION
           "When Input20 reaches or goes below this value a trap will
            be generated signifying a low alarm condition at sensor 20.
            The LowLimit variable is stored in non-volatile memory."
    ::= { FalconInput20  9 }

FalconInput20LowLimit2 OBJECT-TYPE
    SYNTAX  INTEGER (-2147483648..2147483647)
    ACCESS  read-write
    STATUS  mandatory
    DESCRIPTION
           "When Input20 reaches or goes below this value a trap will
            be generated signifying a low alarm condition at sensor 20.
            The LowLimit variable is stored in non-volatile memory."
    ::= { FalconInput20  10 }

FalconInput20RlyControl OBJECT-TYPE
    SYNTAX  INTEGER (-2147483648..2147483647)
    ACCESS  read-write
    STATUS  mandatory
    DESCRIPTION
           "The control of the output relays. This is a binary
            setting with each bit representing an alarm state.
            To set K1 on a high alarm, set the 1st bit (1).
            To set K2 on a high alarm, set the 2nd bit (2).
            To set K1 on a low alarm, set the 3rd bit (4).
            To set K2 on a low alarm, set the 4th bit (8).
            To set K1 on a digital alarm, set the 1st bit (1).
            To set K2 on a digital alarm, set the 2nd bit (2).
            For no action. set this value to 0.
            The range of this setting is 0..15.
            This variable is stored in non-volatile memory."
    ::= { FalconInput20  11 }

FalconInput20Delay OBJECT-TYPE
    SYNTAX  INTEGER (0..600)
    ACCESS  read-write
    STATUS  mandatory
    DESCRIPTION
           "The number of seconds an alarm for this input must
            be present before annunication. The range of this
            setting is 0..600.
            This variable is stored in non-volatile memory."
    ::= { FalconInput20  12 }

FalconInput20Hysteresis OBJECT-TYPE
    SYNTAX  INTEGER (0..2147483647)
    ACCESS  read-write
    STATUS  mandatory
    DESCRIPTION
           "The value of alarm hysteresis for this input.
            The input reading must decrease or increase by this
            value before the alarm will clear.
            This variable is stored in non-volatile memory."
    ::= { FalconInput20  13 }

FalconOutputs OBJECT IDENTIFIER ::= { FalconMIB  4 }

FalconRelay1 OBJECT IDENTIFIER ::= { FalconOutputs 1 }

FalconRelay1State OBJECT-TYPE
    SYNTAX  INTEGER {
    NormallyOff(1),
    NormallyOn(2),
    ForceOn(3),
    ForceOff(4),
    KeypadControlled(5)
}
    ACCESS  read-write
    STATUS  mandatory
    DESCRIPTION
           "The state of use of Relay Number 1. The relay can be
            set for normally open or closed. The relay can be forced
            to an on or off condition, or controlled by the keypad.
            This variable is stored in non-volatile memory."
    ::= { FalconRelay1  1 }

FalconRelay1Status OBJECT-TYPE
    SYNTAX  INTEGER {
    NormalOff(1),
    NormalOn(2),
    ForcedOn(3),
    ForcedOff(4),
    KeycodeActive(5),
    AlarmedActive(6)
}
    ACCESS  read-only
    STATUS  mandatory
    DESCRIPTION
           "The current status for relay 1."
    ::= { FalconRelay1  2 }

FalconRelay1Label OBJECT-TYPE
    SYNTAX  DisplayString
    ACCESS  read-write
    STATUS  mandatory
    DESCRIPTION
           "A user-defined text string associated with Relay Number 1.
            The text string is stored in non-volatile memory."
    ::= { FalconRelay1  3 }

FalconRelay1Time OBJECT-TYPE
    SYNTAX  INTEGER (-2147483648..2147483647)
    MAX-ACCESS read-write
    STATUS     mandatory
    DESCRIPTION
        "The number of seconds the relay will be activated.
         Set this to -1 for indefinitely."
    ::= { FalconRelay1  4 }

FalconRelay2 OBJECT IDENTIFIER ::= { FalconOutputs 2 }

FalconRelay2State OBJECT-TYPE
    SYNTAX  INTEGER {
    NormallyOff(1),
    NormallyOn(2),
    ForceOn(3),
    ForceOff(4),
    KeypadControlled(5)
}
    ACCESS  read-write
    STATUS  mandatory
    DESCRIPTION
           "The state of use of Relay Number 2. The relay can be
            set for normally open or closed. The relay can be forced
            to an on or off condition, or controlled by the keypad.
            This variable is stored in non-volatile memory."
    ::= { FalconRelay2  1 }

FalconRelay2Status OBJECT-TYPE
    SYNTAX  INTEGER {
    NormalOff(1),
    NormalOn(2),
    ForcedOn(3),
    ForcedOff(4),
    KeycodeActive(5),
    AlarmedActive(6)
}
    ACCESS  read-only
    STATUS  mandatory
    DESCRIPTION
           "The current status for relay 2."
    ::= { FalconRelay2  2 }

FalconRelay2Label OBJECT-TYPE
    SYNTAX  DisplayString
    ACCESS  read-write
    STATUS  mandatory
    DESCRIPTION
           "A user-defined text string associated with Relay Number 2.
            The text string is stored in non-volatile memory."
    ::= { FalconRelay2  3 }

FalconRelay2Time OBJECT-TYPE
    SYNTAX  INTEGER (-2147483648..2147483647)
    MAX-ACCESS read-write
    STATUS     mandatory
    DESCRIPTION
        "The number of seconds the relay will be activated.
         Set this to -1 for indefinitely."
    ::= { FalconRelay2  4 }

FalconRelay3 OBJECT IDENTIFIER ::= { FalconOutputs 3 }

FalconRelay3State OBJECT-TYPE
    SYNTAX  INTEGER {
    NormallyOff(1),
    NormallyOn(2),
    ForceOn(3),
    ForceOff(4),
    KeypadControlled(5)
}
    ACCESS  read-write
    STATUS  mandatory
    DESCRIPTION
           "The state of use of Relay Number 3. The relay can be
            set for normally open or closed. The relay can be forced
            to an on or off condition, or controlled by the keypad.
            This variable is stored in non-volatile memory."
    ::= { FalconRelay3  1 }

FalconRelay3Status OBJECT-TYPE
    SYNTAX  INTEGER {
    NormalOff(1),
    NormalOn(2),
    ForcedOn(3),
    ForcedOff(4),
    KeycodeActive(5),
    AlarmedActive(6)
}
    ACCESS  read-only
    STATUS  mandatory
    DESCRIPTION
           "The current status for relay 3."
    ::= { FalconRelay3  2 }

FalconRelay3Label OBJECT-TYPE
    SYNTAX  DisplayString
    ACCESS  read-write
    STATUS  mandatory
    DESCRIPTION
           "A user-defined text string associated with Relay Number 3.
            The text string is stored in non-volatile memory."
    ::= { FalconRelay3  3 }

FalconRelay3Time OBJECT-TYPE
    SYNTAX  INTEGER (-2147483648..2147483647)
    MAX-ACCESS read-write
    STATUS     mandatory
    DESCRIPTION
        "The number of seconds the relay will be activated.
         Set this to -1 for indefinitely."
    ::= { FalconRelay3  4 }

FalconRelay4 OBJECT IDENTIFIER ::= { FalconOutputs 4 }

FalconRelay4State OBJECT-TYPE
    SYNTAX  INTEGER {
    NormallyOff(1),
    NormallyOn(2),
    ForceOn(3),
    ForceOff(4),
    KeypadControlled(5)
}
    ACCESS  read-write
    STATUS  mandatory
    DESCRIPTION
           "The state of use of Relay Number 4. The relay can be
            set for normally open or closed. The relay can be forced
            to an on or off condition, or controlled by the keypad.
            This variable is stored in non-volatile memory."
    ::= { FalconRelay4  1 }

FalconRelay4Status OBJECT-TYPE
    SYNTAX  INTEGER {
    NormalOff(1),
    NormalOn(2),
    ForcedOn(3),
    ForcedOff(4),
    KeycodeActive(5),
    AlarmedActive(6)
}
    ACCESS  read-only
    STATUS  mandatory
    DESCRIPTION
           "The current status for relay 4."
    ::= { FalconRelay4  2 }

FalconRelay4Label OBJECT-TYPE
    SYNTAX  DisplayString
    ACCESS  read-write
    STATUS  mandatory
    DESCRIPTION
           "A user-defined text string associated with Relay Number 4.
            The text string is stored in non-volatile memory."
    ::= { FalconRelay4  3 }

FalconRelay4Time OBJECT-TYPE
    SYNTAX  INTEGER (-2147483648..2147483647)
    MAX-ACCESS read-write
    STATUS     mandatory
    DESCRIPTION
        "The number of seconds the relay will be activated.
         Set this to -1 for indefinitely."
    ::= { FalconRelay4  4 }

FalconRelay5 OBJECT IDENTIFIER ::= { FalconOutputs 5 }

FalconRelay5State OBJECT-TYPE
    SYNTAX  INTEGER {
    NormallyOff(1),
    NormallyOn(2),
    ForceOn(3),
    ForceOff(4),
    KeypadControlled(5)
}
    ACCESS  read-write
    STATUS  mandatory
    DESCRIPTION
           "The state of use of Relay Number 5. The relay can be
            set for normally open or closed. The relay can be forced
            to an on or off condition, or controlled by the keypad.
            This variable is stored in non-volatile memory."
    ::= { FalconRelay5  1 }

FalconRelay5Status OBJECT-TYPE
    SYNTAX  INTEGER {
    NormalOff(1),
    NormalOn(2),
    ForcedOn(3),
    ForcedOff(4),
    KeycodeActive(5),
    AlarmedActive(6)
}
    ACCESS  read-only
    STATUS  mandatory
    DESCRIPTION
           "The current status for relay 5."
    ::= { FalconRelay5  2 }

FalconRelay5Label OBJECT-TYPE
    SYNTAX  DisplayString
    ACCESS  read-write
    STATUS  mandatory
    DESCRIPTION
           "A user-defined text string associated with Relay Number 5.
            The text string is stored in non-volatile memory."
    ::= { FalconRelay5  3 }

FalconRelay5Time OBJECT-TYPE
    SYNTAX  INTEGER (-2147483648..2147483647)
    MAX-ACCESS read-write
    STATUS     mandatory
    DESCRIPTION
        "The number of seconds the relay will be activated.
         Set this to -1 for indefinitely."
    ::= { FalconRelay5  4 }

FalconRelay6 OBJECT IDENTIFIER ::= { FalconOutputs 6 }

FalconRelay6State OBJECT-TYPE
    SYNTAX  INTEGER {
    NormallyOff(1),
    NormallyOn(2),
    ForceOn(3),
    ForceOff(4),
    KeypadControlled(5)
}
    ACCESS  read-write
    STATUS  mandatory
    DESCRIPTION
           "The state of use of Relay Number 6. The relay can be
            set for normally open or closed. The relay can be forced
            to an on or off condition, or controlled by the keypad.
            This variable is stored in non-volatile memory."
    ::= { FalconRelay6  1 }

FalconRelay6Status OBJECT-TYPE
    SYNTAX  INTEGER {
    NormalOff(1),
    NormalOn(2),
    ForcedOn(3),
    ForcedOff(4),
    KeycodeActive(5),
    AlarmedActive(6)
}
    ACCESS  read-only
    STATUS  mandatory
    DESCRIPTION
           "The current status for relay 6."
    ::= { FalconRelay6  2 }

FalconRelay6Label OBJECT-TYPE
    SYNTAX  DisplayString
    ACCESS  read-write
    STATUS  mandatory
    DESCRIPTION
           "A user-defined text string associated with Relay Number 6.
            The text string is stored in non-volatile memory."
    ::= { FalconRelay6  3 }

FalconRelay6Time OBJECT-TYPE
    SYNTAX  INTEGER (-2147483648..2147483647)
    MAX-ACCESS read-write
    STATUS     mandatory
    DESCRIPTION
        "The number of seconds the relay will be activated.
         Set this to -1 for indefinitely."
    ::= { FalconRelay6  4 }

FalconAlarms OBJECT IDENTIFIER ::= { FalconMIB  5 }

FalconAlarmsPresent OBJECT-TYPE
    SYNTAX     Gauge32
    MAX-ACCESS read-only
    STATUS     current
    DESCRIPTION
        "The present number of active alarm conditions."
    ::= { FalconAlarms 1 }

FalconAlarmTable OBJECT-TYPE
    SYNTAX     SEQUENCE OF FalconAlarmEntry
    MAX-ACCESS not-accessible
    STATUS     current
    DESCRIPTION
       "A list of alarm table entries.  The table contains
        zero, one, or many rows at any moment, depending upon
        the number of alarm conditions in effect.  The table
        is initially empty at agent startup.  The agent
        creates a row in the table each time a condition is
        detected and deletes that row when that condition no
        longer pertains.  The agent creates the first row with
        FalconAlarmId equal to 1, and increments the value of
        FalconAlarmId each time a new row is created, wrapping to
        the first free value greater than or equal to 1 when
        the maximum value of FalconAlarmId would otherwise be
        exceeded.  Consequently, after multiple operations,
        the table may become sparse, e.g., containing entries
        for rows 95, 100, 101, and 203 and the entries should
        not be assumed to be in chronological order because
        FalconAlarmId might have wrapped.

        Alarms are named by an AutonomousType (OBJECT
        IDENTIFIER), FalconAlarmDescr, to allow a single table to
        reflect well known alarms plus alarms defined by a
        particular implementation, i.e., as documented in the
        private enterprise MIB definition for the device.  No
        two rows will have the same value of FalconAlarmDescr,
        since alarms define conditions.  In order to meet this
        requirement, care should be taken in the definition of
        alarm conditions to insure that a system cannot enter
        the same condition multiple times simultaneously.

        The number of rows in the table at any given time is
        reflected by the value of FalconAlarmsPresent."
    ::= { FalconAlarms 2 }

FalconAlarmEntry OBJECT-TYPE
    SYNTAX     FalconAlarmEntry
    MAX-ACCESS not-accessible
    STATUS     current
    DESCRIPTION
         "An entry containing information applicable to a
         particular alarm."
   INDEX { FalconAlarmId }
   ::= { FalconAlarmTable 1 }

FalconAlarmEntry ::= SEQUENCE {
    FalconAlarmId          PositiveInteger,
    FalconAlarmDescr       OBJECT IDENTIFIER
}

FalconAlarmId OBJECT-TYPE
    SYNTAX     PositiveInteger
    MAX-ACCESS not-accessible
    STATUS     current
    DESCRIPTION
         "A unique identifier for an alarm condition.  This
          value must remain constant."
    ::= { FalconAlarmEntry 1 }

FalconAlarmDescr OBJECT-TYPE
    SYNTAX     OBJECT IDENTIFIER
    MAX-ACCESS read-only
    STATUS     current
    DESCRIPTION
        "A reference to an alarm description object.  The
         object referenced should not be accessible, but rather
         be used to provide a unique description of the alarm
         condition."
    ::= { FalconAlarmEntry 2 }

--
-- Well known alarm conditions.
--

FalconWellKnownAlarms    OBJECT IDENTIFIER ::= { FalconAlarms 3 }

FalconInput1HighAlarm OBJECT-IDENTITY
    STATUS     current
    DESCRIPTION
        "The reading for sensor 1 has reached the high limit
        value."
    ::= { FalconWellKnownAlarms  1 }

FalconInput1LowAlarm OBJECT-IDENTITY
    STATUS     current
    DESCRIPTION
        "The reading for sensor 1 has reached the low limit
        value."
    ::= { FalconWellKnownAlarms  2 }

FalconInput1High2Alarm OBJECT-IDENTITY
    STATUS     current
    DESCRIPTION
        "The reading for sensor 1 has reached the high limit
        value."
    ::= { FalconWellKnownAlarms  3 }

FalconInput1Low2Alarm OBJECT-IDENTITY
    STATUS     current
    DESCRIPTION
        "The reading for sensor 1 has reached the low limit
        value."
    ::= { FalconWellKnownAlarms  4 }

FalconInput2HighAlarm OBJECT-IDENTITY
    STATUS     current
    DESCRIPTION
        "The reading for sensor 2 has reached the high limit
        value."
    ::= { FalconWellKnownAlarms  5 }

FalconInput2LowAlarm OBJECT-IDENTITY
    STATUS     current
    DESCRIPTION
        "The reading for sensor 2 has reached the low limit
        value."
    ::= { FalconWellKnownAlarms  6 }

FalconInput2High2Alarm OBJECT-IDENTITY
    STATUS     current
    DESCRIPTION
        "The reading for sensor 2 has reached the high limit
        value."
    ::= { FalconWellKnownAlarms  7 }

FalconInput2Low2Alarm OBJECT-IDENTITY
    STATUS     current
    DESCRIPTION
        "The reading for sensor 2 has reached the low limit
        value."
    ::= { FalconWellKnownAlarms  8 }

FalconInput3HighAlarm OBJECT-IDENTITY
    STATUS     current
    DESCRIPTION
        "The reading for sensor 3 has reached the high limit
        value."
    ::= { FalconWellKnownAlarms  9 }

FalconInput3LowAlarm OBJECT-IDENTITY
    STATUS     current
    DESCRIPTION
        "The reading for sensor 3 has reached the low limit
        value."
    ::= { FalconWellKnownAlarms  10 }

FalconInput3High2Alarm OBJECT-IDENTITY
    STATUS     current
    DESCRIPTION
        "The reading for sensor 3 has reached the high limit
        value."
    ::= { FalconWellKnownAlarms  11 }

FalconInput3Low2Alarm OBJECT-IDENTITY
    STATUS     current
    DESCRIPTION
        "The reading for sensor 3 has reached the low limit
        value."
    ::= { FalconWellKnownAlarms  12 }

FalconInput4HighAlarm OBJECT-IDENTITY
    STATUS     current
    DESCRIPTION
        "The reading for sensor 4 has reached the high limit
        value."
    ::= { FalconWellKnownAlarms  13 }

FalconInput4LowAlarm OBJECT-IDENTITY
    STATUS     current
    DESCRIPTION
        "The reading for sensor 4 has reached the low limit
        value."
    ::= { FalconWellKnownAlarms  14 }

FalconInput4High2Alarm OBJECT-IDENTITY
    STATUS     current
    DESCRIPTION
        "The reading for sensor 4 has reached the high limit
        value."
    ::= { FalconWellKnownAlarms  15 }

FalconInput4Low2Alarm OBJECT-IDENTITY
    STATUS     current
    DESCRIPTION
        "The reading for sensor 4 has reached the low limit
        value."
    ::= { FalconWellKnownAlarms  16 }

FalconInput5HighAlarm OBJECT-IDENTITY
    STATUS     current
    DESCRIPTION
        "The reading for sensor 5 has reached the high limit
        value."
    ::= { FalconWellKnownAlarms  17 }

FalconInput5LowAlarm OBJECT-IDENTITY
    STATUS     current
    DESCRIPTION
        "The reading for sensor 5 has reached the low limit
        value."
    ::= { FalconWellKnownAlarms  18 }

FalconInput5High2Alarm OBJECT-IDENTITY
    STATUS     current
    DESCRIPTION
        "The reading for sensor 5 has reached the high limit
        value."
    ::= { FalconWellKnownAlarms  19 }

FalconInput5Low2Alarm OBJECT-IDENTITY
    STATUS     current
    DESCRIPTION
        "The reading for sensor 5 has reached the low limit
        value."
    ::= { FalconWellKnownAlarms  20 }

FalconInput6HighAlarm OBJECT-IDENTITY
    STATUS     current
    DESCRIPTION
        "The reading for sensor 6 has reached the high limit
        value."
    ::= { FalconWellKnownAlarms  21 }

FalconInput6LowAlarm OBJECT-IDENTITY
    STATUS     current
    DESCRIPTION
        "The reading for sensor 6 has reached the low limit
        value."
    ::= { FalconWellKnownAlarms  22 }

FalconInput6High2Alarm OBJECT-IDENTITY
    STATUS     current
    DESCRIPTION
        "The reading for sensor 6 has reached the high limit
        value."
    ::= { FalconWellKnownAlarms  23 }

FalconInput6Low2Alarm OBJECT-IDENTITY
    STATUS     current
    DESCRIPTION
        "The reading for sensor 6 has reached the low limit
        value."
    ::= { FalconWellKnownAlarms  24 }

FalconInput7HighAlarm OBJECT-IDENTITY
    STATUS     current
    DESCRIPTION
        "The reading for sensor 7 has reached the high limit
        value."
    ::= { FalconWellKnownAlarms  25 }

FalconInput7LowAlarm OBJECT-IDENTITY
    STATUS     current
    DESCRIPTION
        "The reading for sensor 7 has reached the low limit
        value."
    ::= { FalconWellKnownAlarms  26 }

FalconInput7High2Alarm OBJECT-IDENTITY
    STATUS     current
    DESCRIPTION
        "The reading for sensor 7 has reached the high limit
        value."
    ::= { FalconWellKnownAlarms  27 }

FalconInput7Low2Alarm OBJECT-IDENTITY
    STATUS     current
    DESCRIPTION
        "The reading for sensor 7 has reached the low limit
        value."
    ::= { FalconWellKnownAlarms  28 }

FalconInput8HighAlarm OBJECT-IDENTITY
    STATUS     current
    DESCRIPTION
        "The reading for sensor 8 has reached the high limit
        value."
    ::= { FalconWellKnownAlarms  29 }

FalconInput8LowAlarm OBJECT-IDENTITY
    STATUS     current
    DESCRIPTION
        "The reading for sensor 8 has reached the low limit
        value."
    ::= { FalconWellKnownAlarms  30 }

FalconInput8High2Alarm OBJECT-IDENTITY
    STATUS     current
    DESCRIPTION
        "The reading for sensor 8 has reached the high limit
        value."
    ::= { FalconWellKnownAlarms  31 }

FalconInput8Low2Alarm OBJECT-IDENTITY
    STATUS     current
    DESCRIPTION
        "The reading for sensor 8 has reached the low limit
        value."
    ::= { FalconWellKnownAlarms  32 }

FalconInput9HighAlarm OBJECT-IDENTITY
    STATUS     current
    DESCRIPTION
        "The reading for sensor 9 has reached the high limit
        value."
    ::= { FalconWellKnownAlarms  33 }

FalconInput9LowAlarm OBJECT-IDENTITY
    STATUS     current
    DESCRIPTION
        "The reading for sensor 9 has reached the low limit
        value."
    ::= { FalconWellKnownAlarms  34 }

FalconInput9High2Alarm OBJECT-IDENTITY
    STATUS     current
    DESCRIPTION
        "The reading for sensor 9 has reached the high limit
        value."
    ::= { FalconWellKnownAlarms  35 }

FalconInput9Low2Alarm OBJECT-IDENTITY
    STATUS     current
    DESCRIPTION
        "The reading for sensor 9 has reached the low limit
        value."
    ::= { FalconWellKnownAlarms  36 }

FalconInput10HighAlarm OBJECT-IDENTITY
    STATUS     current
    DESCRIPTION
        "The reading for sensor 10 has reached the high limit
        value."
    ::= { FalconWellKnownAlarms  37 }

FalconInput10LowAlarm OBJECT-IDENTITY
    STATUS     current
    DESCRIPTION
        "The reading for sensor 10 has reached the low limit
        value."
    ::= { FalconWellKnownAlarms  38 }

FalconInput10High2Alarm OBJECT-IDENTITY
    STATUS     current
    DESCRIPTION
        "The reading for sensor 10 has reached the high limit
        value."
    ::= { FalconWellKnownAlarms  39 }

FalconInput10Low2Alarm OBJECT-IDENTITY
    STATUS     current
    DESCRIPTION
        "The reading for sensor 10 has reached the low limit
        value."
    ::= { FalconWellKnownAlarms  40 }

FalconInput11HighAlarm OBJECT-IDENTITY
    STATUS     current
    DESCRIPTION
        "The reading for sensor 11 has reached the high limit
        value."
    ::= { FalconWellKnownAlarms  41 }

FalconInput11LowAlarm OBJECT-IDENTITY
    STATUS     current
    DESCRIPTION
        "The reading for sensor 11 has reached the low limit
        value."
    ::= { FalconWellKnownAlarms  42 }

FalconInput11High2Alarm OBJECT-IDENTITY
    STATUS     current
    DESCRIPTION
        "The reading for sensor 11 has reached the high limit
        value."
    ::= { FalconWellKnownAlarms  43 }

FalconInput11Low2Alarm OBJECT-IDENTITY
    STATUS     current
    DESCRIPTION
        "The reading for sensor 11 has reached the low limit
        value."
    ::= { FalconWellKnownAlarms  44 }

FalconInput12HighAlarm OBJECT-IDENTITY
    STATUS     current
    DESCRIPTION
        "The reading for sensor 12 has reached the high limit
        value."
    ::= { FalconWellKnownAlarms  45 }

FalconInput12LowAlarm OBJECT-IDENTITY
    STATUS     current
    DESCRIPTION
        "The reading for sensor 12 has reached the low limit
        value."
    ::= { FalconWellKnownAlarms  46 }

FalconInput12High2Alarm OBJECT-IDENTITY
    STATUS     current
    DESCRIPTION
        "The reading for sensor 12 has reached the high limit
        value."
    ::= { FalconWellKnownAlarms  47 }

FalconInput12Low2Alarm OBJECT-IDENTITY
    STATUS     current
    DESCRIPTION
        "The reading for sensor 12 has reached the low limit
        value."
    ::= { FalconWellKnownAlarms  48 }

FalconInput13HighAlarm OBJECT-IDENTITY
    STATUS     current
    DESCRIPTION
        "The reading for sensor 13 has reached the high limit
        value."
    ::= { FalconWellKnownAlarms  49 }

FalconInput13LowAlarm OBJECT-IDENTITY
    STATUS     current
    DESCRIPTION
        "The reading for sensor 13 has reached the low limit
        value."
    ::= { FalconWellKnownAlarms  50 }

FalconInput13High2Alarm OBJECT-IDENTITY
    STATUS     current
    DESCRIPTION
        "The reading for sensor 13 has reached the high limit
        value."
    ::= { FalconWellKnownAlarms  51 }

FalconInput13Low2Alarm OBJECT-IDENTITY
    STATUS     current
    DESCRIPTION
        "The reading for sensor 13 has reached the low limit
        value."
    ::= { FalconWellKnownAlarms  52 }

FalconInput14HighAlarm OBJECT-IDENTITY
    STATUS     current
    DESCRIPTION
        "The reading for sensor 14 has reached the high limit
        value."
    ::= { FalconWellKnownAlarms  53 }

FalconInput14LowAlarm OBJECT-IDENTITY
    STATUS     current
    DESCRIPTION
        "The reading for sensor 14 has reached the low limit
        value."
    ::= { FalconWellKnownAlarms  54 }

FalconInput14High2Alarm OBJECT-IDENTITY
    STATUS     current
    DESCRIPTION
        "The reading for sensor 14 has reached the high limit
        value."
    ::= { FalconWellKnownAlarms  55 }

FalconInput14Low2Alarm OBJECT-IDENTITY
    STATUS     current
    DESCRIPTION
        "The reading for sensor 14 has reached the low limit
        value."
    ::= { FalconWellKnownAlarms  56 }

FalconInput15HighAlarm OBJECT-IDENTITY
    STATUS     current
    DESCRIPTION
        "The reading for sensor 15 has reached the high limit
        value."
    ::= { FalconWellKnownAlarms  57 }

FalconInput15LowAlarm OBJECT-IDENTITY
    STATUS     current
    DESCRIPTION
        "The reading for sensor 15 has reached the low limit
        value."
    ::= { FalconWellKnownAlarms  58 }

FalconInput15High2Alarm OBJECT-IDENTITY
    STATUS     current
    DESCRIPTION
        "The reading for sensor 15 has reached the high limit
        value."
    ::= { FalconWellKnownAlarms  59 }

FalconInput15Low2Alarm OBJECT-IDENTITY
    STATUS     current
    DESCRIPTION
        "The reading for sensor 15 has reached the low limit
        value."
    ::= { FalconWellKnownAlarms  60 }

FalconInput16HighAlarm OBJECT-IDENTITY
    STATUS     current
    DESCRIPTION
        "The reading for sensor 16 has reached the high limit
        value."
    ::= { FalconWellKnownAlarms  61 }

FalconInput16LowAlarm OBJECT-IDENTITY
    STATUS     current
    DESCRIPTION
        "The reading for sensor 16 has reached the low limit
        value."
    ::= { FalconWellKnownAlarms  62 }

FalconInput16High2Alarm OBJECT-IDENTITY
    STATUS     current
    DESCRIPTION
        "The reading for sensor 16 has reached the high limit
        value."
    ::= { FalconWellKnownAlarms  63 }

FalconInput16Low2Alarm OBJECT-IDENTITY
    STATUS     current
    DESCRIPTION
        "The reading for sensor 16 has reached the low limit
        value."
    ::= { FalconWellKnownAlarms  64 }

FalconInput17HighAlarm OBJECT-IDENTITY
    STATUS     current
    DESCRIPTION
        "The reading for sensor 17 has reached the high limit
        value."
    ::= { FalconWellKnownAlarms  65 }

FalconInput17LowAlarm OBJECT-IDENTITY
    STATUS     current
    DESCRIPTION
        "The reading for sensor 17 has reached the low limit
        value."
    ::= { FalconWellKnownAlarms  66 }

FalconInput17High2Alarm OBJECT-IDENTITY
    STATUS     current
    DESCRIPTION
        "The reading for sensor 17 has reached the high limit
        value."
    ::= { FalconWellKnownAlarms  67 }

FalconInput17Low2Alarm OBJECT-IDENTITY
    STATUS     current
    DESCRIPTION
        "The reading for sensor 17 has reached the low limit
        value."
    ::= { FalconWellKnownAlarms  68 }

FalconInput18HighAlarm OBJECT-IDENTITY
    STATUS     current
    DESCRIPTION
        "The reading for sensor 18 has reached the high limit
        value."
    ::= { FalconWellKnownAlarms  69 }

FalconInput18LowAlarm OBJECT-IDENTITY
    STATUS     current
    DESCRIPTION
        "The reading for sensor 18 has reached the low limit
        value."
    ::= { FalconWellKnownAlarms  70 }

FalconInput18High2Alarm OBJECT-IDENTITY
    STATUS     current
    DESCRIPTION
        "The reading for sensor 18 has reached the high limit
        value."
    ::= { FalconWellKnownAlarms  71 }

FalconInput18Low2Alarm OBJECT-IDENTITY
    STATUS     current
    DESCRIPTION
        "The reading for sensor 18 has reached the low limit
        value."
    ::= { FalconWellKnownAlarms  72 }

FalconInput19HighAlarm OBJECT-IDENTITY
    STATUS     current
    DESCRIPTION
        "The reading for sensor 19 has reached the high limit
        value."
    ::= { FalconWellKnownAlarms  73 }

FalconInput19LowAlarm OBJECT-IDENTITY
    STATUS     current
    DESCRIPTION
        "The reading for sensor 19 has reached the low limit
        value."
    ::= { FalconWellKnownAlarms  74 }

FalconInput19High2Alarm OBJECT-IDENTITY
    STATUS     current
    DESCRIPTION
        "The reading for sensor 19 has reached the high limit
        value."
    ::= { FalconWellKnownAlarms  75 }

FalconInput19Low2Alarm OBJECT-IDENTITY
    STATUS     current
    DESCRIPTION
        "The reading for sensor 19 has reached the low limit
        value."
    ::= { FalconWellKnownAlarms  76 }

FalconInput20HighAlarm OBJECT-IDENTITY
    STATUS     current
    DESCRIPTION
        "The reading for sensor 20 has reached the high limit
        value."
    ::= { FalconWellKnownAlarms  77 }

FalconInput20LowAlarm OBJECT-IDENTITY
    STATUS     current
    DESCRIPTION
        "The reading for sensor 20 has reached the low limit
        value."
    ::= { FalconWellKnownAlarms  78 }

FalconInput20High2Alarm OBJECT-IDENTITY
    STATUS     current
    DESCRIPTION
        "The reading for sensor 20 has reached the high limit
        value."
    ::= { FalconWellKnownAlarms  79 }

FalconInput20Low2Alarm OBJECT-IDENTITY
    STATUS     current
    DESCRIPTION
        "The reading for sensor 20 has reached the low limit
        value."
    ::= { FalconWellKnownAlarms  80 }

FalconInput1DigAlarm OBJECT-IDENTITY
    STATUS     current
    DESCRIPTION
        "The digital input 1 has been activated."
    ::= { FalconWellKnownAlarms  81 }

FalconInput2DigAlarm OBJECT-IDENTITY
    STATUS     current
    DESCRIPTION
        "The digital input 2 has been activated."
    ::= { FalconWellKnownAlarms  82 }

FalconInput3DigAlarm OBJECT-IDENTITY
    STATUS     current
    DESCRIPTION
        "The digital input 3 has been activated."
    ::= { FalconWellKnownAlarms  83 }

FalconInput4DigAlarm OBJECT-IDENTITY
    STATUS     current
    DESCRIPTION
        "The digital input 4 has been activated."
    ::= { FalconWellKnownAlarms  84 }

FalconInput5DigAlarm OBJECT-IDENTITY
    STATUS     current
    DESCRIPTION
        "The digital input 5 has been activated."
    ::= { FalconWellKnownAlarms  85 }

FalconInput6DigAlarm OBJECT-IDENTITY
    STATUS     current
    DESCRIPTION
        "The digital input 6 has been activated."
    ::= { FalconWellKnownAlarms  86 }

FalconInput7DigAlarm OBJECT-IDENTITY
    STATUS     current
    DESCRIPTION
        "The digital input 7 has been activated."
    ::= { FalconWellKnownAlarms  87 }

FalconInput8DigAlarm OBJECT-IDENTITY
    STATUS     current
    DESCRIPTION
        "The digital input 8 has been activated."
    ::= { FalconWellKnownAlarms  88 }

FalconInput9DigAlarm OBJECT-IDENTITY
    STATUS     current
    DESCRIPTION
        "The digital input 9 has been activated."
    ::= { FalconWellKnownAlarms  89 }

FalconInput10DigAlarm OBJECT-IDENTITY
    STATUS     current
    DESCRIPTION
        "The digital input 10 has been activated."
    ::= { FalconWellKnownAlarms  90 }

FalconInput11DigAlarm OBJECT-IDENTITY
    STATUS     current
    DESCRIPTION
        "The digital input 11 has been activated."
    ::= { FalconWellKnownAlarms  91 }

FalconInput12DigAlarm OBJECT-IDENTITY
    STATUS     current
    DESCRIPTION
        "The digital input 12 has been activated."
    ::= { FalconWellKnownAlarms  92 }

FalconInput13DigAlarm OBJECT-IDENTITY
    STATUS     current
    DESCRIPTION
        "The digital input 13 has been activated."
    ::= { FalconWellKnownAlarms  93 }

FalconInput14DigAlarm OBJECT-IDENTITY
    STATUS     current
    DESCRIPTION
        "The digital input 14 has been activated."
    ::= { FalconWellKnownAlarms  94 }

FalconInput15DigAlarm OBJECT-IDENTITY
    STATUS     current
    DESCRIPTION
        "The digital input 15 has been activated."
    ::= { FalconWellKnownAlarms  95 }

FalconInput16DigAlarm OBJECT-IDENTITY
    STATUS     current
    DESCRIPTION
        "The digital input 16 has been activated."
    ::= { FalconWellKnownAlarms  96 }

FalconInput17DigAlarm OBJECT-IDENTITY
    STATUS     current
    DESCRIPTION
        "The digital input 17 has been activated."
    ::= { FalconWellKnownAlarms  97 }

FalconInput18DigAlarm OBJECT-IDENTITY
    STATUS     current
    DESCRIPTION
        "The digital input 18 has been activated."
    ::= { FalconWellKnownAlarms  98 }

FalconInput19DigAlarm OBJECT-IDENTITY
    STATUS     current
    DESCRIPTION
        "The digital input 19 has been activated."
    ::= { FalconWellKnownAlarms  99 }

FalconInput20DigAlarm OBJECT-IDENTITY
    STATUS     current
    DESCRIPTION
        "The digital input 20 has been activated."
    ::= { FalconWellKnownAlarms  100 }

FalconOnBatteryAlarm OBJECT-IDENTITY
    STATUS     current
    DESCRIPTION
        "The On Battery input has been activated."
    ::= { FalconWellKnownAlarms  102 }

FalconLowBatteryAlarm OBJECT-IDENTITY
    STATUS     current
    DESCRIPTION
        "The Faclon has detected a low battery condition."
    ::= { FalconWellKnownAlarms  103 }

FalconTraps OBJECT IDENTIFIER ::= { FalconMIB  6 }

FalconAlarmEntryAdded TRAP-TYPE
    ENTERPRISE   FalconTraps 
    DESCRIPTION
           "An AlarmEntryAdded Trap signifies that the a sensor
            reading has reached a high or low limit value."
    ::= 1

FalconAlarmEntryRemoved TRAP-TYPE
    ENTERPRISE   FalconTraps 
    DESCRIPTION
           "An AlarmEntryAdded Trap signifies that the a sensor
            reading has gone below the high limit value or above
            the low limit value."
    ::= 2

FalconAccessGranted TRAP-TYPE
    ENTERPRISE   FalconTraps 
    DESCRIPTION
           "An FalconAccessGranted Trap signifies that a valid
            key code sequence was processed by the Falcon."
    ::= 3

FalconAccessDenied TRAP-TYPE
    ENTERPRISE   FalconTraps 
    DESCRIPTION
           "An FalconAccessedDenied Trap signifies that an invalid
            key code sequence was processed by the Falcon."
    ::= 4

FalconAlarmHistory OBJECT IDENTIFIER ::= { FalconMIB  7 }

FalconAlarmHistoryEntries OBJECT-TYPE
    SYNTAX     Gauge32
    MAX-ACCESS read-only
    STATUS     current
    DESCRIPTION
        "The present number of entries in the alarm history."
    ::= { FalconAlarmHistory 1 }

FalconAlarmHistoryClear OBJECT-TYPE
    SYNTAX  INTEGER {
    ClearBuffer(1)
}
    ACCESS  read-write
    STATUS  mandatory
    DESCRIPTION
           "Setting this value to ClearBuffer(1) will clear the
            alarm history buffer. "
    ::= { FalconAlarmHistory 2 }

FalconAlarmHistoryTable OBJECT-TYPE
    SYNTAX     SEQUENCE OF FalconAlarmHistoryEntry
    MAX-ACCESS not-accessible
    STATUS     current
    DESCRIPTION
       "A list of alarm history table entries stored in the
        in the non-volatile memory.  The table contains zero,
        one, or many rows at any moment, depending upon the
        number of alarm conditions in effect. The Falcon creates
        a row in the table each time a new alarm is detected.
        The Falcon creates the first row with FalconAlarmHistoryId
        equal to 1, and increments the value of FalconAlarmHistoryId
        each time a new row is created, up to a maximum of 100.
        After 100 entries are created, the Falcon will overwrite
        the earliest entry with the latest alarm.
        The number of rows in the table at any given time is
        reflected by the value of FalconAlarmHistoryEntries."
    ::= { FalconAlarmHistory 3 }

FalconAlarmHistoryEntry OBJECT-TYPE
    SYNTAX     FalconAlarmHistoryEntry
    MAX-ACCESS not-accessible
    STATUS     current
    DESCRIPTION
         "An entry containing information applicable to a
         particular alarm history entry."
   INDEX { FalconAlarmHistoryId }
   ::= { FalconAlarmHistoryTable 1 }

FalconAlarmHistoryEntry ::= SEQUENCE {
    FalconAlarmHistoryId     PositiveInteger,
    FalconAlarmHistoryText   DisplayString
}

FalconAlarmHistoryId OBJECT-TYPE
    SYNTAX     PositiveInteger
    MAX-ACCESS not-accessible
    STATUS     current
    DESCRIPTION
         "A unique identifier for an alarm condition.  This
          value must remain constant."
    ::= { FalconAlarmHistoryEntry 1 }

FalconAlarmHistoryText OBJECT-TYPE
    SYNTAX     DisplayString
    MAX-ACCESS read-only
    STATUS     current
    DESCRIPTION
        "A text desciption of the alarm history entry.
         Each of the strings will have the following format,
         AHxxx-id-type-timestamp label
         xxx  = number entry in the table
         id   = Alarm ID
         type = HIGH, LOW, ALM or RTN
         timestamp = MM/DD/YY HH:MM:SS
         Label = The label associated with the input channel
         These alarms are stored in non-volatile memory."
    ::= { FalconAlarmHistoryEntry 2 }

FalconTrapSettings OBJECT IDENTIFIER ::= { FalconMIB  8 }

FalconPersistantTraps OBJECT-TYPE
    SYNTAX  INTEGER (0..2147483647)
    MAX-ACCESS read-write
    STATUS     mandatory
    DESCRIPTION
        "The number of minutes between persistant traps.
         Set this to 0 to turn off persistant traps.
         This value is stored in non-volatile memory."
    ::= { FalconTrapSettings 1 }

FalconAlarmAcknowledge OBJECT-TYPE
    SYNTAX  INTEGER {
    AcknowledgeAlarms(1)
}
    ACCESS  read-write
    STATUS  mandatory
    DESCRIPTION
           "Setting this value to AcknowledgeAlarms(1) will
            stop the Falcon from sending persistant traps
            and dial out sequences."
    ::= { FalconTrapSettings 2 }

--
-- The Falcon Extension
--
        Falcon812A4 OBJECT IDENTIFIER ::= { Falcon 4 }

END
