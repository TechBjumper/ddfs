-- Last edit: Fri Aug 02 12:03:52 2002
-- By: Yigal Hochberg, DMH Software
-- Sat Nov 18 2000: emacs local var for version mib-compiler 1.1.0
-- Fri Nov 17 2000: rename module to DemoMIB2-SMIV2 (was DemoMIB)
-- Fri Oct 13 2000: add compliance/conformance definitions,
--                  update imports, add comments.
-- Sun Feb 13 2000: upgrade to smiv2

-- *********************************************************************
-- **
-- ** Confidential and proprietary Information
-- **
-- ** Copyright (c) Yigal Hochberg, DMH Software 1990-2003
-- **
-- *********************************************************************
-- ** Filename:   ASCO_72EE-SMVI2.mib
-- ** Project:    Ethernet Adapter
-- ** Purpose:    ASCO requirement
-- ** Author:     Vardhaman
-- ** Created:    Tue Jan 29 2013
-- ** Comments:   To convert this mib to smiv2 use: smidump option: "-f SMIv1"
-- **E:\Test\SNMPV2 Stack\DMH-SMIv2-MIB-Compiler-1.4.3.0.5-2\DMH-SMIv2-MIB-Compiler-1.4.3.0.5-2\w32-bin>smidump -c smi.cfg -f dmhsnmp ASCO_72EE-SMVI2.mib
-- **Mib file and output path:E:\Test\SNMPV2 Stack\DMH-SMIv2-MIB-Compiler-1.4.3.0.5-2\DMH-SMIv2-MIB-Compiler-1.4.3.0.5-2\w32-bin
-- *********************************************************************
--**Last edit: Fri July 03 2013 By Vardhaman ver.2
--**Last edit: Mon Jan  06 2013 By Vardhaman ver.3
--**ASCO-72EE-SMIV2 DEFINITIONS ::= BEGIN

SNMP2ASCO72EEVER3 DEFINITIONS ::= BEGIN

IMPORTS

    MODULE-COMPLIANCE, OBJECT-GROUP
        FROM SNMPv2-CONF

    MODULE-IDENTITY, OBJECT-TYPE,NOTIFICATION-TYPE, enterprises, Counter32, Integer32
        FROM SNMPv2-SMI

    DisplayString
        FROM SNMPv2-TC;




-- A MIB with definitions for ASCO Version 2.0

		-- 1.3.6.1.4.1.7777
		asco OBJECT IDENTIFIER ::= { enterprises 7777 }


		-- 1.3.6.1.4.1.7777.1
		device OBJECT IDENTIFIER ::= { asco 1 }


		-- 1.3.6.1.4.1.7777.1.2.1
		groupG       OBJECT IDENTIFIER ::= { device 1 }
		dpmNormal    OBJECT IDENTIFIER ::= { device 2 }
		dpmEmergency OBJECT IDENTIFIER ::= { device 3 }
		dpmLoad      OBJECT IDENTIFIER ::= { device 4 }
		dpmOther     OBJECT IDENTIFIER ::= { device 5 }
		traps        OBJECT IDENTIFIER ::= { device 6 }

		-- 1.3.6.1.4.1.7777.1.2.1.1
		ggATSName OBJECT-TYPE
			SYNTAX DisplayString (SIZE (0..128))
			MAX-ACCESS read-only
			STATUS current
			DESCRIPTION
				"gg ATS name."
			::= { groupG 1 }


		-- 1.3.6.1.4.1.7777.1.2.1.2
		ggATSLocation OBJECT-TYPE
			SYNTAX DisplayString (SIZE (0..128))
			MAX-ACCESS read-only
			STATUS current
			DESCRIPTION
				"gg Location."
			::= { groupG 2 }


		-- 1.3.6.1.4.1.7777.1.2.1.3
		ggNominalVoltage OBJECT-TYPE
			SYNTAX Integer32
			MAX-ACCESS read-only
			STATUS current
			DESCRIPTION
				"Nominal Voltage."
			::= { groupG 3 }


		-- 1.3.6.1.4.1.7777.1.2.1.4
		ggNominalCurrent OBJECT-TYPE
			SYNTAX Integer32
			MAX-ACCESS read-only
			STATUS current
			DESCRIPTION
				"Nominal Current."
			::= { groupG 4 }


		-- 1.3.6.1.4.1.7777.1.2.1.5
		ggNominalFrequency OBJECT-TYPE
			SYNTAX Integer32
			MAX-ACCESS read-only
			STATUS current
			DESCRIPTION
				"Nominal Frequency."
			::= { groupG 5 }


		-- 1.3.6.1.4.1.7777.1.2.1.6
		ggSwitchType OBJECT-TYPE
			SYNTAX Integer32
			MAX-ACCESS read-only
			STATUS current
			DESCRIPTION
				"Switch type.0-OTTS,1-DTTS,2-NOT USED,3-OTTS"
			::= { groupG 6 }


		-- 1.3.6.1.4.1.7777.1.2.1.7
		ggCommonAlarm OBJECT-TYPE
			SYNTAX DisplayString (SIZE (0..128))
			MAX-ACCESS read-only
			STATUS current
			DESCRIPTION
				"Common alarm.Multiple alarm separated by '/'"
			::= { groupG 7 }


		-- 1.3.6.1.4.1.7777.1.2.1.8
		ggNotInAuto OBJECT-TYPE
			SYNTAX Integer32
			MAX-ACCESS read-only
			STATUS current
			DESCRIPTION
				"GG Not in Auto.
				 1-ACTIVE,
				 0-INACTIVE"
			::= { groupG 8 }


		-- 1.3.6.1.4.1.7777.1.2.1.9
		ggNormalContactor OBJECT-TYPE
			SYNTAX Integer32
			MAX-ACCESS read-only
			STATUS current
			DESCRIPTION
				"GG Normal Contactor.This(ggNormalContactor) value& ggEmergencyContactor
				both together define the load status if (ggNormalContactor/ggEmergencyContactor)is
				0/0-Load is disconnected
				1/0 -Load is on Normal
				0/1 - Load is on Emergency"
			::= { groupG 9 }

		-- 1.3.6.1.4.1.7777.1.2.1.10
		ggEmergencyContactor OBJECT-TYPE
			SYNTAX Integer32
			MAX-ACCESS read-only
			STATUS current
			DESCRIPTION
				"GG Emergency Contactor.This(ggEmergencyContactor) value& ggNormalContactor
				both together define the load status if (ggNormalContactor/ggEmergencyContactor)is
				0/0-Load is disconnected
				1/0 -Load is on Normal
				0/1 - Load is on Emergency"
			::= { groupG 10 }

		-- 1.3.6.1.4.1.7777.1.2.1.11
		ggEngineStartSignal OBJECT-TYPE
			SYNTAX Integer32
			MAX-ACCESS read-only
			STATUS current
			DESCRIPTION
				" Engine Start Signal .
				1 -Engine Start Signal
				0 -Engine Off Signal"
			::= { groupG 11 }

		-- 1.3.6.1.4.1.7777.1.2.1.12
		ggNormalVoltagePhaseAB OBJECT-TYPE
			SYNTAX Integer32
			MAX-ACCESS read-only
			STATUS current
			DESCRIPTION
				"GG Normal Voltage Phase AB."
			::= { groupG 12 }

		-- 1.3.6.1.4.1.7777.1.2.1.13
		ggNormalVoltagePhaseBC OBJECT-TYPE
			SYNTAX Integer32
			MAX-ACCESS read-only
			STATUS current
			DESCRIPTION
				"GG Normal Voltage Phase BC."
			::= { groupG 13 }

		-- 1.3.6.1.4.1.7777.1.2.1.14
  		ggNormalVoltagePhaseCA OBJECT-TYPE
			SYNTAX Integer32
			MAX-ACCESS read-only
			STATUS current
			DESCRIPTION
				"GG Normal Voltage Phase CA."
			::= { groupG 14 }

		-- 1.3.6.1.4.1.7777.1.2.1.15
  		ggEmergencyVoltagePhaseAB OBJECT-TYPE
			SYNTAX Integer32
			MAX-ACCESS read-only
			STATUS current
			DESCRIPTION
				"GG Emergency Voltage Phase AB.Ignore this value if single Phase available."
			::= { groupG 15 }

		-- 1.3.6.1.4.1.7777.1.2.1.16
		ggEmergencyVoltagePhaseBC OBJECT-TYPE
			SYNTAX Integer32
			MAX-ACCESS read-only
			STATUS current
			DESCRIPTION
				"GG Emergency Voltage Phase BC.Ignore this value if single Phase available."
			::= { groupG 16 }


		-- 1.3.6.1.4.1.7777.1.2.1.17
		ggEmergencyVoltagePhaseCA OBJECT-TYPE
			SYNTAX Integer32
			MAX-ACCESS read-only
			STATUS current
			DESCRIPTION
				"GG Emergency Voltage Phase CA."
			::= { groupG 17 }


		-- 1.3.6.1.4.1.7777.1.2.1.18
		ggNormalFrequency OBJECT-TYPE
			SYNTAX Integer32
			MAX-ACCESS read-only
			STATUS current
			DESCRIPTION
				"Normal Frequency in Hz."
			::= { groupG 18 }

		-- 1.3.6.1.4.1.7777.1.2.1.19
		ggEmergencyFrequency OBJECT-TYPE
			SYNTAX Integer32
			MAX-ACCESS read-only
			STATUS current
			DESCRIPTION
				"Emergency Frequency in Hz."
			::= { groupG 19 }


		-- 1.3.6.1.4.1.7777.1.2.1.20
		ggTotalTransfers OBJECT-TYPE
			SYNTAX Integer32
			MAX-ACCESS read-only
			STATUS current
			DESCRIPTION
				"GG Total Transfers."
			::= { groupG 20 }

		-- 1.3.6.1.4.1.7777.1.2.1.21
		ggTotalTimeOnNormal OBJECT-TYPE
			SYNTAX Integer32
			MAX-ACCESS read-only
			STATUS current
			DESCRIPTION
				"Total Time on Normal in Minutes."
			::= { groupG 21 }

		-- 1.3.6.1.4.1.7777.1.2.1.22
		ggTotalTimeOnEmergency OBJECT-TYPE
			SYNTAX Integer32
			MAX-ACCESS read-only
			STATUS current
			DESCRIPTION
				"Total Time on Emergency in Minutes."
			::= { groupG 22 }

		-- 1.3.6.1.4.1.7777.1.2.1.23
		ggFirmwareVersion OBJECT-TYPE
			SYNTAX DisplayString (SIZE (0..128))
			MAX-ACCESS read-only
			STATUS current
			DESCRIPTION
				"Firmware version."
			::= { groupG 23 }




-- gg end

        -- 1.3.6.1.4.1.7777.1.2.2.1
		dpmNormalDPMName OBJECT-TYPE
			SYNTAX DisplayString (SIZE (0..128))
			MAX-ACCESS read-only
			STATUS current
			DESCRIPTION
				"Normal DPM name."
			::= { dpmNormal 1 }


		-- 1.3.6.1.4.1.7777.1.2.2.2
		dpmNormalDPMLoca OBJECT-TYPE
			SYNTAX DisplayString (SIZE (0..128))
			MAX-ACCESS read-only
			STATUS current
			DESCRIPTION
				"Normal DPM Location."
			::= { dpmNormal 2 }


		-- 1.3.6.1.4.1.7777.1.2.2.3
		dpmNormalNominalVoltage OBJECT-TYPE
			SYNTAX Integer32
			MAX-ACCESS read-only
			STATUS current
			DESCRIPTION
				"Normal Nominal Voltage."
			::= { dpmNormal 3 }


		-- 1.3.6.1.4.1.7777.1.2.2.4
		dpmNormalNominalCurrent OBJECT-TYPE
			SYNTAX Integer32
			MAX-ACCESS read-only
			STATUS current
			DESCRIPTION
				"Normal Nominal Current."
			::= { dpmNormal 4 }


		-- 1.3.6.1.4.1.7777.1.2.2.5
		dpmNormalInstantaneousDemandKwMW OBJECT-TYPE
			SYNTAX Integer32
			MAX-ACCESS read-only
			STATUS current
			DESCRIPTION
				"Normal Instantaneous Demand kW MW"
			::= { dpmNormal 5 }


		-- 1.3.6.1.4.1.7777.1.2.2.6
		dpmNormalInstantaneousDemandDate OBJECT-TYPE
			SYNTAX DisplayString (SIZE (0..128))
			MAX-ACCESS read-only
			STATUS current
			DESCRIPTION
				"Demand Date."
			::= { dpmNormal 6 }


		-- 1.3.6.1.4.1.7777.1.2.2.7
		dpmNormalInstantaneousDemandTime OBJECT-TYPE
			SYNTAX DisplayString (SIZE (0..128))
			MAX-ACCESS read-only
			STATUS current
			DESCRIPTION
				"Demand Time."
			::= { dpmNormal 7 }


		-- 1.3.6.1.4.1.7777.1.2.2.8
		dpmNormalBlockDemandforFullHouInkW OBJECT-TYPE
			SYNTAX Integer32
			MAX-ACCESS read-only
			STATUS current
			DESCRIPTION
				"Block Demand for Full Hou In kW."
			::= { dpmNormal 8 }


		-- 1.3.6.1.4.1.7777.1.2.2.9
		dpmNormalBlockDemandforFullDayInkW OBJECT-TYPE
			SYNTAX Integer32
			MAX-ACCESS read-only
			STATUS current
			DESCRIPTION
				"Block Demand for Full Day In kW."
			::= { dpmNormal 9 }

		-- 1.3.6.1.4.1.7777.1.2.2.10
		dpmNormalBlockDemandforFullMonthInKW OBJECT-TYPE
			SYNTAX Integer32
			MAX-ACCESS read-only
			STATUS current
			DESCRIPTION
				"Block Demand for Full Month In kW."
			::= { dpmNormal 10 }

		-- 1.3.6.1.4.1.7777.1.2.2.11
		dpmNormalBlockDemandforFullYear OBJECT-TYPE
			SYNTAX Integer32
			MAX-ACCESS read-only
			STATUS current
			DESCRIPTION
				"Block Demand for Full Year In kW."
			::= { dpmNormal 11 }

		-- 1.3.6.1.4.1.7777.1.2.2.12
		dpmNormalCurrentThdA OBJECT-TYPE
			SYNTAX Integer32
			MAX-ACCESS read-only
			STATUS current
			DESCRIPTION
				"Phase A THD Current.In percentage "
			::= { dpmNormal 12 }

		-- 1.3.6.1.4.1.7777.1.2.2.13
		dpmNormalCurrentThdB OBJECT-TYPE
			SYNTAX Integer32
			MAX-ACCESS read-only
			STATUS current
			DESCRIPTION
				"Phase B THD Current.In percentage"
			::= { dpmNormal 13 }

		-- 1.3.6.1.4.1.7777.1.2.2.14
  		dpmNormalCurrentThdC OBJECT-TYPE
			SYNTAX Integer32
			MAX-ACCESS read-only
			STATUS current
			DESCRIPTION
				"Phase C THD Current.In percentage"
			::= { dpmNormal 14 }

		-- 1.3.6.1.4.1.7777.1.2.2.15
  		dpmNormalVoltageThdA OBJECT-TYPE
			SYNTAX Integer32
			MAX-ACCESS read-only
			STATUS current
			DESCRIPTION
				"Phase A THD Voltage.In percentage"
			::= { dpmNormal 15 }

		-- 1.3.6.1.4.1.7777.1.2.2.16
		dpmNormalVoltageThdB OBJECT-TYPE
			SYNTAX Integer32
			MAX-ACCESS read-only
			STATUS current
			DESCRIPTION
				"Phase B THD Voltage.In percentage"
			::= { dpmNormal 16 }


		-- 1.3.6.1.4.1.7777.1.2.2.17
		dpmNormalVoltageThdC OBJECT-TYPE
			SYNTAX Integer32
			MAX-ACCESS read-only
			STATUS current
			DESCRIPTION
				"Phase C THD Voltage.In percentage"
			::= { dpmNormal 17 }


		-- 1.3.6.1.4.1.7777.1.2.2.18
		dpmNormalVab OBJECT-TYPE
			SYNTAX Integer32
			MAX-ACCESS read-only
			STATUS current
			DESCRIPTION
				"Normal Vab Volatage."
			::= { dpmNormal 18 }

		-- 1.3.6.1.4.1.7777.1.2.2.19
		dpmNormalVbc OBJECT-TYPE
			SYNTAX Integer32
			MAX-ACCESS read-only
			STATUS current
			DESCRIPTION
				"Normal Vbc Volatage."
			::= { dpmNormal 19 }


		-- 1.3.6.1.4.1.7777.1.2.2.20
		dpmNormalVca OBJECT-TYPE
			SYNTAX Integer32
			MAX-ACCESS read-only
			STATUS current
			DESCRIPTION
				"Normal Vca Volatage."
			::= { dpmNormal 20 }

		-- 1.3.6.1.4.1.7777.1.2.2.21
		dpmNormalVolAverage OBJECT-TYPE
			SYNTAX Integer32
			MAX-ACCESS read-only
			STATUS current
			DESCRIPTION
				"Normal Vol Average."
			::= { dpmNormal 21 }

		-- 1.3.6.1.4.1.7777.1.2.2.22
		dpmNormalVolUnbal OBJECT-TYPE
			SYNTAX Integer32
			MAX-ACCESS read-only
			STATUS current
			DESCRIPTION
				"Normal Vol Unbal."
			::= { dpmNormal 22 }

		-- 1.3.6.1.4.1.7777.1.2.2.23
		dpmNormalVan OBJECT-TYPE
			SYNTAX Integer32
			MAX-ACCESS read-only
			STATUS current
			DESCRIPTION
				"Normal Vol Van."
			::= { dpmNormal 23 }


		-- 1.3.6.1.4.1.7777.1.2.2.24
		dpmNormalVbn OBJECT-TYPE
			SYNTAX Integer32
			MAX-ACCESS read-only
			STATUS current
			DESCRIPTION
				"Normal Vbn.."
			::= { dpmNormal 24 }


		-- 1.3.6.1.4.1.7777.1.2.2.25
		dpmNormalVcn OBJECT-TYPE
			SYNTAX Integer32
			MAX-ACCESS read-only
			STATUS current
			DESCRIPTION
				"Normal Vcn. "
			::= { dpmNormal 25 }


		-- 1.3.6.1.4.1.7777.1.2.2.26
		dpmNormalVavgneutral OBJECT-TYPE
			SYNTAX Integer32
			MAX-ACCESS read-only
			STATUS current
			DESCRIPTION
				"Normal Avg neutral Volatagae."
			::= { dpmNormal 26 }

		-- 1.3.6.1.4.1.7777.1.2.2.27
		dpmNormalFrequency OBJECT-TYPE
			SYNTAX Integer32
			MAX-ACCESS read-only
			STATUS current
			DESCRIPTION
				"Normal Frequency."
			::= { dpmNormal 27 }

		-- 1.3.6.1.4.1.7777.1.2.2.28
		dpmNormalPowerFactor OBJECT-TYPE
			SYNTAX Integer32
			MAX-ACCESS read-only
			STATUS current
			DESCRIPTION
				"Normal Power factor."
			::= { dpmNormal 28 }

		-- 1.3.6.1.4.1.7777.1.2.2.29
		dpmNormalCurPhaseA OBJECT-TYPE
			SYNTAX Integer32
			MAX-ACCESS read-only
			STATUS current
			DESCRIPTION
				"Normal Phase A Current."
			::= { dpmNormal 29 }

		-- 1.3.6.1.4.1.7777.1.2.2.30
		dpmNormalCurPhaseB OBJECT-TYPE
			SYNTAX Integer32
			MAX-ACCESS read-only
			STATUS current
			DESCRIPTION
				"Normal Phase B Current."
			::= { dpmNormal 30 }


		-- 1.3.6.1.4.1.7777.1.2.2.31
		dpmNormalCurPhaseC OBJECT-TYPE
			SYNTAX Integer32
			MAX-ACCESS read-only
			STATUS current
			DESCRIPTION
				"Normal Phase C Current."
			::= { dpmNormal 31 }

		-- 1.3.6.1.4.1.7777.1.2.2.32
		dpmNormalPhaseCurAvg OBJECT-TYPE
			SYNTAX Integer32
			MAX-ACCESS read-only
			STATUS current
			DESCRIPTION
				"Normal Phase Current aVG."
			::= { dpmNormal 32 }

		-- 1.3.6.1.4.1.7777.1.2.2.33
		dpmNormalPhaseCurUnbalancecePercentage OBJECT-TYPE
			SYNTAX Integer32
			MAX-ACCESS read-only
			STATUS current
			DESCRIPTION
				"Normal Phase Cur Unbalancece Percentage."
			::= { dpmNormal 33 }

		-- 1.3.6.1.4.1.7777.1.2.2.34
		dpmNormalRealTotalPower OBJECT-TYPE
			SYNTAX Integer32
			MAX-ACCESS read-only
			STATUS current
			DESCRIPTION
				"Normal Real Total power factor."
			::= { dpmNormal 34 }

		-- 1.3.6.1.4.1.7777.1.2.2.35
		dpmNormalReactiveTotalPower OBJECT-TYPE
			SYNTAX Integer32
			MAX-ACCESS read-only
			STATUS current
			DESCRIPTION
				"Normal Reactive Total power."
			::= { dpmNormal 35 }

		-- 1.3.6.1.4.1.7777.1.2.2.36
  		dpmNormalApparentTotalPower OBJECT-TYPE
			SYNTAX Integer32
			MAX-ACCESS read-only
			STATUS current
			DESCRIPTION
				"Normal AApparent Total power."
			::= { dpmNormal 36 }

		-- 1.3.6.1.4.1.7777.1.2.2.37
  		dpmNormalNetActiveEnergy OBJECT-TYPE
			SYNTAX Integer32
			MAX-ACCESS read-only
			STATUS current
			DESCRIPTION
				"Normal Net Active Energy."
			::= { dpmNormal 37 }


		-- 1.3.6.1.4.1.7777.1.2.2.39
		dpmNormalFirmwareVersion OBJECT-TYPE
			SYNTAX DisplayString (SIZE (0..128))
			MAX-ACCESS read-only
			STATUS current
			DESCRIPTION
				"Normal DPM Firmware ."
			::= { dpmNormal 38 }

--Emergency
        -- 1.3.6.1.4.1.7777.1.2.3.1
		dpmEmergencyDPMName OBJECT-TYPE
			SYNTAX DisplayString (SIZE (0..128))
			MAX-ACCESS read-only
			STATUS current
			DESCRIPTION
				"Emergency DPM name."
			::= { dpmEmergency 1 }


		-- 1.3.6.1.4.1.7777.1.2.3.2
		dpmEmergencyDPMLoca OBJECT-TYPE
			SYNTAX DisplayString (SIZE (0..128))
			MAX-ACCESS read-only
			STATUS current
			DESCRIPTION
				"Emergency DPM Location."
			::= { dpmEmergency 2 }


		-- 1.3.6.1.4.1.7777.1.2.3.3
		dpmEmergencyNominalVoltage OBJECT-TYPE
			SYNTAX Integer32
			MAX-ACCESS read-only
			STATUS current
			DESCRIPTION
				"Emergency Nominal Voltage."
			::= { dpmEmergency 3 }


		-- 1.3.6.1.4.1.7777.1.2.3.4
		dpmEmergencyNominalCurrent OBJECT-TYPE
			SYNTAX Integer32
			MAX-ACCESS read-only
			STATUS current
			DESCRIPTION
				"Emergency Nominal Current."
			::= { dpmEmergency 4 }


		-- 1.3.6.1.4.1.7777.1.2.3.5
		dpmEmergencyInstantaneousDemandKwMW OBJECT-TYPE
			SYNTAX Integer32
			MAX-ACCESS read-only
			STATUS current
			DESCRIPTION
				"Emergency Instantaneous Demand Kw MW"
			::= { dpmEmergency 5 }


		-- 1.3.6.1.4.1.7777.1.2.3.6
		dpmEmergencyInstantaneousDemandDate OBJECT-TYPE
			SYNTAX DisplayString (SIZE (0..128))
			MAX-ACCESS read-only
			STATUS current
			DESCRIPTION
				"Demand Date."
			::= { dpmEmergency 6 }


		-- 1.3.6.1.4.1.7777.1.2.3.7
		dpmEmergencyInstantaneousDemandTime OBJECT-TYPE
			SYNTAX DisplayString (SIZE (0..128))
			MAX-ACCESS read-only
			STATUS current
			DESCRIPTION
				"Demand Time."
			::= { dpmEmergency 7 }


		-- 1.3.6.1.4.1.7777.1.2.3.8
		dpmEmergencyBlockDemandforFullHouInkW OBJECT-TYPE
			SYNTAX Integer32
			MAX-ACCESS read-only
			STATUS current
			DESCRIPTION
				"Block Demand for Full Hou In kW."
			::= { dpmEmergency 8 }


		-- 1.3.6.1.4.1.7777.1.2.3.9
		dpmEmergencyBlockDemandforFullDayInkW OBJECT-TYPE
			SYNTAX Integer32
			MAX-ACCESS read-only
			STATUS current
			DESCRIPTION
				"Block Demand for Full Day In kW."
			::= { dpmEmergency 9 }

		-- 1.3.6.1.4.1.7777.1.2.3.10
		dpmEmergencyBlockDemandforFullMonthInKW OBJECT-TYPE
			SYNTAX Integer32
			MAX-ACCESS read-only
			STATUS current
			DESCRIPTION
				"Block Demand for Full Month In kW."
			::= { dpmEmergency 10 }

		-- 1.3.6.1.4.1.7777.1.2.3.11
		dpmEmergencyBlockDemandforFullYear OBJECT-TYPE
			SYNTAX Integer32
			MAX-ACCESS read-only
			STATUS current
			DESCRIPTION
				"Block Demand for Full Yearin kW"
			::= { dpmEmergency 11 }

		-- 1.3.6.1.4.1.7777.1.2.3.12
		dpmEmergencyCurrentThdA OBJECT-TYPE
			SYNTAX Integer32
			MAX-ACCESS read-only
			STATUS current
			DESCRIPTION
				"Phase A THD Current.In percentage"
			::= { dpmEmergency 12 }

		-- 1.3.6.1.4.1.7777.1.2.3.13
		dpmEmergencyCurrentThdB OBJECT-TYPE
			SYNTAX Integer32
			MAX-ACCESS read-only
			STATUS current
			DESCRIPTION
				"Phase B THD Current.In percentage"
			::= { dpmEmergency 13 }

		-- 1.3.6.1.4.1.7777.1.2.3.14
  		dpmEmergencyCurrentThdC OBJECT-TYPE
			SYNTAX Integer32
			MAX-ACCESS read-only
			STATUS current
			DESCRIPTION
				"Phase C THD Current.In percentage"
			::= { dpmEmergency 14 }

		-- 1.3.6.1.4.1.7777.1.2.3.15
  		dpmEmergencyVoltageThdA OBJECT-TYPE
			SYNTAX Integer32
			MAX-ACCESS read-only
			STATUS current
			DESCRIPTION
				"Phase A THD Voltage.In percentage"
			::= { dpmEmergency 15 }

		-- 1.3.6.1.4.1.7777.1.2.3.16
		dpmEmergencyVoltageThdB OBJECT-TYPE
			SYNTAX Integer32
			MAX-ACCESS read-only
			STATUS current
			DESCRIPTION
				"Phase B THD Voltage.In percentage"
			::= { dpmEmergency 16 }


		-- 1.3.6.1.4.1.7777.1.2.3.17
		dpmEmergencyVoltageThdC OBJECT-TYPE
			SYNTAX Integer32
			MAX-ACCESS read-only
			STATUS current
			DESCRIPTION
				"Phase C THD Voltage.In percentage"
			::= { dpmEmergency 17 }


		-- 1.3.6.1.4.1.7777.1.2.3.18
		dpmEmergencyVab OBJECT-TYPE
			SYNTAX Integer32
			MAX-ACCESS read-only
			STATUS current
			DESCRIPTION
				"Emergency Vab Volatage."
			::= { dpmEmergency 18 }

		-- 1.3.6.1.4.1.7777.1.2.3.19
		dpmEmergencyVbc OBJECT-TYPE
			SYNTAX Integer32
			MAX-ACCESS read-only
			STATUS current
			DESCRIPTION
				"Emergency Vbc Volatage."
			::= { dpmEmergency 19 }


		-- 1.3.6.1.4.1.7777.1.2.3.20
		dpmEmergencyVca OBJECT-TYPE
			SYNTAX Integer32
			MAX-ACCESS read-only
			STATUS current
			DESCRIPTION
				"Emergency Vca Volatage."
			::= { dpmEmergency 20 }

		-- 1.3.6.1.4.1.7777.1.2.3.21
		dpmEmergencyVolAverage OBJECT-TYPE
			SYNTAX Integer32
			MAX-ACCESS read-only
			STATUS current
			DESCRIPTION
				"Emergency Vol Average."
			::= { dpmEmergency 21 }

		-- 1.3.6.1.4.1.7777.1.2.3.22
		dpmEmergencyVolUnbal OBJECT-TYPE
			SYNTAX Integer32
			MAX-ACCESS read-only
			STATUS current
			DESCRIPTION
				"Emergency Vol Unbal."
			::= { dpmEmergency 22 }

		-- 1.3.6.1.4.1.7777.1.2.3.23
		dpmEmergencyVan OBJECT-TYPE
			SYNTAX Integer32
			MAX-ACCESS read-only
			STATUS current
			DESCRIPTION
				"Emergency Vol Van."
			::= { dpmEmergency 23 }


		-- 1.3.6.1.4.1.7777.1.2.3.24
		dpmEmergencyVbn OBJECT-TYPE
			SYNTAX Integer32
			MAX-ACCESS read-only
			STATUS current
			DESCRIPTION
				"Emergency Vbn.."
			::= { dpmEmergency 24 }


		-- 1.3.6.1.4.1.7777.1.2.3.25
		dpmEmergencyVcn OBJECT-TYPE
			SYNTAX Integer32
			MAX-ACCESS read-only
			STATUS current
			DESCRIPTION
				"Emergency Vcn. "
			::= { dpmEmergency 25 }


		-- 1.3.6.1.4.1.7777.1.2.3.26
		dpmEmergencyVavgneutral OBJECT-TYPE
			SYNTAX Integer32
			MAX-ACCESS read-only
			STATUS current
			DESCRIPTION
				"Emergency Avg neutral Volatagae."
			::= { dpmEmergency 26 }

		-- 1.3.6.1.4.1.7777.1.2.3.27
		dpmEmergencyFrequency OBJECT-TYPE
			SYNTAX Integer32
			MAX-ACCESS read-only
			STATUS current
			DESCRIPTION
				"Emergency Frequency."
			::= { dpmEmergency 27 }

		-- 1.3.6.1.4.1.7777.1.2.3.28
		dpmEmergencyPowerFactor OBJECT-TYPE
			SYNTAX Integer32
			MAX-ACCESS read-only
			STATUS current
			DESCRIPTION
				"Emergency Power factor."
			::= { dpmEmergency 28 }

		-- 1.3.6.1.4.1.7777.1.2.3.29
		dpmEmergencyCurPhaseA OBJECT-TYPE
			SYNTAX Integer32
			MAX-ACCESS read-only
			STATUS current
			DESCRIPTION
				"Emergency Phase A Current."
			::= { dpmEmergency 29 }

		-- 1.3.6.1.4.1.7777.1.2.3.30
		dpmEmergencyCurPhaseB OBJECT-TYPE
			SYNTAX Integer32
			MAX-ACCESS read-only
			STATUS current
			DESCRIPTION
				"Emergency Phase B Current."
			::= { dpmEmergency 30 }


		-- 1.3.6.1.4.1.7777.1.2.3.31
		dpmEmergencyCurPhaseC OBJECT-TYPE
			SYNTAX Integer32
			MAX-ACCESS read-only
			STATUS current
			DESCRIPTION
				"Emergency Phase C Current."
			::= { dpmEmergency 31 }

		-- 1.3.6.1.4.1.7777.1.2.3.32
		dpmEmergencyPhaseCurAvg OBJECT-TYPE
			SYNTAX Integer32
			MAX-ACCESS read-only
			STATUS current
			DESCRIPTION
				"Emergency Phase Current aVG."
			::= { dpmEmergency 32 }

		-- 1.3.6.1.4.1.7777.1.2.3.33
		dpmEmergencyPhaseCurUnbalancecePercentage OBJECT-TYPE
			SYNTAX Integer32
			MAX-ACCESS read-only
			STATUS current
			DESCRIPTION
				"Emergency Phase Cur Unbalancece Percentage."
			::= { dpmEmergency 33 }

		-- 1.3.6.1.4.1.7777.1.2.3.34
		dpmEmergencyRealTotalPower OBJECT-TYPE
			SYNTAX Integer32
			MAX-ACCESS read-only
			STATUS current
			DESCRIPTION
				"Emergency Real Total power factor."
			::= { dpmEmergency 34 }

		-- 1.3.6.1.4.1.7777.1.2.3.35
		dpmEmergencyReactiveTotalPower OBJECT-TYPE
			SYNTAX Integer32
			MAX-ACCESS read-only
			STATUS current
			DESCRIPTION
				"Emergency Reactive Total power."
			::= { dpmEmergency 35 }

		-- 1.3.6.1.4.1.7777.1.2.3.36
  		dpmEmergencyApparentTotalPower OBJECT-TYPE
			SYNTAX Integer32
			MAX-ACCESS read-only
			STATUS current
			DESCRIPTION
				"Emergency AApparent Total power."
			::= { dpmEmergency 36 }

		-- 1.3.6.1.4.1.7777.1.2.3.37
  		dpmEmergencyNetActiveEnergy OBJECT-TYPE
			SYNTAX Integer32
			MAX-ACCESS read-only
			STATUS current
			DESCRIPTION
				"Emergency Net Active Energy."
			::= { dpmEmergency 37 }


		-- 1.3.6.1.4.1.7777.1.2.3.39
		dpmEmergencyFirmwareVersion OBJECT-TYPE
			SYNTAX DisplayString (SIZE (0..128))
			MAX-ACCESS read-only
			STATUS current
			DESCRIPTION
				"Emergency DPM Firmware ."
			::= { dpmEmergency 38 }

--Load

        -- 1.3.6.1.4.1.7777.1.2.4.1
		dpmLoadDPMName OBJECT-TYPE
			SYNTAX DisplayString (SIZE (0..128))
			MAX-ACCESS read-only
			STATUS current
			DESCRIPTION
				"Load DPM name."
			::= { dpmLoad 1 }


		-- 1.3.6.1.4.1.7777.1.2.4.2
		dpmLoadDPMLoca OBJECT-TYPE
			SYNTAX DisplayString (SIZE (0..128))
			MAX-ACCESS read-only
			STATUS current
			DESCRIPTION
				"Load DPM Location."
			::= { dpmLoad 2 }


		-- 1.3.6.1.4.1.7777.1.2.4.3
		dpmLoadNominalVoltage OBJECT-TYPE
			SYNTAX Integer32
			MAX-ACCESS read-only
			STATUS current
			DESCRIPTION
				"Load Nominal Voltage."
			::= { dpmLoad 3 }


		-- 1.3.6.1.4.1.7777.1.2.4.4
		dpmLoadNominalCurrent OBJECT-TYPE
			SYNTAX Integer32
			MAX-ACCESS read-only
			STATUS current
			DESCRIPTION
				"Load Nominal Current."
			::= { dpmLoad 4 }


		-- 1.3.6.1.4.1.7777.1.2.4.5
		dpmLoadInstantaneousDemandKwMW OBJECT-TYPE
			SYNTAX Integer32
			MAX-ACCESS read-only
			STATUS current
			DESCRIPTION
				"Load Instantaneous Demand Kw MW"
			::= { dpmLoad 5 }


		-- 1.3.6.1.4.1.7777.1.2.4.6
		dpmLoadInstantaneousDemandDate OBJECT-TYPE
			SYNTAX DisplayString (SIZE (0..128))
			MAX-ACCESS read-only
			STATUS current
			DESCRIPTION
				"Demand Date."
			::= { dpmLoad 6 }


		-- 1.3.6.1.4.1.7777.1.2.4.7
		dpmLoadInstantaneousDemandTime OBJECT-TYPE
			SYNTAX DisplayString (SIZE (0..128))
			MAX-ACCESS read-only
			STATUS current
			DESCRIPTION
				"Demand Time."
			::= { dpmLoad 7 }


		-- 1.3.6.1.4.1.7777.1.2.4.8
		dpmLoadBlockDemandforFullHouInkW OBJECT-TYPE
			SYNTAX Integer32
			MAX-ACCESS read-only
			STATUS current
			DESCRIPTION
				"Block Demand for Full Hou In kW."
			::= { dpmLoad 8 }


		-- 1.3.6.1.4.1.7777.1.2.4.9
		dpmLoadBlockDemandforFullDayInkW OBJECT-TYPE
			SYNTAX Integer32
			MAX-ACCESS read-only
			STATUS current
			DESCRIPTION
				"Block Demand for Full Day In kW."
			::= { dpmLoad 9 }

		-- 1.3.6.1.4.1.7777.1.2.4.10
		dpmLoadBlockDemandforFullMonthInKW OBJECT-TYPE
			SYNTAX Integer32
			MAX-ACCESS read-only
			STATUS current
			DESCRIPTION
				"Block Demand for Full Month In kW."
			::= { dpmLoad 10 }

		-- 1.3.6.1.4.1.7777.1.2.4.11
		dpmLoadBlockDemandforFullYear OBJECT-TYPE
			SYNTAX Integer32
			MAX-ACCESS read-only
			STATUS current
			DESCRIPTION
				"Block Demand for Full Yearin kW"
			::= { dpmLoad 11 }

		-- 1.3.6.1.4.1.7777.1.2.4.12
		dpmLoadCurrentThdA OBJECT-TYPE
			SYNTAX Integer32
			MAX-ACCESS read-only
			STATUS current
			DESCRIPTION
				"Phase A THD Current.In percentage"
			::= { dpmLoad 12 }

		-- 1.3.6.1.4.1.7777.1.2.4.13
		dpmLoadCurrentThdB OBJECT-TYPE
			SYNTAX Integer32
			MAX-ACCESS read-only
			STATUS current
			DESCRIPTION
				"Phase B THD Current.In percentage"
			::= { dpmLoad 13 }

		-- 1.3.6.1.4.1.7777.1.2.4.14
  		dpmLoadCurrentThdC OBJECT-TYPE
			SYNTAX Integer32
			MAX-ACCESS read-only
			STATUS current
			DESCRIPTION
				"Phase C THD Current.In percentage"
			::= { dpmLoad 14 }

		-- 1.3.6.1.4.1.7777.1.2.4.15
  		dpmLoadVoltageThdA OBJECT-TYPE
			SYNTAX Integer32
			MAX-ACCESS read-only
			STATUS current
			DESCRIPTION
				"Phase A THD Voltage.In percentage"
			::= { dpmLoad 15 }

		-- 1.3.6.1.4.1.7777.1.2.4.16
		dpmLoadVoltageThdB OBJECT-TYPE
			SYNTAX Integer32
			MAX-ACCESS read-only
			STATUS current
			DESCRIPTION
				"Phase B THD Voltage.In percentage"
			::= { dpmLoad 16 }


		-- 1.3.6.1.4.1.7777.1.2.4.17
		dpmLoadVoltageThdC OBJECT-TYPE
			SYNTAX Integer32
			MAX-ACCESS read-only
			STATUS current
			DESCRIPTION
				"Phase C THD Voltage.In percentage"
			::= { dpmLoad 17 }


		-- 1.3.6.1.4.1.7777.1.2.4.18
		dpmLoadVab OBJECT-TYPE
			SYNTAX Integer32
			MAX-ACCESS read-only
			STATUS current
			DESCRIPTION
				"Load Vab Volatage."
			::= { dpmLoad 18 }

		-- 1.3.6.1.4.1.7777.1.2.4.19
		dpmLoadVbc OBJECT-TYPE
			SYNTAX Integer32
			MAX-ACCESS read-only
			STATUS current
			DESCRIPTION
				"Load Vbc Volatage."
			::= { dpmLoad 19 }


		-- 1.3.6.1.4.1.7777.1.2.4.20
		dpmLoadVca OBJECT-TYPE
			SYNTAX Integer32
			MAX-ACCESS read-only
			STATUS current
			DESCRIPTION
				"Load Vca Volatage."
			::= { dpmLoad 20 }

		-- 1.3.6.1.4.1.7777.1.2.4.21
		dpmLoadVolAverage OBJECT-TYPE
			SYNTAX Integer32
			MAX-ACCESS read-only
			STATUS current
			DESCRIPTION
				"Load Vol Average."
			::= { dpmLoad 21 }

		-- 1.3.6.1.4.1.7777.1.2.4.22
		dpmLoadVolUnbal OBJECT-TYPE
			SYNTAX Integer32
			MAX-ACCESS read-only
			STATUS current
			DESCRIPTION
				"Load Vol Unbal."
			::= { dpmLoad 22 }

		-- 1.3.6.1.4.1.7777.1.2.4.23
		dpmLoadVan OBJECT-TYPE
			SYNTAX Integer32
			MAX-ACCESS read-only
			STATUS current
			DESCRIPTION
				"Load Vol Van."
			::= { dpmLoad 23 }


		-- 1.3.6.1.4.1.7777.1.2.4.24
		dpmLoadVbn OBJECT-TYPE
			SYNTAX Integer32
			MAX-ACCESS read-only
			STATUS current
			DESCRIPTION
				"Load Vbn.."
			::= { dpmLoad 24 }


		-- 1.3.6.1.4.1.7777.1.2.4.25
		dpmLoadVcn OBJECT-TYPE
			SYNTAX Integer32
			MAX-ACCESS read-only
			STATUS current
			DESCRIPTION
				"Load Vcn. "
			::= { dpmLoad 25 }


		-- 1.3.6.1.4.1.7777.1.2.4.26
		dpmLoadVavgneutral OBJECT-TYPE
			SYNTAX Integer32
			MAX-ACCESS read-only
			STATUS current
			DESCRIPTION
				"Load Avg neutral Volatagae."
			::= { dpmLoad 26 }

		-- 1.3.6.1.4.1.7777.1.2.4.27
		dpmLoadFrequency OBJECT-TYPE
			SYNTAX Integer32
			MAX-ACCESS read-only
			STATUS current
			DESCRIPTION
				"Load Frequency."
			::= { dpmLoad 27 }

		-- 1.3.6.1.4.1.7777.1.2.4.28
		dpmLoadPowerFactor OBJECT-TYPE
			SYNTAX Integer32
			MAX-ACCESS read-only
			STATUS current
			DESCRIPTION
				"Load Power factor."
			::= { dpmLoad 28 }

		-- 1.3.6.1.4.1.7777.1.2.4.29
		dpmLoadCurPhaseA OBJECT-TYPE
			SYNTAX Integer32
			MAX-ACCESS read-only
			STATUS current
			DESCRIPTION
				"Load Phase A Current."
			::= { dpmLoad 29 }

		-- 1.3.6.1.4.1.7777.1.2.4.30
		dpmLoadCurPhaseB OBJECT-TYPE
			SYNTAX Integer32
			MAX-ACCESS read-only
			STATUS current
			DESCRIPTION
				"Load Phase B Current."
			::= { dpmLoad 30 }


		-- 1.3.6.1.4.1.7777.1.2.4.31
		dpmLoadCurPhaseC OBJECT-TYPE
			SYNTAX Integer32
			MAX-ACCESS read-only
			STATUS current
			DESCRIPTION
				"Load Phase C Current."
			::= { dpmLoad 31 }

		-- 1.3.6.1.4.1.7777.1.2.4.32
		dpmLoadPhaseCurAvg OBJECT-TYPE
			SYNTAX Integer32
			MAX-ACCESS read-only
			STATUS current
			DESCRIPTION
				"Load Phase Current aVG."
			::= { dpmLoad 32 }

		-- 1.3.6.1.4.1.7777.1.2.4.33
		dpmLoadPhaseCurUnbalancecePercentage OBJECT-TYPE
			SYNTAX Integer32
			MAX-ACCESS read-only
			STATUS current
			DESCRIPTION
				"Load Phase Cur Unbalancece Percentage."
			::= { dpmLoad 33 }

		-- 1.3.6.1.4.1.7777.1.2.4.34
		dpmLoadRealTotalPower OBJECT-TYPE
			SYNTAX Integer32
			MAX-ACCESS read-only
			STATUS current
			DESCRIPTION
				"Load Real Total power factor."
			::= { dpmLoad 34 }

		-- 1.3.6.1.4.1.7777.1.2.4.35
		dpmLoadReactiveTotalPower OBJECT-TYPE
			SYNTAX Integer32
			MAX-ACCESS read-only
			STATUS current
			DESCRIPTION
				"Load Reactive Total power."
			::= { dpmLoad 35 }

		-- 1.3.6.1.4.1.7777.1.2.4.36
  		dpmLoadApparentTotalPower OBJECT-TYPE
			SYNTAX Integer32
			MAX-ACCESS read-only
			STATUS current
			DESCRIPTION
				"Load AApparent Total power."
			::= { dpmLoad 36 }

		-- 1.3.6.1.4.1.7777.1.2.4.37
  		dpmLoadNetActiveEnergy OBJECT-TYPE
			SYNTAX Integer32
			MAX-ACCESS read-only
			STATUS current
			DESCRIPTION
				"Load Net Active Energy."
			::= { dpmLoad 37 }


		-- 1.3.6.1.4.1.7777.1.2.4.39
		dpmLoadFirmwareVersion OBJECT-TYPE
			SYNTAX DisplayString (SIZE (0..128))
			MAX-ACCESS read-only
			STATUS current
			DESCRIPTION
				"Load DPM Firmware."
			::= { dpmLoad 38 }


--Other

        -- 1.3.6.1.4.1.7777.1.2.5.1
		dpmOtherDPMName OBJECT-TYPE
			SYNTAX DisplayString (SIZE (0..128))
			MAX-ACCESS read-only
			STATUS current
			DESCRIPTION
				"Other DPM name."
			::= { dpmOther 1 }


		-- 1.3.6.1.4.1.7777.1.2.5.2
		dpmOtherDPMLoca OBJECT-TYPE
			SYNTAX DisplayString (SIZE (0..128))
			MAX-ACCESS read-only
			STATUS current
			DESCRIPTION
				"Other DPM Location."
			::= { dpmOther 2 }


		-- 1.3.6.1.4.1.7777.1.2.5.3
		dpmOtherNominalVoltage OBJECT-TYPE
			SYNTAX Integer32
			MAX-ACCESS read-only
			STATUS current
			DESCRIPTION
				"Other Nominal Voltage."
			::= { dpmOther 3 }


		-- 1.3.6.1.4.1.7777.1.2.5.4
		dpmOtherNominalCurrent OBJECT-TYPE
			SYNTAX Integer32
			MAX-ACCESS read-only
			STATUS current
			DESCRIPTION
				"Other Nominal Current."
			::= { dpmOther 4 }


		-- 1.3.6.1.4.1.7777.1.2.5.5
		dpmOtherInstantaneousDemandKwMW OBJECT-TYPE
			SYNTAX Integer32
			MAX-ACCESS read-only
			STATUS current
			DESCRIPTION
				"Other Instantaneous Demand kw MW"
			::= { dpmOther 5 }


		-- 1.3.6.1.4.1.7777.1.2.5.6
		dpmOtherInstantaneousDemandDate OBJECT-TYPE
			SYNTAX DisplayString (SIZE (0..128))
			MAX-ACCESS read-only
			STATUS current
			DESCRIPTION
				"Demand Date."
			::= { dpmOther 6 }


		-- 1.3.6.1.4.1.7777.1.2.5.7
		dpmOtherInstantaneousDemandTime OBJECT-TYPE
			SYNTAX DisplayString (SIZE (0..128))
			MAX-ACCESS read-only
			STATUS current
			DESCRIPTION
				"Demand Time."
			::= { dpmOther 7 }


		-- 1.3.6.1.4.1.7777.1.2.5.8
		dpmOtherBlockDemandforFullHouInkW OBJECT-TYPE
			SYNTAX Integer32
			MAX-ACCESS read-only
			STATUS current
			DESCRIPTION
				"Block Demand for Full Hou In kW."
			::= { dpmOther 8 }


		-- 1.3.6.1.4.1.7777.1.2.5.9
		dpmOtherBlockDemandforFullDayInkW OBJECT-TYPE
			SYNTAX Integer32
			MAX-ACCESS read-only
			STATUS current
			DESCRIPTION
				"Block Demand for Full Day In kW."
			::= { dpmOther 9 }

		-- 1.3.6.1.4.1.7777.1.2.5.10
		dpmOtherBlockDemandforFullMonthInKW OBJECT-TYPE
			SYNTAX Integer32
			MAX-ACCESS read-only
			STATUS current
			DESCRIPTION
				"Block Demand for Full Month In kW."
			::= { dpmOther 10 }

		-- 1.3.6.1.4.1.7777.1.2.5.11
		dpmOtherBlockDemandforFullYear OBJECT-TYPE
			SYNTAX Integer32
			MAX-ACCESS read-only
			STATUS current
			DESCRIPTION
				"Block Demand for Full Year."
			::= { dpmOther 11 }

		-- 1.3.6.1.4.1.7777.1.2.5.12
		dpmOtherCurrentThdA OBJECT-TYPE
			SYNTAX Integer32
			MAX-ACCESS read-only
			STATUS current
			DESCRIPTION
				"Phase A THD Current.In percentage"
			::= { dpmOther 12 }

		-- 1.3.6.1.4.1.7777.1.2.5.13
		dpmOtherCurrentThdB OBJECT-TYPE
			SYNTAX Integer32
			MAX-ACCESS read-only
			STATUS current
			DESCRIPTION
				"Phase B THD Current.In percentage"
			::= { dpmOther 13 }

		-- 1.3.6.1.4.1.7777.1.2.5.14
  		dpmOtherCurrentThdC OBJECT-TYPE
			SYNTAX Integer32
			MAX-ACCESS read-only
			STATUS current
			DESCRIPTION
				"Phase C THD Current.In percentage"
			::= { dpmOther 14 }

		-- 1.3.6.1.4.1.7777.1.2.5.15
  		dpmOtherVoltageThdA OBJECT-TYPE
			SYNTAX Integer32
			MAX-ACCESS read-only
			STATUS current
			DESCRIPTION
				"Phase A THD Voltage.In percentage"
			::= { dpmOther 15 }

		-- 1.3.6.1.4.1.7777.1.2.5.16
		dpmOtherVoltageThdB OBJECT-TYPE
			SYNTAX Integer32
			MAX-ACCESS read-only
			STATUS current
			DESCRIPTION
				"Phase B THD Voltage.In percentage"
			::= { dpmOther 16 }


		-- 1.3.6.1.4.1.7777.1.2.5.17
		dpmOtherVoltageThdC OBJECT-TYPE
			SYNTAX Integer32
			MAX-ACCESS read-only
			STATUS current
			DESCRIPTION
				"Phase C THD Voltage.In percentage"
			::= { dpmOther 17 }


		-- 1.3.6.1.4.1.7777.1.2.5.18
		dpmOtherVab OBJECT-TYPE
			SYNTAX Integer32
			MAX-ACCESS read-only
			STATUS current
			DESCRIPTION
				"Other Vab Volatage."
			::= { dpmOther 18 }

		-- 1.3.6.1.4.1.7777.1.2.5.19
		dpmOtherVbc OBJECT-TYPE
			SYNTAX Integer32
			MAX-ACCESS read-only
			STATUS current
			DESCRIPTION
				"Other Vbc Volatage."
			::= { dpmOther 19 }


		-- 1.3.6.1.4.1.7777.1.2.5.20
		dpmOtherVca OBJECT-TYPE
			SYNTAX Integer32
			MAX-ACCESS read-only
			STATUS current
			DESCRIPTION
				"Other Vca Volatage."
			::= { dpmOther 20 }

		-- 1.3.6.1.4.1.7777.1.2.5.21
		dpmOtherVolAverage OBJECT-TYPE
			SYNTAX Integer32
			MAX-ACCESS read-only
			STATUS current
			DESCRIPTION
				"Other Vol Average."
			::= { dpmOther 21 }

		-- 1.3.6.1.4.1.7777.1.2.5.22
		dpmOtherVolUnbal OBJECT-TYPE
			SYNTAX Integer32
			MAX-ACCESS read-only
			STATUS current
			DESCRIPTION
				"Other Vol Unbal."
			::= { dpmOther 22 }

		-- 1.3.6.1.4.1.7777.1.2.5.23
		dpmOtherVan OBJECT-TYPE
			SYNTAX Integer32
			MAX-ACCESS read-only
			STATUS current
			DESCRIPTION
				"Other Vol Van."
			::= { dpmOther 23 }


		-- 1.3.6.1.4.1.7777.1.2.5.24
		dpmOtherVbn OBJECT-TYPE
			SYNTAX Integer32
			MAX-ACCESS read-only
			STATUS current
			DESCRIPTION
				"Other Vbn.."
			::= { dpmOther 24 }


		-- 1.3.6.1.4.1.7777.1.2.5.25
		dpmOtherVcn OBJECT-TYPE
			SYNTAX Integer32
			MAX-ACCESS read-only
			STATUS current
			DESCRIPTION
				"Other Vcn. "
			::= { dpmOther 25 }


		-- 1.3.6.1.4.1.7777.1.2.5.26
		dpmOtherVavgneutral OBJECT-TYPE
			SYNTAX Integer32
			MAX-ACCESS read-only
			STATUS current
			DESCRIPTION
				"Other Avg neutral Volatagae."
			::= { dpmOther 26 }

		-- 1.3.6.1.4.1.7777.1.2.5.27
		dpmOtherFrequency OBJECT-TYPE
			SYNTAX Integer32
			MAX-ACCESS read-only
			STATUS current
			DESCRIPTION
				"Other Frequency."
			::= { dpmOther 27 }

		-- 1.3.6.1.4.1.7777.1.2.5.28
		dpmOtherPowerFactor OBJECT-TYPE
			SYNTAX Integer32
			MAX-ACCESS read-only
			STATUS current
			DESCRIPTION
				"Other Power factor."
			::= { dpmOther 28 }

		-- 1.3.6.1.4.1.7777.1.2.5.29
		dpmOtherCurPhaseA OBJECT-TYPE
			SYNTAX Integer32
			MAX-ACCESS read-only
			STATUS current
			DESCRIPTION
				"Other Phase A Current."
			::= { dpmOther 29 }

		-- 1.3.6.1.4.1.7777.1.2.5.30
		dpmOtherCurPhaseB OBJECT-TYPE
			SYNTAX Integer32
			MAX-ACCESS read-only
			STATUS current
			DESCRIPTION
				"Other Phase B Current."
			::= { dpmOther 30 }


		-- 1.3.6.1.4.1.7777.1.2.5.31
		dpmOtherCurPhaseC OBJECT-TYPE
			SYNTAX Integer32
			MAX-ACCESS read-only
			STATUS current
			DESCRIPTION
				"Other Phase C Current."
			::= { dpmOther 31 }

		-- 1.3.6.1.4.1.7777.1.2.5.32
		dpmOtherPhaseCurAvg OBJECT-TYPE
			SYNTAX Integer32
			MAX-ACCESS read-only
			STATUS current
			DESCRIPTION
				"Other Phase Current aVG."
			::= { dpmOther 32 }

		-- 1.3.6.1.4.1.7777.1.2.5.33
		dpmOtherPhaseCurUnbalancecePercentage OBJECT-TYPE
			SYNTAX Integer32
			MAX-ACCESS read-only
			STATUS current
			DESCRIPTION
				"Other Phase Cur Unbalancece Percentage."
			::= { dpmOther 33 }

		-- 1.3.6.1.4.1.7777.1.2.5.34
		dpmOtherRealTotalPower OBJECT-TYPE
			SYNTAX Integer32
			MAX-ACCESS read-only
			STATUS current
			DESCRIPTION
				"Other Real Total power factor."
			::= { dpmOther 34 }

		-- 1.3.6.1.4.1.7777.1.2.5.35
		dpmOtherReactiveTotalPower OBJECT-TYPE
			SYNTAX Integer32
			MAX-ACCESS read-only
			STATUS current
			DESCRIPTION
				"Other Reactive Total power."
			::= { dpmOther 35 }

		-- 1.3.6.1.4.1.7777.1.2.5.36
  		dpmOtherApparentTotalPower OBJECT-TYPE
			SYNTAX Integer32
			MAX-ACCESS read-only
			STATUS current
			DESCRIPTION
				"Other AApparent Total power."
			::= { dpmOther 36 }

		-- 1.3.6.1.4.1.7777.1.2.5.37
  		dpmOtherNetActiveEnergy OBJECT-TYPE
			SYNTAX Integer32
			MAX-ACCESS read-only
			STATUS current
			DESCRIPTION
				"Other Net Active Energy."
			::= { dpmOther 37 }


		-- 1.3.6.1.4.1.7777.1.2.5.39
		dpmOtherFirmwareVersion OBJECT-TYPE
			SYNTAX DisplayString (SIZE (0..128))
			MAX-ACCESS read-only
			STATUS current
			DESCRIPTION
				"Other DPM Firmware."
			::= { dpmOther 38 }


		-- 1.3.6.1.4.1.7777.1.2.6.1
		psAlarmVariable OBJECT-TYPE
			SYNTAX DisplayString (SIZE (0..128))
			MAX-ACCESS read-only
			STATUS current
			DESCRIPTION
				"Alarm notification."
			::= { traps 1 }



lockedOutAlarmSNMPSend NOTIFICATION-TYPE
        OBJECTS { psAlarmVariable }
        STATUS  current
        DESCRIPTION
            "Locked Out."
    ::= { traps 2 }

atsPositionErrSNMPSend NOTIFICATION-TYPE
        OBJECTS { psAlarmVariable }
        STATUS  current
        DESCRIPTION
            "ATS Position Error."
    ::= { traps 3 }

failToSyncSNMPSend NOTIFICATION-TYPE
        OBJECTS { psAlarmVariable }
        STATUS  current
        DESCRIPTION
            "Failure to Synchronize."
    ::= { traps 4 }

extendedParallelSNMPSend NOTIFICATION-TYPE
        OBJECTS { psAlarmVariable }
        STATUS  current
        DESCRIPTION
            "Failure to Synchronize."
    ::= { traps 5 }

isolationBypassActivitySNMPSend NOTIFICATION-TYPE
        OBJECTS { psAlarmVariable }
        STATUS  current
        DESCRIPTION
            "Isolation Bypass Activity."
    ::= { traps 6 }

engineStartSNMPSend NOTIFICATION-TYPE
        OBJECTS { psAlarmVariable }
        STATUS  current
        DESCRIPTION
            "Engine Start."
    ::= { traps 7 }

sourceFailureSNMPSend NOTIFICATION-TYPE
        OBJECTS { psAlarmVariable }
        STATUS  current
        DESCRIPTION
            "Source Failure."
    ::= { traps 8 }

transferAlarmSNMPSend NOTIFICATION-TYPE
        OBJECTS { psAlarmVariable }
        STATUS  current
        DESCRIPTION
            "Transfer Alarm."
    ::= { traps 9 }

transferFailureSNMPSend NOTIFICATION-TYPE
        OBJECTS { psAlarmVariable }
        STATUS  current
        DESCRIPTION
            "Transfer Failure."
    ::= { traps 10 }

failureToAcceptTimerSNMPSend NOTIFICATION-TYPE
        OBJECTS { psAlarmVariable }
        STATUS  current
        DESCRIPTION
            "Expiration of Failure to Accept Timer."
    ::= { traps 11 }

loadDisconnectedSNMPSend NOTIFICATION-TYPE
        OBJECTS { psAlarmVariable }
        STATUS  current
        DESCRIPTION
            "Load Disconnected."
    ::= { traps 12 }

lossOfEWhenOnESNMPSend NOTIFICATION-TYPE
        OBJECTS { psAlarmVariable }
        STATUS  current
        DESCRIPTION
            "Loss Of E When On E."
    ::= { traps 13 }

-- Conformance information ******************************************


END

--  Filename:   ASCO_72EE-SMVI2.mib
--  Project:    Ethernet Adapter
--  Purpose:    ASCO requirement
--  Author:     Vardhaman
--  Created:    Tue Jan 29 2013
-- Local Variables:
-- mibcc: "smidump "
-- mibc-flags: "-c smi.cfg -f dmhsnmp "
-- eval: (make-local-variable 'compile-command)
-- eval: (make-local-variable 'file)
-- eval: (make-local-variable 'outfile)
-- eval: (setq file (file-name-nondirectory buffer-file-name))
-- eval: (setq outfile (concat (base-name file) "-pe"))
-- eval: (setq compile-command (concat mibcc " " mibc-flags "-o " outfile " "file))
-- End:
--
