GEIST-QUETZAL-MIB DEFINITIONS ::= BEGIN
                                   
IMPORTS 

DisplayString, TEXTUAL-CONVENTION, RowStatus, 	
DateAndTime												FROM SNMPv2-TC
MODULE-IDENTITY, OBJECT-TYPE, NOTIFICATION-TYPE, Counter32,
enterprises, Gauge32, Integer32, Unsigned32				FROM SNMPv2-SMI
InetAddress, InetAddressType, InetPortNumber			FROM INET-ADDRESS-MIB;

geist MODULE-IDENTITY
	LAST-UPDATED "201209210000Z"
	ORGANIZATION "Geist Global"
	CONTACT-INFO "support@geistglobal.com"
	DESCRIPTION "Geist Quetzal MIB"
		
	REVISION "201209210000Z"
	DESCRIPTION "Initial version"
	::= { enterprises 21239 }
	
DeviceSerial ::= TEXTUAL-CONVENTION
    STATUS		current
	DESCRIPTION
		"Unique serial number used to identify a device. A serial
		number is a string, with a length of 16. The string will only
		contain the characters 0 to 9, and A to F. "
	SYNTAX 		OCTET STRING (SIZE (1..16))

DeviceStatus ::= TEXTUAL-CONVENTION
	STATUS		current
	DESCRIPTION
		"Indicates the condition of the device"				                       
	SYNTAX 		INTEGER { 
	                      ok(1), 
	                      notFound(2), 
	                      ioError(3), 
	                      unknown(4), 
	                      deleted(5) 
	                    }
	
DeviceLabel ::= TEXTUAL-CONVENTION
	STATUS		current
	DESCRIPTION
		"User-defined device name"
	SYNTAX 		OCTET STRING (SIZE (0..32))
	
TemperatureUnits ::= TEXTUAL-CONVENTION
	STATUS		current
	DESCRIPTION
		"Used to tell the units of a temperature reading"
	SYNTAX 		INTEGER { fahrenheit(1), celsius(2) }
	
TemperatureValue ::= TEXTUAL-CONVENTION
	DISPLAY-HINT "d-1"
	STATUS		current
	DESCRIPTION
		"0.1 degree"
	SYNTAX 		Integer32

DeciAmps ::= TEXTUAL-CONVENTION
	DISPLAY-HINT "d-1"
	STATUS		current
	DESCRIPTION
		"0.1 Amps"
	SYNTAX 		Gauge32
	
EmailAddress ::= TEXTUAL-CONVENTION
	STATUS		current
	DESCRIPTION
		"String containing an email address"
	SYNTAX 		OCTET STRING (SIZE (0..64))
	
quetzal OBJECT IDENTIFIER ::= { geist 6 }

devices OBJECT IDENTIFIER ::= { quetzal 1 }	
alarms OBJECT IDENTIFIER ::= { quetzal 2 }	
general OBJECT IDENTIFIER ::= { quetzal 3 }
traps OBJECT IDENTIFIER ::= { quetzal 32767 }	

pdu OBJECT IDENTIFIER ::= { devices 1 }
ccat OBJECT IDENTIFIER ::= { devices 2 }	
rtafhd3 OBJECT IDENTIFIER ::= { devices 3 }	
dm OBJECT IDENTIFIER ::= { devices 4 }
-- reserved: { devices 5 }
rs2 OBJECT IDENTIFIER ::= { devices 6 }
rss OBJECT IDENTIFIER ::= { devices 7 }
rt OBJECT IDENTIFIER ::= { devices 8 }
t3hd OBJECT IDENTIFIER ::= { devices 9 }
thd OBJECT IDENTIFIER ::= { devices 10 }
legacyPDU OBJECT IDENTIFIER ::= { devices 99 }

pduBaseDeltaTable OBJECT-TYPE
	SYNTAX SEQUENCE OF PduBaseDeltaEntry
	MAX-ACCESS  not-accessible
	STATUS current
	DESCRIPTION 
	    "Base table for a delta-wired PDU. It contains general information
	    about the PDU. Entries in sub-tables provide data for channels, 
	    groups and outlets. The system creates these sub-table entries based
	    on hardware and configuration options, set at the factory."
	::= { legacyPDU 1 }	    

pduBaseDeltaEntry OBJECT-TYPE
	SYNTAX  PduBaseDeltaEntry
	MAX-ACCESS  not-accessible
	STATUS current
	DESCRIPTION 
		"Entry for a delta PDU device. This table will only have an entry
	    if the main device is a delta-wired PDU."
	INDEX { pduBaseDeltaIndex }
	::= { pduBaseDeltaTable 1 }     
	
PduBaseDeltaEntry ::= SEQUENCE {
	pduBaseDeltaIndex		Unsigned32,
	pduBaseDeltaSerial		DeviceSerial,
	pduBaseDeltaLabel		DeviceLabel,
	pduBaseDeltaStatus		DeviceStatus,
	pduBaseDeltaKWattHrsTotal		Gauge32,
	pduBaseDeltaRealPowerTotal		Gauge32,
	pduBaseDeltaAmpsA		DeciAmps,
	pduBaseDeltaAmpsB		DeciAmps,
	pduBaseDeltaAmpsC		DeciAmps
}

pduBaseDeltaIndex OBJECT-TYPE
	SYNTAX  Unsigned32(1..64)
	MAX-ACCESS  not-accessible
	STATUS current
	DESCRIPTION "Table entry index value"
	::= { pduBaseDeltaEntry  1 }

pduBaseDeltaSerial OBJECT-TYPE
	SYNTAX  DeviceSerial
	MAX-ACCESS  read-only
	STATUS current
	DESCRIPTION 
	    "PDU's unique ID, used as a reference for channels, groups 
	    and outlets"
	::= { pduBaseDeltaEntry 2 }
	
pduBaseDeltaLabel OBJECT-TYPE
	SYNTAX  DeviceLabel
	MAX-ACCESS  read-write
	STATUS current
	DESCRIPTION "User-defined name for the delta PDU device"
	::= { pduBaseDeltaEntry 3 }
	
pduBaseDeltaStatus OBJECT-TYPE
	SYNTAX  DeviceStatus
	MAX-ACCESS  read-only
	STATUS current
	DESCRIPTION "Condition of the device"
	::= { pduBaseDeltaEntry 4 }
	
pduBaseDeltaKWattHrsTotal OBJECT-TYPE
	SYNTAX  Gauge32
	MAX-ACCESS  read-only
	STATUS current
	DESCRIPTION "Total kilowatt hours for the delta PDU"
	::= { pduBaseDeltaEntry 5 }
	
pduBaseDeltaRealPowerTotal OBJECT-TYPE
	SYNTAX  Gauge32
	MAX-ACCESS  read-only
	STATUS current
	DESCRIPTION "Total real power for the delta PDU"
	::= { pduBaseDeltaEntry 6 }
	
pduBaseDeltaAmpsA OBJECT-TYPE
	SYNTAX  DeciAmps
	MAX-ACCESS  read-only
	STATUS current
	DESCRIPTION "Current reading for A"
	::= { pduBaseDeltaEntry 7 }
	
pduBaseDeltaAmpsB OBJECT-TYPE
	SYNTAX  DeciAmps
	MAX-ACCESS  read-only
	STATUS current
	DESCRIPTION "Current reading for B"
	::= { pduBaseDeltaEntry 8 }
	
pduBaseDeltaAmpsC OBJECT-TYPE
	SYNTAX  DeciAmps
	MAX-ACCESS  read-only
	STATUS current
	DESCRIPTION "Current reading for C"
	::= { pduBaseDeltaEntry 9 }
	

pduBaseWyeTable OBJECT-TYPE
	SYNTAX SEQUENCE OF PduBaseWyeEntry
	MAX-ACCESS  not-accessible
	STATUS current
	DESCRIPTION
	    "Base table for a Wye-wired PDU. It contains general information
	    about the PDU. Entries in sub-tables provide data for channels, 
	    groups and outlets. The system creates these sub-table entries based
	    on hardware, wiring and configuration options, set at the factory."
	::= { legacyPDU 2 }	    

pduBaseWyeEntry OBJECT-TYPE
	SYNTAX  PduBaseWyeEntry
	MAX-ACCESS  not-accessible
	STATUS current
	DESCRIPTION 
		"Entry for a Wye-wired PDU device. This table will only have an entry
	    if the PDU uses a Wye wiring."
	INDEX { pduBaseWyeIndex }
	::= { pduBaseWyeTable 1 }     
	
PduBaseWyeEntry ::= SEQUENCE {
	pduBaseWyeIndex		Unsigned32,
	pduBaseWyeSerial		DeviceSerial,
	pduBaseWyeLabel		DeviceLabel,
	pduBaseWyeStatus		DeviceStatus,
	pduBaseWyeKWattHrsTotal		Gauge32,
	pduBaseWyeRealPowerTotal		Gauge32,
	pduBaseWyeWyeChannelCount		Unsigned32
}

pduBaseWyeIndex OBJECT-TYPE
	SYNTAX  Unsigned32(1..64)
	MAX-ACCESS  not-accessible
	STATUS current
	DESCRIPTION "Table entry index value"
	::= { pduBaseWyeEntry  1 }

pduBaseWyeSerial OBJECT-TYPE
	SYNTAX  DeviceSerial
	MAX-ACCESS  read-only
	STATUS current
	DESCRIPTION 
	    "PDU's unique ID, used as a reference for channels, 
	    groups and outlets"
	::= { pduBaseWyeEntry 2 }
	
pduBaseWyeLabel OBJECT-TYPE
	SYNTAX  DeviceLabel
	MAX-ACCESS  read-write
	STATUS current
	DESCRIPTION "Used-defined name for the PDU"
	::= { pduBaseWyeEntry 3 }
	
pduBaseWyeStatus OBJECT-TYPE
	SYNTAX  DeviceStatus
	MAX-ACCESS  read-only
	STATUS current
	DESCRIPTION "Condition of the device"
	::= { pduBaseWyeEntry 4 }
	
pduBaseWyeKWattHrsTotal OBJECT-TYPE
	SYNTAX  Gauge32
	MAX-ACCESS  read-only
	STATUS current
	DESCRIPTION "Total kilowatt hours for the PDU"
	::= { pduBaseWyeEntry 5 }
	
pduBaseWyeRealPowerTotal OBJECT-TYPE
	SYNTAX  Gauge32
	MAX-ACCESS  read-only
	STATUS current
	DESCRIPTION "Total real power used by the PDU"
	::= { pduBaseWyeEntry 6 }
	
pduBaseWyeWyeChannelCount OBJECT-TYPE
	SYNTAX  Unsigned32 (1..3)
	MAX-ACCESS  read-only
	STATUS current
	DESCRIPTION 
	    "Count of the total number of Wye channels. Data for these channels
	    is found in the pduChannelWyeTable."
	::= { pduBaseWyeEntry 7 }
	

pduChannelDeltaTable OBJECT-TYPE
	SYNTAX SEQUENCE OF PduChannelDeltaEntry
	MAX-ACCESS  not-accessible
	STATUS current
	DESCRIPTION 
	    "The pduChannelDeltaTable contains specific channel information for
	    a delta PDU. "
	::= { legacyPDU 3 }	    

pduChannelDeltaEntry OBJECT-TYPE
	SYNTAX  PduChannelDeltaEntry
	MAX-ACCESS  not-accessible
	STATUS current
	DESCRIPTION 
		"Each entry represents a delta channel. Entries are indexed by the
		PDU instance number and a channel id number. This table will
		only have entries if a corresponding delta PDU exists."
	INDEX { pduBaseDeltaIndex, pduChannelDeltaID }
	::= { pduChannelDeltaTable 1 }     
	
PduChannelDeltaEntry ::= SEQUENCE {
	pduChannelDeltaID		Unsigned32,
	pduChannelDeltaLabel        DeviceLabel,
	pduChannelDeltaTitle		DisplayString,
	pduChannelDeltaKWattHrs		Gauge32,
	pduChannelDeltaVolts		Gauge32,
	pduChannelDeltaVoltPeak		Gauge32,
	pduChannelDeltaRealPower		Gauge32,
	pduChannelDeltaApparentPower		Gauge32,
	pduChannelDeltaPowerFactor		Gauge32
}

pduChannelDeltaID OBJECT-TYPE
	SYNTAX  Unsigned32 (1..3)
	MAX-ACCESS  read-only
	STATUS current
	DESCRIPTION "Delta channel id number"
	::= { pduChannelDeltaEntry 1 }

pduChannelDeltaLabel OBJECT-TYPE
	SYNTAX  DeviceLabel
	MAX-ACCESS  read-only
	STATUS current
	DESCRIPTION "User-defined name for this channel"
	::= { pduChannelDeltaEntry 2 }

pduChannelDeltaTitle OBJECT-TYPE
	SYNTAX  DisplayString
	MAX-ACCESS  read-only
	STATUS current
	DESCRIPTION "Factory-assigned name for this channel"
	::= { pduChannelDeltaEntry 3 }

pduChannelDeltaKWattHrs OBJECT-TYPE
	SYNTAX  Gauge32
	MAX-ACCESS  read-only
	STATUS current
	DESCRIPTION "Kilowatt hours for this channel"
	::= { pduChannelDeltaEntry 4 }
	
pduChannelDeltaVolts OBJECT-TYPE
	SYNTAX  Gauge32
	MAX-ACCESS  read-only
	STATUS current
	DESCRIPTION "Volt reading"
	::= { pduChannelDeltaEntry 5 }
	
pduChannelDeltaVoltPeak OBJECT-TYPE
	SYNTAX  Gauge32
	MAX-ACCESS  read-only
	STATUS current
	DESCRIPTION "Peak volt reading"
	::= { pduChannelDeltaEntry 6 }
	
pduChannelDeltaRealPower OBJECT-TYPE
	SYNTAX  Gauge32
	MAX-ACCESS  read-only
	STATUS current
	DESCRIPTION "Real power"
	::= { pduChannelDeltaEntry 7 }
	
pduChannelDeltaApparentPower OBJECT-TYPE
	SYNTAX  Gauge32
	MAX-ACCESS  read-only
	STATUS current
	DESCRIPTION "Apparent Power"
	::= { pduChannelDeltaEntry 8 }
	
pduChannelDeltaPowerFactor OBJECT-TYPE
	SYNTAX  Gauge32
	MAX-ACCESS  read-only
	STATUS current
	DESCRIPTION "Power Factor"
	::= { pduChannelDeltaEntry 9 }
	

pduChannelWyeTable OBJECT-TYPE
	SYNTAX SEQUENCE OF PduChannelWyeEntry
	MAX-ACCESS  not-accessible
	STATUS current
	DESCRIPTION
	     "The pduChannelWyeTable contains specific channel information for
	    a wye-wired PDU. "	    
	::= { legacyPDU 4 }	    

pduChannelWyeEntry OBJECT-TYPE
	SYNTAX  PduChannelWyeEntry
	MAX-ACCESS  not-accessible
	STATUS current
	DESCRIPTION 
		"Each entry represents a wye channel. Entries are indexed by the
		instance number of a PDU and a channel id number. This table will
		only have entries if a corresponding wye-wired PDU exists."
	INDEX { pduBaseWyeIndex, pduChannelWyeID }
	::= { pduChannelWyeTable 1 }     
	
PduChannelWyeEntry ::= SEQUENCE {
	pduChannelWyeID		Unsigned32,
	pduChannelWyeLabel		DeviceLabel,
	pduChannelWyeTitle		DisplayString,
	pduChannelWyeKWattHrs		Gauge32,
	pduChannelWyeVolts		Gauge32,
	pduChannelWyeVoltPeak		Gauge32,
	pduChannelWyeAmps		DeciAmps,
	pduChannelWyeAmpsPeak		DeciAmps,
	pduChannelWyeRealPower		Gauge32,
	pduChannelWyeApparentPower		Gauge32,
	pduChannelWyePowerFactor		Gauge32
}

pduChannelWyeID OBJECT-TYPE
	SYNTAX  Unsigned32 (1..3)
	MAX-ACCESS  read-only
	STATUS current
	DESCRIPTION "Wye channel id"
	::= { pduChannelWyeEntry 1 }

pduChannelWyeLabel OBJECT-TYPE
	SYNTAX  DeviceLabel
	MAX-ACCESS  read-only
	STATUS current
	DESCRIPTION "User-defined name for this channel"
	::= { pduChannelWyeEntry 2 }

pduChannelWyeTitle OBJECT-TYPE
	SYNTAX  DisplayString
	MAX-ACCESS  read-only
	STATUS current
	DESCRIPTION "Factory-assigned name for this channel"
	::= { pduChannelWyeEntry 3 }
	
pduChannelWyeKWattHrs OBJECT-TYPE
	SYNTAX  Gauge32
	MAX-ACCESS  read-only
	STATUS current
	DESCRIPTION "Kilowatt hours"
	::= { pduChannelWyeEntry 4 }
	
pduChannelWyeVolts OBJECT-TYPE
	SYNTAX  Gauge32
	MAX-ACCESS  read-only
	STATUS current
	DESCRIPTION "Volt reading"
	::= { pduChannelWyeEntry 5 }
	
pduChannelWyeVoltPeak OBJECT-TYPE
	SYNTAX  Gauge32
	MAX-ACCESS  read-only
	STATUS current
	DESCRIPTION "Peak volt reading"
	::= { pduChannelWyeEntry 6 }
	
pduChannelWyeAmps OBJECT-TYPE
	SYNTAX  DeciAmps
	MAX-ACCESS  read-only
	STATUS current
	DESCRIPTION "Current reading"
	::= { pduChannelWyeEntry 7 }
	
pduChannelWyeAmpsPeak OBJECT-TYPE
	SYNTAX  DeciAmps
	MAX-ACCESS  read-only
	STATUS current
	DESCRIPTION "Peak current reading"
	::= { pduChannelWyeEntry 8 }
	
pduChannelWyeRealPower OBJECT-TYPE
	SYNTAX  Gauge32
	MAX-ACCESS  read-only
	STATUS current
	DESCRIPTION "Real Power"
	::= { pduChannelWyeEntry 9 }
	
pduChannelWyeApparentPower OBJECT-TYPE
	SYNTAX  Gauge32
	MAX-ACCESS  read-only
	STATUS current
	DESCRIPTION "Apparent power"
	::= { pduChannelWyeEntry 10 }
	
pduChannelWyePowerFactor OBJECT-TYPE
	SYNTAX  Gauge32
	MAX-ACCESS  read-only
	STATUS current
	DESCRIPTION "Power Factor"
	::= { pduChannelWyeEntry 11 }
	

pduGroupTable OBJECT-TYPE
	SYNTAX SEQUENCE OF PduGroupEntry
	MAX-ACCESS  not-accessible
	STATUS current
	DESCRIPTION 
	    "Contains meter readings per outlet group"
	::= { legacyPDU 5 }	    

pduGroupEntry OBJECT-TYPE
	SYNTAX  PduGroupEntry
	MAX-ACCESS  not-accessible
	STATUS current
	DESCRIPTION 
		"Each entry represents an outlet group for a specific PDU. Groups
		are indexed by a PDU instance number and a group id number.
		The pduGroupIndex corresponds to a matching instance number in a
		base PDU table. For group entries to exist, a PDU that supports
		groups must also exist."
	INDEX { pduGroupIndex, pduGroupID }
	::= { pduGroupTable 1 }     
	
PduGroupEntry ::= SEQUENCE {
	pduGroupIndex		Unsigned32,
	pduGroupSerial		DeviceSerial,
	pduGroupID		    Unsigned32,
	pduGroupLabel		DeviceLabel,
	pduGroupTitle		DisplayString,
	pduGroupAmps		DeciAmps,
	pduGroupAmpsPeak	DeciAmps,
	pduGroupApparentPower	Gauge32,
	pduGroupPowerFactor	Gauge32,
	pduGroupRealPower	Gauge32,
	pduGroupVolts		Gauge32,
	pduGroupVoltsPeak		Gauge32,
	pduGroupWattHours		Gauge32
}

pduGroupIndex OBJECT-TYPE
	SYNTAX  Unsigned32(1..64)
	MAX-ACCESS  not-accessible
	STATUS current
	DESCRIPTION "Table entry index value"
	::= { pduGroupEntry  1 }

pduGroupSerial OBJECT-TYPE
	SYNTAX  DeviceSerial
	MAX-ACCESS  read-only
	STATUS current
	DESCRIPTION "Serial number of an existing base PDU"
	::= { pduGroupEntry 2 }
	
pduGroupID OBJECT-TYPE
	SYNTAX  Unsigned32 (1..8)
	MAX-ACCESS  read-only
	STATUS current
	DESCRIPTION "group id number"
	::= { pduGroupEntry 3 }

pduGroupLabel OBJECT-TYPE
	SYNTAX  DeviceLabel
	MAX-ACCESS  read-only
	STATUS current
	DESCRIPTION "User-defined name for this group"
	::= { pduGroupEntry 4 }

pduGroupTitle OBJECT-TYPE
	SYNTAX  DisplayString
	MAX-ACCESS  read-only
	STATUS current
	DESCRIPTION "Factory-assigned name for this group"
	::= { pduGroupEntry 5 }

pduGroupAmps OBJECT-TYPE
	SYNTAX  DeciAmps
	MAX-ACCESS  read-only
	STATUS current
	DESCRIPTION "Total amps for outlet group"
	::= { pduGroupEntry 6 }

pduGroupAmpsPeak OBJECT-TYPE
	SYNTAX  DeciAmps
	MAX-ACCESS  read-only
	STATUS current
	DESCRIPTION "Total amps-peak for outlet group"
	::= { pduGroupEntry 7 }

pduGroupApparentPower OBJECT-TYPE
	SYNTAX  Gauge32
	MAX-ACCESS  read-only
	STATUS current
	DESCRIPTION "Total apparent-power for outlet group"
	::= { pduGroupEntry 8 }

pduGroupPowerFactor OBJECT-TYPE
	SYNTAX  Gauge32
	MAX-ACCESS  read-only
	STATUS current
	DESCRIPTION "Total power-factor for outlet group"
	::= { pduGroupEntry 9 }

pduGroupRealPower OBJECT-TYPE
	SYNTAX  Gauge32
	MAX-ACCESS  read-only
	STATUS current
	DESCRIPTION "Total real_power for outlet group"
	::= { pduGroupEntry 10 }
	
pduGroupVolts OBJECT-TYPE
	SYNTAX  Gauge32
	MAX-ACCESS  read-only
	STATUS current
	DESCRIPTION "Volts reading for outlet group"
	::= { pduGroupEntry 11 }

pduGroupVoltsPeak OBJECT-TYPE
	SYNTAX  Gauge32
	MAX-ACCESS  read-only
	STATUS current
	DESCRIPTION "volts-peak reading for outlet group"
	::= { pduGroupEntry 12 }

pduGroupWattHours OBJECT-TYPE
	SYNTAX  Gauge32
	MAX-ACCESS  read-only
	STATUS current
	DESCRIPTION "watt-hours reading for outlet group"
	::= { pduGroupEntry 13 }
	

pduOutletMainTable OBJECT-TYPE
	SYNTAX SEQUENCE OF PduOutletMainEntry
	MAX-ACCESS  not-accessible
	STATUS current
	DESCRIPTION 
	    "Outlet data common to all outlet types. Other tables provide 
	    additional data, based on the outlet type."
	::= { legacyPDU 6 }	    

pduOutletMainEntry OBJECT-TYPE
	SYNTAX  PduOutletMainEntry
	MAX-ACCESS  not-accessible
	STATUS current
	DESCRIPTION 
		"One entry per outlet. Each entry corresponds to an outlet on a
		PDU, so they are indexed by the PDU's instance number and an outlet
		id number. The pduOutletMainIndex corresponds to an instance number 
		for an existing PDU."
	INDEX { pduOutletMainIndex, pduOutletMainID }
	::= { pduOutletMainTable 1 }     
	
PduOutletMainEntry ::= SEQUENCE {
	pduOutletMainIndex		Unsigned32,
	pduOutletMainSerial		DeviceSerial,
	pduOutletMainID		Unsigned32,
	pduOutletMainLabel		DeviceLabel,
	pduOutletMainTitle		DisplayString,
	pduOutletMainGroup		DisplayString,
	pduOutletMainURL		DisplayString
}

pduOutletMainIndex OBJECT-TYPE
	SYNTAX  Unsigned32(1..64)
	MAX-ACCESS  not-accessible
	STATUS current
	DESCRIPTION "Table entry index value"
	::= { pduOutletMainEntry  1 }

pduOutletMainSerial OBJECT-TYPE
	SYNTAX  DeviceSerial
	MAX-ACCESS  read-only
	STATUS current
	DESCRIPTION "Serial number of an existing PDU device"
	::= { pduOutletMainEntry 2 }
	
pduOutletMainID OBJECT-TYPE
	SYNTAX  Unsigned32 (1..64)
	MAX-ACCESS  read-only
	STATUS current
	DESCRIPTION "Outlet id number"
	::= { pduOutletMainEntry 3 }
	
pduOutletMainLabel OBJECT-TYPE
	SYNTAX  DeviceLabel
	MAX-ACCESS  read-write
	STATUS current
	DESCRIPTION "User-defined outlet name"
	::= { pduOutletMainEntry 4 }
	
pduOutletMainTitle OBJECT-TYPE
	SYNTAX  DisplayString
	MAX-ACCESS  read-only
	STATUS current
	DESCRIPTION "Factory-assigned outlet name"
	::= { pduOutletMainEntry 5 }

pduOutletMainGroup OBJECT-TYPE
	SYNTAX  DisplayString
	MAX-ACCESS  read-only
	STATUS current
	DESCRIPTION "Outlet's group name"
	::= { pduOutletMainEntry 6 }
	
pduOutletMainURL OBJECT-TYPE
	SYNTAX  DisplayString
	MAX-ACCESS  read-write
	STATUS current
	DESCRIPTION "Link info for outlet"
	::= { pduOutletMainEntry 7 }
	

pduOutletSwitchTable OBJECT-TYPE
	SYNTAX SEQUENCE OF PduOutletSwitchEntry
	MAX-ACCESS  not-accessible
	STATUS current
	DESCRIPTION 
	    "Contains entries for outlets that support switching. This table
	    supplements the corresponding entries in pduOutletMainTable."
	::= { legacyPDU 7 }	    

pduOutletSwitchEntry OBJECT-TYPE
	SYNTAX  PduOutletSwitchEntry
	MAX-ACCESS  not-accessible
	STATUS current
	DESCRIPTION 
		"One entry is created per switching outlet. These entries correspond
		to an outlet entry in pduOutletMainTable. Each entry in this table
		uses the index and outlet id from the pduOutletMainTable."
	INDEX { pduOutletMainIndex, pduOutletMainID }
	::= { pduOutletSwitchTable 1 }     
	
PduOutletSwitchEntry ::= SEQUENCE {
	pduOutletSwitchState		INTEGER,
	pduOutletSwitchStateChangeTime		Unsigned32,
	pduOutletSwitchCurrentAction		INTEGER,
	pduOutletSwitchOnDelay		Unsigned32,
	pduOutletSwitchOffDelay		Unsigned32,
	pduOutletSwitchRebootDelay		Unsigned32,
	pduOutletSwitchRebootHold		Unsigned32,
	pduOutletSwitchStartupAction		INTEGER,
	pduOutletSwitchStartupStateDelay		Unsigned32,
	pduOutletSwitchControl    INTEGER
}

pduOutletSwitchState OBJECT-TYPE
	SYNTAX  INTEGER { 
	                  outletOff(0), 
	                  outletOn(1), 
	                  outletError(2) 
	                }
	MAX-ACCESS  read-only
	STATUS current
	DESCRIPTION "Switch state of the outlet"
	::= { pduOutletSwitchEntry 1 }
	
pduOutletSwitchStateChangeTime OBJECT-TYPE
	SYNTAX  Unsigned32
	MAX-ACCESS  read-only
	STATUS current
	DESCRIPTION "Seconds until an action will occur"
	::= { pduOutletSwitchEntry 2 }
	
pduOutletSwitchCurrentAction OBJECT-TYPE
	SYNTAX  INTEGER { 
	                  manual(1), 
	                  reboot(2), 
	                  startUp(3),     
	                  other(4) 
	                }
	MAX-ACCESS  read-only
	STATUS current
	DESCRIPTION "Outlet action in progress"
	::= { pduOutletSwitchEntry 3 }
	
pduOutletSwitchOnDelay OBJECT-TYPE
	SYNTAX  Unsigned32
	MAX-ACCESS  read-write
	STATUS current
	DESCRIPTION "Delay used in turning the outlet on"
	::= { pduOutletSwitchEntry 4 }
	
pduOutletSwitchOffDelay OBJECT-TYPE
	SYNTAX  Unsigned32
	MAX-ACCESS  read-write
	STATUS current
	DESCRIPTION "Delay used in turning the outlet off"
	::= { pduOutletSwitchEntry 5 }
	
pduOutletSwitchRebootDelay OBJECT-TYPE
	SYNTAX  Unsigned32
	MAX-ACCESS  read-write
	STATUS current
	DESCRIPTION "Delay used prior to outlet reboot"
	::= { pduOutletSwitchEntry 6 }
	
pduOutletSwitchRebootHold OBJECT-TYPE
	SYNTAX  Unsigned32
	MAX-ACCESS  read-write
	STATUS current
	DESCRIPTION "Time the outlet is kept off during a reboot"
	::= { pduOutletSwitchEntry 7 }
	
pduOutletSwitchStartupAction OBJECT-TYPE
	SYNTAX  INTEGER { startOff(0), startOn(1), lastKnown(2) }
	MAX-ACCESS  read-write
	STATUS current
	DESCRIPTION "State the outlet should take at startup (first powered)"
	::= { pduOutletSwitchEntry 8 }
	
pduOutletSwitchStartupStateDelay OBJECT-TYPE
	SYNTAX  Unsigned32
	MAX-ACCESS  read-write
	STATUS current
	DESCRIPTION 
	    "Delay from startup before the outlet changes to the StartupAction"
	::= { pduOutletSwitchEntry 9 }

pduOutletSwitchControl OBJECT-TYPE
	SYNTAX  INTEGER { 	                  
	                    none(0),	                  	                  
	                    cancelActions(1), 	                  	                  
	                    onNoDelay(2),
	                    onDelay(3),
	                    offNoDelay(4),
	                    offDelay(5),
	                    rebootNoDelay(6),
	                    rebootDelay(7)	                   	                   
	                }
	MAX-ACCESS  read-write
	STATUS current
	DESCRIPTION 
	    "Used for manual control of the outlet. This is accomplished by setting
	    this value to one of the following:
        
	    onNoDelay(2): Turn outlet on, no delay        
	    onDelay(3): After delay (pduOutletSwitchOnDelay), turn outlet on        
	    offNoDelay(4): Turn outlet off, no delay
        offDelay(5): After delay (pduOutletSwitchOffDelay), turn outlet off
        rebootNoDelay(6): Turn off, delay (pduOutletSwitchRebootHold), turn on 
        rebootDelay(7): Delay (pduOutletSwitchRebootDelay), turn off, 
                        delay ((pduOutletSwitchOffDelay)), turn on
                        
        cancelActions(1): cancel one of the above actions
        
        The default value is none(0). When set, it keeps this value until the
        operation is complete. Then the value goes back to none(0)."
	::= { pduOutletSwitchEntry 10 }


	

pduOutletMeterTable OBJECT-TYPE
	SYNTAX SEQUENCE OF PduOutletMeterEntry
	MAX-ACCESS  not-accessible
	STATUS current
	DESCRIPTION
	    "Contains entries for outlets that support metering. This table
	    supplements the corresponding entries in pduOutletMainTable."	    
	::= { legacyPDU 8 }	    

pduOutletMeterEntry OBJECT-TYPE
	SYNTAX  PduOutletMeterEntry
	MAX-ACCESS  not-accessible
	STATUS current
	DESCRIPTION 
		"One entry is created per metering outlet. These entries correspond
		to an outlet entry in pduOutletMainTable. Each entry in this table
		uses the index and outlet id from the pduOutletMainTable."
	INDEX { pduOutletMainIndex, pduOutletMainID }
	::= { pduOutletMeterTable 1 }     
	
PduOutletMeterEntry ::= SEQUENCE {
	pduOutletMeterKWattHrs		Gauge32,
	pduOutletMeterAmps		DeciAmps,
	pduOutletMeterPower		Gauge32
}

pduOutletMeterKWattHrs OBJECT-TYPE
	SYNTAX  Gauge32
	MAX-ACCESS  read-only
	STATUS current
	DESCRIPTION "Kilowatt hours for outlet"
	::= { pduOutletMeterEntry 1 }
	
pduOutletMeterAmps OBJECT-TYPE
	SYNTAX  DeciAmps
	MAX-ACCESS  read-only
	STATUS current
	DESCRIPTION "Current reading for outlet"
	::= { pduOutletMeterEntry 2 }
	
pduOutletMeterPower OBJECT-TYPE
	SYNTAX  Gauge32
	MAX-ACCESS  read-only
	STATUS current
	DESCRIPTION "Power measurement for outlet"
	::= { pduOutletMeterEntry 3 }
	

ccatTable OBJECT-TYPE
	SYNTAX SEQUENCE OF CcatEntry
	MAX-ACCESS  not-accessible
	STATUS current
	DESCRIPTION "Remote analog to digital sensor device"
	::= { ccat 1 }	    

ccatEntry OBJECT-TYPE
	SYNTAX  CcatEntry
	MAX-ACCESS  not-accessible
	STATUS current
	DESCRIPTION 
		"One entry per CCAT device. Indexed by an instance number."
	INDEX { ccatIndex }
	::= { ccatTable 1 }     
	
CcatEntry ::= SEQUENCE {
	ccatIndex		Unsigned32,
	ccatSerial		DeviceSerial,
	ccatLabel		DeviceLabel,
	ccatStatus		DeviceStatus,
	ccatType		INTEGER,
	ccatTypeDesc		DisplayString,
	ccatTypeValue		DisplayString,
	ccatRawValue		Integer32,
	ccatScaledValue		Integer32,
	ccatScaledUnits		DisplayString,
	ccatScaledMin		Integer32,
	ccatScaledMax		Integer32
}

ccatIndex OBJECT-TYPE
	SYNTAX  Unsigned32(1..64)
	MAX-ACCESS  not-accessible
	STATUS current
	DESCRIPTION "Table entry index value"
	::= { ccatEntry  1 }

ccatSerial OBJECT-TYPE
	SYNTAX  DeviceSerial
	MAX-ACCESS  read-only
	STATUS current
	DESCRIPTION "Unique device id"
	::= { ccatEntry 2 }
	
ccatLabel OBJECT-TYPE
	SYNTAX  DeviceLabel
	MAX-ACCESS  read-write
	STATUS current
	DESCRIPTION "User-defined name"
	::= { ccatEntry 3 }
	
ccatStatus OBJECT-TYPE
	SYNTAX  DeviceStatus
	MAX-ACCESS  read-only
	STATUS current
	DESCRIPTION "Condition of the sensor"
	::= { ccatEntry 4 }
	
ccatType OBJECT-TYPE
	SYNTAX  INTEGER { 
	                  door(1), 
	                  water(2), 
	                  current(3), 
	                  millivolt(4), 
	                  digital(5), 
	                  cpm(6), 
	                  smoke(7), 
	                  neg48vdc(8), 
	                  pos30vdc(9), 
	                  analog(10) 
	                }
	MAX-ACCESS  read-only
	STATUS current
	DESCRIPTION 
	    "Indicates the CCAT type. The type is used to convert the raw analog
	    value to one appropriate for the type."
	::= { ccatEntry 5 }
	
ccatTypeDesc OBJECT-TYPE
	SYNTAX  DisplayString
	MAX-ACCESS  read-only
	STATUS current
	DESCRIPTION "Human-readable device type"
	::= { ccatEntry 6 }
	
ccatTypeValue OBJECT-TYPE
	SYNTAX  DisplayString
	MAX-ACCESS  read-only
	STATUS current
	DESCRIPTION "String version of the sensor reading"
	::= { ccatEntry 7 }
	
ccatRawValue OBJECT-TYPE
	SYNTAX  Integer32
	MAX-ACCESS  read-only
	STATUS current
	DESCRIPTION "Raw ADC value"
	::= { ccatEntry 8 }
	
ccatScaledValue OBJECT-TYPE
	SYNTAX  Integer32
	MAX-ACCESS  read-only
	STATUS current
	DESCRIPTION 
	    "Final scaled sensor value. This is the value after being adjusted for
	    CCAT type and range."
	::= { ccatEntry 9 }
	
ccatScaledUnits OBJECT-TYPE
	SYNTAX  DisplayString
	MAX-ACCESS  read-write
	STATUS current
	DESCRIPTION "Units for the final sensor value after scaling."
	::= { ccatEntry 10 }
	
ccatScaledMin OBJECT-TYPE
	SYNTAX  Integer32
	MAX-ACCESS  read-write
	STATUS current
	DESCRIPTION "The lowest possible value for the sensor"
	::= { ccatEntry 11 }
	
ccatScaledMax OBJECT-TYPE
	SYNTAX  Integer32
	MAX-ACCESS  read-write
	STATUS current
	DESCRIPTION "Highest possible value for the sensor"
	::= { ccatEntry 12 }
	

rtafhd3Table OBJECT-TYPE
	SYNTAX SEQUENCE OF Rtafhd3Entry
	MAX-ACCESS  not-accessible
	STATUS current
	DESCRIPTION "Combo airflow, temp, humidity and dewpoint sensor"
	::= { rtafhd3 1 }	    

rtafhd3Entry OBJECT-TYPE
	SYNTAX  Rtafhd3Entry
	MAX-ACCESS  not-accessible
	STATUS current
	DESCRIPTION 
		"One entry per device. Indexed by an instance number."
	INDEX { rtafhd3Index }
	::= { rtafhd3Table 1 }     
	
Rtafhd3Entry ::= SEQUENCE {
	rtafhd3Index		Unsigned32,
	rtafhd3Serial		DeviceSerial,
	rtafhd3Label		DeviceLabel,
	rtafhd3Status		DeviceStatus,
	rtafhd3Airflow		Gauge32,
	rtafhd3Humidity		Gauge32,
	rtafhd3Temp		TemperatureValue,
	rtafhd3DewPoint		TemperatureValue,
	rtafhd3TDUnits		TemperatureUnits
}

rtafhd3Index OBJECT-TYPE
	SYNTAX  Unsigned32(1..64)
	MAX-ACCESS  not-accessible
	STATUS current
	DESCRIPTION "Table entry index value"
	::= { rtafhd3Entry  1 }

rtafhd3Serial OBJECT-TYPE
	SYNTAX  DeviceSerial
	MAX-ACCESS  read-only
	STATUS current
	DESCRIPTION "Unique device id"
	::= { rtafhd3Entry 2 }
	
rtafhd3Label OBJECT-TYPE
	SYNTAX  DeviceLabel
	MAX-ACCESS  read-write
	STATUS current
	DESCRIPTION "User-defined name"
	::= { rtafhd3Entry 3 }
	
rtafhd3Status OBJECT-TYPE
	SYNTAX  DeviceStatus
	MAX-ACCESS  read-only
	STATUS current
	DESCRIPTION "Sensor condition"
	::= { rtafhd3Entry 4 }
	
rtafhd3Airflow OBJECT-TYPE
	SYNTAX  Gauge32
	MAX-ACCESS  read-only
	STATUS current
	DESCRIPTION "Airflow reading"
	::= { rtafhd3Entry 5 }
	
rtafhd3Humidity OBJECT-TYPE
	SYNTAX  Gauge32
	MAX-ACCESS  read-only
	STATUS current
	DESCRIPTION "Humidity reading"
	::= { rtafhd3Entry 6 }
	
rtafhd3Temp OBJECT-TYPE
	SYNTAX  TemperatureValue
	MAX-ACCESS  read-only
	STATUS current
	DESCRIPTION 
	    "Temperature reading in units indicated by rtafhd3TDUnits"
	::= { rtafhd3Entry 7 }
	
rtafhd3DewPoint OBJECT-TYPE
	SYNTAX  TemperatureValue
	MAX-ACCESS  read-only
	STATUS current
	DESCRIPTION 
	    "Dewpoint reading in units indicated by rtafhd3TDUnits"
	::= { rtafhd3Entry 8 }
	
rtafhd3TDUnits OBJECT-TYPE
	SYNTAX  TemperatureUnits
	MAX-ACCESS  read-only
	STATUS current
	DESCRIPTION "Tells what units are used for temperature and dewpoint"
	::= { rtafhd3Entry 9 }

dmMainTable OBJECT-TYPE
	SYNTAX SEQUENCE OF DmMainEntry
	MAX-ACCESS  not-accessible
	STATUS current
	DESCRIPTION "Contains entries for DM devices (multi-channel power meter)"
	::= { dm 1 }	    

dmMainEntry OBJECT-TYPE
	SYNTAX  DmMainEntry
	MAX-ACCESS  not-accessible
	STATUS current
	DESCRIPTION 
		"Each entry corresponds to one DM device. Each entry is indexed by
		an instance number."
	INDEX { dmMainSerial }
	::= { dmMainTable 1 }     
	
DmMainEntry ::= SEQUENCE {
	dmMainIndex		Unsigned32,
	dmMainSerial		DeviceSerial,
	dmMainLabel		DeviceLabel,
	dmMainStatus		DeviceStatus,
	dmMainDevType		DisplayString,
	dmMainDevVer		DisplayString,
	dmMainMainChCount		Unsigned32,
	dmMainAuxChCount		Unsigned32
}

dmMainIndex OBJECT-TYPE
	SYNTAX  Unsigned32(1..64)
	MAX-ACCESS  not-accessible
	STATUS current
	DESCRIPTION "Table entry index value"
	::= { dmMainEntry  1 }

dmMainSerial OBJECT-TYPE
	SYNTAX  DeviceSerial
	MAX-ACCESS  read-only
	STATUS current
	DESCRIPTION "Unique device id"
	::= { dmMainEntry 2 }
	
dmMainLabel OBJECT-TYPE
	SYNTAX  DeviceLabel
	MAX-ACCESS  read-write
	STATUS current
	DESCRIPTION "User-defined name"
	::= { dmMainEntry 3 }
	
dmMainStatus OBJECT-TYPE
	SYNTAX  DeviceStatus
	MAX-ACCESS  read-only
	STATUS current
	DESCRIPTION "Condition of the sensor"
	::= { dmMainEntry 4 }
	
dmMainDevType OBJECT-TYPE
	SYNTAX  DisplayString
	MAX-ACCESS  read-only
	STATUS current
	DESCRIPTION "Device type"
	::= { dmMainEntry 5 }
	
dmMainDevVer OBJECT-TYPE
	SYNTAX  DisplayString
	MAX-ACCESS  read-only
	STATUS current
	DESCRIPTION "Device version"
	::= { dmMainEntry 6 }
	
dmMainMainChCount OBJECT-TYPE
	SYNTAX  Unsigned32 (0..16)
	MAX-ACCESS  read-only
	STATUS current
	DESCRIPTION 
	    "Number of main channels. The dmChannelTable contains one entry
	    for each channel."
	::= { dmMainEntry 7 }
	
dmMainAuxChCount OBJECT-TYPE
	SYNTAX  Unsigned32 (0..48)
	MAX-ACCESS  read-only
	STATUS current
	DESCRIPTION 
	    "Number of aux channels. The dmChannelTable contains one entry
	    for each channel."
	::= { dmMainEntry 8 }
	

dmChannelTable OBJECT-TYPE
	SYNTAX SEQUENCE OF DmChannelEntry
	MAX-ACCESS  not-accessible
	STATUS current
	DESCRIPTION 
	    "Contains entries that represent DM power channels."
	::= { dm 2 }	    

dmChannelEntry OBJECT-TYPE
	SYNTAX  DmChannelEntry
	MAX-ACCESS  not-accessible
	STATUS current
	DESCRIPTION 
		"One entry for each channel on a DM. Channels are indexed by the
		instance number of the DM device they belong to and a channel number."
	INDEX { dmMainIndex, dmChannelID }
	::= { dmChannelTable 1 }     
	
DmChannelEntry ::= SEQUENCE {
	dmChannelID		Unsigned32,
	dmChannelLabel		DisplayString,
	dmChannelType		DisplayString,
	dmChannelGroup		INTEGER,
	dmChannelKey		DisplayString,
	dmChannelAmps		DeciAmps
}

dmChannelID OBJECT-TYPE
	SYNTAX  Unsigned32 (1..48)
	MAX-ACCESS  read-only
	STATUS current
	DESCRIPTION "Identifies power channel on a particular DM device"
	::= { dmChannelEntry 1 }
	
dmChannelLabel OBJECT-TYPE
	SYNTAX  DisplayString
	MAX-ACCESS  read-write
	STATUS current
	DESCRIPTION "User-defined channel name"
	::= { dmChannelEntry 2 }

dmChannelType OBJECT-TYPE
	SYNTAX  DisplayString
	MAX-ACCESS  read-only
	STATUS current
	DESCRIPTION 
	    "Tells if this is a main channel or aux channel."
	::= { dmChannelEntry 3 }

dmChannelGroup OBJECT-TYPE
	SYNTAX  INTEGER { main(1), aux(2) }
	MAX-ACCESS  read-only
	STATUS current
	DESCRIPTION "Tells what group this channel belongs to"
	::= { dmChannelEntry 4 }
	
dmChannelKey OBJECT-TYPE
	SYNTAX  DisplayString
	MAX-ACCESS  read-only
	STATUS current
	DESCRIPTION "Fixed channel name"
	::= { dmChannelEntry 5 }
	
dmChannelAmps OBJECT-TYPE
	SYNTAX  DeciAmps
	MAX-ACCESS  read-only
	STATUS current
	DESCRIPTION "Current reading for this channel"
	::= { dmChannelEntry 6 }

rs2MainTable OBJECT-TYPE
	SYNTAX SEQUENCE OF Rs2MainEntry
	MAX-ACCESS  not-accessible
	STATUS current
	DESCRIPTION 
	    "Contains entries for remote power monitor with switching outlets"
	::= { rs2 1 }	    

rs2MainEntry OBJECT-TYPE
	SYNTAX  Rs2MainEntry
	MAX-ACCESS  not-accessible
	STATUS current
	DESCRIPTION 
		"Each entry corresponds to an RS2 device. Indexed by an instance
		number. A sub-table rs2OutletTable provides access to outlet
		data for this device."
	INDEX { rs2MainSerial }
	::= { rs2MainTable 1 }     
	
Rs2MainEntry ::= SEQUENCE {
	rs2MainIndex		Unsigned32,
	rs2MainSerial		DeviceSerial,
	rs2MainLabel		DeviceLabel,
	rs2MainStatus		DeviceStatus,
	rs2MainKWattHrs		Gauge32,
	rs2MainVolts		Gauge32,
	rs2MainVoltMax		Gauge32,
	rs2MainVoltMin		Gauge32,
	rs2MainVoltPeak		Gauge32,
	rs2MainAmps		DeciAmps,
	rs2MainRealPower		Gauge32,
	rs2MainApparentPower		Gauge32,
	rs2MainPowerFactor		Gauge32
}

rs2MainIndex OBJECT-TYPE
	SYNTAX  Unsigned32(1..64)
	MAX-ACCESS  not-accessible
	STATUS current
	DESCRIPTION "Table entry index value"
	::= { rs2MainEntry  1 }

rs2MainSerial OBJECT-TYPE
	SYNTAX  DeviceSerial
	MAX-ACCESS  read-only
	STATUS current
	DESCRIPTION 
	    "Unique device id, used to index outlet entries in rs2OutletTable"
	::= { rs2MainEntry 2 }
	
rs2MainLabel OBJECT-TYPE
	SYNTAX  DeviceLabel
	MAX-ACCESS  read-write
	STATUS current
	DESCRIPTION "User-defined name"
	::= { rs2MainEntry 3 }
	
rs2MainStatus OBJECT-TYPE
	SYNTAX  DeviceStatus
	MAX-ACCESS  read-only
	STATUS current
	DESCRIPTION "Device condition"
	::= { rs2MainEntry 4 }
	
rs2MainKWattHrs OBJECT-TYPE
	SYNTAX  Gauge32
	MAX-ACCESS  read-only
	STATUS current
	DESCRIPTION "Kilowatt hours for the device"
	::= { rs2MainEntry 5 }
	
rs2MainVolts OBJECT-TYPE
	SYNTAX  Gauge32
	MAX-ACCESS  read-only
	STATUS current
	DESCRIPTION "Volt measurment for the device"
	::= { rs2MainEntry 6 }
	
rs2MainVoltMax OBJECT-TYPE
	SYNTAX  Gauge32
	MAX-ACCESS  read-only
	STATUS current
	DESCRIPTION "Max volt reading"
	::= { rs2MainEntry 7 }
	
rs2MainVoltMin OBJECT-TYPE
	SYNTAX  Gauge32
	MAX-ACCESS  read-only
	STATUS current
	DESCRIPTION "Min volt reading"
	::= { rs2MainEntry 8 }
	
rs2MainVoltPeak OBJECT-TYPE
	SYNTAX  Gauge32
	MAX-ACCESS  read-only
	STATUS current
	DESCRIPTION "Peak volt reading"
	::= { rs2MainEntry 9 }
	
rs2MainAmps OBJECT-TYPE
	SYNTAX  DeciAmps
	MAX-ACCESS  read-only
	STATUS current
	DESCRIPTION "Current reading"
	::= { rs2MainEntry 10 }
	
rs2MainRealPower OBJECT-TYPE
	SYNTAX  Gauge32
	MAX-ACCESS  read-only
	STATUS current
	DESCRIPTION "Real power"
	::= { rs2MainEntry 11 }
	
rs2MainApparentPower OBJECT-TYPE
	SYNTAX  Gauge32
	MAX-ACCESS  read-only
	STATUS current
	DESCRIPTION "Apparent power"
	::= { rs2MainEntry 12 }
	
rs2MainPowerFactor OBJECT-TYPE
	SYNTAX  Gauge32
	MAX-ACCESS  read-only
	STATUS current
	DESCRIPTION "Power factor"
	::= { rs2MainEntry 13 }

	
rs2OutletTable OBJECT-TYPE
	SYNTAX SEQUENCE OF Rs2OutletEntry
	MAX-ACCESS  not-accessible
	STATUS current
	DESCRIPTION 
	    "Contains entries for RS2 outlets. This is a sub-table of rs2MainTable."
	::= { rs2 2 }	    

rs2OutletEntry OBJECT-TYPE
	SYNTAX  Rs2OutletEntry
	MAX-ACCESS  not-accessible
	STATUS current
	DESCRIPTION 
		"One entry per outlet. Entries are indexed by the instance number for
		the RS2 and an outlet id number. Two outlet entries exist in this table
		for each entry in the rs2MainTable. "
	INDEX { rs2MainIndex, rs2OutletID }
	::= { rs2OutletTable 1 }     
	
Rs2OutletEntry ::= SEQUENCE {
	rs2OutletID		    Unsigned32,
	rs2OutletLabel		    DisplayString,
	rs2OutletState		    INTEGER,
	rs2OutletControl        INTEGER,
	rs2OutletCurrentAction  INTEGER
}

rs2OutletID OBJECT-TYPE
	SYNTAX  Unsigned32 (1..2)
	MAX-ACCESS  read-only
	STATUS current
	DESCRIPTION "Outlet id number"
	::= { rs2OutletEntry 1 }
	
rs2OutletLabel OBJECT-TYPE
	SYNTAX  DisplayString
	MAX-ACCESS  read-write
	STATUS current
	DESCRIPTION "User-defined outlet name"
	::= { rs2OutletEntry 2 }
	
rs2OutletState OBJECT-TYPE
	SYNTAX  INTEGER { 
	                  outletOff(0),
	                  outletOn(1),
	                  outletError(2)
	                }
	MAX-ACCESS  read-only
	STATUS current
	DESCRIPTION 
	    "Tells the state of the outlet.
	    outletOff(0): Outlet is off
	    outletOn(1): Outlet is powered
	    outletError(2): Outlet control error - possible relay failure.
	    "
	::= { rs2OutletEntry 3 }
	
rs2OutletControl OBJECT-TYPE
	SYNTAX  INTEGER {
	                    none(0),
	                    -- reserved for future use (1)
	                    on(2),
	                    -- reserved for future use (3)
	                    off(4),
	                    -- reserved for future use (5)
	                    reboot(6)
	                    -- reserved for future use (7)
	                }
	MAX-ACCESS  read-write
	STATUS current
	DESCRIPTION 
	    "Used for manual control of the outlet. This is accomplished by setting
	    this value to one of the following:
        
	    on(2): Turn outlet on
	    off(4): Turn outlet off
        reboot(6): Turn off, short delay, turn on
        
        The default value is none(0). This means that none of the above
        operations is pending. If the outlet is performing an action, then
        it will report a value other than none(0). Once complete, the value
        returns to none(0)."
	::= { rs2OutletEntry 4 }
		
rs2OutletCurrentAction OBJECT-TYPE
	SYNTAX  INTEGER { 
	                  manual(1),
	                  reboot(2),
	                  -- reserved for future use (3)
	                  other(4)
	                }
	MAX-ACCESS  read-only
	STATUS current
	DESCRIPTION 
	    "Outlet action in progress"
	::= { rs2OutletEntry 5 }

	
rssMainTable OBJECT-TYPE
	SYNTAX SEQUENCE OF RssMainEntry
	MAX-ACCESS  not-accessible
	STATUS current
	DESCRIPTION 
	    "Entries for RSS devices ( remote power monitor ). This table provides
	    overall device info, while power channel data is provided by the
	    sub-table, rssChannelTable."
	::= { rss 1 }	    

rssMainEntry OBJECT-TYPE
	SYNTAX  RssMainEntry
	MAX-ACCESS  not-accessible
	STATUS current
	DESCRIPTION 
		"One entry per RSS device. Indexed by an instance number.
		For each entry, there will be one or more channel entries in
		rssChannelTable. "
	INDEX { rssMainSerial }
	::= { rssMainTable 1 }     
	
RssMainEntry ::= SEQUENCE {
	rssMainIndex		Unsigned32,
	rssMainSerial		DeviceSerial,
	rssMainLabel		DeviceLabel,
	rssMainStatus		DeviceStatus,
	rssMainKWattHrsTotal		Gauge32,
	rssMainRealPowerTotal		Gauge32,
	rssMainChannelCount		Unsigned32
}


rssMainIndex OBJECT-TYPE
	SYNTAX  Unsigned32(1..64)
	MAX-ACCESS  not-accessible
	STATUS current
	DESCRIPTION "Table entry index value"
	::= { rssMainEntry 1 }

rssMainSerial OBJECT-TYPE
	SYNTAX  DeviceSerial
	MAX-ACCESS  read-only
	STATUS current
	DESCRIPTION "Unique device id"
	::= { rssMainEntry 2}
	
rssMainLabel OBJECT-TYPE
	SYNTAX  DeviceLabel
	MAX-ACCESS  read-write
	STATUS current
	DESCRIPTION "User-defined RSS name"
	::= { rssMainEntry 3 }
	
rssMainStatus OBJECT-TYPE
	SYNTAX  DeviceStatus
	MAX-ACCESS  read-only
	STATUS current
	DESCRIPTION "Device condition"
	::= { rssMainEntry 4 }
	
rssMainKWattHrsTotal OBJECT-TYPE
	SYNTAX  Gauge32
	MAX-ACCESS  read-only
	STATUS current
	DESCRIPTION "Total kilowatt hours"
	::= { rssMainEntry 5 }
	
rssMainRealPowerTotal OBJECT-TYPE
	SYNTAX  Gauge32
	MAX-ACCESS  read-only
	STATUS current
	DESCRIPTION "Toal real power"
	::= { rssMainEntry 6 }
	
rssMainChannelCount OBJECT-TYPE
	SYNTAX  Unsigned32 (1..3)
	MAX-ACCESS  read-only
	STATUS current
	DESCRIPTION 
	    "Number of power channels, tells how many channel entries will
	    exist in rssChannelTable for this device."
	::= { rssMainEntry 7 }
	

rssChannelTable OBJECT-TYPE
	SYNTAX SEQUENCE OF RssChannelEntry
	MAX-ACCESS  not-accessible
	STATUS current
	DESCRIPTION 
	    "Power channels for RSS devices. This is a table contains channel
	    entries that correspond to a device in rssMainTable."
	::= { rss 2 }	    

rssChannelEntry OBJECT-TYPE
	SYNTAX  RssChannelEntry
	MAX-ACCESS  not-accessible
	STATUS current
	DESCRIPTION 
		"Each entry represents a power channel from an RSS device. For each 
		entry in rssMainTable, this table will have one or more channel
		entries. Entries are indexed by RSS instance number and channel number."
	INDEX { rssMainIndex, rssChannelID }
	::= { rssChannelTable 1 }     
	
RssChannelEntry ::= SEQUENCE {
	rssChannelID		Unsigned32,
	rssChannelTitle    DisplayString,
	rssChannelKWattHrs		Gauge32,
	rssChannelVolts		Gauge32,
	rssChannelVoltMax		Gauge32,
	rssChannelVoltMin		Gauge32,
	rssChannelVoltPeak		Gauge32,
	rssChannelAmps		DeciAmps,
	rssChannelRealPower		Gauge32,
	rssChannelApparentPower		Gauge32,
	rssChannelPowerFactor		Gauge32
}

rssChannelID OBJECT-TYPE
	SYNTAX  Unsigned32 (1..3)
	MAX-ACCESS  read-only
	STATUS current
	DESCRIPTION "Channel id number"
	::= { rssChannelEntry 1 }

rssChannelTitle OBJECT-TYPE
	SYNTAX  DisplayString
	MAX-ACCESS  read-only
	STATUS current
	DESCRIPTION "Factory-assigned name for this channel"
	::= { rssChannelEntry 2 }
	
rssChannelKWattHrs OBJECT-TYPE
	SYNTAX  Gauge32
	MAX-ACCESS  read-only
	STATUS current
	DESCRIPTION "Kilowatt hours for power channel"
	::= { rssChannelEntry 3 }
	
rssChannelVolts OBJECT-TYPE
	SYNTAX  Gauge32
	MAX-ACCESS  read-only
	STATUS current
	DESCRIPTION "Volts reading for power channel"
	::= { rssChannelEntry 4 }
	
rssChannelVoltMax OBJECT-TYPE
	SYNTAX  Gauge32
	MAX-ACCESS  read-only
	STATUS current
	DESCRIPTION "Max volts reading for power channel"
	::= { rssChannelEntry 5 }
	
rssChannelVoltMin OBJECT-TYPE
	SYNTAX  Gauge32
	MAX-ACCESS  read-only
	STATUS current
	DESCRIPTION "Min volts reading for power channel"
	::= { rssChannelEntry 6 }
	
rssChannelVoltPeak OBJECT-TYPE
	SYNTAX  Gauge32
	MAX-ACCESS  read-only
	STATUS current
	DESCRIPTION "Peak volts reading for power channel"
	::= { rssChannelEntry 7 }
	
rssChannelAmps OBJECT-TYPE
	SYNTAX  DeciAmps
	MAX-ACCESS  read-only
	STATUS current
	DESCRIPTION "Current reading for power channel"
	::= { rssChannelEntry 8 }
	
rssChannelRealPower OBJECT-TYPE
	SYNTAX  Gauge32
	MAX-ACCESS  read-only
	STATUS current
	DESCRIPTION "Real power for power channel"
	::= { rssChannelEntry 9 }
	
rssChannelApparentPower OBJECT-TYPE
	SYNTAX  Gauge32
	MAX-ACCESS  read-only
	STATUS current
	DESCRIPTION "Apparent power for power channel"
	::= { rssChannelEntry 10 }
	
rssChannelPowerFactor OBJECT-TYPE
	SYNTAX  Gauge32
	MAX-ACCESS  read-only
	STATUS current
	DESCRIPTION "Power factor for power channel"
	::= { rssChannelEntry 11 }

	
rtTable OBJECT-TYPE
	SYNTAX SEQUENCE OF RtEntry
	MAX-ACCESS  not-accessible
	STATUS current
	DESCRIPTION 
	    "Contains entries for remote temperature devices"
	::= { rt 1 }	    

rtEntry OBJECT-TYPE
	SYNTAX  RtEntry
	MAX-ACCESS  not-accessible
	STATUS current
	DESCRIPTION 
		"One entry per device. Indexed by an instance number."
	INDEX { rtIndex }
	::= { rtTable 1 }     
	
RtEntry ::= SEQUENCE {
	rtIndex		Unsigned32,
	rtSerial		DeviceSerial,
	rtLabel		DeviceLabel,
	rtStatus		DeviceStatus,
	rtTemp		TemperatureValue,
	rtUnits		TemperatureUnits
}

rtIndex OBJECT-TYPE
	SYNTAX  Unsigned32(1..64)
	MAX-ACCESS  not-accessible
	STATUS current
	DESCRIPTION "Table entry index value"
	::= { rtEntry  1 }

rtSerial OBJECT-TYPE
	SYNTAX  DeviceSerial
	MAX-ACCESS  read-only
	STATUS current
	DESCRIPTION "Unique device id"
	::= { rtEntry 2 }
	
rtLabel OBJECT-TYPE
	SYNTAX  DeviceLabel
	MAX-ACCESS  read-write
	STATUS current
	DESCRIPTION "User-defined name"
	::= { rtEntry 3 }
	
rtStatus OBJECT-TYPE
	SYNTAX  DeviceStatus
	MAX-ACCESS  read-only
	STATUS current
	DESCRIPTION "Device condition"
	::= { rtEntry 4 }
	
rtTemp OBJECT-TYPE
	SYNTAX  TemperatureValue
	MAX-ACCESS  read-only
	STATUS current
	DESCRIPTION 
	    "Temperature reading. The units for this measurement 
	    are given by rtUnits."
	::= { rtEntry 5 }
	
rtUnits OBJECT-TYPE
	SYNTAX  TemperatureUnits
	MAX-ACCESS  read-only
	STATUS current
	DESCRIPTION "Indicates what units rtTemp will be given in."
	::= { rtEntry 6 }



t3hdTable OBJECT-TYPE
	SYNTAX SEQUENCE OF T3hdEntry
	MAX-ACCESS  not-accessible
	STATUS current
	DESCRIPTION 
	    "Contains entries for T3HD devices"
	::= { t3hd 1 }	    

t3hdEntry OBJECT-TYPE
	SYNTAX  T3hdEntry
	MAX-ACCESS  not-accessible
	STATUS current
	DESCRIPTION 
		"Each entry represents a T3HD device. They are indexed by
		an instance number."
	INDEX { t3hdIndex }
	::= { t3hdTable 1 }     
	
T3hdEntry ::= SEQUENCE {
	t3hdIndex		Unsigned32,
	t3hdSerial		 DeviceSerial,
	t3hdLabel		 DeviceLabel,
	t3hdStatus		 DeviceStatus,	
	t3hdMainLabel     DeviceLabel,
	t3hdMainTemp      TemperatureValue,	
	t3hdMainHumidity  Gauge32,              
	t3hdMainDewPoint  TemperatureValue,    
	t3hdExt1Status   INTEGER,
    t3hdExt1Label    DeviceLabel,
    t3hdExt1Temp     TemperatureValue,    
    t3hdExt2Status   INTEGER,
    t3hdExt2Label    DeviceLabel,
    t3hdExt2Temp     TemperatureValue,
    t3hdTDUnits      TemperatureUnits
}

t3hdIndex OBJECT-TYPE
	SYNTAX  Unsigned32(1..64)
	MAX-ACCESS  not-accessible
	STATUS current
	DESCRIPTION "Table entry index value"
	::= { t3hdEntry  1 }

t3hdSerial OBJECT-TYPE
	SYNTAX  DeviceSerial
	MAX-ACCESS  read-only
	STATUS current
	DESCRIPTION "Unique device id"
	::= { t3hdEntry 2 }
	
t3hdLabel OBJECT-TYPE
	SYNTAX  DeviceLabel
	MAX-ACCESS  read-write
	STATUS current
	DESCRIPTION "User-defined name" 
	::= { t3hdEntry 3 }
	
t3hdStatus OBJECT-TYPE
	SYNTAX  DeviceStatus
	MAX-ACCESS  read-only
	STATUS current
	DESCRIPTION "Device condition"
	::= { t3hdEntry 4 }

t3hdMainLabel OBJECT-TYPE		    
	SYNTAX  DeviceLabel
	MAX-ACCESS  read-write
	STATUS current
	DESCRIPTION "User-defined label for measurements from the main device"
	::= { t3hdEntry 5 }

t3hdMainTemp OBJECT-TYPE         
	SYNTAX  TemperatureValue
	MAX-ACCESS  read-only
	STATUS current
    DESCRIPTION "Temperature reading from the main device"
	::= { t3hdEntry 6 }

t3hdMainHumidity OBJECT-TYPE     
	SYNTAX  Gauge32
	MAX-ACCESS  read-only
	STATUS current
	DESCRIPTION "Humidity reading from main device"
	::= { t3hdEntry 7 }

t3hdMainDewPoint OBJECT-TYPE
	SYNTAX  TemperatureValue
	MAX-ACCESS  read-only
	STATUS current
	DESCRIPTION "Dew Point value from main device"
	::= { t3hdEntry 8 }

t3hdExt1Status OBJECT-TYPE
	SYNTAX  INTEGER {
	                    unplugged(0),
	                    normal(1),
	                    error(2)
	                }
	MAX-ACCESS  read-only
	STATUS current
	DESCRIPTION 
	    "Sensor status for external temp 1. The status is one of the 
	    following values:
	           0 = sensor unplugged
               1 = normal operation
               2 = sensor error "
	::= { t3hdEntry 9 }

t3hdExt1Label OBJECT-TYPE
	SYNTAX  DeviceLabel
	MAX-ACCESS  read-write
	STATUS current
	DESCRIPTION "User-defined name for external temp 1" 
	::= { t3hdEntry 10 }

t3hdExt1Temp OBJECT-TYPE         
	SYNTAX  TemperatureValue
	MAX-ACCESS  read-only
	STATUS current
    DESCRIPTION "Temperature reading from external temp 1"
	::= { t3hdEntry 11 }

t3hdExt2Status OBJECT-TYPE
	SYNTAX  INTEGER {
	                    unplugged(0),
	                    normal(1),
	                    error(2)
	                }
	MAX-ACCESS  read-only
	STATUS current
	DESCRIPTION 
	    "Sensor status for external temp 2. The status is one of the 
	    following values:
	           0 = sensor unplugged
               1 = normal operation
               2 = sensor error "
	::= { t3hdEntry 12 }

t3hdExt2Label OBJECT-TYPE
	SYNTAX  DeviceLabel
	MAX-ACCESS  read-write
	STATUS current
	DESCRIPTION "User-defined name for external temp 2" 
	::= { t3hdEntry 13 }

t3hdExt2Temp OBJECT-TYPE         
	SYNTAX  TemperatureValue
	MAX-ACCESS  read-only
	STATUS current
    DESCRIPTION "Temperature reading from external temp 2"
	::= { t3hdEntry 14 }

t3hdTDUnits OBJECT-TYPE
	SYNTAX  TemperatureUnits
	MAX-ACCESS  read-only
	STATUS current
	DESCRIPTION "Tells what units are used for temperatures and dewpoint"
	::= { t3hdEntry 15 }

thdTable OBJECT-TYPE
	SYNTAX SEQUENCE OF ThdEntry
	MAX-ACCESS  not-accessible
	STATUS current
	DESCRIPTION 
	    "Contains entries for THD devices."
	::= { thd 1 }	    

thdEntry OBJECT-TYPE
	SYNTAX  ThdEntry
	MAX-ACCESS  not-accessible
	STATUS current
	DESCRIPTION 
		"Each entry represents a THD device. They are indexed by
		an instance number."
	INDEX { thdIndex }
	::= { thdTable 1 }     
	
ThdEntry ::= SEQUENCE {
	thdIndex		Unsigned32,
	thdSerial		DeviceSerial,
	thdLabel		DeviceLabel,
	thdStatus		DeviceStatus,	
	thdTemp         TemperatureValue,	
	thdHumidity     Gauge32,              
	thdDewPoint     TemperatureValue,
	thdTDUnits      TemperatureUnits
}

thdIndex OBJECT-TYPE
	SYNTAX  Unsigned32(1..64)
	MAX-ACCESS  not-accessible
	STATUS current
	DESCRIPTION "Table entry index value"
	::= { thdEntry  1 }

thdSerial OBJECT-TYPE
	SYNTAX  DeviceSerial
	MAX-ACCESS  read-only
	STATUS current
	DESCRIPTION "Unique device id"
	::= { thdEntry 2 }
	
thdLabel OBJECT-TYPE
	SYNTAX  DeviceLabel
	MAX-ACCESS  read-write
	STATUS current
	DESCRIPTION "User-defined name" 
	::= { thdEntry 3 }
	
thdStatus OBJECT-TYPE
	SYNTAX  DeviceStatus
	MAX-ACCESS  read-only
	STATUS current
	DESCRIPTION "Device condition"
	::= { thdEntry 4 }

thdTemp OBJECT-TYPE         
	SYNTAX  TemperatureValue
	MAX-ACCESS  read-only
	STATUS current
    DESCRIPTION "Temperature reading"
	::= { thdEntry 5 }

thdHumidity OBJECT-TYPE     
	SYNTAX  Gauge32
	MAX-ACCESS  read-only
	STATUS current
	DESCRIPTION "Humidity reading"
	::= { thdEntry 6 }

thdDewPoint OBJECT-TYPE
	SYNTAX  TemperatureValue
	MAX-ACCESS  read-only
	STATUS current
	DESCRIPTION "Dew Point value"
	::= { thdEntry 7 }

thdTDUnits OBJECT-TYPE
	SYNTAX  TemperatureUnits
	MAX-ACCESS  read-only
	STATUS current
	DESCRIPTION "Units used for temperature and dew point."
	::= { thdEntry 8 }


--
-- alarms entries 
-- 
-- provides SNMP access to the alarm system
--

alarmTriggers OBJECT IDENTIFIER ::= { alarms 1 }
alarmActions OBJECT IDENTIFIER ::= { alarms 2 }
alarmLinks OBJECT IDENTIFIER ::= { alarms 3 }


--
-- alarmTriggers group
--
-- Triggers are used to define alarm conditions and to start or stop 
-- alarm actions based on this condition
--

triggerCommonTable OBJECT-TYPE
	SYNTAX SEQUENCE OF TriggerCommonEntry
	MAX-ACCESS  not-accessible
	STATUS current
	DESCRIPTION 
	    "Attributes common to all triggers. A sub-table provides the additional
	    attributes based on trigger type."
	::= { alarmTriggers 1 }	    

triggerCommonEntry OBJECT-TYPE
	SYNTAX  TriggerCommonEntry
	MAX-ACCESS  not-accessible
	STATUS current
	DESCRIPTION 
		"One entry per trigger. Indexed by trigger number. For each entry
		there will be a corresponding entry in the trigger sub-table for
		the trigger type."
	INDEX { triggerCommonIndex }
	::= { triggerCommonTable 1 }
	
TriggerCommonEntry ::= SEQUENCE {
	triggerCommonIndex		        Unsigned32,		
	triggerCommonLastScan		DateAndTime,
    triggerCommonCond			INTEGER,
    triggerCommonStable			Unsigned32,
    triggerCommonType		    INTEGER,	
    triggerCommonRowStatus		RowStatus		
}

triggerCommonIndex OBJECT-TYPE
	SYNTAX  Unsigned32
	MAX-ACCESS  read-only
	STATUS current
	DESCRIPTION "Uniquely identifies a trigger"
	::= { triggerCommonEntry 1 }
	
triggerCommonLastScan OBJECT-TYPE
	SYNTAX  DateAndTime
	MAX-ACCESS  read-only
	STATUS current
	DESCRIPTION "Last scan timestamp"
	::= { triggerCommonEntry 2 }

triggerCommonCond OBJECT-TYPE
	SYNTAX INTEGER { clear(1), stabilizing(2), tripped(3) }
	MAX-ACCESS  read-only
	STATUS current
	DESCRIPTION "Indicates which state this trigger is in"
	::= { triggerCommonEntry 3 }

triggerCommonStable OBJECT-TYPE
	SYNTAX  Unsigned32
	UNITS "seconds"
	MAX-ACCESS  read-only
	STATUS current
	DESCRIPTION 
		"Tells how long the trigger must stay in 
		stabilizing before it becomes triggered"
	::= { triggerCommonEntry 4 }

triggerCommonType OBJECT-TYPE
	SYNTAX  INTEGER { devThreshold(1), devStatus(2) }
	MAX-ACCESS  read-only
	STATUS current
	DESCRIPTION 
	    "Indicates the trigger type, as well as which sub-table will have
	    a corresponding entry for this trigger."
	::= { triggerCommonEntry 5 }

triggerCommonRowStatus OBJECT-TYPE
	SYNTAX  RowStatus
	MAX-ACCESS  read-only
	STATUS current
	DESCRIPTION "Used to create and destroy trigger instances"
	::= { triggerCommonEntry 6 }
	
--
--
--

triggerDevThresholdTable OBJECT-TYPE
	SYNTAX SEQUENCE OF TriggerDevThresholdEntry
	MAX-ACCESS  not-accessible
	STATUS current
	DESCRIPTION 
	    "Contains info for threshold-type triggers. This is a sub-table of
	    triggerCommonTable."
	::= { alarmTriggers 2 }	    

triggerDevThresholdEntry OBJECT-TYPE
	SYNTAX  TriggerDevThresholdEntry
	MAX-ACCESS  not-accessible
	STATUS current
	DESCRIPTION 
		"One entry per trigger threshold. For each entry in this table there
		is a corresponding entry in triggerCommonTable. Entries are indexed
		by triggerCommonIndex for triggerCommonTable."
	INDEX { triggerCommonIndex }
	::= { triggerDevThresholdTable 1 }     
	
TriggerDevThresholdEntry ::= SEQUENCE {
	triggerDevThresholdReadingID		OBJECT IDENTIFIER,
	triggerDevThresholdValue		    Integer32,
	triggerDevThresholdHysteresis		Integer32,
	triggerDevThresholdTransition		INTEGER,
	triggerDevThresholdTransStr			DisplayString	
}

triggerDevThresholdReadingID OBJECT-TYPE
	SYNTAX  OBJECT IDENTIFIER
	MAX-ACCESS  read-only
	STATUS current
	DESCRIPTION "Identifies the sensor reading to monitor"
	::= { triggerDevThresholdEntry 1 }
	
triggerDevThresholdValue OBJECT-TYPE
	SYNTAX  Integer32
	MAX-ACCESS  read-only
	STATUS current
	DESCRIPTION "Threshold value"
	::= { triggerDevThresholdEntry 2 }

triggerDevThresholdHysteresis OBJECT-TYPE
	SYNTAX  Integer32
	MAX-ACCESS  read-only
	STATUS current
	DESCRIPTION 
		"If tripped, the trigger will untrip once the 
		reading has gone this amount below the threshold "
	::= { triggerDevThresholdEntry 3 }
	
triggerDevThresholdTransition OBJECT-TYPE
	SYNTAX  INTEGER { below(1), above(2) }
	MAX-ACCESS  read-only
	STATUS current
	DESCRIPTION 
		"Tells whether a value above or below 
		the threshold value is considered tripped"
	::= { triggerDevThresholdEntry 4 }
	
triggerDevThresholdTransStr OBJECT-TYPE
	SYNTAX  DisplayString
	MAX-ACCESS  read-only
	STATUS current
	DESCRIPTION "String version of ThresholdTransition"
	::= { triggerDevThresholdEntry 5 }
	
---
---
---

triggerDevStatusTable OBJECT-TYPE
	SYNTAX SEQUENCE OF TriggerDevStatusEntry
	MAX-ACCESS  not-accessible
	STATUS current
	DESCRIPTION
	     "Contains info for status-type triggers. This is a sub-table of
	    triggerCommonTable."
	::= { alarmTriggers 3 }	    

triggerDevStatusEntry OBJECT-TYPE
	SYNTAX  TriggerDevStatusEntry
	MAX-ACCESS  not-accessible
	STATUS current
	DESCRIPTION 
		"One entry per status trigger. For each entry in this table there
		is a corresponding entry in triggerCommonTable. Entries are indexed
		by triggerCommonIndex from triggerCommonTable."
	INDEX { triggerCommonIndex }
	::= { triggerDevStatusTable 1 }     
	
TriggerDevStatusEntry ::= SEQUENCE {
	triggerDevStatusDeviceID		OBJECT IDENTIFIER		
}

triggerDevStatusDeviceID OBJECT-TYPE
	SYNTAX  OBJECT IDENTIFIER
	MAX-ACCESS  read-only
	STATUS current
	DESCRIPTION "Tells which device status to monitor"
	::= { triggerDevStatusEntry 1 }


--
-- alarmActions group
--
-- Actions are peformed depending on the condition of triggers that are linked
--

actionCommonTable OBJECT-TYPE
	SYNTAX SEQUENCE OF ActionCommonEntry
	MAX-ACCESS  not-accessible
	STATUS current
	DESCRIPTION 
	    "Attributes common to all actions. A sub-table provides the additional
	    attributes based on action type."
	::= { alarmActions 1 }	    

actionCommonEntry OBJECT-TYPE
	SYNTAX  ActionCommonEntry
	MAX-ACCESS  not-accessible
	STATUS current
	DESCRIPTION 
		"One entry per action. Indexed by action number. For each entry
		there will be a corresponding entry in the action sub-table for
		the action type."
	INDEX { actionCommonIndex }
	::= { actionCommonTable 1 }     
	
ActionCommonEntry ::= SEQUENCE {
	actionCommonIndex    Unsigned32,
	actionCommonType		INTEGER,
	actionCommonRepeat		Unsigned32,
	actionCommonSuccess		Counter32,
	actionCommonFail		Counter32
}

actionCommonIndex OBJECT-TYPE
	SYNTAX  Unsigned32
	MAX-ACCESS  read-only
	STATUS current
	DESCRIPTION 
	    "Id of action, used as an index into an action sub-table"
	::= { actionCommonEntry 1 }
	
actionCommonType OBJECT-TYPE
	SYNTAX  INTEGER { dev(1), email(2), trap(3) }
	MAX-ACCESS  read-only
	STATUS current
	DESCRIPTION 
	    "Action type, attributes for this action type are supplied by a
	    corresponding entry in an action sub-table."
	::= { actionCommonEntry 2 }

actionCommonRepeat OBJECT-TYPE
	SYNTAX  Unsigned32
	MAX-ACCESS  read-only
	STATUS current
	DESCRIPTION "Time to wait before repeating this action"
	::= { actionCommonEntry 3 }

actionCommonSuccess OBJECT-TYPE
	SYNTAX  Counter32
	MAX-ACCESS  read-only
	STATUS current
	DESCRIPTION "Number of times this action was performed successfully"
	::= { actionCommonEntry 4 }

actionCommonFail OBJECT-TYPE
	SYNTAX  Counter32
	MAX-ACCESS  read-only
	STATUS current
	DESCRIPTION "Number of failed action attempts"
	::= { actionCommonEntry 5 }

--
--
--

actionDevTable OBJECT-TYPE
	SYNTAX SEQUENCE OF ActionDevEntry
	MAX-ACCESS  not-accessible
	STATUS current
	DESCRIPTION
	    "Contains info for device actions. This is a sub-table of
	    actionCommonTable. These actions are used to control devices."
	::= { alarmActions 2 }	    

actionDevEntry OBJECT-TYPE
	SYNTAX  ActionDevEntry
	MAX-ACCESS  not-accessible
	STATUS current
	DESCRIPTION 		
		"One entry per dev action. For each entry in this table there
		is a corresponding entry in actionCommonTable. Entries are indexed
		by actionCommonIndex from actionCommonTable."
	INDEX { actionCommonIndex }
	::= { actionDevTable 1 }     
	
ActionDevEntry ::= SEQUENCE {
	actionDevID		    OBJECT IDENTIFIER	
}

actionDevID OBJECT-TYPE
	SYNTAX  OBJECT IDENTIFIER
	MAX-ACCESS  read-only
	STATUS current
	DESCRIPTION "Identifies the device action"
	::= { actionDevEntry 1 }		
--
--
--

actionEmailTable OBJECT-TYPE
	SYNTAX SEQUENCE OF ActionEmailEntry
	MAX-ACCESS  not-accessible
	STATUS current
	DESCRIPTION
	    "Contains info for email actions. This is a sub-table of
	    actionCommonTable. These actions are used to send email."
	::= { alarmActions 3 }	    

actionEmailEntry OBJECT-TYPE
	SYNTAX  ActionEmailEntry
	MAX-ACCESS  not-accessible
	STATUS current
	DESCRIPTION 		
		"One entry per email action. For each entry in this table there
		is a corresponding entry in actionCommonTable. Entries are indexed
		by actionCommonIndex from actionCommonTable."
	INDEX { actionCommonIndex }
	::= { actionEmailTable 1 }     
	
ActionEmailEntry ::= SEQUENCE {
	actionEmailAddress		EmailAddress,
	actionEmailFormat		INTEGER	
}

actionEmailAddress OBJECT-TYPE
	SYNTAX  EmailAddress
	MAX-ACCESS  read-only
	STATUS current
	DESCRIPTION "Address to send email"
	::= { actionEmailEntry 1 }
	
actionEmailFormat OBJECT-TYPE
	SYNTAX  INTEGER { standard(1), sms(2) }
	MAX-ACCESS  read-only
	STATUS current
	DESCRIPTION 
	    "Indicates what format should be used when generating an email"
	::= { actionEmailEntry 2 }
		
--
--
--

actionTrapTable OBJECT-TYPE
	SYNTAX SEQUENCE OF ActionTrapEntry
	MAX-ACCESS  not-accessible
	STATUS current
	DESCRIPTION 	    
	    "Contains info for trap actions. This is a sub-table of
	    actionCommonTable. These actions are used to SNMP traps."
	::= { alarmActions 4 }	    

actionTrapEntry OBJECT-TYPE
	SYNTAX  ActionTrapEntry
	MAX-ACCESS  not-accessible
	STATUS current
	DESCRIPTION 		
		"One entry per trap action. For each entry in this table there
		is a corresponding entry in actionCommonTable. Entries are indexed
		by actionCommonIndex from actionCommonTable."
	INDEX { actionCommonIndex }
	::= { actionTrapTable 1 }     
	
ActionTrapEntry ::= SEQUENCE {
	actionTrapDestIndex		Unsigned32
}

actionTrapDestIndex OBJECT-TYPE
	SYNTAX  Unsigned32
	MAX-ACCESS  read-only
	STATUS current
	DESCRIPTION "Index of an entry in the trapDestTable"
	::= { actionTrapEntry 1 }

--
-- alarmLinks group
--
-- Links are used to associate a trigger with an action
--

linkCommonTable OBJECT-TYPE
	SYNTAX SEQUENCE OF LinkCommonEntry
	MAX-ACCESS  not-accessible
	STATUS current
	DESCRIPTION 
	    "Attributes common to all links. Entries link triggers to actions to
	    form alarms. Once the link is established, if a trigger activates, the
	    linked action is executed."
	::= { alarmLinks 1 }	    

linkCommonEntry OBJECT-TYPE
	SYNTAX  LinkCommonEntry
	MAX-ACCESS  not-accessible
	STATUS current
	DESCRIPTION 	
		"One entry per link. Each entry represents a link between a trigger 
		and action. Indices correspond to a triggerCommonIndex and 
		actionCommonIndex." 
	INDEX { linkCommonTrigger, linkCommonAction }
	::= { linkCommonTable 1 }     
	
LinkCommonEntry ::= SEQUENCE {
	linkCommonTrigger		Unsigned32,
	linkCommonAction		    Unsigned32,	
	linkCommonRowStatus		RowStatus
}

linkCommonTrigger OBJECT-TYPE
	SYNTAX  Unsigned32
	MAX-ACCESS  read-only
	STATUS current
	DESCRIPTION 
	    "Index of trigger, corresponds to a triggerCommonIndex"
	::= { linkCommonEntry 1 }
	
linkCommonAction OBJECT-TYPE
	SYNTAX  Unsigned32
	MAX-ACCESS  read-only
	STATUS current
	DESCRIPTION 
	    "Index of action, corresponds to an actionCommonIndex"
	::= { linkCommonEntry 2 }
		
linkCommonRowStatus OBJECT-TYPE
	SYNTAX  RowStatus
	MAX-ACCESS  read-only
	STATUS current
	DESCRIPTION "Used to create/destroy a link entry"
	::= { linkCommonEntry 3 }


--
-- general group
--
-- Contains additional definitions used for general system info and configuration
--

trapDestTable OBJECT-TYPE
	SYNTAX SEQUENCE OF TrapDestEntry
	MAX-ACCESS  not-accessible
	STATUS current
	DESCRIPTION "Contains destinations used for trap actions"
	::= { general 1 }	    

trapDestEntry OBJECT-TYPE
	SYNTAX  TrapDestEntry
	MAX-ACCESS  not-accessible
	STATUS current
	DESCRIPTION 
		"Each entry represents a trap destination. Indexed by a unique
		trap destination id number."
	INDEX { trapDestIndex }
	::= { trapDestTable 1 }     
	
TrapDestEntry ::= SEQUENCE {
	trapDestIndex		    Unsigned32,
	trapDestAddressType		InetAddressType,
	trapDestAddress			InetAddress,
	trapDestPort			InetPortNumber,	
	trapDestRowStatus		RowStatus
}

trapDestIndex OBJECT-TYPE
	SYNTAX  Unsigned32
	MAX-ACCESS  read-only
	STATUS current
	DESCRIPTION "Index of trap destination"
	::= { trapDestEntry 1 }

trapDestAddressType OBJECT-TYPE
	SYNTAX  InetAddressType
	MAX-ACCESS  read-only
	STATUS current
	DESCRIPTION "Indicates the type of address represented by trapDestAddress"
	::= { trapDestEntry 2 }

trapDestAddress OBJECT-TYPE
	SYNTAX  InetAddress
	MAX-ACCESS  read-only
	STATUS current
	DESCRIPTION 
		"Address to send traps to. The type in trapDestAddressType 
		needs to agree with this address."
	::= { trapDestEntry 3 }

trapDestPort OBJECT-TYPE
	SYNTAX  InetPortNumber
	MAX-ACCESS  read-only
	STATUS current
	DESCRIPTION 
	    "Port used when sending a trap to this destination. Normally, 
	    this is set to port 162."
	::= { trapDestEntry 4 }

trapDestRowStatus OBJECT-TYPE
	SYNTAX  RowStatus
	MAX-ACCESS  read-only
	STATUS current
	DESCRIPTION "Used for adding or deleting row from this table"
	::= { trapDestEntry 5 }

--
-- traps group
--
-- Definitions of traps and trap-specific objects included in the var-binds
--

trapDefs OBJECT IDENTIFIER ::= { traps 0 }	
trapObjs OBJECT IDENTIFIER ::= { traps 1 }	

trapObjReadingValue OBJECT-TYPE
	SYNTAX  Integer32
	MAX-ACCESS  accessible-for-notify
	STATUS current
	DESCRIPTION "Used to include a sensor value in a trap"
	::= { trapObjs 1 }
	
trapObjTrapType OBJECT-TYPE
	SYNTAX  INTEGER { clear(0), trip(1) }
	MAX-ACCESS  accessible-for-notify
	STATUS current
	DESCRIPTION "Tells if the trap is a trip or clear"
	::= { trapObjs 2 }
	
trapObjTrapTypeStr OBJECT-TYPE
	SYNTAX  DisplayString
	MAX-ACCESS  accessible-for-notify
	STATUS current
	DESCRIPTION "String version of TrapType"
	::= { trapObjs 3 }
	
trapObjAlarmPtr OBJECT-TYPE
	SYNTAX  OBJECT IDENTIFIER
	MAX-ACCESS  accessible-for-notify
	STATUS current
	DESCRIPTION "Reference to an alarm instance"
	::= { trapObjs 4 }
	
trapObjDevPtr OBJECT-TYPE
	SYNTAX  OBJECT IDENTIFIER
	MAX-ACCESS  accessible-for-notify
	STATUS current
	DESCRIPTION "Reference to a device instance"
	::= { trapObjs 5 }

trapObjDevStatus OBJECT-TYPE
	SYNTAX  DeviceStatus
	MAX-ACCESS  accessible-for-notify
	STATUS current
	DESCRIPTION "Used to include a device status with a trap"
	::= { trapObjs 6 }
	

	
--
-- trapDefs group
--
-- Defines trap types sent by the device
--

internalTestNOTIFY NOTIFICATION-TYPE
	STATUS current
	DESCRIPTION "test SNMP Trap"
	::= { trapDefs 10101 }

alarmDevThresholdNOTIFY NOTIFICATION-TYPE
	OBJECTS { 
	          trapObjTrapType,
	          trapObjTrapTypeStr,
	          trapObjAlarmPtr,
	          triggerDevThresholdReadingID,
	          trapObjReadingValue,
	          triggerDevThresholdTransition,
	          triggerDevThresholdTransStr 
	        }
	STATUS current
	DESCRIPTION "Indicates a change to an alarm threshold"
	::= { trapDefs 1 }
	
alarmDevStatusNOTIFY NOTIFICATION-TYPE
	OBJECTS { 
	          trapObjTrapType,
	          trapObjTrapTypeStr, 
	          trapObjDevPtr, 
	          trapObjDevStatus 
	        }
	STATUS current
	DESCRIPTION "Tells if the status of a device changed"
	::= { trapDefs 2 }
	


END
