BACS2-MIB DEFINITIONS ::= BEGIN

   IMPORTS
       MODULE-IDENTITY, OBJECT-TYPE, NOTIFICATION-TYPE,
       OBJECT-IDENTITY, Counter32, Gauge32, Integer32
           FROM SNMPv2-SMI
       DisplayString, TimeStamp, AutonomousType
           FROM SNMPv2-TC
       MODULE-COMPLIANCE, OBJECT-GROUP
           FROM SNMPv2-CONF;

   PositiveInteger ::= TEXTUAL-CONVENTION
       DISPLAY-HINT "d"
       STATUS       current
       DESCRIPTION
               "This data type is a non-zero and non-negative value."
       SYNTAX       INTEGER (1..2147483647)

   NonNegativeInteger ::= TEXTUAL-CONVENTION
       DISPLAY-HINT "d"
       STATUS       current
       DESCRIPTION
               "This data type is a non-negative value."
       SYNTAX       INTEGER (0..2147483647)

   org         OBJECT IDENTIFIER ::= { iso 3 }  --  "iso" = 1
   dod         OBJECT IDENTIFIER ::= { org 6 }
   internet    OBJECT IDENTIFIER ::= { dod 1 }
   mgmt        OBJECT IDENTIFIER ::= { internet 2 }
   mib-2       OBJECT IDENTIFIER ::= { mgmt 1 }
   upsMIB      OBJECT IDENTIFIER ::= { mib-2 33 }
   bacs2       OBJECT IDENTIFIER ::= { upsMIB 5 }

   --
   -- BACS2 Settings
   --

   bacsSettings OBJECT IDENTIFIER ::= { bacs2 1 }

   bacsModuleType OBJECT-TYPE
       SYNTAX      INTEGER {
           c20     (0),
           c21     (1),
           c30     (10),
           c40     (20),
       }
       MAX-ACCESS  read-only
       STATUS      current
       DESCRIPTION "BACS Module Type. (0=C20, 1=C21, 10=C30, 20=C40)"
       ::= { bacsSettings 1 }

   bacsNumStrings OBJECT-TYPE
       SYNTAX      NonNegativeInteger
       UNITS       "strings"
       MAX-ACCESS  read-only
       STATUS      current
       DESCRIPTION "Number of battery strings."
       ::= { bacsSettings 2 }

   bacsNumBatteries OBJECT-TYPE
       SYNTAX      NonNegativeInteger
       UNITS       "batteries"
       MAX-ACCESS  read-only
       STATUS      current
       DESCRIPTION "Total number of batteries."
       ::= { bacsSettings 3 }

   bacsBattCap OBJECT-TYPE
       SYNTAX      PositiveInteger
       UNITS       "Ah"
       MAX-ACCESS  read-only
       STATUS      current
       DESCRIPTION "Capacity of installed batteries."
       ::= { bacsSettings 4 }

   bacsLogRate1 OBJECT-TYPE
       SYNTAX      PositiveInteger
       UNITS       "seconds"
       MAX-ACCESS  read-only
       STATUS      current
       DESCRIPTION "Lograte during normal operation."
       ::= { bacsSettings 5 }

   bacsLogRate2 OBJECT-TYPE
       SYNTAX      PositiveInteger
       UNITS       "seconds"
       MAX-ACCESS  read-only
       STATUS      current
       DESCRIPTION "Lograte during charge or discharge."
       ::= { bacsSettings 6 }

   bacsImpcPollRate OBJECT-TYPE
       SYNTAX      PositiveInteger
       UNITS       "minutes"
       MAX-ACCESS  read-write
       STATUS      current
       DESCRIPTION "Pollrate internal impedance."
       ::= { bacsSettings 7 }

   bacsImpcLowAlarm OBJECT-TYPE
       SYNTAX      PositiveInteger
       UNITS       "0.01 mOhm"
       MAX-ACCESS  read-write
       STATUS      current
       DESCRIPTION "Impedance low alarm level."
       ::= { bacsSettings 8 }

   bacsImpcHighAlarm OBJECT-TYPE
       SYNTAX      PositiveInteger
       UNITS       "0.01 mOhm"
       MAX-ACCESS  read-write
       STATUS      current
       DESCRIPTION "Impedance low alarm level."
       ::= { bacsSettings 9 }

   bacsTemperatureLowAlarm OBJECT-TYPE
       SYNTAX      Integer32
       UNITS       "0.1 deg celsius"
       MAX-ACCESS  read-write
       STATUS      current
       DESCRIPTION "Temperature alarm below this level."
       ::= { bacsSettings 10 }

   bacsTemperatureHighAlarm OBJECT-TYPE
       SYNTAX      Integer32
       UNITS       "0.1 deg celsius"
       MAX-ACCESS  read-write
       STATUS      current
       DESCRIPTION "Temperature alarm above this level."
       ::= { bacsSettings 11 }

   bacsVoltageLowAlarm OBJECT-TYPE
       SYNTAX      PositiveInteger
       UNITS       "0.01 volt"
       MAX-ACCESS  read-write
       STATUS      current
       DESCRIPTION "Voltage alarm below this level."
       ::= { bacsSettings 12 }

   bacsVoltageHighAlarm OBJECT-TYPE
       SYNTAX      PositiveInteger
       UNITS       "0.01 volt"
       MAX-ACCESS  read-write
       STATUS      current
       DESCRIPTION "Voltage alarm above this level."
       ::= { bacsSettings 13 }

   bacsImpcLowWarn OBJECT-TYPE
       SYNTAX      PositiveInteger
       UNITS       "0.01 mOhm"
       MAX-ACCESS  read-write
       STATUS      current
       DESCRIPTION "Impedance low warning level."
       ::= { bacsSettings 14 }

   bacsImpcHighWarn OBJECT-TYPE
       SYNTAX      PositiveInteger
       UNITS       "0.01 mOhm"
       MAX-ACCESS  read-write
       STATUS      current
       DESCRIPTION "Impedance high warning level."
       ::= { bacsSettings 15 }

   bacsTemperatureLowWarn OBJECT-TYPE
       SYNTAX      Integer32
       UNITS       "0.1 deg celsius"
       MAX-ACCESS  read-write
       STATUS      current
       DESCRIPTION "Temperature warning below this level."
       ::= { bacsSettings 16 }

   bacsTemperatureHighWarn OBJECT-TYPE
       SYNTAX      Integer32
       UNITS       "0.1 deg celsius"
       MAX-ACCESS  read-write
       STATUS      current
       DESCRIPTION "Temperature warning above this level."
       ::= { bacsSettings 17 }

   bacsVoltageLowWarn OBJECT-TYPE
       SYNTAX      PositiveInteger
       UNITS       "0.01 volt"
       MAX-ACCESS  read-write
       STATUS      current
       DESCRIPTION "Voltage warning below this level."
       ::= { bacsSettings 18 }

   bacsVoltageHighWarn OBJECT-TYPE
       SYNTAX      PositiveInteger
       UNITS       "0.01 volt"
       MAX-ACCESS  read-write
       STATUS      current
       DESCRIPTION "Voltage warning above this level."
       ::= { bacsSettings 19 }


   --
   -- BACS Objects
   --

   bacsObjects   OBJECT IDENTIFIER ::= { bacs2 2 }

   bacsStatus OBJECT-TYPE
       SYNTAX      PositiveInteger
       UNITS       "HEX flags"
       MAX-ACCESS  read-only
       STATUS      current
       DESCRIPTION "BACS System Status Flags."
       ::= { bacsObjects 1 }

  bacsAvModuleVolt OBJECT-TYPE
      SYNTAX      PositiveInteger
      UNITS       "0.01 Volt"
      MAX-ACCESS  read-only
      STATUS      current
      DESCRIPTION "Average module voltage."
      ::= { bacsObjects 2 }

  bacsTotalVolt OBJECT-TYPE
      SYNTAX      PositiveInteger
      UNITS       "0.01 Volt"
      MAX-ACCESS  read-only
      STATUS      current
      DESCRIPTION "Total voltage of all modules."
      ::= { bacsObjects 3 }

   bacsNumModules OBJECT-TYPE
       SYNTAX      NonNegativeInteger
       MAX-ACCESS  read-only
       STATUS      current
       DESCRIPTION "The number of installed battery modules."
       ::= { bacsObjects 4 }

   BacsEntry ::= SEQUENCE {
       bacsModuleIndex         PositiveInteger,
       bacsModuleVoltage       PositiveInteger,
       bacsModuleTemperature   Integer32,
       bacsModuleBypass        NonNegativeInteger,
       bacsModuleResistance    NonNegativeInteger,
       bacsModuleState         NonNegativeInteger
   }

   bacsModuleTable    OBJECT-TYPE
       SYNTAX      SEQUENCE OF BacsEntry
       MAX-ACCESS  not-accessible
       STATUS      current
       DESCRIPTION "The list of battery table entries."
       ::= { bacsObjects 5 }

   bacsModuleEntry  OBJECT-TYPE
       SYNTAX      BacsEntry
       MAX-ACCESS  not-accessible
       STATUS      current
       DESCRIPTION "An entry containing information applicable to a particular battery."
       INDEX       { bacsModuleIndex }
       ::= { bacsModuleTable 1 }

   bacsModuleIndex OBJECT-TYPE
       SYNTAX      PositiveInteger
       MAX-ACCESS  not-accessible
       STATUS      current
       DESCRIPTION "The module identifier."
       ::= { bacsModuleEntry 1 }

   bacsModuleVoltage OBJECT-TYPE
       SYNTAX      PositiveInteger
       UNITS       "0.01 volt"
       MAX-ACCESS  read-only
       STATUS      current
       DESCRIPTION "The module voltage."
       ::= { bacsModuleEntry 2 }

   bacsModuleTemperature OBJECT-TYPE
       SYNTAX      Integer32
       UNITS       "0.1 degrees celcius"
       MAX-ACCESS  read-only
       STATUS      current
       DESCRIPTION "The module temperature."
       ::= { bacsModuleEntry 3 }

   bacsModuleBypass OBJECT-TYPE
       SYNTAX      NonNegativeInteger
       UNITS       "0.1 percent"
       MAX-ACCESS  read-only
       STATUS      current
       DESCRIPTION "The module bypass voltage."
       ::= { bacsModuleEntry 4 }

   bacsModuleResistance OBJECT-TYPE
       SYNTAX      NonNegativeInteger
       UNITS       "0.01 mOhm"
       MAX-ACCESS  read-only
       STATUS      current
       DESCRIPTION "The module impedance."
       ::= { bacsModuleEntry 5 }

   bacsModuleState OBJECT-TYPE
       SYNTAX      NonNegativeInteger
       MAX-ACCESS  read-only
       STATUS      current
       DESCRIPTION "The module alarm flags(0x0=No Alarm, 0x1=General Alarm, 0x2=System Failure, 0x4=Voltage High Alarm, 0x8=Voltage Low Alarm, 0x10=Temperature High Alarm, 0x20=Temperature Low Alarm, 0x40=Resistor High Alarm, 0x80=Resistor Low Alarm, 0x100=Equalizing Error Alarm, 0x200=Voltage High Warning, 0x400=Voltage Low Warning, 0x800=Temperature High Warning, 0x1000=Temperature Low Warning, 0x2000=Resistor High Warning, 0x4000=Resistor Low Warning, 0x8000=Incompatible Module Rev)."
       ::= { bacsModuleEntry 6 }

   bacsNumStrings OBJECT-TYPE
       SYNTAX      NonNegativeInteger
       MAX-ACCESS  read-only
       STATUS      current
       DESCRIPTION "The number of installed battery strings."
       ::= { bacsObjects 6 }

   StringEntry ::= SEQUENCE {
       bacsStringIndex         PositiveInteger,
       bacsStringCurrent       PositiveInteger,
       bacsStringTotalVolt     PositiveInteger,
       bacsStringAverageVolt   PositiveInteger
   }

   bacsStringTable    OBJECT-TYPE
       SYNTAX      SEQUENCE OF StringEntry
       MAX-ACCESS  not-accessible
       STATUS      current
       DESCRIPTION "The list of stringy table entries."
       ::= { bacsObjects 7 }

   bacsStringEntry  OBJECT-TYPE
       SYNTAX      StringEntry
       MAX-ACCESS  not-accessible
       STATUS      current
       DESCRIPTION "An entry containing information applicable to a particular string of batteries."
       INDEX       { bacsStringIndex }
       ::= { bacsStringTable 1 }

   bacsStringIndex OBJECT-TYPE
       SYNTAX      PositiveInteger
       MAX-ACCESS  not-accessible
       STATUS      current
       DESCRIPTION "The string identifier."
       ::= { bacsStringEntry 1 }

   bacsStringCurrent OBJECT-TYPE
       SYNTAX      PositiveInteger
       UNITS       "0.01 ampere"
       MAX-ACCESS  read-only
       STATUS      current
       DESCRIPTION "The string current."
       ::= { bacsStringEntry 2 }

   bacsStringTotalVolt OBJECT-TYPE
       SYNTAX      PositiveInteger
       UNITS       "0.01 volt"
       MAX-ACCESS  read-only
       STATUS      current
       DESCRIPTION "The string total voltage."
       ::= { bacsStringEntry 3 }

   bacsStringAverageVolt OBJECT-TYPE
       SYNTAX      PositiveInteger
       UNITS       "0.01 volt"
       MAX-ACCESS  read-only
       STATUS      current
       DESCRIPTION "The string average voltage per battery."
       ::= { bacsStringEntry 4 }

   --
   -- BACS Alarms
   --

   bacsAlarms   OBJECT IDENTIFIER ::= { bacs2 3 }

   bacsAlarmsPresent OBJECT-TYPE
       SYNTAX      Gauge32
       MAX-ACCESS  read-only
       STATUS      current
       DESCRIPTION "The present number of active alarm conditions."
       ::= { bacsAlarms 1 }

   bacsAlarmTable OBJECT-TYPE
       SYNTAX      SEQUENCE OF BacsAlarm
       MAX-ACCESS  not-accessible
       STATUS      current
       DESCRIPTION "A list of alarm entries."
       ::= { bacsAlarms 2 }

   bacsAlarmEntry OBJECT-TYPE
       SYNTAX      BacsAlarm
       MAX-ACCESS  not-accessible
       STATUS      current
       DESCRIPTION "An entry containing information applicable to a particular alarm."
       INDEX      { bacsAlarmId }
       ::= { bacsAlarmTable 1 }

   BacsAlarm ::= SEQUENCE {
       bacsAlarmId          PositiveInteger,
       bacsAlarmDescr       AutonomousType,
       bacsAlarmTime        TimeStamp
   }

   bacsAlarmId OBJECT-TYPE
       SYNTAX      PositiveInteger
       MAX-ACCESS  read-only
       STATUS      current
       DESCRIPTION "A unique identifier for an alarm condition. This value must remain constant."
       ::= { bacsAlarmEntry 1 }

   bacsAlarmDescr OBJECT-TYPE
       SYNTAX      AutonomousType
       MAX-ACCESS  read-only
       STATUS      current
       DESCRIPTION "A reference to an alarm description object. The object referenced should not be
                 accessible, but rather be used to provide a unique description of the alarm condition."
       ::= { bacsAlarmEntry 2 }

   bacsAlarmTime OBJECT-TYPE
       SYNTAX      TimeStamp
       MAX-ACCESS  read-only
       STATUS      current
       DESCRIPTION "The value of sysUpTime when the alarm condition was detected. If the alarm
               condition was detected at the time of agent startup and presumably existed before
               agent startup, the value of dcAlarmTime shall equal 0."
       ::= { bacsAlarmEntry 3 }

   bacsWellKnownAlarms OBJECT IDENTIFIER ::= { bacsAlarms 3 }

   bacsAlarmSystemError OBJECT-IDENTITY
       STATUS      current
       DESCRIPTION "This object indicates a communication problem from the agent to one or more of the battery modules."
       ::= { bacsWellKnownAlarms  1 }

   bacsAlarmResistWarn OBJECT-IDENTITY
       STATUS      current
       DESCRIPTION "This object indicates that the internal restiance of one or more batteries is above the warning level."
       ::= { bacsWellKnownAlarms  2 }

   bacsAlarmResistAlarm OBJECT-IDENTITY
       STATUS      current
       DESCRIPTION "This object indicates that the internal restiance of one or more batteries is above the alarm level."
       ::= { bacsWellKnownAlarms  3 }

   bacsAlarmVoltage OBJECT-IDENTITY
       STATUS      current
       DESCRIPTION "This object indicates that the voltage of one or more batteries is outside the defined rage."
       ::= { bacsWellKnownAlarms  4 }

   bacsAlarmTemperature OBJECT-IDENTITY
       STATUS      current
       DESCRIPTION "This object indicates that the temperature of one or more batteries is outside the defined range."
       ::= { bacsWellKnownAlarms  5 }

   bacsAlarmVoltageHigh OBJECT-IDENTITY
       STATUS      current
       DESCRIPTION "This object indicates that the voltage of one or more batteries is higher than the defined range."
       ::= { bacsWellKnownAlarms  6 }

   bacsAlarmVoltageLow OBJECT-IDENTITY
       STATUS      current
       DESCRIPTION "This object indicates that the voltage of one or more batteries is lower than the defined range."
       ::= { bacsWellKnownAlarms  7 }

   bacsAlarmTemperatureHigh OBJECT-IDENTITY
       STATUS      current
       DESCRIPTION "This object indicates that the temperature of one or more batteries is higher than the defined range."
       ::= { bacsWellKnownAlarms  8 }

   bacsAlarmTemperatureLow OBJECT-IDENTITY
       STATUS      current
       DESCRIPTION "This object indicates that the temperature of one or more batteries is lower than the defined range."
       ::= { bacsWellKnownAlarms  9 }

   bacsAlarmResistAlarmHigh OBJECT-IDENTITY
       STATUS      current
       DESCRIPTION "This object indicates that the internal restiance of one or more batteries is above the alarm level."
       ::= { bacsWellKnownAlarms  10 }

   bacsAlarmResistAlarmLow OBJECT-IDENTITY
       STATUS      current
       DESCRIPTION "This object indicates that the internal restiance of one or more batteries is below the alarm level."
       ::= { bacsWellKnownAlarms  11 }

   bacsAlarmEqualizing OBJECT-IDENTITY
       STATUS      current
       DESCRIPTION "This object indicates that there is an error with Equalizing."
       ::= { bacsWellKnownAlarms  12 }

   bacsAlarmVoltageWarnHigh OBJECT-IDENTITY
       STATUS      current
       DESCRIPTION "This object indicates that the voltage of one or more batteries is higher than the defined warning range."
       ::= { bacsWellKnownAlarms  13 }

   bacsAlarmVoltageWarnLow OBJECT-IDENTITY
       STATUS      current
       DESCRIPTION "This object indicates that the voltage of one or more batteries is lower than the defined warning range."
       ::= { bacsWellKnownAlarms  14 }

   bacsAlarmTemperatureWarnHigh OBJECT-IDENTITY
       STATUS      current
       DESCRIPTION "This object indicates that the Temperature of one or more batteries is higher than the defined warning range."
       ::= { bacsWellKnownAlarms  15 }

   bacsAlarmTemperatureWarnLow OBJECT-IDENTITY
       STATUS      current
       DESCRIPTION "This object indicates that the Temperature of one or more batteries is lower than the defined warning range."
       ::= { bacsWellKnownAlarms  16 }

   bacsAlarmResistWarnHigh OBJECT-IDENTITY
       STATUS      current
       DESCRIPTION "This object indicates that the internal restiance of one or more batteries is higher than the defined warning range."
       ::= { bacsWellKnownAlarms  17 }

   bacsAlarmResistWarnLow OBJECT-IDENTITY
       STATUS      current
       DESCRIPTION "This object indicates that the internal restiance of one or more batteries is lower than the defined warning range."
       ::= { bacsWellKnownAlarms  18 }

    bacsAlarmInitializing OBJECT-IDENTITY
       STATUS      current
       DESCRIPTION "Bacs Alarm Initializing ."
       ::= { bacsWellKnownAlarms  19 }

    bacsAlarmCommunicationLost OBJECT-IDENTITY
       STATUS      current
       DESCRIPTION "Bacs Alarm Communication Lost ."
       ::= { bacsWellKnownAlarms  20 }

    bacsAlarmBatteryBreakerOpen OBJECT-IDENTITY
       STATUS      current
       DESCRIPTION "Bacs Alarm Battery Breaker Open ."
       ::= { bacsWellKnownAlarms  21 }

    bacsAlarmThermalRunaway OBJECT-IDENTITY
       STATUS      current
       DESCRIPTION "Bacs Alarm Thermal Runaway."
       ::= { bacsWellKnownAlarms  22 }

    bacsAlarmSensorCommunicationLost OBJECT-IDENTITY
       STATUS      current
       DESCRIPTION "Bacs Alarm Sensor Communication Lost ."
       ::= { bacsWellKnownAlarms  23 }

    bacsAlarmDischarging OBJECT-IDENTITY
       STATUS      current
       DESCRIPTION "Bacs Alarm Discharging ."
       ::= { bacsWellKnownAlarms  24 }

    bacsAlarmDischargingStopped OBJECT-IDENTITY
       STATUS      current
       DESCRIPTION "Bacs Alarm Discharging Stopped ."
       ::= { bacsWellKnownAlarms  25 }

    bacsAlarmMaxVoltageDiff OBJECT-IDENTITY
       STATUS      current
       DESCRIPTION "Bacs Alarm Max Voltage difference."
       ::= { bacsWellKnownAlarms  26 }

    bacsModuleAlarmsPresent OBJECT-TYPE
       SYNTAX      Gauge32
       MAX-ACCESS  read-only
       STATUS      current
       DESCRIPTION "The number of BACS modules presently in an alarm state."
       ::= { bacsAlarms 4 }

    bacsModuleWarningsPresent OBJECT-TYPE
       SYNTAX      Gauge32
       MAX-ACCESS  read-only
       STATUS      current
       DESCRIPTION "The number of BACS modules presently in a warning state."
       ::= { bacsAlarms 5 }

   --
   -- BACS Traps
   --

   bacsTraps   OBJECT IDENTIFIER ::= { bacs2 4 }

   bacsTrapAlarmEntryAdded NOTIFICATION-TYPE
       OBJECTS { bacsAlarmId, bacsAlarmDescr }
       STATUS      current
       DESCRIPTION "This trap is sent upon a alarm in the system appears."
       ::= { bacsTraps 1 }

   bacsTrapAlarmEntryRemoved NOTIFICATION-TYPE
       OBJECTS { bacsAlarmId, bacsAlarmDescr }
       STATUS      current
       DESCRIPTION "This trap is sent upon a alarm in the system disappears."
       ::= { bacsTraps 2 }


   END
