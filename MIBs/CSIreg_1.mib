Control-Solutions-MIB-Registrations 
-- ******************************************************
--Control Solutions, Inc., SNMP  MIB
--Prefix for private enterprises:  1.3.6.1.4.1	
--Control Solutions, Inc. private enterprize number:  3815
--
-- The following MIB is the registration tree for all Control Solutions products. 
-- Products registered include:
--	System 700/SNMP on BAS-700 hardware
--  Babel Buster 10/100 Modbus to LonWorks gateway
--
--The following objects are implemented in the MIB-II System Group
--
--1.3.6.1.2.1.1.1	sysDescr
--1.3.6.1.2.1.1.2	sysObjectID
--1.3.6.1.2.1.1.3	sysUpTime
--1.3.6.1.2.1.1.4	sysContact
--1.3.6.1.2.1.1.5	sysName
--1.3.6.1.2.1.1.6	sysLocation
--1.3.6.1.2.1.1.7	sysServices
--
--
--
-- ************************************************************

DEFINITIONS ::= BEGIN

IMPORTS
	enterprises
		FROM RFC1155-SMI;

-- Control Solutions, Inc. MIBs
csi		OBJECT IDENTIFIER ::= { enterprises 3815 }	-- 1.3.6.1.4.1.3815

-- Product MIB tree
csiProduct	OBJECT IDENTIFIER ::= { csi 1 }			-- 3815.1

-- Product Registration tree
csiRegister	OBJECT IDENTIFIER ::= { csi 2 }			-- 3815.2

-- Product group
bas700		OBJECT IDENTIFIER ::= { csiProduct 1 }		-- 3815.1.1
bbuster100	OBJECT IDENTIFIER ::= { csiProduct 2 }		-- 3815.1.2

-- Applications - base for product MIBs
sys700		OBJECT IDENTIFIER ::= { bas700 1 }			-- 3815.1.1.1
snmpio7050  OBJECT IDENTIFIER ::= { bas700 2 }			-- 3815.1.1.2
bb100modbus	OBJECT IDENTIFIER ::= { bbuster100 1 }		-- 3815.1.2.1
bbx2		OBJECT IDENTIFIER ::= { bbuster100 2 }      -- 3815.1.2.2

-- Product registration OID
bas700reg		OBJECT IDENTIFIER ::= { csiRegister 1 }		-- 3815.2.1
bbuster100reg	OBJECT IDENTIFIER ::= { csiRegister 2 }		-- 3815.2.2

-- Registration objects for sysObjectID
sys700reg		OBJECT IDENTIFIER ::= { bas700reg 1 }		-- 3815.2.1.1
bas7050reg		OBJECT IDENTIFIER ::= { bas700reg 2 }       -- 3815.2.1.2
bb100modbusreg	OBJECT IDENTIFIER ::= { bbuster100reg 1 }	-- 3815.2.2.1
bbx2reg			OBJECT IDENTIFIER ::= { bbuster100reg 2 }   -- 3815.2.2.2

-- Application MIB revision registrations
sys700v1		OBJECT IDENTIFIER ::= { sys700reg 1 }		-- 3815.2.1.1.1
sys700v2		OBJECT IDENTIFIER ::= { sys700reg 2 }		-- 3815.2.1.1.2
snmp7050v1		OBJECT IDENTIFIER ::= { bas7050reg 1 }      -- 3815.2.1.2.1
bb100modbusV1	OBJECT IDENTIFIER ::= { bb100modbusreg 1 }	-- 3815.2.2.1.1
bbx2v1			OBJECT IDENTIFIER ::= { bbx2reg 1 }			-- 3815.2.2.2.1
	
END
