-- =================================================================
-- Copyright (C) 2001,2002 by  Huawei-3Com TECHNOLOGIES. All rights reserved.
--
-- Description:the Huawei 3Com root mib
-- Reference:
-- Version:     V1.36
-- History:
--	V1.0 2004-08-05 Initial version, created by gaolong.
--  V1.22 add MIB identifier
--            'h3cVoiceVlan'
--            'h3cL4Redirect' 
--            'h3cUser', 'h3cRadius'
--            'h3cPowerEthernetExt'
--            'h3cEntityRelation'
--            'h3cProtocolVlan'
--            'h3cQosProfile'
-- V1.23 add MIB identifier
--            'hwQoS'
-- V1.3 2004-10-12 updated by gaolong
--      add MIB identifier 'rmonExtend'
-- V1.31 2004-10-23 updated by gaolong
--       add 'h3cEntityVendorTypeOID', 'dlsw', 'hwpaeExtMib', 'hwDevice', 'h3cNat',
--       'h3cPos', 'h3cNetStream', 'voice', object identifiers.
-- V1.32 2004-11-8 update by xiejianping
--       add 'h3cAAL5' and 'h3cSSH';
-- V1.33 2004-11-10 update by xiejianping
--       add 'h3cRSA';
-- V1.34 2004-12-12 updated by gaolong
--       add h3cVrrpExt, h3cIpa, h3cPortSecurity, h3cVpls, h3cE1, 
--           h3cT1, h3cIkeMonitor
-- V1.35 2004-12-25 updated by gaolong
--       add 'h3cIfExt', 'h3cWebSwitch', 'h3cAutoDetect', 'h3cIpBroadcast', 
--           and 'h3cIpx'.
-- V1.36 2005-03-10 updated by gaolong
--       modify 'h3cIkeMonitor' to 'h3cIKEMonitor' by gaolong
--       add 'h3cDldp' and 'h3cRrpp'
-- =================================================================
A3COM-HUAWEI-OID-MIB DEFINITIONS ::= BEGIN

	IMPORTS
	enterprises			
		FROM RFC1155-SMI;

-- level 1 under .enterprises
	a3Com           OBJECT IDENTIFIER ::= { enterprises 43 }

	jv-mib          OBJECT IDENTIFIER ::= { a3Com 45 }
	huawei		OBJECT IDENTIFIER ::= { jv-mib 1 }
-- level 2 under .huawei		
	hwLocal OBJECT IDENTIFIER ::= { huawei 1 }
	hwproducts OBJECT IDENTIFIER ::= { huawei 2 }

	huaweiMgmt      OBJECT IDENTIFIER ::= { huawei 5 }

	huaweiUtility   OBJECT IDENTIFIER ::= { huawei 6 }
	h3c             OBJECT IDENTIFIER ::= { huawei 10 }
-- level 3
	hwInternetProtocol OBJECT IDENTIFIER ::= { hwLocal 3 }
	router	OBJECT IDENTIFIER ::= { hwproducts 2 }
	lanSw	OBJECT IDENTIFIER ::= { hwproducts 23 }
	mlsr	OBJECT IDENTIFIER ::= { hwproducts 33 }
	dlsw	OBJECT IDENTIFIER ::= { hwproducts 34 }   -- Reference: huawei-dlsw.mib
	hwDhcp OBJECT IDENTIFIER ::= { huaweiMgmt 7 }
	hwMpls OBJECT IDENTIFIER ::= { huaweiMgmt 12 }
	hwpaeExtMib OBJECT IDENTIFIER ::= { huaweiMgmt 22 }   -- Reference: huawei-8021x-ext.mib
	huaweiDatacomm OBJECT IDENTIFIER ::= { huaweiMgmt 25 }
	hwDevice OBJECT IDENTIFIER ::= { huaweiUtility 1 }    -- Reference: huawei-splat-devm.mib

	-- under h3c
	h3cCommon   OBJECT IDENTIFIER ::= { h3c 2 }		-- 2004/1/12, xiejianping changed
	h3cEntityVendorTypeOID OBJECT IDENTIFIER ::= { h3c 3 }  -- 2004/5/18, xiejianping added
	hwSystem    OBJECT IDENTIFIER ::= { h3c 6 }             -- 2004/4/24, xiejianping changed


	vrpProtocol OBJECT IDENTIFIER ::= { hwInternetProtocol 3 } 
	rmonExtend OBJECT IDENTIFIER ::= { hwInternetProtocol 4 }
	-- under lanSw
	lswCommon       OBJECT IDENTIFIER ::= { lanSw 1 }

        voice                   OBJECT IDENTIFIER ::= { huaweiDatacomm 1 }
    hwQoS    OBJECT IDENTIFIER ::= { huaweiDatacomm 32 }

        h3cFtm    OBJECT IDENTIFIER ::= { h3cCommon 1 }
        h3cUIMgt    OBJECT IDENTIFIER ::= { h3cCommon 2 }
        h3cEntityExtend    OBJECT IDENTIFIER ::= { h3cCommon 6 }
        h3cIpSecMonitor    OBJECT IDENTIFIER ::= { h3cCommon 7 }
        h3cAcl    OBJECT IDENTIFIER ::= { h3cCommon 8 }
	h3cVoiceVlan	OBJECT IDENTIFIER ::= { h3cCommon 9 }
	h3cL4Redirect	OBJECT IDENTIFIER ::= { h3cCommon 10 }
	h3cUser        OBJECT IDENTIFIER ::= { h3cCommon 12 }
	h3cRadius        OBJECT IDENTIFIER ::= { h3cCommon 13 }
	h3cPowerEthernetExt        OBJECT IDENTIFIER ::= { h3cCommon 14 }
	h3cEntityRelation        OBJECT IDENTIFIER ::= { h3cCommon 15 }
	h3cProtocolVlan        OBJECT IDENTIFIER ::= { h3cCommon 16 }
	h3cQosProfile        OBJECT IDENTIFIER ::= { h3cCommon 17 }
	h3cNat        OBJECT IDENTIFIER ::= { h3cCommon 18 }
	h3cPos        OBJECT IDENTIFIER ::= { h3cCommon 19 }
	h3cNetStream        OBJECT IDENTIFIER ::= { h3cCommon 20 }
	h3cAAL5        OBJECT IDENTIFIER ::= { h3cCommon 21 }
	h3cSSH        OBJECT IDENTIFIER ::= { h3cCommon 22 }
	h3cRSA        OBJECT IDENTIFIER ::= { h3cCommon 23 }
	h3cVrrpExt        OBJECT IDENTIFIER ::= { h3cCommon 24 }
	
	h3cIpa        OBJECT IDENTIFIER ::= { h3cCommon 25 }
	h3cPortSecurity         OBJECT IDENTIFIER ::= { h3cCommon 26 }
	h3cVpls         OBJECT IDENTIFIER ::= { h3cCommon 27 }
	h3cE1         OBJECT IDENTIFIER ::= { h3cCommon 28 }
	h3cT1         OBJECT IDENTIFIER ::= { h3cCommon 29 }
	h3cIKEMonitor         OBJECT IDENTIFIER ::= { h3cCommon 30 }
	h3cWebSwitch         OBJECT IDENTIFIER ::= { h3cCommon 31 }
	h3cAutoDetect         OBJECT IDENTIFIER ::= { h3cCommon 32 }
	h3cIpBroadcast         OBJECT IDENTIFIER ::= { h3cCommon 33 }
	h3cIpx         OBJECT IDENTIFIER ::= { h3cCommon 34 }
	h3cIfExt         OBJECT IDENTIFIER ::= { h3cCommon 40 }
	h3cDldp         OBJECT IDENTIFIER ::= { h3cCommon 43 }
	h3cRrpp         OBJECT IDENTIFIER ::= { h3cCommon 45 }
END
