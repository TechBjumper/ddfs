-- ********************************************************************
-- RITTAL GmbH & Co. KG, Herborn
-- CMC-III-MIB Version 1.2
-- CMC-III-Processing Unit - 7030.000, 7030.010, 7030.020
--
-- Management Information Base for SNMP Network Management
--
-- Copyright 2011 Rittal Herborn.
-- All Rights Reserved.
--
-- The information in this document is subject to change without notice.
-- Refer to document "AGB_Software_Rittal.pdf"
--
-- ********************************************************************
-- File   : $RCSfile: $
-- Rev.   : $Revision: $
-- Date   : $Date: $
-- Author : $Author: $
-- Id     : $Id: $
-- ********************************************************************

RITTAL-CMC-III-MIB DEFINITIONS ::= BEGIN

IMPORTS
        MODULE-IDENTITY, 
        NOTIFICATION-TYPE, 
        OBJECT-TYPE,
        Integer32, 
        Unsigned32, 
        TimeTicks
    FROM                    SNMPv2-SMI
        MODULE-COMPLIANCE, 
        OBJECT-GROUP, 
        NOTIFICATION-GROUP
    FROM                    SNMPv2-CONF
        DisplayString
    FROM                    SNMPv2-TC
        rittal
    FROM                    RITTAL-SMI-MIB;


cmcIII                      MODULE-IDENTITY
        LAST-UPDATED        "201111010000Z"
        ORGANIZATION        "RITTAL GmbH & Co. KG"
        CONTACT-INFO        "www.rittal.de

                            RITTAL GmbH & Co. KG
                            Forschung & Entwicklung
                            Auf dem Stuetzelberg
                            D-35745 Herborn
                            Germany, Europe

                            +49(0)2772 5050
                            info@rittal.de"
        DESCRIPTION         "The MIB module for representing cmcIII SNMP agent"
        REVISION            "201109020000Z"
        DESCRIPTION         "SMIv2 Version of cmcIII MIB."
        REVISION            "201103070000Z"
        DESCRIPTION         "Initial Version of cmcIII MIB."
--      ::=                 { iso(1) org(3) dod(6) internet(1) private(4) enterprises(1) rittal(2606) 7 }
        ::=                 { rittal 7 }


--  rittal                          OBJECT IDENTIFIER ::= { enterprises 2606 }
--    cmcIII                        OBJECT IDENTIFIER ::= {   rittal 7 }
        cmcIIINotifications         OBJECT IDENTIFIER ::= {     cmcIII 0 }
        cmcIIIMibRev                OBJECT IDENTIFIER ::= {     cmcIII 1 }
        cmcIIIUnit                  OBJECT IDENTIFIER ::= {     cmcIII 2 }
        cmcIIISetup                 OBJECT IDENTIFIER ::= {     cmcIII 3 }
          cmcIIISetupGeneral        OBJECT IDENTIFIER ::= {       cmcIIISetup 2 }
          cmcIIISetupTimer          OBJECT IDENTIFIER ::= {       cmcIIISetup 3 }
          cmcIIISetupTrap           OBJECT IDENTIFIER ::= {       cmcIIISetup 4 }
          cmcIIISetupSMTP           OBJECT IDENTIFIER ::= {       cmcIIISetup 5 }
          cmcIIISetupSMS            OBJECT IDENTIFIER ::= {       cmcIIISetup 6 }
          cmcIIISetupSysLog         OBJECT IDENTIFIER ::= {       cmcIIISetup 7 }
          cmcIIISetupNTP            OBJECT IDENTIFIER ::= {       cmcIIISetup 8 }
          cmcIIISetupLDAP           OBJECT IDENTIFIER ::= {       cmcIIISetup 9 }
        cmcIIIDevice                OBJECT IDENTIFIER ::= {     cmcIII 4 }
          cmcIIIDevs                OBJECT IDENTIFIER ::= {       cmcIIIDevice 1 }
            cmcIIIDevInfo           OBJECT IDENTIFIER ::= {       cmcIIIDevs 1 }
          cmcIIIVars                OBJECT IDENTIFIER ::= {       cmcIIIDevice 2 }
            cmcIIIVarInfo           OBJECT IDENTIFIER ::= {       cmcIIIVars 1 }
          cmcIIIMsgs                OBJECT IDENTIFIER ::= {       cmcIIIDevice 3 }
            cmcIIIMsgInfo           OBJECT IDENTIFIER ::= {       cmcIIIMsgs 1 }
        cmcIIIControl               OBJECT IDENTIFIER ::= {     cmcIII 5 }
--          cmcIIIExtAlarm          OBJECT IDENTIFIER ::= {       cmcIIIControl 4 }
        cmcIIIConformance           OBJECT IDENTIFIER ::= {     cmcIII 6 }
          cmcIIIMibCompliances      OBJECT IDENTIFIER ::= {       cmcIIIConformance 1 }
          cmcIIIMibGroups           OBJECT IDENTIFIER ::= {       cmcIIIConformance 2 }
--      cmcIIIProducts              OBJECT IDENTIFIER ::= {     cmcIII 7 }
--      cmcIIICapability            OBJECT IDENTIFIER ::= {     cmcIII 8 }


--  *****************************************************************************
--  CMC-III ComputerMultiControl DK7030.yyy  --
--  *****************************************************************************

--  cmcIIIMibRev  --

    cmcIIIMibMajRev         OBJECT-TYPE
        SYNTAX              Unsigned32          (1..65535)
        MAX-ACCESS          read-only
        STATUS              current
        DESCRIPTION         "The Major Revision level.
                            A change in the major revision level represents a major change
                            in the architecture of the MIB. A change in the major revision
                            level may indicate a significant change in the information,
                            correct interpretation of data may require a MIB document
                            with the same major revision level."
        ::=                 { cmcIIIMibRev       1 }


    cmcIIIMibMinRev         OBJECT-TYPE
        SYNTAX              Unsigned32          (0..65535)
        MAX-ACCESS          read-only
        STATUS              current
        DESCRIPTION         "The Minor Revision level.
                            A change in the minor revision level may represent some minor
                            additional support, no changes to any pre-existing information
                            has occurred."
        ::=                 { cmcIIIMibRev       2 }


    cmcIIIAgentRev          OBJECT-TYPE
        SYNTAX              DisplayString       (SIZE (0..20))
        MAX-ACCESS          read-only
        STATUS              current
        DESCRIPTION         "The SNMP Agent Revision level."
        ::=                 { cmcIIIMibRev       3 }


--  cmcIIIUnit  --

    cmcIIIUnitStatus        OBJECT-TYPE
        SYNTAX              INTEGER {
                                ok      	(1),
                                failed  	(2),
                                overload	(3)
                            }
        MAX-ACCESS          read-only
        STATUS              current
        DESCRIPTION         "General Status of CMCIII PU unit itself
                            (1) OK
                            (2) failed
                            (3) overload (current too high)"
        ::=                 { cmcIIIUnit         1 }


    cmcIIIUnitURL           OBJECT-TYPE
        SYNTAX              DisplayString       (SIZE (0..30))
        MAX-ACCESS          read-only
        STATUS              current
        DESCRIPTION         "URL of CMCIII PU"
        ::=                 { cmcIIIUnit         2 }


    cmcIIIUnitHWRev         OBJECT-TYPE
        SYNTAX              DisplayString       (SIZE (0..12))
        MAX-ACCESS          read-only
        STATUS              current
        DESCRIPTION         "Hardware Revision of CMCIII PU"
        ::=                 { cmcIIIUnit         3 }


    cmcIIIUnitFWRev         OBJECT-TYPE
        SYNTAX              DisplayString       (SIZE (0..12))
        MAX-ACCESS          read-only
        STATUS              current
        DESCRIPTION         "Firmware Revision of CMCIII PU"
        ::=                 { cmcIIIUnit         4 }


    cmcIIIUnitOSRev         OBJECT-TYPE
        SYNTAX              DisplayString       (SIZE (0..20))
        MAX-ACCESS          read-only
        STATUS              current
        DESCRIPTION         "Linux Revision of CMCIII PU"
        ::=                 { cmcIIIUnit         5 }


    cmcIIIUnitSerial        OBJECT-TYPE
        SYNTAX              DisplayString       (SIZE (0..7))
        MAX-ACCESS          read-only
        STATUS              current
        DESCRIPTION         "Serial Number of CMCIII PU"
        ::=                 { cmcIIIUnit         6 }


    cmcIIIUnitProd          OBJECT-TYPE
        SYNTAX              DisplayString       (SIZE (0..20))
        MAX-ACCESS          read-only
        STATUS              current
        DESCRIPTION         "Production Code of CMCIII PU"
        ::=                 { cmcIIIUnit         7 }


    cmcIIIUnitType          OBJECT-TYPE
        SYNTAX              INTEGER {
                                unknown 	(1),
                                pu      	(2),
                                compact     	(3)
                            }
        MAX-ACCESS          read-only
        STATUS              current
        DESCRIPTION         "Type of CMCIII
                            (1) Unit unknown
                            (2) Processing Unit
                            (3) Processing Unit Compact"
        ::=                 { cmcIIIUnit         8 }


    cmcIIIUnitCurrentSource  OBJECT-TYPE
        SYNTAX              INTEGER {
                                unknown 	(1),
                                acAdapter	(2),
                                terminalStrip	(3),
                                poe     	(4),
                                usb     	(5)
                            }
        MAX-ACCESS          read-only
        STATUS              current
        DESCRIPTION         "Current source of CMCIII PU
                            (1) unknown
                            (2) AC Adapter Power Supply
                            (3) Terminal Strip
                            (4) poe: Power Over Ethernet
                            (5) usb: Universal Serial Bus"
        ::=                 { cmcIIIUnit         9 }


    cmcIIICan0CurrentConsumption  OBJECT-TYPE
        SYNTAX              Integer32
        MAX-ACCESS          read-only
        STATUS              current
        DESCRIPTION         "Maximal current consumption required by CANopen fieldbus 1"
        ::=                 { cmcIIIUnit         10 }


    cmcIIICan1CurrentConsumption  OBJECT-TYPE
        SYNTAX              Integer32
        MAX-ACCESS          read-only
        STATUS              current
        DESCRIPTION         "Maximal current consumption required by CANopen fieldbus 2"
        ::=                 { cmcIIIUnit         11 }


    cmcIIIUnitUpTime        OBJECT-TYPE
        SYNTAX              TimeTicks
        MAX-ACCESS          read-only
        STATUS              current
        DESCRIPTION         "Operating time of CMCIII PU"
        ::=                 { cmcIIIUnit         12 }



--  cmcIIISetup  --

    cmcIIILastChangeSetup   OBJECT-TYPE
        SYNTAX              TimeTicks
        MAX-ACCESS          read-only
        STATUS              current
        DESCRIPTION         "Last change of configuration
                            according to operating time cmcIIIUnitUpTime"
        ::=                 { cmcIIISetup        1 }

--  cmcIIISetupGeneral  --

    cmcIIISetTempUnit       OBJECT-TYPE
        SYNTAX              INTEGER {
                                celsius 	(1),
                                fahrenheit	(2)
                            }
        MAX-ACCESS          read-write
        STATUS              current
        DESCRIPTION         "Unit of all temperature values and setpoints"
        ::=                 { cmcIIISetupGeneral 1 }


    cmcIIISetBeeper         OBJECT-TYPE
        SYNTAX              INTEGER {
                                off     	(1),
                                on      	(2)
                            }
        MAX-ACCESS          read-write
        STATUS              current
        DESCRIPTION         "Audible alarm in CMCIII unit:
                            (1) beeper is off (general)
                            (2) beeper is on"
        ::=                 { cmcIIISetupGeneral 2 }


    cmcIIIQuitRelay         OBJECT-TYPE
        SYNTAX              INTEGER {
                                disabled	(1),
                                enabled 	(2)
                            }
        MAX-ACCESS          read-write
        STATUS              current
        DESCRIPTION         "Enable or disable acknowledging currently active alarm relay
                            (with 'C' on CMCIII)."
        ::=                 { cmcIIISetupGeneral 3 }


    cmcIIILogicRelay        OBJECT-TYPE
        SYNTAX              INTEGER {
                                closeAtAlarm	(1),
                                openAtAlarm	(2),
                                disabled     	(3)
                            }
        MAX-ACCESS          read-write
        STATUS              current
        DESCRIPTION         "Logic of alarm relay:
                            (1) Relay will pick up in case of an alarm
                            (2) Relay will release in case of an alarm
                            (3) Relay disabled"
        ::=                 { cmcIIISetupGeneral 4 }


    cmcIIIUnitMsgRelay      OBJECT-TYPE
        SYNTAX              INTEGER {
                                disabled	(1),
                                enabled 	(2)
                            }
        MAX-ACCESS          read-write
        STATUS              current
        DESCRIPTION         "Alarm relay in case of Device Messages (detect, lost, changed..):
                            (1) Relay disabled, relay will not switch in case of a device message
                            (2) Relay enabled, relay will switch in case of a unit message"
        ::=                 { cmcIIISetupGeneral 5 }


    cmcIIIFunctionRelay     OBJECT-TYPE
        SYNTAX              INTEGER {
                                warningOnly	(1),
                                alarmOnly	(2),
                                warningOrAlarm	(3)
                            }
        MAX-ACCESS          read-write
        STATUS              current
        DESCRIPTION         "Logic of alarm relay:
                            (1) Relay will switch in case of a warning only
                            (2) Relay will switch in case of an alarm only
                            (3) Relay will switch in case of an alarm or warning"
        ::=                 { cmcIIISetupGeneral 6 }


    cmcIIITimeZone          OBJECT-TYPE
        SYNTAX              Integer32           (0..74)
        MAX-ACCESS          read-write
        STATUS              current
        DESCRIPTION         "Time Zone
                            0  : (GMT-12:00) International Date Line West
                            1  : (GMT-11:00) Midway Island, Samoa
                            2  : (GMT-10:00) Hawaii
                            3  : (GMT-09:00) Alaska
                            4  : (GMT-08:00) Pacific Time (US and Canada), Tijuana
                            5  : (GMT-07:00) Arizona
                            6  : (GMT-07:00) Chihuahua, La Paz, Mazatlan
                            7  : (GMT-07:00) Mountain Time (US & Canada)
                            8  : (GMT-06:00) Central America
                            9  : (GMT-06:00) Central Time (US and Canada)
                            10 : (GMT-06:00) Guadalajara, Mexico City, Monterrey
                            11 : (GMT-06:00) Saskatchewan
                            12 : (GMT-05:00) Bogota, Lima, Quito
                            13 : (GMT-05:00) Eastern Time (Us and Canada)
                            14 : (GMT-05:00) Indiana (East)
                            15 : (GMT-04:00) Atlantic Time (Canada)
                            16 : (GMT-04:00) Caracas, La Paz
                            17 : (GMT-04:00) Santiago
                            18 : (GMT-03:30) Newfoundland
                            19 : (GMT-03:00) Brasilia
                            20 : (GMT-03:00) Buenos Aires, Georgetown
                            21 : (GMT-03:00) Greenland
                            22 : (GMT-02:00) Mid-Atlantic
                            23 : (GMT-01:00) Azores
                            24 : (GMT-01:00) Cape Verde Is.
                            25 : (GMT) Casablanca, Monrovia
                            26 : (GMT) Greenwich Mean Time : Dublin, Lisbon, London
                            27 : (GMT+01:00) Amsterdam, Berlin, Bern, Rome, Vienna
                            28 : (GMT+01:00) Belgrade, Bratislava, Budapest, Prague
                            29 : (GMT+01:00) Brussels, Copenhagen, Madrid, Paris
                            30 : (GMT+01:00) Sarajevo, Skopje, Warsaw, Zagreb
                            31 : (GMT+01:00) West Central Africa
                            32 : (GMT+02:00) Athens, Istanbul, Minsk
                            33 : (GMT+02:00) Bucharest
                            34 : (GMT+02:00) Harare, Pretoria
                            35 : (GMT+02:00) Helsinki, Kyiv, Sofia
                            36 : (GMT+02:00) Riga, Tallinn, Vilnius
                            37 : (GMT+02:00) Jerusalem
                            38 : (GMT+03:00) Baghdad
                            39 : (GMT+03:00) Kuwait, Riyadh
                            40 : (GMT+03:00) Moscow, St. Petersburg, Volgograd
                            41 : (GMT+03:00) Nairobi
                            42 : (GMT+03:30) Tehran
                            43 : (GMT+04:00) Abu Dhabi, Muscat
                            44 : (GMT+04:00) Baku, Tbilisi, Yerevan
                            45 : (GMT+04:30) Kabul
                            46 : (GMT+05:00) Ekaterinburg
                            47 : (GMT+05:00) Islamabad, Karachi, Tashkent
                            48 : (GMT+05:30) Chennai, Kolkata, Mumbai, New Delhi
                            49 : (GMT+05:45) Kathmandu
                            50 : (GMT+06:00) Almaty, Novosibirsk
                            51 : (GMT+06:00) Astana, Dhaka
                            52 : (GMT+06:00) Sri Jayawardenepura
                            53 : (GMT+06:30) Rangoon
                            54 : (GMT+07:00) Bangkok, Hanoi, Jakarta
                            55 : (GMT+07:00) Krasnoyarsk
                            56 : (GMT+08:00) Beijing, Chongqing, Hong Kong, Urumqi
                            57 : (GMT+08:00) Irkutsk, Ulaan Bataar
                            58 : (GMT+08:00) Kuala Lumpur, Singapore
                            59 : (GMT+08:00) Perth
                            60 : (GMT+08:00) Taipei
                            61 : (GMT+09:00) Osaka, Sapporo, Tokyo
                            62 : (GMT+09:00) Seoul
                            63 : (GMT+09:00) Yakutsk
                            64 : (GMT+09:30) Adelaide
                            65 : (GMT+09:30) Darwin
                            66 : (GMT+10:00) Brisbane
                            67 : (GMT+10:00) Canberra, Melbourne, Sydney
                            68 : (GMT+10:00) Guam, Port Moresby
                            69 : (GMT+10:00) Hobart
                            70 : (GMT+10:00) Vladivostok
                            71 : (GMT+11:00) Magadan, Solomon Is., New Caledonia
                            72 : (GMT+12:00) Auckland, Wellington
                            73 : (GMT+12:00) Fiji, Kamchatka, Marshall Is.
                            74 : (GMT+13:00) Nukualofa"
        ::=                 { cmcIIISetupGeneral 7 }

    cmcIIISetupDate         OBJECT-TYPE
        SYNTAX              DisplayString       (SIZE (10..10))
        MAX-ACCESS          read-write
        STATUS              current
        DESCRIPTION         "Actual date in format DD.MM.YYYY
                             Use UTC date to set date."
         ::=                 { cmcIIISetupGeneral 8 }


    cmcIIISetupTime         OBJECT-TYPE
        SYNTAX              DisplayString       (SIZE (8..8))
        MAX-ACCESS          read-write
        STATUS              current
        DESCRIPTION         "Actual time in format HH:MM:SS, HH (0-23), MM (0-59), SS (0-59).
                            Use UTC time to set time."
        ::=                 { cmcIIISetupGeneral 9 }

    cmcIIIWebAccess         OBJECT-TYPE
        SYNTAX              BITS {
                                httpEnabled	(0),
                                httpsEnabled	(1)
                            }
        MAX-ACCESS          read-write
        STATUS              current
        DESCRIPTION         "Web access status:
                            (0) httpEnabled  : http protocol is enabled
                            (1) httpsEnabled : https protocol is enabled"
        ::=                 { cmcIIISetupGeneral 10 }

    cmcIIIHttpPort          OBJECT-TYPE
        SYNTAX              Unsigned32
        MAX-ACCESS          read-write
        STATUS              current
        DESCRIPTION         "TCP/IP port of HTTP daemon"
        ::=                 { cmcIIISetupGeneral 11 }

    cmcIIIHttpsPort         OBJECT-TYPE
        SYNTAX              Unsigned32
        MAX-ACCESS          read-write
        STATUS              current
        DESCRIPTION         "TCP/IP port of HTTPS daemon"
        ::=                 { cmcIIISetupGeneral 12 }

    cmcIIIFtpAccess         OBJECT-TYPE
        SYNTAX              INTEGER {
                                disabled	(1),
                                enabled 	(2)
                            }
        MAX-ACCESS          read-write
        STATUS              current
        DESCRIPTION         "Ftp access:
                            (1) disabled
                            (2) enabled"
        ::=                 { cmcIIISetupGeneral 13 }

    cmcIIIFtpPort           OBJECT-TYPE
        SYNTAX              Unsigned32
        MAX-ACCESS          read-write
        STATUS              current
        DESCRIPTION         "TCP/IP port of FTP daemon"
        ::=                 { cmcIIISetupGeneral 14 }

    cmcIIISshAccess         OBJECT-TYPE
        SYNTAX              INTEGER {
                                disabled	(1),
                                enabled 	(2)
                            }
        MAX-ACCESS          read-write
        STATUS              current
        DESCRIPTION         "Ssh access:
                            (1) disabled
                            (2) enabled"
        ::=                 { cmcIIISetupGeneral 15 }

    cmcIIISshPort           OBJECT-TYPE
        SYNTAX              Unsigned32
        MAX-ACCESS          read-write
        STATUS              current
        DESCRIPTION         "TCP/IP port of SSH daemon"
        ::=                 { cmcIIISetupGeneral 16 }

    cmcIIITelnetAccess      OBJECT-TYPE
        SYNTAX              INTEGER {
                                disabled	(1),
                                enabled 	(2)
                            }
        MAX-ACCESS          read-write
        STATUS              current
        DESCRIPTION         "Telnet access:
                            (1) disabled
                            (2) enabled"
        ::=                 { cmcIIISetupGeneral 17 }

    cmcIIITelnetPort        OBJECT-TYPE
        SYNTAX              Unsigned32
        MAX-ACCESS          read-write
        STATUS              current
        DESCRIPTION         "TCP/IP port of telnet daemon"
        ::=                 { cmcIIISetupGeneral 18 }

    cmcIIILanguage          OBJECT-TYPE
        SYNTAX              INTEGER {
                                english 	(1),
                                other   	(2)
                            }
        MAX-ACCESS          read-write
        STATUS              current
        DESCRIPTION         "Language:
                            (1) English,
                            (2) other"
        ::=                 { cmcIIISetupGeneral 19 }

--  cmcIIISetupTimer  --

    cmcIIINumberOfTimers    OBJECT-TYPE
        SYNTAX              Integer32
        MAX-ACCESS          read-only
        STATUS              current
        DESCRIPTION         "Number of value table entries=number of outlets available on this unit"
        ::=                 { cmcIIISetupTimer   1 }

    cmcIIITimerTable        OBJECT-TYPE
        SYNTAX              SEQUENCE OF CmcIIITimerEntry
        MAX-ACCESS          not-accessible
        STATUS              current
        DESCRIPTION         "Headline of Timer Table"
        ::=                 { cmcIIISetupTimer   2 }

    cmcIIITimerEntry        OBJECT-TYPE
        SYNTAX              CmcIIITimerEntry
        MAX-ACCESS          not-accessible
        STATUS              current
        DESCRIPTION         "Entries of Timer Table"
        INDEX               { cmcIIITimerIndex }
        ::=                 { cmcIIITimerTable   1 }

    CmcIIITimerEntry        ::=
        SEQUENCE            {
                                cmcIIITimerIndex        Unsigned32,
                                cmcIIITimerStatus       INTEGER,
                                cmcIIITimerDayOfWeek    INTEGER,
                                cmcIIITimeOn            DisplayString,
                                cmcIIITimeOff           DisplayString,
                                cmcIIITimeControl       INTEGER,
                                cmcIIITimerFunction     INTEGER
                            }

    cmcIIITimerIndex        OBJECT-TYPE
        SYNTAX              Unsigned32          (1..65535)
        MAX-ACCESS          not-accessible
        STATUS              current
        DESCRIPTION         "Index for the list of timer entries. Its value ranges
                            between 1 and the value of cmcIIINumberOfTimers."
        ::=                 { cmcIIITimerEntry   1 }

    cmcIIITimerStatus       OBJECT-TYPE
        SYNTAX              INTEGER {
                                switchedOff	(1),
                                switchedOn	(2),
                                noTime  	(3)
                            }
        MAX-ACCESS          read-only
        STATUS              current
        DESCRIPTION         "Actual status of the timer"
        ::=                 { cmcIIITimerEntry   2 }

    cmcIIITimerDayOfWeek    OBJECT-TYPE
        SYNTAX              INTEGER {
                                sun     	(1),
                                mon     	(2),
                                tue     	(3),
                                wed     	(4),
                                thu     	(5),
                                fri     	(6),
                                sat     	(7),
                                sat2sun 	(8),
                                mon2fri 	(9),
                                mon2sun 	(10)
                            }
        MAX-ACCESS          read-write
        STATUS              current
        DESCRIPTION         "Selection of day of week for timer to switch"
        ::=                 { cmcIIITimerEntry   3 }

    cmcIIITimeOn            OBJECT-TYPE
        SYNTAX              DisplayString       (SIZE (5..5))
        MAX-ACCESS          read-write
        STATUS              current
        DESCRIPTION         "Time to switch on current function, Format: HH:MM"
        ::=                 { cmcIIITimerEntry   4 }

    cmcIIITimeOff           OBJECT-TYPE
        SYNTAX              DisplayString       (SIZE (5..5))
        MAX-ACCESS          read-write
        STATUS              current
        DESCRIPTION         "Time to switch off current function, Format: HH:MM"
        ::=                 { cmcIIITimerEntry   5 }

    cmcIIITimeControl       OBJECT-TYPE
        SYNTAX              INTEGER {
                                disabled	(1),
                                enabled 	(2)
                            }
        MAX-ACCESS          read-write
        STATUS              current
        DESCRIPTION         "Control via RTC"
        ::=                 { cmcIIITimerEntry   6 }

    cmcIIITimerFunction     OBJECT-TYPE
        SYNTAX              INTEGER {
                                disKeypads	(1),
                                unlDoors	(2),
                                disTrapRec1	(3),
                                disTrapRec2	(4),
                                disTrapRec3	(5),
                                disTrapRec4	(6),
                                disSMS1         (7),
                                disSMS2         (8),
                                disSMS3         (9),
                                disSMS4         (10),
                                schedule1	(11),
                                schedule2	(12),
                                schedule3	(13),
                                schedule4	(14),
                                schedule5	(15),
                                schedule6	(16),
                                schedule7	(17),
                                schedule8	(18)
                            }
        MAX-ACCESS          read-write
        STATUS              current
        DESCRIPTION         "Function which is controlled via timer
                            1: Unlock of doors via keypad is disabled
                            2: Doors will be unlocked
                            3-6: sending traps to this trap receiver will be disabled
                            7-10: sending SMS to phone number 1..4 will be disabled
                            11-18: Scheduled alarm off"
        ::=                 { cmcIIITimerEntry   7 }

--  cmcIIISetupTrapReceiver  --

    cmcIIINumberOfTrapReceivers  OBJECT-TYPE
        SYNTAX              Integer32
        MAX-ACCESS          read-only
        STATUS              current
        DESCRIPTION         "Number of TrapReceiverTable entries. The number of trap receivers"
        ::=                 { cmcIIISetupTrap    1 }

    cmcIIITrapReceiverTable  OBJECT-TYPE
        SYNTAX              SEQUENCE OF CmcIIITrapReceiverEntry
        MAX-ACCESS          not-accessible
        STATUS              current
        DESCRIPTION         "A list of trap receiver entries"
        ::=                 { cmcIIISetupTrap    2 }

    cmcIIITrapReceiverEntry  OBJECT-TYPE
        SYNTAX              CmcIIITrapReceiverEntry
        MAX-ACCESS          not-accessible
        STATUS              current
        DESCRIPTION         "Entries of trapTable"
        INDEX               { cmcIIITrapReceiverIndex }
        ::=                 { cmcIIITrapReceiverTable 1 }

    CmcIIITrapReceiverEntry  ::=
        SEQUENCE            {
                                cmcIIITrapReceiverIndex         Unsigned32,
                                cmcIIITrapReceiverStatus        INTEGER,
                                cmcIIITrapReceiverIpAddress     DisplayString
                            }

    cmcIIITrapReceiverIndex  OBJECT-TYPE
        SYNTAX              Unsigned32          (1..65535)
        MAX-ACCESS          not-accessible
        STATUS              current
        DESCRIPTION         "Index for the trap receiver table. Its value ranges between
                            1 and the value of NumberOfTrapReceivers"
        ::=                 { cmcIIITrapReceiverEntry 1 }

    cmcIIITrapReceiverStatus  OBJECT-TYPE
        SYNTAX              INTEGER {
                                disabled       (1),
                                snmpv1         (2),
                                snmpv2c        (3),
                                snmpv3         (4)
                            }
        MAX-ACCESS          read-write
        STATUS              current
        DESCRIPTION         "Enable trap version or disable trap receiver"
        ::=                 { cmcIIITrapReceiverEntry 2 }

    cmcIIITrapReceiverIpAddress  OBJECT-TYPE
        SYNTAX              DisplayString       (SIZE (0..15))
        MAX-ACCESS          read-write
        STATUS              current
        DESCRIPTION         "IP address of trap receiver"
        ::=                 { cmcIIITrapReceiverEntry 3 }

--  cmcIIISetupSMTP  --

    cmcIIISmtpStatus        OBJECT-TYPE
        SYNTAX              INTEGER {
                                disabled	(1),
                                enabled 	(2)
                            }
        MAX-ACCESS          read-write
        STATUS              current
        DESCRIPTION         "SMTP (email) usage:
                            (1) disabled
                            (2) enabled"
        ::=                 { cmcIIISetupSMTP    1 }

    cmcIIISmtpServer        OBJECT-TYPE
        SYNTAX              DisplayString       (SIZE (0..15))
        MAX-ACCESS          read-write
        STATUS              current
        DESCRIPTION         "IP address of SMTP server"
        ::=                 { cmcIIISetupSMTP    2 }

    cmcIIISmtpPort          OBJECT-TYPE
        SYNTAX              Unsigned32
        MAX-ACCESS          read-write
        STATUS              current
        DESCRIPTION         "TCP/IP port of SMTP server"
        ::=                 { cmcIIISetupSMTP    3 }

    cmcIIISmtpAuth          OBJECT-TYPE
        SYNTAX              INTEGER {
                                disabled	(1),
                                enabled 	(2)
                            }
        MAX-ACCESS          read-write
        STATUS              current
        DESCRIPTION         "SMTP authentication usage:
                            (1) disabled
                            (2) enabled"
        ::=                 { cmcIIISetupSMTP    4 }

    cmcIIISmtpUsername      OBJECT-TYPE
        SYNTAX              DisplayString       (SIZE (0..20))
        MAX-ACCESS          read-write
        STATUS              current
        DESCRIPTION         "Username required to authenticate at the SMTP server"
        ::=                 { cmcIIISetupSMTP    5 }

    cmcIIISmtpPassword      OBJECT-TYPE
        SYNTAX              DisplayString       (SIZE (0..20))
        MAX-ACCESS          read-write
        STATUS              current
        DESCRIPTION         "Password required to authenticate at the SMTP server"
        ::=                 { cmcIIISetupSMTP    6 }

    cmcIIISmtpSender        OBJECT-TYPE
        SYNTAX              DisplayString       (SIZE (0..40))
        MAX-ACCESS          read-write
        STATUS              current
        DESCRIPTION         "Sender address (FROM:) of the SMTP message"
        ::=                 { cmcIIISetupSMTP    7 }

    cmcIIISmtpReply         OBJECT-TYPE
        SYNTAX              DisplayString       (SIZE (0..40))
        MAX-ACCESS          read-write
        STATUS              current
        DESCRIPTION         "Reply address (REPLY:) of the SMTP message"
        ::=                 { cmcIIISetupSMTP    8 }

    cmcIIINumberOfSmtpReceivers  OBJECT-TYPE
        SYNTAX              Integer32
        MAX-ACCESS          read-only
        STATUS              current
        DESCRIPTION         "Number of SmtpReceiverTable entries. The number of SMTP receivers"
        ::=                 { cmcIIISetupSMTP    9 }

    cmcIIISmtpReceiverTable  OBJECT-TYPE
        SYNTAX              SEQUENCE OF CmcIIISmtpReceiverEntry
        MAX-ACCESS          not-accessible
        STATUS              current
        DESCRIPTION         "A list of SMTP receiver entries"
        ::=                 { cmcIIISetupSMTP    10 }

    cmcIIISmtpReceiverEntry  OBJECT-TYPE
        SYNTAX              CmcIIISmtpReceiverEntry
        MAX-ACCESS          not-accessible
        STATUS              current
        DESCRIPTION         "Entries of SMTPTable"
        INDEX               { cmcIIISmtpReceiverIndex }
        ::=                 { cmcIIISmtpReceiverTable 1 }

    CmcIIISmtpReceiverEntry  ::=
        SEQUENCE            {
                                cmcIIISmtpReceiverIndex     Unsigned32,
                                cmcIIISmtpReceiverStatus    INTEGER,
                                cmcIIISmtpReceiverAddress   DisplayString
                            }

    cmcIIISmtpReceiverIndex  OBJECT-TYPE
        SYNTAX              Unsigned32          (1..65535)
        MAX-ACCESS          not-accessible
        STATUS              current
        DESCRIPTION         "Index for the SMTP receiver table. Its value ranges between
                            1 and the value of NumberOfSmtpReceivers "
        ::=                 { cmcIIISmtpReceiverEntry 1 }

    cmcIIISmtpReceiverStatus  OBJECT-TYPE
        SYNTAX              INTEGER {
                                disabled	(1),
                                enabled 	(2)
                            }
        MAX-ACCESS          read-write
        STATUS              current
        DESCRIPTION         "Enable or disable SMTP receiver"
        ::=                 { cmcIIISmtpReceiverEntry 2 }

    cmcIIISmtpReceiverAddress  OBJECT-TYPE
        SYNTAX              DisplayString       (SIZE (0..40))
        MAX-ACCESS          read-write
        STATUS              current
        DESCRIPTION         "IP address of SMTP receiver"
        ::=                 { cmcIIISmtpReceiverEntry 3 }

--  cmcIIISetupSMS  --

    cmcIIISmsStatus         OBJECT-TYPE
        SYNTAX              INTEGER {
                                disabled	(1),
                                enabled 	(2)
                            }
        MAX-ACCESS          read-write
        STATUS              current
        DESCRIPTION         "SMS usage:
                            (1) disabled
                            (2) enabled"
        ::=                 { cmcIIISetupSMS     1 }

    cmcIIISmsPIN            OBJECT-TYPE
        SYNTAX              DisplayString       (SIZE (0..4))
        MAX-ACCESS          read-write
        STATUS              current
        DESCRIPTION         "SMS PIN number"
        ::=                 { cmcIIISetupSMS     2 }

    cmcIIISmsService        OBJECT-TYPE
        SYNTAX              DisplayString       (SIZE (0..30))
        MAX-ACCESS          read-write
        STATUS              current
        DESCRIPTION         "SMS service number"
        ::=                 { cmcIIISetupSMS     3 }

    cmcIIISmsMSN            OBJECT-TYPE
        SYNTAX              DisplayString       (SIZE (0..30))
        MAX-ACCESS          read-write
        STATUS              current
        DESCRIPTION         "SMS MSN for ISDN"
        ::=                 { cmcIIISetupSMS     4 }

    cmcIIISmsPreDial        OBJECT-TYPE
        SYNTAX              DisplayString       (SIZE (0..2))
        MAX-ACCESS          read-write
        STATUS              current
        DESCRIPTION         "SMS PreDial number"
        ::=                 { cmcIIISetupSMS     5 }

    cmcIIINumberOfSmsReceivers  OBJECT-TYPE
        SYNTAX              Integer32
        MAX-ACCESS          read-only
        STATUS              current
        DESCRIPTION         "Number of SmsReceiverTable entries. The number of SMS receivers"
        ::=                 { cmcIIISetupSMS     6 }

    cmcIIISmsReceiverTable  OBJECT-TYPE
        SYNTAX              SEQUENCE OF CmcIIISmsReceiverEntry
        MAX-ACCESS          not-accessible
        STATUS              current
        DESCRIPTION         "A list of SMS receiver entries"
        ::=                 { cmcIIISetupSMS     7 }

    cmcIIISmsReceiverEntry  OBJECT-TYPE
        SYNTAX              CmcIIISmsReceiverEntry
        MAX-ACCESS          not-accessible
        STATUS              current
        DESCRIPTION         "Entries of SMSTable"
        INDEX               { cmcIIISmsReceiverIndex }
        ::=                 { cmcIIISmsReceiverTable 1 }

    CmcIIISmsReceiverEntry  ::=
        SEQUENCE            {
                                cmcIIISmsReceiverIndex  Unsigned32,
                                cmcIIISmsReceiverStatus INTEGER,
                                cmcIIISmsReceiverNumber DisplayString
                            }

    cmcIIISmsReceiverIndex  OBJECT-TYPE
        SYNTAX              Unsigned32          (1..65535)
        MAX-ACCESS          not-accessible
        STATUS              current
        DESCRIPTION         "Index for the SMS receiver table. Its value ranges between
                            1 and the value of NumberOfSmsReceivers "
        ::=                 { cmcIIISmsReceiverEntry 1 }

    cmcIIISmsReceiverStatus  OBJECT-TYPE
        SYNTAX              INTEGER {
                                disabled	(1),
                                enabled 	(2)
                            }
        MAX-ACCESS          read-write
        STATUS              current
        DESCRIPTION         "Enable or disable SMS receiver"
        ::=                 { cmcIIISmsReceiverEntry 2 }

    cmcIIISmsReceiverNumber  OBJECT-TYPE
        SYNTAX              DisplayString       (SIZE (0..30))
        MAX-ACCESS          read-write
        STATUS              current
        DESCRIPTION         "Phone number of SMS receiver"
        ::=                 { cmcIIISmsReceiverEntry 3 }

--  cmcIIISetupSysLog  --

    cmcIIISysLogStatus      OBJECT-TYPE
        SYNTAX              INTEGER {
                                disabled	(1),
                                enabled 	(2)
                            }
        MAX-ACCESS          read-write
        STATUS              current
        DESCRIPTION         "SysLog usage:
                            (1) disabled
                            (2) enabled"
        ::=                 { cmcIIISetupSysLog  1 }

    cmcIIISysLogFacility    OBJECT-TYPE
        SYNTAX              INTEGER {
                                local0  	(1),
                                local1  	(2),
                                local2  	(3),
                                local3  	(4),
                                local4  	(5),
                                local5  	(6),
                                local6  	(7),
                                local7  	(8)
                            }
        MAX-ACCESS          read-write
        STATUS              current
        DESCRIPTION         "SysLog facility local0..7"
        ::=                 { cmcIIISetupSysLog  2 }

    cmcIIISysLogServer1     OBJECT-TYPE
        SYNTAX              DisplayString       (SIZE (0..15))
        MAX-ACCESS          read-write
        STATUS              current
        DESCRIPTION         "IP address of first SysLog server"
        ::=                 { cmcIIISetupSysLog  3 }

    cmcIIISysLogServer2     OBJECT-TYPE
        SYNTAX              DisplayString       (SIZE (0..15))
        MAX-ACCESS          read-write
        STATUS              current
        DESCRIPTION         "IP address of second SysLog server"
        ::=                 { cmcIIISetupSysLog  4 }

--  cmcIIISetupNTP  --

    cmcIIINtpStatus         OBJECT-TYPE
        SYNTAX              INTEGER {
                                disabled	(1),
                                enabled 	(2)
                            }
        MAX-ACCESS          read-write
        STATUS              current
        DESCRIPTION         "NTP usage:
                            (1) disabled
                            (2) enabled"
        ::=                 { cmcIIISetupNTP     1 }

    cmcIIINtpTimeZone       OBJECT-TYPE
        SYNTAX              Integer32           (0..74)
        MAX-ACCESS          read-write
        STATUS              current
        DESCRIPTION         "NTP time zone, see cmcIIITimeZone for valid time zones"
        ::=                 { cmcIIISetupNTP     2 }

    cmcIIINtpServer1        OBJECT-TYPE
        SYNTAX              DisplayString       (SIZE (0..15))
        MAX-ACCESS          read-write
        STATUS              current
        DESCRIPTION         "IP address of first NTP server"
        ::=                 { cmcIIISetupNTP     3 }

    cmcIIINtpServer2        OBJECT-TYPE
        SYNTAX              DisplayString       (SIZE (0..15))
        MAX-ACCESS          read-write
        STATUS              current
        DESCRIPTION         "IP address of second NTP server"
        ::=                 { cmcIIISetupNTP     4 }

--  cmcIIISetupLDAP  --

    cmcIIILdapStatus        OBJECT-TYPE
        SYNTAX              INTEGER {
                                disabled	(1),
                                enabled 	(2)
                            }
        MAX-ACCESS          read-write
        STATUS              current
        DESCRIPTION         "LDAP usage:
                            (1) disabled
                            (2) enabled"
        ::=                 { cmcIIISetupLDAP    1 }

    cmcIIILdapServer        OBJECT-TYPE
        SYNTAX              DisplayString       (SIZE (0..15))
        MAX-ACCESS          read-write
        STATUS              current
        DESCRIPTION         "IP address of LDAP server"
        ::=                 { cmcIIISetupLDAP    2 }


--  cmcIIIDevs  --

    cmcIIIOverallDevStatus  OBJECT-TYPE
        SYNTAX              INTEGER {
                                ok      	(1),
                                warning 	(2),
                                alarm   	(3)
                            }
        MAX-ACCESS          read-only
        STATUS              current
        DESCRIPTION         "Overall status of all devices"
        ::=                 { cmcIIIDevInfo      1 }

    cmcIIINumberOfDevs      OBJECT-TYPE
        SYNTAX              Integer32
        MAX-ACCESS          read-only
        STATUS              current
        DESCRIPTION         "Number of devices available"
        ::=                 { cmcIIIDevInfo      2 }

    cmcIIILastChangeOverallDevStatus  OBJECT-TYPE
        SYNTAX              TimeTicks
        MAX-ACCESS          read-only
        STATUS              current
        DESCRIPTION         "Timestamp of last status change of any device connected to CMCIII PU
                            according to operating time cmcIIIUnitUpTime"
        ::=                 { cmcIIIDevInfo      3 }

    cmcIIILastChangeNumberOfDevs  OBJECT-TYPE
        SYNTAX              TimeTicks
        MAX-ACCESS          read-only
        STATUS              current
        DESCRIPTION         "Timestamp of last device number change
                            according to operating time cmcIIIUnitUpTime"
        ::=                 { cmcIIIDevInfo      4 }

    cmcIIILastChangeDevSettings  OBJECT-TYPE
        SYNTAX              TimeTicks
        MAX-ACCESS          read-only
        STATUS              current
        DESCRIPTION         "Timestamp of last setting change of any device connected to CMCIII PU
                            according to operating time cmcIIIUnitUpTime"
        ::=                 { cmcIIIDevInfo      5 }

    cmcIIILastChangeDevs    OBJECT-TYPE
        SYNTAX              TimeTicks
        MAX-ACCESS          read-only
        STATUS              current
        DESCRIPTION         "Timestamp of last device change
                            according to operating time cmcIIIUnitUpTime"
        ::=                 { cmcIIIDevInfo      6 }


    cmcIIIDevTable          OBJECT-TYPE
        SYNTAX              SEQUENCE OF CmcIIIDevEntry
        MAX-ACCESS          not-accessible
        STATUS              current
        DESCRIPTION         "Headline of device table"
        ::=                 { cmcIIIDevs         2 }

    cmcIIIDevEntry          OBJECT-TYPE
        SYNTAX              CmcIIIDevEntry
        MAX-ACCESS          not-accessible
        STATUS              current
        DESCRIPTION         "Entries of device table"
        INDEX               { cmcIIIDevIndex }
        ::=                 { cmcIIIDevTable     1 }


    CmcIIIDevEntry          ::=
        SEQUENCE            {
                                cmcIIIDevIndex          Unsigned32,
                                cmcIIIDevName           DisplayString,
                                cmcIIIDevAlias          DisplayString,
                                cmcIIIDevType           OBJECT IDENTIFIER,
                                cmcIIIDevNodeID         Integer32,
                                cmcIIIDevStatus         INTEGER,
                                cmcIIIDevArtNr          DisplayString,
                                cmcIIIDevLocation       DisplayString,
                                cmcIIIDevBus            INTEGER,
                                cmcIIIDevPos            Integer32,
                                cmcIIIDevFW             DisplayString,
                                cmcIIIDevHW             DisplayString,
                                cmcIIIDevSerial         DisplayString,
                                cmcIIIDevProductWeek    DisplayString,
                                cmcIIIDevLastChange     TimeTicks,
                                cmcIIIDevURL            DisplayString,
                                cmcIIIDevNumberOfVars   Integer32,
                                cmcIIIDevNumberOfMsgs   Integer32,
                                cmcIIIDevStatusText     DisplayString,
                                cmcIIIDevCurrentMinConsumption  Integer32,
                                cmcIIIDevCurrentMaxConsumption  Integer32,
                                cmcIIIDevEntPhysicalIndex       Integer32
                            }

    cmcIIIDevIndex          OBJECT-TYPE
        SYNTAX              Unsigned32          (1..126)
        MAX-ACCESS          not-accessible
        STATUS              current
        DESCRIPTION         "Index of device connected to CMCIII PU"
        ::=                 { cmcIIIDevEntry     1 }

    cmcIIIDevName           OBJECT-TYPE
        SYNTAX              DisplayString       (SIZE (0..30))
        MAX-ACCESS          read-only
        STATUS              current
        DESCRIPTION         "Name of the device connected to CMCIII PU"
        ::=                 { cmcIIIDevEntry     2 }

    cmcIIIDevAlias          OBJECT-TYPE
        SYNTAX              DisplayString       (SIZE (0..40))
        MAX-ACCESS          read-write
        STATUS              current
        DESCRIPTION         "Descriptional text for device connected to CMCIII PU"
        ::=                 { cmcIIIDevEntry     3 }

    cmcIIIDevType           OBJECT-TYPE
        SYNTAX              OBJECT IDENTIFIER
        MAX-ACCESS          read-only
        STATUS              current
        DESCRIPTION         "Type of device chassis connected to CMCIII PU.
                            The authoritative identification of the device contained
                            in the entity is allocated within the SMI cmcIIIProducts
                            subtree (1.3.6.1.4.1.2606.7.7) and provides an easy and
                            unambiguous means for determining `what kind of box' is
                            connected.
                            E.g.: in cmcIIIProductChassis (1.3.6.1.4.1.2606.7.7.4.x)
                            the placeholder x is used for
                            
                            1 : Not Available
                            2 : Internal Device of Processing Unit
                            3 : Virtual Device
                            4 : Temperature Sensor 7030.110
                            5 : Temp/Humidity Sensor 7030.111
                            6 : Vandalism Sensor 7030.130
                            7 : Access Sensor 7030.120
                            8 : Door Lock Device 7030.200, .210
                            9 : Universal Sensor 7030.190
                            10: Sensor Gateway 7030.100
                            11: Power Unit 7030.050
                            12: Pressure Sensor 7030.150
                            20-25: Gateways to RS422, RS485"
        ::=                 { cmcIIIDevEntry     4 }

    cmcIIIDevNodeID         OBJECT-TYPE
        SYNTAX              Integer32
        MAX-ACCESS          read-only
        STATUS              current
        DESCRIPTION         "Node ID of device connected to CMCIII PU"
        ::=                 { cmcIIIDevEntry     5 }

    cmcIIIDevStatus         OBJECT-TYPE
        SYNTAX              INTEGER {
                                notAvail	(1),
                                ok      	(2),
                                detect  	(3),
                                lost    	(4),
                                changed 	(5),
                                error   	(6)
                            }
        MAX-ACCESS          read-only
        STATUS              current
        DESCRIPTION         "General Status of device connected to CMCIII PU
                            (1) Device not available
                            (2) OK
                            (3) Device detected, confirmation required
                            (4) Device lost (disconnected), confirmation required
                            (5) Device changed
                            (6) Error"
        ::=                 { cmcIIIDevEntry     6 }

    cmcIIIDevArtNr          OBJECT-TYPE
        SYNTAX              DisplayString       (SIZE (0..10))
        MAX-ACCESS          read-only
        STATUS              current
        DESCRIPTION         "Article number of device connected to CMCIII PU"
        ::=                 { cmcIIIDevEntry     7 }

    cmcIIIDevLocation       OBJECT-TYPE
        SYNTAX              DisplayString       (SIZE (0..40))
        MAX-ACCESS          read-write
        STATUS              current
        DESCRIPTION         "Location of device connected to CMCIII PU"
        ::=                 { cmcIIIDevEntry     8 }

    cmcIIIDevBus            OBJECT-TYPE
        SYNTAX              INTEGER {
                                canBus1 	(1),
                                canBus2 	(2),
								virtual     (3)
                            }
        MAX-ACCESS          read-only
        STATUS              current
        DESCRIPTION         "CAN bus of device connected to CMCIII PU"
        ::=                 { cmcIIIDevEntry     9 }

    cmcIIIDevPos            OBJECT-TYPE
        SYNTAX              Integer32
        MAX-ACCESS          read-only
        STATUS              current
        DESCRIPTION         "Position (order) of device in CAN bus connected to CMCIII PU"
        ::=                 { cmcIIIDevEntry     10 }

    cmcIIIDevFW             OBJECT-TYPE
        SYNTAX              DisplayString       (SIZE (0..12))
        MAX-ACCESS          read-only
        STATUS              current
        DESCRIPTION         "FW version of device connected to CMCIII PU"
        ::=                 { cmcIIIDevEntry     11 }

    cmcIIIDevHW             OBJECT-TYPE
        SYNTAX              DisplayString       (SIZE (0..12))
        MAX-ACCESS          read-only
        STATUS              current
        DESCRIPTION         "HW version of device connected to CMCIII PU"
        ::=                 { cmcIIIDevEntry     12 }

    cmcIIIDevSerial         OBJECT-TYPE
        SYNTAX              DisplayString       (SIZE (8..8))
        MAX-ACCESS          read-only
        STATUS              current
        DESCRIPTION         "Serial number of device connected to CMCIII PU"
        ::=                 { cmcIIIDevEntry     13 }

    cmcIIIDevProductWeek    OBJECT-TYPE
        SYNTAX              DisplayString       (SIZE (8..8))
        MAX-ACCESS          read-only
        STATUS              current
        DESCRIPTION         "Production week of device connected to CMCIII PU"
        ::=                 { cmcIIIDevEntry     14 }

    cmcIIIDevLastChange     OBJECT-TYPE
        SYNTAX              TimeTicks
        MAX-ACCESS          read-only
        STATUS              current
        DESCRIPTION         "Timestamp of last change of device connected to CMCIII PU
                            according to operating time cmcIIIUnitUpTime"
        ::=                 { cmcIIIDevEntry     15 }

    cmcIIIDevURL            OBJECT-TYPE
        SYNTAX              DisplayString       (SIZE (0..30))
        MAX-ACCESS          read-only
        STATUS              current
        DESCRIPTION         "URL to device page of CMCIII PU (if available)"
        ::=                 { cmcIIIDevEntry     16 }

    cmcIIIDevNumberOfVars   OBJECT-TYPE
        SYNTAX              Integer32
        MAX-ACCESS          read-only
        STATUS              current
        DESCRIPTION         "Number of variables available on this device.
                            This variable will give the number of rows of the 
                            variable table cmcIIIVarTable belonging to this device"
        ::=                 { cmcIIIDevEntry     17 }

    cmcIIIDevNumberOfMsgs   OBJECT-TYPE
        SYNTAX              Integer32
        MAX-ACCESS          read-only
        STATUS              current
        DESCRIPTION         "Number of messages available in this device.
                            This variable will give the number of rows of the message
                            table cmcIIIMsgTable belonging to this device"
        ::=                 { cmcIIIDevEntry     18 }

    cmcIIIDevStatusText     OBJECT-TYPE
        SYNTAX              DisplayString       (SIZE (0..160))
        MAX-ACCESS          read-only
        STATUS              current
        DESCRIPTION         "Latest status of this device"
        ::=                 { cmcIIIDevEntry     19 }

    cmcIIIDevCurrentMinConsumption  OBJECT-TYPE
        SYNTAX              Integer32
        MAX-ACCESS          read-only
        STATUS              current
        DESCRIPTION         "Standby power consumption of device in mA"
        ::=                 { cmcIIIDevEntry     20 }

    cmcIIIDevCurrentMaxConsumption  OBJECT-TYPE
        SYNTAX              Integer32
        MAX-ACCESS          read-only
        STATUS              current
        DESCRIPTION         "Maximal power consumption of device in mA"
        ::=                 { cmcIIIDevEntry     21 }

    cmcIIIDevEntPhysicalIndex  OBJECT-TYPE
        SYNTAX              Integer32
        MAX-ACCESS          read-only
        STATUS              current
        DESCRIPTION         "Corresponding entPhysicalIndex of this device. 0 if none exists."
        ::=                 { cmcIIIDevEntry     22 }


--  cmcIIIVars  --

    cmcIIINumberOfVars      OBJECT-TYPE
        SYNTAX              Integer32
        MAX-ACCESS          read-only
        STATUS              current
        DESCRIPTION         "Total number of variables available"
        ::=                 { cmcIIIVarInfo      1 }

    cmcIIILastChangeNumberOfVars  OBJECT-TYPE
        SYNTAX              TimeTicks
        MAX-ACCESS          read-only
        STATUS              current
        DESCRIPTION         "Timestamp of last message number change
                            according to operating time cmcIIIUnitUpTime"
        ::=                 { cmcIIIVarInfo      2 }

    cmcIIILastChangeVarSettings  OBJECT-TYPE
        SYNTAX              TimeTicks
        MAX-ACCESS          read-only
        STATUS              current
        DESCRIPTION         "Timestamp of last setting change
                            according to operating time cmcIIIUnitUpTime"
        ::=                 { cmcIIIVarInfo      3 }

    cmcIIILastChangeVars    OBJECT-TYPE
        SYNTAX              TimeTicks
        MAX-ACCESS          read-only
        STATUS              current
        DESCRIPTION         "Timestamp of last variable change
                            according to operating time cmcIIIUnitUpTime"
        ::=                 { cmcIIIVarInfo      4 }

-- table with entry for each variable available on this unit

    cmcIIIVarTable          OBJECT-TYPE
        SYNTAX              SEQUENCE OF CmcIIIVariableEntry
        MAX-ACCESS          not-accessible
        STATUS              current
        DESCRIPTION         "Headline of variable table"
        ::=                 { cmcIIIVars         2 }

    cmcIIIVarEntry          OBJECT-TYPE
        SYNTAX              CmcIIIVariableEntry
        MAX-ACCESS          not-accessible
        STATUS              current
        DESCRIPTION         "Entries of variable table"
        INDEX               { cmcIIIDevIndex,cmcIIIVarIndex }
        ::=                 { cmcIIIVarTable     1 }

    CmcIIIVariableEntry     ::=
        SEQUENCE            {
                                cmcIIIVarDeviceIndex    Unsigned32,
                                cmcIIIVarIndex          Unsigned32,
                                cmcIIIVarName           DisplayString,
                                cmcIIIVarType           INTEGER,
                                cmcIIIVarUnit           DisplayString,
                                cmcIIIVarDatatype       INTEGER,
                                cmcIIIVarScale          Integer32,
                                cmcIIIVarConstraints    DisplayString,
                                cmcIIIVarSteps          Integer32,
                                cmcIIIVarValueStr       DisplayString,
                                cmcIIIVarValueInt       Integer32,
                                cmcIIIVarLastChange     TimeTicks,
                                cmcIIIVarAccess         INTEGER,
                                cmcIIIVarQuality        INTEGER,
                                cmcIIIVarEntPhysicalIndex   Integer32
                            }

    cmcIIIVarDeviceIndex    OBJECT-TYPE
        SYNTAX              Unsigned32          (1..65535)
        MAX-ACCESS          not-accessible
        STATUS              current
        DESCRIPTION         "Index for the device. Its value ranges
                            between 1 and the value of cmcIIINumberOfDevs."
        ::=                 { cmcIIIVarEntry     1 }

    cmcIIIVarIndex          OBJECT-TYPE
        SYNTAX              Unsigned32          (1..65535)
        MAX-ACCESS          not-accessible
        STATUS              current
        DESCRIPTION         "Index for the list of value entries. Its value ranges
                            between 1 and the value of cmcIIINumberOfVars."
        ::=                 { cmcIIIVarEntry     2 }

    cmcIIIVarName           OBJECT-TYPE
        SYNTAX              DisplayString       (SIZE (0..30))
        MAX-ACCESS          read-only
        STATUS              current
        DESCRIPTION         "Clear name of variable"
        ::=                 { cmcIIIVarEntry     3 }

    cmcIIIVarType           OBJECT-TYPE
        SYNTAX              INTEGER {
                                description	(1),
                                value   	(2),
                                setHigh 	(3),
                                setWarn 	(4),
                                setLow  	(5),
                                hysteresis	(6),
                                status  	(7),
                                statusEnum	(8),
                                setWarnLow	(9),
                                unit    	(10),
                                alarmDur	(11),
                                steps   	(12),
                                configPar	(13),
                                category	(14),
                                logic           (15),
                                logicEnum       (16),
                                output  	(20),
                                outputdelay	(21),
                                outputaction	(22),
                                sensitivity	(30),
                                accessTime      (31),
                                outputPWM	(40),
                                rotation	(41),
                                productDate	(50),
                                orderNr 	(51),
                                devName 	(52),
                                devLocation	(53),
                                keycode         (80),
                                command         (81),
                                commandEnum     (82),
                                commandKeypad   (83),
                                unitType        (90),
                                swVersion       (91),
                                serialNumber    (92),
                                position        (93),
                                ignore  	(254),
                                illegal 	(255)
                            }

        MAX-ACCESS          read-only
        STATUS              current
        DESCRIPTION         "Type of variable"
        ::=                 { cmcIIIVarEntry     4 }

    cmcIIIVarUnit           OBJECT-TYPE
        SYNTAX              DisplayString       (SIZE (0..12))
        MAX-ACCESS          read-only
        STATUS              current
        DESCRIPTION         "Unit of variable e. g. degree C"
        ::=                 { cmcIIIVarEntry     5 }

    cmcIIIVarDatatype       OBJECT-TYPE
        SYNTAX              INTEGER {
                                notAvail	(1),
                                int     	(2),
                                string  	(3),
                                enum    	(4)
                            }
        MAX-ACCESS          read-only
        STATUS              current
        DESCRIPTION         "Datatype of variable"
        ::=                 { cmcIIIVarEntry     6 }

    cmcIIIVarScale          OBJECT-TYPE
        SYNTAX              Integer32
        MAX-ACCESS          read-only
        STATUS              current
        DESCRIPTION         "Scaling factor of variable value,
                            e. g. -100 -> value has to be divided by 100
                            +100 -> value has to be multiplied by 100"
        ::=                 { cmcIIIVarEntry     7 }

    cmcIIIVarConstraints    OBJECT-TYPE
        SYNTAX              DisplayString       (SIZE (0..64))
        MAX-ACCESS          read-only
        STATUS              current
        DESCRIPTION         "Constraints of value, 
                            e. g. [-_ a-zA-Z0-9]+ (if VariableDatatype is 'string')"
        ::=                 { cmcIIIVarEntry     8 }

    cmcIIIVarSteps          OBJECT-TYPE
        SYNTAX              Integer32
        MAX-ACCESS          read-only
        STATUS              current
        DESCRIPTION         "Steps of variable value (resolution)"
        ::=                 { cmcIIIVarEntry     9 }

    cmcIIIVarValueStr       OBJECT-TYPE
        SYNTAX              DisplayString       (SIZE (0..40))
        MAX-ACCESS          read-write
        STATUS              current
        DESCRIPTION         "Value as string, including sign (+/-) and unit (deg C)"
        ::=                 { cmcIIIVarEntry     10 }

    cmcIIIVarValueInt       OBJECT-TYPE
        SYNTAX              Integer32
        MAX-ACCESS          read-write
        STATUS              current
        DESCRIPTION         "Value as int"
        ::=                 { cmcIIIVarEntry     11 }

    cmcIIIVarLastChange     OBJECT-TYPE
        SYNTAX              TimeTicks
        MAX-ACCESS          read-only
        STATUS              current
        DESCRIPTION         "Timestamp of last update or change
                            according to operating time cmcIIIUnitUpTime"
        ::=                 { cmcIIIVarEntry     12 }

    cmcIIIVarAccess         OBJECT-TYPE
        SYNTAX              INTEGER {
                                none    	(1),
                                readonly	(2),
                                readwrite	(3),
                                readwriteswitch	(4),
                                readwriteextended	(5)
                            }
        MAX-ACCESS          read-only
        STATUS              current
        DESCRIPTION         "Access for value"
        ::=                 { cmcIIIVarEntry     13 }

    cmcIIIVarQuality        OBJECT-TYPE
        SYNTAX              INTEGER {
                                undefined	(1),
                                ok      	(2),
                                warning 	(3),
                                alarm   	(4),
                                common  	(5)
                            }
        MAX-ACCESS          read-only
        STATUS              current
        DESCRIPTION         "Quality of variable"
        ::=                 { cmcIIIVarEntry     14 }

    cmcIIIVarEntPhysicalIndex  OBJECT-TYPE
        SYNTAX              Integer32
        MAX-ACCESS          read-only
        STATUS              current
        DESCRIPTION         "Corresponding entPhysicalIndex of this variable. 0 if none exists."
        ::=                 { cmcIIIVarEntry     15 }


--  cmcIIIMsgs  --

    cmcIIIOverallMsgStatus  OBJECT-TYPE
        SYNTAX              INTEGER {
                                ok      	(1),
                                warning 	(2),
                                alarm   	(3)
                            }
        MAX-ACCESS          read-only
        STATUS              current
        DESCRIPTION         "Overall message status of device"
        ::=                 { cmcIIIMsgInfo      1 }

    cmcIIINumberOfMsgs      OBJECT-TYPE
        SYNTAX              Integer32
        MAX-ACCESS          read-only
        STATUS              current
        DESCRIPTION         "Number of messages. 
        		    All status vars available in cmcIIIVarTable will cause a message in cmcIIIMsgTable."
        ::=                 { cmcIIIMsgInfo      2 }

    cmcIIILastChangeOverallMsgStatus  OBJECT-TYPE
        SYNTAX              TimeTicks
        MAX-ACCESS          read-only
        STATUS              current
        DESCRIPTION         "Timestamp of last status change
                            according to operating time cmcIIIUnitUpTime"
        ::=                 { cmcIIIMsgInfo      3 }

    cmcIIILastChangeNumberOfMsgs  OBJECT-TYPE
        SYNTAX              TimeTicks
        MAX-ACCESS          read-only
        STATUS              current
        DESCRIPTION         "Timestamp of last message number change
                            according to operating time cmcIIIUnitUpTime"
        ::=                 { cmcIIIMsgInfo      4 }

    cmcIIILastChangeMsgSettings  OBJECT-TYPE
        SYNTAX              TimeTicks
        MAX-ACCESS          read-only
        STATUS              current
        DESCRIPTION         "Timestamp of last setting change
                            according to operating time cmcIIIUnitUpTime"
        ::=                 { cmcIIIMsgInfo      5 }


-- table with entry for each alarm available on this unit

    cmcIIIMsgTable          OBJECT-TYPE
        SYNTAX              SEQUENCE OF CmcIIIMsgEntry
        MAX-ACCESS          not-accessible
        STATUS              current
        DESCRIPTION         "Headline of message table"
        ::=                 { cmcIIIMsgs         2 }

    cmcIIIMsgEntry          OBJECT-TYPE
        SYNTAX              CmcIIIMsgEntry
        MAX-ACCESS          not-accessible
        STATUS              current
        DESCRIPTION         "Entries of message table"
        INDEX               { cmcIIIDevIndex,cmcIIIMsgIndex }
        ::=                 { cmcIIIMsgTable     1 }

    CmcIIIMsgEntry          ::=
        SEQUENCE            {
                                cmcIIIMsgDeviceIndex    Unsigned32,
                                cmcIIIMsgIndex          Unsigned32,
                                cmcIIIMsgText           DisplayString,
                                cmcIIIMsgStatus         INTEGER,
                                cmcIIIMsgRelay          INTEGER,
                                cmcIIIMsgBeeper         INTEGER,
                                cmcIIIMsgTrap           BITS,
                                cmcIIIMsgSMTP           BITS,
                                cmcIIIMsgSMS            BITS,
                                cmcIIIMsgQuit           INTEGER,
                                cmcIIIMsgDelay          Unsigned32,
                                cmcIIIMsgSchedAlarmOff  Integer32,
                                cmcIIIMsgQuality        INTEGER,
                                cmcIIIMsgVarIdx         Integer32,
                                cmcIIIMsgVarValueIdx    Integer32,
                                cmcIIIMsgStatusText     DisplayString
                            }

    cmcIIIMsgDeviceIndex    OBJECT-TYPE
        SYNTAX              Unsigned32          (1..65535)
        MAX-ACCESS          not-accessible
        STATUS              current
        DESCRIPTION         "Index for the device. Its value ranges
                            between 1 and the value of cmcIIINumberOfDevs."
        ::=                 { cmcIIIMsgEntry     1 }

    cmcIIIMsgIndex          OBJECT-TYPE
        SYNTAX              Unsigned32          (1..65535)
        MAX-ACCESS          not-accessible
        STATUS              current
        DESCRIPTION         "Index for the list of message entries. Its value ranges
                            between 1 and the value of cmcIIINumberOfMsgs."
        ::=                 { cmcIIIMsgEntry     2 }

    cmcIIIMsgText           OBJECT-TYPE
        SYNTAX              DisplayString       (SIZE (0..40))
        MAX-ACCESS          read-only
        STATUS              current
        DESCRIPTION         "Text for each message (entry in the table)"
        ::=                 { cmcIIIMsgEntry     3 }

    cmcIIIMsgStatus         OBJECT-TYPE
        SYNTAX              INTEGER {
                                notAvail	(1),
                                configChanged	(2),
                                error   	(3),
                                ok      	(4),
                                alarm   	(5),
                                highWarn	(6),
                                lowAlarm	(7),
                                highAlarm	(8),
                                lowWarn 	(9),
                                setOff  	(10),
                                setOn   	(11),
                                open    	(12),
                                closed  	(13),
                                locked  	(14),
                                unlRemote	(15),
                                doorOpen	(16),
                                unlSNMP 	(17),
                                unlWEB  	(18),
                                unlTimer	(19),
                                noAccess	(20),
                                circuit1	(21),
                                circuit2	(22),
                                lowbatt 	(23),
                                probeopen	(24),
                                probeshort	(25),
                                calibration	(26),
                                inactive    (27),
                                active      (28),
								noPower		(29)
                            }
        MAX-ACCESS          read-only
        STATUS              current
        DESCRIPTION         "Actual message status
                            1: not available
                            2: configuration has changed (sensor new, changed, lost)
                            3: error
                            4: OK
                            5: alarm, e.g. smoke, vibration...
                            6: warning of analog value, value reached high warning threshold
                            7: analog value too low, value reached low threshold (Alarm)
                            8: analog value too high, value reached high threshold (Alarm)
                            9: warning of analog value, value reached low warning threshold
                            10: output is set to OFF
                            11: output is set to ON
                            12: door is open
                            13: door is closed
                            14: door is locked
                            15: door is unlocked by remote input, e.g. external card reader
                            16: door is unlocked by reader or keypad connected
                            17: door is unlocked by SNMP set command
                            18: door is unlocked by WEB
                            19: door is unlocked by timer
                            20: no access, wrong key code or card number
                            21: orientation of PSM unit is circuit 1
                            22: orientation of PSM unit is circuit 2
                            23: battery low, wireless sensor
                            24: sensor cable broken
                            25: sensor cable short
                            26: sensor calibration in progress
                            27: sensor is inactive
                            28: sensor is active
							29: no Power (PSM)"
        ::=                 { cmcIIIMsgEntry     4 }

    cmcIIIMsgRelay          OBJECT-TYPE
        SYNTAX              INTEGER {
                                disable 	(1),
                                enable  	(2)
                            }
        MAX-ACCESS          read-write
        STATUS              current
        DESCRIPTION         "Setup of Alarm relay for this message/alarm
                            1:        no switching of alarm relay
                            2:        switching of alarm relay"
        ::=                 { cmcIIIMsgEntry     5 }

    cmcIIIMsgBeeper         OBJECT-TYPE
        SYNTAX              INTEGER {
                                disable 	(1),
                                enable  	(2)
                            }
        MAX-ACCESS          read-write
        STATUS              current
        DESCRIPTION         "Setup of Alarm beeper for this alarm
                            1:        no audible alarm
                            2:        audible alarm"
        ::=                 { cmcIIIMsgEntry     6 }

    cmcIIIMsgTrap           OBJECT-TYPE
        SYNTAX              BITS {
                                receiver1	(0),
                                receiver2	(1),
                                receiver3	(2),
                                receiver4	(3),
                                receiver5	(4),
                                receiver6	(5),
                                receiver7	(6),
                                receiver8	(7),
                                receiver9	(8),
                                receiver10	(9),
                                receiver11	(10),
                                receiver12	(11),
                                receiver13	(12),
                                receiver14	(13),
                                receiver15	(14),
                                receiver16	(15)
                            }
        MAX-ACCESS          read-write
        STATUS              current
        DESCRIPTION         "Each bit is representing an entry of cmcIIITrapReceiverTable.
                            If the corresponding cmcIIITrapReceiverStatus is enabled
                            setting this bit enables sending messages to this receiver."
        ::=                 { cmcIIIMsgEntry     7 }

    cmcIIIMsgSMTP           OBJECT-TYPE
        SYNTAX              BITS {
                                receiver1	(0),
                                receiver2	(1),
                                receiver3	(2),
                                receiver4	(3),
                                receiver5	(4),
                                receiver6	(5),
                                receiver7	(6),
                                receiver8	(7),
                                receiver9	(8),
                                receiver10	(9),
                                receiver11	(10),
                                receiver12	(11),
                                receiver13	(12),
                                receiver14	(13),
                                receiver15	(14),
                                receiver16	(15)
                            }
        MAX-ACCESS          read-write
        STATUS              current
        DESCRIPTION         "Each bit is representing an entry of cmcIIISmtpReceiverTable.
                            If the corresponding cmcIIISmtpReceiverStatus is enabled
                            setting this bit enables sending messages to this receiver."
        ::=                 { cmcIIIMsgEntry     8 }

    cmcIIIMsgSMS            OBJECT-TYPE
        SYNTAX              BITS {
                                receiver1	(0),
                                receiver2	(1),
                                receiver3	(2),
                                receiver4	(3),
                                receiver5	(4),
                                receiver6	(5),
                                receiver7	(6),
                                receiver8	(7),
                                receiver9	(8),
                                receiver10	(9),
                                receiver11	(10),
                                receiver12	(11),
                                receiver13	(12),
                                receiver14	(13),
                                receiver15	(14),
                                receiver16	(15)
                            }
        MAX-ACCESS          read-write
        STATUS              current
        DESCRIPTION         "Each bit is representing an entry of cmcIIISmsReceiverTable.
                            If the corresponding cmcIIISmsReceiverStatus is enabled
                            setting this bit enables sending messages to this receiver."
        ::=                 { cmcIIIMsgEntry     9 }

    cmcIIIMsgQuit           OBJECT-TYPE
        SYNTAX              INTEGER {
                                auto    	(1),
                                manual  	(2)
                            }
        MAX-ACCESS          read-write
        STATUS              current
        DESCRIPTION         "Reset of this alarm
                            1:  auto
                            2:  manual, alarm needs confirmation, e. g. with 'C' key"
        ::=                 { cmcIIIMsgEntry     10 }

    cmcIIIMsgDelay          OBJECT-TYPE
        SYNTAX              Unsigned32
        MAX-ACCESS          read-write
        STATUS              current
        DESCRIPTION         "Delay of alarm condition"
        ::=                 { cmcIIIMsgEntry     11 }

    cmcIIIMsgSchedAlarmOff  OBJECT-TYPE
        SYNTAX              Integer32
        MAX-ACCESS          read-write
        STATUS              current
        DESCRIPTION         "Alarm condition disabled by scheduler"
        ::=                 { cmcIIIMsgEntry     12 }

    cmcIIIMsgQuality        OBJECT-TYPE
        SYNTAX              INTEGER {
                                undefined	(1),
                                ok      	(2),
                                warning 	(3),
                                alarm   	(4),
                                common  	(5)
                            }
        MAX-ACCESS          read-only
        STATUS              current
        DESCRIPTION         "Quality of variable"
        ::=                 { cmcIIIMsgEntry     13 }

    cmcIIIMsgVarIdx         OBJECT-TYPE
        SYNTAX              Integer32
        MAX-ACCESS          read-only
        STATUS              current
        DESCRIPTION         "Index of variable 'Status' in variable table generating this message"
        ::=                 { cmcIIIMsgEntry     14 }

    cmcIIIMsgVarValueIdx    OBJECT-TYPE
        SYNTAX              Integer32
        MAX-ACCESS          read-write
        STATUS              current
        DESCRIPTION         "Index of variable 'Value' in the variable table"
        ::=                 { cmcIIIMsgEntry     15 }

    cmcIIIMsgStatusText     OBJECT-TYPE
        SYNTAX              DisplayString       (SIZE (0..160))
        MAX-ACCESS          read-only
        STATUS              current
        DESCRIPTION         "Message status text"
        ::=                 { cmcIIIMsgEntry     16 }


--  cmcIIIControl  --

    cmcIIIQuitUnit          OBJECT-TYPE
        SYNTAX              INTEGER {
                                noQuit  	(1),
                                quit    	(2)
                            }
        MAX-ACCESS          read-write
        STATUS              current
        DESCRIPTION         "Command to quit (acknowledge) alarms of CMCIII unit.
                            Setting to 'quit' (2) will have same result as pressing 'C' on CMCIII.
                            Variable is automatically set back to 'noQuit' (1)."
        ::=                 { cmcIIIControl      1 }

    cmcIIISmsQueue          OBJECT-TYPE
        SYNTAX              DisplayString       (SIZE (0..180))
        MAX-ACCESS          read-write
        STATUS              current
        DESCRIPTION         "Fast track to send a SMS message based on configuration of 
                            cmcIIISetupSMS.
                            Message format: MessageText TabulatorAsSeparator ReceiverPhoneNumber
                            e.g.: Hello World!\t0123456789"
        ::=                 { cmcIIIControl      2 }


--  Traps  --

    alarmSensorDevice       NOTIFICATION-TYPE
        OBJECTS             {
                                cmcIIIDevName, 
                                cmcIIIMsgText, 
                                cmcIIIMsgStatus, 
                                cmcIIIMsgStatusText
                            }
        STATUS              current
        DESCRIPTION         "Alarm of sensors of device"
--            #TYPE         "Sensor unit alarm"
--            #SUMMARY      "Device: %s, Message %s, Status: %s, Text: %s"
--            #ARGUMENTS    {0,1,2,3}
--            #SEVERITY     MAJOR
--            #TIMEINDEX    6
--            #STATE        OPERATIONAL
        ::=                 { cmcIIINotifications 1 }


    alarmDevice             NOTIFICATION-TYPE
        OBJECTS             {
                                cmcIIIDevName, 
                                cmcIIIDevAlias, 
                                cmcIIIDevStatus, 
                                cmcIIIDevStatusText
                            }
        STATUS              current
        DESCRIPTION         "Alarm of device"
--            #TYPE         "Device alarm"
--            #SUMMARY      "Device: %s, Alias %s, Status: %s, Text: %s"
--            #ARGUMENTS    {0,1,2,3}
--            #SEVERITY     MAJOR
--            #TIMEINDEX    6
--            #STATE        OPERATIONAL
        ::=                 { cmcIIINotifications 2 }


--  Compliance Statements  --

    cmcIIIMibCompliance     MODULE-COMPLIANCE
        STATUS              current
        DESCRIPTION         "The core compliance statement for all cmcIII implementations."
        MODULE              MANDATORY-GROUPS  {
                                cmcIIITrapGroup,
                                cmcIIINotificationGroup,
                                cmcIIIInfoMibGroup,
                                cmcIIISetupMibGroup,
                                cmcIIIDeviceMibGroup
                            }
                            
        GROUP               cmcIIITrapGroup
        DESCRIPTION         "trap handling"

        GROUP               cmcIIINotificationGroup
        DESCRIPTION         "notification handling"

        GROUP               cmcIIIInfoMibGroup
        DESCRIPTION         "base information handling"

        GROUP               cmcIIISetupMibGroup
        DESCRIPTION         "setup handling"

        GROUP               cmcIIIDeviceMibGroup
        DESCRIPTION         "device handling"

        GROUP               cmcIIIControlMibGroup
        DESCRIPTION         "device contol"

        ::=                 { cmcIIIMibCompliances 1 }


--  Conformance Groups  --

    cmcIIITrapGroup         OBJECT-GROUP
        OBJECTS             {
                                cmcIIIDevName,
                                cmcIIIDevAlias,
                                cmcIIIDevStatus,
                                cmcIIIDevStatusText,
                                cmcIIIMsgText,
                                cmcIIIMsgStatus,
                                cmcIIIMsgStatusText
                            }
        STATUS              current
        DESCRIPTION         "Conformance group for objects contained in cmcIII notifications."
        ::=                 { cmcIIIMibGroups    1 }

    cmcIIINotificationGroup  NOTIFICATION-GROUP
        NOTIFICATIONS       {
                                alarmSensorDevice,
                                alarmDevice
                            }
        STATUS              current
        DESCRIPTION         "The cmcIII MIB notification group."
        ::=                 { cmcIIIMibGroups    2 }

    cmcIIIInfoMibGroup      OBJECT-GROUP
        OBJECTS             {
                                cmcIIIMibMajRev,
                                cmcIIIMibMinRev,
                                cmcIIIAgentRev,
                                cmcIIIUnitStatus,
                                cmcIIIUnitURL,
                                cmcIIIUnitHWRev,
                                cmcIIIUnitFWRev,
                                cmcIIIUnitOSRev,
                                cmcIIIUnitSerial,
                                cmcIIIUnitProd,
                                cmcIIIUnitType,
                                cmcIIIUnitCurrentSource,
                                cmcIIICan0CurrentConsumption,
                                cmcIIICan1CurrentConsumption,
                                cmcIIIUnitUpTime
                            }
        STATUS              current
        DESCRIPTION         "Conformance group for all cmcIII base information."
        ::=                 { cmcIIIMibGroups    3 }

    cmcIIISetupMibGroup     OBJECT-GROUP
        OBJECTS             {
                                cmcIIILastChangeSetup,
                                cmcIIISetTempUnit,
                                cmcIIISetBeeper,
                                cmcIIIQuitRelay,
                                cmcIIILogicRelay,
                                cmcIIIUnitMsgRelay,
                                cmcIIIFunctionRelay,
                                cmcIIITimeZone,
                                cmcIIISetupDate,
                                cmcIIISetupTime,
                                cmcIIIWebAccess,
                                cmcIIIHttpPort,
                                cmcIIIHttpsPort,
                                cmcIIIFtpAccess,
                                cmcIIIFtpPort,
                                cmcIIISshAccess,
                                cmcIIISshPort,
                                cmcIIITelnetAccess,
                                cmcIIITelnetPort,
                                cmcIIILanguage,
                                cmcIIINumberOfTimers,
                                cmcIIITimerStatus,
                                cmcIIITimerDayOfWeek,
                                cmcIIITimeOn,
                                cmcIIITimeOff,
                                cmcIIITimeControl,
                                cmcIIITimerFunction,
                                cmcIIINumberOfTrapReceivers,
                                cmcIIITrapReceiverStatus,
                                cmcIIITrapReceiverIpAddress,
                                cmcIIISmtpStatus,
                                cmcIIISmtpServer,
                                cmcIIISmtpPort,
                                cmcIIISmtpAuth,
                                cmcIIISmtpUsername,
                                cmcIIISmtpPassword,
                                cmcIIISmtpSender,
                                cmcIIISmtpReply,
                                cmcIIINumberOfSmtpReceivers,
                                cmcIIISmtpReceiverStatus,
                                cmcIIISmtpReceiverAddress,
                                cmcIIISmsStatus,
                                cmcIIISmsPIN,
                                cmcIIISmsService,
                                cmcIIISmsMSN,
                                cmcIIISmsPreDial,
                                cmcIIINumberOfSmsReceivers,
                                cmcIIISmsReceiverStatus,
                                cmcIIISmsReceiverNumber,
                                cmcIIISysLogStatus,
                                cmcIIISysLogFacility,
                                cmcIIISysLogServer1,
                                cmcIIISysLogServer2,
                                cmcIIINtpStatus,
                                cmcIIINtpTimeZone,
                                cmcIIINtpServer1,
                                cmcIIINtpServer2,
                                cmcIIILdapStatus,
                                cmcIIILdapServer
                            }
        STATUS              current
        DESCRIPTION         "Conformance group for all cmcIII setup operations."
        ::=                 { cmcIIIMibGroups    4 }

    cmcIIIDeviceMibGroup    OBJECT-GROUP
        OBJECTS             {
                                cmcIIIOverallDevStatus,
                                cmcIIINumberOfDevs,
                                cmcIIILastChangeOverallDevStatus,
                                cmcIIILastChangeNumberOfDevs,
                                cmcIIILastChangeDevSettings,
                                cmcIIILastChangeDevs,
                                cmcIIIDevName,
                                cmcIIIDevAlias,
                                cmcIIIDevType,
                                cmcIIIDevNodeID,
                                cmcIIIDevStatus,
                                cmcIIIDevArtNr,
                                cmcIIIDevLocation,
                                cmcIIIDevBus,
                                cmcIIIDevPos,
                                cmcIIIDevFW,
                                cmcIIIDevHW,
                                cmcIIIDevSerial,
                                cmcIIIDevProductWeek,
                                cmcIIIDevLastChange,
                                cmcIIIDevURL,
                                cmcIIIDevNumberOfVars,
                                cmcIIIDevNumberOfMsgs,
                                cmcIIIDevStatusText,
                                cmcIIIDevCurrentMinConsumption,
                                cmcIIIDevCurrentMaxConsumption,
                                cmcIIIDevEntPhysicalIndex,
                                cmcIIINumberOfVars,
                                cmcIIILastChangeNumberOfVars,
                                cmcIIILastChangeVarSettings,
                                cmcIIILastChangeVars,
                                cmcIIIVarName,
                                cmcIIIVarType,
                                cmcIIIVarUnit,
                                cmcIIIVarDatatype,
                                cmcIIIVarScale,
                                cmcIIIVarConstraints,
                                cmcIIIVarSteps,
                                cmcIIIVarValueStr,
                                cmcIIIVarValueInt,
                                cmcIIIVarAccess,
                                cmcIIIVarLastChange,
                                cmcIIIVarQuality,
                                cmcIIIVarEntPhysicalIndex,
                                cmcIIIOverallMsgStatus,
                                cmcIIINumberOfMsgs,
                                cmcIIILastChangeOverallMsgStatus,
                                cmcIIILastChangeNumberOfMsgs,
                                cmcIIILastChangeMsgSettings,
                                cmcIIIMsgText,
                                cmcIIIMsgStatus,
                                cmcIIIMsgRelay,
                                cmcIIIMsgBeeper,
                                cmcIIIMsgTrap,
                                cmcIIIMsgSMS,
                                cmcIIIMsgSMTP,
                                cmcIIIMsgQuit,
                                cmcIIIMsgDelay,
                                cmcIIIMsgSchedAlarmOff,
                                cmcIIIMsgQuality,
                                cmcIIIMsgVarIdx,
                                cmcIIIMsgVarValueIdx,
                                cmcIIIMsgStatusText
                            }
        STATUS              current
        DESCRIPTION         "Conformance group for all cmcIII device information."
        ::=                 { cmcIIIMibGroups    5 }

    cmcIIIControlMibGroup   OBJECT-GROUP
        OBJECTS             {
                                cmcIIIQuitUnit,
                                cmcIIISmsQueue
                            }
        STATUS              current
        DESCRIPTION         "Conformance group for all cmcIII control operations."
        ::=                 { cmcIIIMibGroups    6 }
     
END
