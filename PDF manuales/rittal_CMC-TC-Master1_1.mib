-- RITTAL GmbH & Co. KG, Herborn
-- CMC-TC-Master-MIB Version 1.1
-- CMC-TC-Master - DK7320.000
--
-- Management Information Base für SNMP Network Management
--
-- Copyright 2003,2004 Rittal Herborn.
-- All Rights Reserved.
--
-- The information in this document is subject to change without notice.
-- Refer to document "AGB_Software_Rittal.pdf"
--
--******************************************************************************
--Release History
--Date: January 24, 2003 (Version 1.0)
--Revised by DRosenthal
--Date: September 01, 2003 (Version 1.0a)
--Changed: additional hyphens removed in remark lines
--added CR/LF after END, range of integer variables limited to 30000
--Date: September 17, 2004 (Version 1.1)
--Added: cmcTcMasterTcXStatusUnitXMsgQuit, cmcTcMasterTcXControl,
--       new units (FCS, RTT, RLCP, PSM), new sensors, new outputs, new messages
--******************************************************************************

          RITTAL-CMC-TC-MASTER-MIB DEFINITIONS ::= BEGIN

          IMPORTS
           enterprises FROM RFC1155-SMI
           DisplayString FROM RFC1213-MIB
           sysName,sysDescr,sysContact,sysLocation FROM RFC1213-MIB  

           OBJECT-TYPE FROM RFC-1212
           TRAP-TYPE FROM RFC-1215;


  rittal                                    OBJECT IDENTIFIER ::= { enterprises 2606 }
    cmcTcMaster                             OBJECT IDENTIFIER ::= { rittal 5 }
      cmcTcMasterMibRev                     OBJECT IDENTIFIER ::= { cmcTcMaster 1 }
      cmcTcMasterValues                     OBJECT IDENTIFIER ::= { cmcTcMaster 2 }
      cmcTcMasterStatus                     OBJECT IDENTIFIER ::= { cmcTcMaster 3 }
      cmcTcMasterSetup                      OBJECT IDENTIFIER ::= { cmcTcMaster 4 }
        cmcTcMasterSetupGeneral             OBJECT IDENTIFIER ::= { cmcTcMasterSetup 1 }
          cmcTcMasterActionTable1           OBJECT IDENTIFIER ::= { cmcTcMasterSetupGeneral 7 }
        cmcTcMasterSetupDevice              OBJECT IDENTIFIER ::= { cmcTcMasterSetup 2 }
          cmcTcMasterSetupTemperature       OBJECT IDENTIFIER ::= { cmcTcMasterSetupDevice 1 }
      cmcTcMasterSetpoints                  OBJECT IDENTIFIER ::= { cmcTcMaster 5 }
      cmcTcMasterControl                    OBJECT IDENTIFIER ::= { cmcTcMaster 6 }
      cmcTcMasterDevices                    OBJECT IDENTIFIER ::= { cmcTcMaster 7 }
        cmcTcMasterDevice1                  OBJECT IDENTIFIER ::= { cmcTcMasterDevices 1 }
          cmcTcMasterCmc1                   OBJECT IDENTIFIER ::= { cmcTcMasterDevice1 8 }
          cmcTcMasterCmc1Values             OBJECT IDENTIFIER ::= { cmcTcMasterCmc1 1 }
          cmcTcMasterCmc1Table1             OBJECT IDENTIFIER ::= { cmcTcMasterCmc1Values 6 }
          cmcTcMasterCmc1Status             OBJECT IDENTIFIER ::= { cmcTcMasterCmc1 2 }
          cmcTcMasterCmc1Table              OBJECT IDENTIFIER ::= { cmcTcMasterCmc1Status 17 }
          cmcTcMasterCmc1Set                OBJECT IDENTIFIER ::= { cmcTcMasterCmc1 3 }
          cmcTcMasterCmc1RelayControl       OBJECT IDENTIFIER ::= { cmcTcMasterCmc1Set 5 }
          cmcTcMasterCmc1Setpoints          OBJECT IDENTIFIER ::= { cmcTcMasterCmc1 4 }
          cmcTcMasterCmc1TrapControl        OBJECT IDENTIFIER ::= { cmcTcMasterCmc1 5 }
          cmcTcMasterCmc1Traps              OBJECT IDENTIFIER ::= { cmcTcMasterCmc1TrapControl 4 }
          cmcTcMasterPcu1                   OBJECT IDENTIFIER ::= { cmcTcMasterDevice1 10 }
          cmcTcMasterPcu1MibRev             OBJECT IDENTIFIER ::= { cmcTcMasterPcu1 1 }
          cmcTcMasterPcu1Values             OBJECT IDENTIFIER ::= { cmcTcMasterPcu1 2 }
          cmcTcMasterPcu1Status             OBJECT IDENTIFIER ::= { cmcTcMasterPcu1 3 }
          cmcTcMasterPcu1StatusTable1       OBJECT IDENTIFIER ::= { cmcTcMasterPcu1Status 6 }
          cmcTcMasterPcu1Setup              OBJECT IDENTIFIER ::= { cmcTcMasterPcu1 4 }
          cmcTcMasterPcu1SetupGeneral       OBJECT IDENTIFIER ::= { cmcTcMasterPcu1Setup 1 }
          cmcTcMasterPcu1TimerTable1        OBJECT IDENTIFIER ::= { cmcTcMasterPcu1SetupGeneral 8 }
          cmcTcMasterPcu1SetupDevice        OBJECT IDENTIFIER ::= { cmcTcMasterPcu1Setup 2 }
          cmcTcMasterPcu1SetupPower1        OBJECT IDENTIFIER ::= { cmcTcMasterPcu1SetupDevice 2 }
          cmcTcMasterPcu1SetupPower2        OBJECT IDENTIFIER ::= { cmcTcMasterPcu1SetupDevice 3 }
          cmcTcMasterPcu1SetupInput1        OBJECT IDENTIFIER ::= { cmcTcMasterPcu1SetupDevice 4 }
          cmcTcMasterPcu1SetupInput2        OBJECT IDENTIFIER ::= { cmcTcMasterPcu1SetupDevice 5 }
          cmcTcMasterPcu1SetupTemperature   OBJECT IDENTIFIER ::= { cmcTcMasterPcu1SetupDevice 6 }
          cmcTcMasterPcu1Setpoints          OBJECT IDENTIFIER ::= { cmcTcMasterPcu1 5 }
          cmcTcMasterPcu1Control            OBJECT IDENTIFIER ::= { cmcTcMasterPcu1 6 }
          cmcTcMasterPcu1TrapControl        OBJECT IDENTIFIER ::= { cmcTcMasterPcu1 7 }
          cmcTcMasterPcu1Traps              OBJECT IDENTIFIER ::= { cmcTcMasterPcu1TrapControl 7 }
          cmcTcMasterTc1                    OBJECT IDENTIFIER ::= { cmcTcMasterDevice1 11 }
          cmcTcMasterTc1MibRev              OBJECT IDENTIFIER ::= { cmcTcMasterTc1 1 }
          cmcTcMasterTc1Status              OBJECT IDENTIFIER ::= { cmcTcMasterTc1 2 }
          cmcTcMasterTc1StatusSensorUnit1   OBJECT IDENTIFIER ::= { cmcTcMasterTc1Status 3 }
          cmcTcMasterTc1StatusUnit1Sensors  OBJECT IDENTIFIER ::= { cmcTcMasterTc1StatusSensorUnit1 5 }
          cmcTcMasterTc1StatusUnit1Outputs  OBJECT IDENTIFIER ::= { cmcTcMasterTc1StatusSensorUnit1 6 }
          cmcTcMasterTc1StatusUnit1Msg      OBJECT IDENTIFIER ::= { cmcTcMasterTc1StatusSensorUnit1 7 }
          cmcTcMasterTc1StatusSensorUnit2   OBJECT IDENTIFIER ::= { cmcTcMasterTc1Status 4 }
          cmcTcMasterTc1StatusUnit2Sensors  OBJECT IDENTIFIER ::= { cmcTcMasterTc1StatusSensorUnit2 5 }
          cmcTcMasterTc1StatusUnit2Outputs  OBJECT IDENTIFIER ::= { cmcTcMasterTc1StatusSensorUnit2 6 }
          cmcTcMasterTc1StatusUnit2Msg      OBJECT IDENTIFIER ::= { cmcTcMasterTc1StatusSensorUnit2 7 }
          cmcTcMasterTc1StatusSensorUnit3   OBJECT IDENTIFIER ::= { cmcTcMasterTc1Status 5 }
          cmcTcMasterTc1StatusUnit3Sensors  OBJECT IDENTIFIER ::= { cmcTcMasterTc1StatusSensorUnit3 5 }
          cmcTcMasterTc1StatusUnit3Outputs  OBJECT IDENTIFIER ::= { cmcTcMasterTc1StatusSensorUnit3 6 }
          cmcTcMasterTc1StatusUnit3Msg      OBJECT IDENTIFIER ::= { cmcTcMasterTc1StatusSensorUnit3 7 }
          cmcTcMasterTc1StatusSensorUnit4   OBJECT IDENTIFIER ::= { cmcTcMasterTc1Status 6 }
          cmcTcMasterTc1StatusUnit4Sensors  OBJECT IDENTIFIER ::= { cmcTcMasterTc1StatusSensorUnit4 5 }
          cmcTcMasterTc1StatusUnit4Outputs  OBJECT IDENTIFIER ::= { cmcTcMasterTc1StatusSensorUnit4 6 }
          cmcTcMasterTc1StatusUnit4Msg      OBJECT IDENTIFIER ::= { cmcTcMasterTc1StatusSensorUnit4 7 }
          cmcTcMasterTc1StatusExtUnit       OBJECT IDENTIFIER ::= { cmcTcMasterTc1Status 7 }
          cmcTcMasterTc1Setup               OBJECT IDENTIFIER ::= { cmcTcMasterTc1 3 }
          cmcTcMasterTc1SetupGeneral        OBJECT IDENTIFIER ::= { cmcTcMasterTc1Setup 1 }
          cmcTcMasterTc1TimerTable1         OBJECT IDENTIFIER ::= { cmcTcMasterTc1SetupGeneral 8 }
          cmcTcMasterTc1TrapControl         OBJECT IDENTIFIER ::= { cmcTcMasterTc1 4 }
          cmcTcMasterTc1Traps               OBJECT IDENTIFIER ::= { cmcTcMasterTc1TrapControl 7 }
          cmcTcMasterTc1Control             OBJECT IDENTIFIER ::= { cmcTcMasterTc1 5 }
        cmcTcMasterDevice2                  OBJECT IDENTIFIER ::= { cmcTcMasterDevices 2 }
          cmcTcMasterCmc2                   OBJECT IDENTIFIER ::= { cmcTcMasterDevice2 8 }
          cmcTcMasterCmc2Values             OBJECT IDENTIFIER ::= { cmcTcMasterCmc2 1 }
          cmcTcMasterCmc2Table1             OBJECT IDENTIFIER ::= { cmcTcMasterCmc2Values 6 }
          cmcTcMasterCmc2Status             OBJECT IDENTIFIER ::= { cmcTcMasterCmc2 2 }
          cmcTcMasterCmc2Table              OBJECT IDENTIFIER ::= { cmcTcMasterCmc2Status 17 }
          cmcTcMasterCmc2Set                OBJECT IDENTIFIER ::= { cmcTcMasterCmc2 3 }
          cmcTcMasterCmc2RelayControl       OBJECT IDENTIFIER ::= { cmcTcMasterCmc2Set 5 }
          cmcTcMasterCmc2Setpoints          OBJECT IDENTIFIER ::= { cmcTcMasterCmc2 4 }
          cmcTcMasterCmc2TrapControl        OBJECT IDENTIFIER ::= { cmcTcMasterCmc2 5 }
          cmcTcMasterCmc2Traps              OBJECT IDENTIFIER ::= { cmcTcMasterCmc2TrapControl 4 }
          cmcTcMasterPcu2                   OBJECT IDENTIFIER ::= { cmcTcMasterDevice2 10 }
          cmcTcMasterPcu2MibRev             OBJECT IDENTIFIER ::= { cmcTcMasterPcu2 1 }
          cmcTcMasterPcu2Values             OBJECT IDENTIFIER ::= { cmcTcMasterPcu2 2 }
          cmcTcMasterPcu2Status             OBJECT IDENTIFIER ::= { cmcTcMasterPcu2 3 }
          cmcTcMasterPcu2StatusTable1       OBJECT IDENTIFIER ::= { cmcTcMasterPcu2Status 6 }
          cmcTcMasterPcu2Setup              OBJECT IDENTIFIER ::= { cmcTcMasterPcu2 4 }
          cmcTcMasterPcu2SetupGeneral       OBJECT IDENTIFIER ::= { cmcTcMasterPcu2Setup 1 }
          cmcTcMasterPcu2TimerTable1        OBJECT IDENTIFIER ::= { cmcTcMasterPcu2SetupGeneral 8 }
          cmcTcMasterPcu2SetupDevice        OBJECT IDENTIFIER ::= { cmcTcMasterPcu2Setup 2 }
          cmcTcMasterPcu2SetupPower1        OBJECT IDENTIFIER ::= { cmcTcMasterPcu2SetupDevice 2 }
          cmcTcMasterPcu2SetupPower2        OBJECT IDENTIFIER ::= { cmcTcMasterPcu2SetupDevice 3 }
          cmcTcMasterPcu2SetupInput1        OBJECT IDENTIFIER ::= { cmcTcMasterPcu2SetupDevice 4 }
          cmcTcMasterPcu2SetupInput2        OBJECT IDENTIFIER ::= { cmcTcMasterPcu2SetupDevice 5 }
          cmcTcMasterPcu2SetupTemperature   OBJECT IDENTIFIER ::= { cmcTcMasterPcu2SetupDevice 6 }
          cmcTcMasterPcu2Setpoints          OBJECT IDENTIFIER ::= { cmcTcMasterPcu2 5 }
          cmcTcMasterPcu2Control            OBJECT IDENTIFIER ::= { cmcTcMasterPcu2 6 }
          cmcTcMasterPcu2TrapControl        OBJECT IDENTIFIER ::= { cmcTcMasterPcu2 7 }
          cmcTcMasterPcu2Traps              OBJECT IDENTIFIER ::= { cmcTcMasterPcu2TrapControl 7 }
          cmcTcMasterTc2                    OBJECT IDENTIFIER ::= { cmcTcMasterDevice2 11 }
          cmcTcMasterTc2MibRev              OBJECT IDENTIFIER ::= { cmcTcMasterTc2 1 }
          cmcTcMasterTc2Status              OBJECT IDENTIFIER ::= { cmcTcMasterTc2 2 }
          cmcTcMasterTc2StatusSensorUnit1   OBJECT IDENTIFIER ::= { cmcTcMasterTc2Status 3 }
          cmcTcMasterTc2StatusUnit1Sensors  OBJECT IDENTIFIER ::= { cmcTcMasterTc2StatusSensorUnit1 5 }
          cmcTcMasterTc2StatusUnit1Outputs  OBJECT IDENTIFIER ::= { cmcTcMasterTc2StatusSensorUnit1 6 }
          cmcTcMasterTc2StatusUnit1Msg      OBJECT IDENTIFIER ::= { cmcTcMasterTc2StatusSensorUnit1 7 }
          cmcTcMasterTc2StatusSensorUnit2   OBJECT IDENTIFIER ::= { cmcTcMasterTc2Status 4 }
          cmcTcMasterTc2StatusUnit2Sensors  OBJECT IDENTIFIER ::= { cmcTcMasterTc2StatusSensorUnit2 5 }
          cmcTcMasterTc2StatusUnit2Outputs  OBJECT IDENTIFIER ::= { cmcTcMasterTc2StatusSensorUnit2 6 }
          cmcTcMasterTc2StatusUnit2Msg      OBJECT IDENTIFIER ::= { cmcTcMasterTc2StatusSensorUnit2 7 }
          cmcTcMasterTc2StatusSensorUnit3   OBJECT IDENTIFIER ::= { cmcTcMasterTc2Status 5 }
          cmcTcMasterTc2StatusUnit3Sensors  OBJECT IDENTIFIER ::= { cmcTcMasterTc2StatusSensorUnit3 5 }
          cmcTcMasterTc2StatusUnit3Outputs  OBJECT IDENTIFIER ::= { cmcTcMasterTc2StatusSensorUnit3 6 }
          cmcTcMasterTc2StatusUnit3Msg      OBJECT IDENTIFIER ::= { cmcTcMasterTc2StatusSensorUnit3 7 }
          cmcTcMasterTc2StatusSensorUnit4   OBJECT IDENTIFIER ::= { cmcTcMasterTc2Status 6 }
          cmcTcMasterTc2StatusUnit4Sensors  OBJECT IDENTIFIER ::= { cmcTcMasterTc2StatusSensorUnit4 5 }
          cmcTcMasterTc2StatusUnit4Outputs  OBJECT IDENTIFIER ::= { cmcTcMasterTc2StatusSensorUnit4 6 }
          cmcTcMasterTc2StatusUnit4Msg      OBJECT IDENTIFIER ::= { cmcTcMasterTc2StatusSensorUnit4 7 }
          cmcTcMasterTc2StatusExtUnit       OBJECT IDENTIFIER ::= { cmcTcMasterTc2Status 7 }
          cmcTcMasterTc2Setup               OBJECT IDENTIFIER ::= { cmcTcMasterTc2 3 }
          cmcTcMasterTc2SetupGeneral        OBJECT IDENTIFIER ::= { cmcTcMasterTc2Setup 1 }
          cmcTcMasterTc2TimerTable1         OBJECT IDENTIFIER ::= { cmcTcMasterTc2SetupGeneral 8 }
          cmcTcMasterTc2TrapControl         OBJECT IDENTIFIER ::= { cmcTcMasterTc2 4 }
          cmcTcMasterTc2Traps               OBJECT IDENTIFIER ::= { cmcTcMasterTc2TrapControl 7 }
          cmcTcMasterTc2Control             OBJECT IDENTIFIER ::= { cmcTcMasterTc2 5 }
        cmcTcMasterDevice3                  OBJECT IDENTIFIER ::= { cmcTcMasterDevices 3 }
          cmcTcMasterCmc3                   OBJECT IDENTIFIER ::= { cmcTcMasterDevice3 8 }
          cmcTcMasterCmc3Values             OBJECT IDENTIFIER ::= { cmcTcMasterCmc3 1 }
          cmcTcMasterCmc3Table1             OBJECT IDENTIFIER ::= { cmcTcMasterCmc3Values 6 }
          cmcTcMasterCmc3Status             OBJECT IDENTIFIER ::= { cmcTcMasterCmc3 2 }
          cmcTcMasterCmc3Table              OBJECT IDENTIFIER ::= { cmcTcMasterCmc3Status 17 }
          cmcTcMasterCmc3Set                OBJECT IDENTIFIER ::= { cmcTcMasterCmc3 3 }
          cmcTcMasterCmc3RelayControl       OBJECT IDENTIFIER ::= { cmcTcMasterCmc3Set 5 }
          cmcTcMasterCmc3Setpoints          OBJECT IDENTIFIER ::= { cmcTcMasterCmc3 4 }
          cmcTcMasterCmc3TrapControl        OBJECT IDENTIFIER ::= { cmcTcMasterCmc3 5 }
          cmcTcMasterCmc3Traps              OBJECT IDENTIFIER ::= { cmcTcMasterCmc3TrapControl 4 }
          cmcTcMasterPcu3                   OBJECT IDENTIFIER ::= { cmcTcMasterDevice3 10 }
          cmcTcMasterPcu3MibRev             OBJECT IDENTIFIER ::= { cmcTcMasterPcu3 1 }
          cmcTcMasterPcu3Values             OBJECT IDENTIFIER ::= { cmcTcMasterPcu3 2 }
          cmcTcMasterPcu3Status             OBJECT IDENTIFIER ::= { cmcTcMasterPcu3 3 }
          cmcTcMasterPcu3StatusTable1       OBJECT IDENTIFIER ::= { cmcTcMasterPcu3Status 6 }
          cmcTcMasterPcu3Setup              OBJECT IDENTIFIER ::= { cmcTcMasterPcu3 4 }
          cmcTcMasterPcu3SetupGeneral       OBJECT IDENTIFIER ::= { cmcTcMasterPcu3Setup 1 }
          cmcTcMasterPcu3TimerTable1        OBJECT IDENTIFIER ::= { cmcTcMasterPcu3SetupGeneral 8 }
          cmcTcMasterPcu3SetupDevice        OBJECT IDENTIFIER ::= { cmcTcMasterPcu3Setup 2 }
          cmcTcMasterPcu3SetupPower1        OBJECT IDENTIFIER ::= { cmcTcMasterPcu3SetupDevice 2 }
          cmcTcMasterPcu3SetupPower2        OBJECT IDENTIFIER ::= { cmcTcMasterPcu3SetupDevice 3 }
          cmcTcMasterPcu3SetupInput1        OBJECT IDENTIFIER ::= { cmcTcMasterPcu3SetupDevice 4 }
          cmcTcMasterPcu3SetupInput2        OBJECT IDENTIFIER ::= { cmcTcMasterPcu3SetupDevice 5 }
          cmcTcMasterPcu3SetupTemperature   OBJECT IDENTIFIER ::= { cmcTcMasterPcu3SetupDevice 6 }
          cmcTcMasterPcu3Setpoints          OBJECT IDENTIFIER ::= { cmcTcMasterPcu3 5 }
          cmcTcMasterPcu3Control            OBJECT IDENTIFIER ::= { cmcTcMasterPcu3 6 }
          cmcTcMasterPcu3TrapControl        OBJECT IDENTIFIER ::= { cmcTcMasterPcu3 7 }
          cmcTcMasterPcu3Traps              OBJECT IDENTIFIER ::= { cmcTcMasterPcu3TrapControl 7 }
          cmcTcMasterTc3                    OBJECT IDENTIFIER ::= { cmcTcMasterDevice3 11 }
          cmcTcMasterTc3MibRev              OBJECT IDENTIFIER ::= { cmcTcMasterTc3 1 }
          cmcTcMasterTc3Status              OBJECT IDENTIFIER ::= { cmcTcMasterTc3 2 }
          cmcTcMasterTc3StatusSensorUnit1   OBJECT IDENTIFIER ::= { cmcTcMasterTc3Status 3 }
          cmcTcMasterTc3StatusUnit1Sensors  OBJECT IDENTIFIER ::= { cmcTcMasterTc3StatusSensorUnit1 5 }
          cmcTcMasterTc3StatusUnit1Outputs  OBJECT IDENTIFIER ::= { cmcTcMasterTc3StatusSensorUnit1 6 }
          cmcTcMasterTc3StatusUnit1Msg      OBJECT IDENTIFIER ::= { cmcTcMasterTc3StatusSensorUnit1 7 }
          cmcTcMasterTc3StatusSensorUnit2   OBJECT IDENTIFIER ::= { cmcTcMasterTc3Status 4 }
          cmcTcMasterTc3StatusUnit2Sensors  OBJECT IDENTIFIER ::= { cmcTcMasterTc3StatusSensorUnit2 5 }
          cmcTcMasterTc3StatusUnit2Outputs  OBJECT IDENTIFIER ::= { cmcTcMasterTc3StatusSensorUnit2 6 }
          cmcTcMasterTc3StatusUnit2Msg      OBJECT IDENTIFIER ::= { cmcTcMasterTc3StatusSensorUnit2 7 }
          cmcTcMasterTc3StatusSensorUnit3   OBJECT IDENTIFIER ::= { cmcTcMasterTc3Status 5 }
          cmcTcMasterTc3StatusUnit3Sensors  OBJECT IDENTIFIER ::= { cmcTcMasterTc3StatusSensorUnit3 5 }
          cmcTcMasterTc3StatusUnit3Outputs  OBJECT IDENTIFIER ::= { cmcTcMasterTc3StatusSensorUnit3 6 }
          cmcTcMasterTc3StatusUnit3Msg      OBJECT IDENTIFIER ::= { cmcTcMasterTc3StatusSensorUnit3 7 }
          cmcTcMasterTc3StatusSensorUnit4   OBJECT IDENTIFIER ::= { cmcTcMasterTc3Status 6 }
          cmcTcMasterTc3StatusUnit4Sensors  OBJECT IDENTIFIER ::= { cmcTcMasterTc3StatusSensorUnit4 5 }
          cmcTcMasterTc3StatusUnit4Outputs  OBJECT IDENTIFIER ::= { cmcTcMasterTc3StatusSensorUnit4 6 }
          cmcTcMasterTc3StatusUnit4Msg      OBJECT IDENTIFIER ::= { cmcTcMasterTc3StatusSensorUnit4 7 }
          cmcTcMasterTc3StatusExtUnit       OBJECT IDENTIFIER ::= { cmcTcMasterTc3Status 7 }
          cmcTcMasterTc3Setup               OBJECT IDENTIFIER ::= { cmcTcMasterTc3 3 }
          cmcTcMasterTc3SetupGeneral        OBJECT IDENTIFIER ::= { cmcTcMasterTc3Setup 1 }
          cmcTcMasterTc3TimerTable1         OBJECT IDENTIFIER ::= { cmcTcMasterTc3SetupGeneral 8 }
          cmcTcMasterTc3TrapControl         OBJECT IDENTIFIER ::= { cmcTcMasterTc3 4 }
          cmcTcMasterTc3Traps               OBJECT IDENTIFIER ::= { cmcTcMasterTc3TrapControl 7 }
          cmcTcMasterTc3Control             OBJECT IDENTIFIER ::= { cmcTcMasterTc3 5 }
        cmcTcMasterDevice4                  OBJECT IDENTIFIER ::= { cmcTcMasterDevices 4 }
          cmcTcMasterCmc4                   OBJECT IDENTIFIER ::= { cmcTcMasterDevice4 8 }
          cmcTcMasterCmc4Values             OBJECT IDENTIFIER ::= { cmcTcMasterCmc4 1 }
          cmcTcMasterCmc4Table1             OBJECT IDENTIFIER ::= { cmcTcMasterCmc4Values 6 }
          cmcTcMasterCmc4Status             OBJECT IDENTIFIER ::= { cmcTcMasterCmc4 2 }
          cmcTcMasterCmc4Table              OBJECT IDENTIFIER ::= { cmcTcMasterCmc4Status 17 }
          cmcTcMasterCmc4Set                OBJECT IDENTIFIER ::= { cmcTcMasterCmc4 3 }
          cmcTcMasterCmc4RelayControl       OBJECT IDENTIFIER ::= { cmcTcMasterCmc4Set 5 }
          cmcTcMasterCmc4Setpoints          OBJECT IDENTIFIER ::= { cmcTcMasterCmc4 4 }
          cmcTcMasterCmc4TrapControl        OBJECT IDENTIFIER ::= { cmcTcMasterCmc4 5 }
          cmcTcMasterCmc4Traps              OBJECT IDENTIFIER ::= { cmcTcMasterCmc4TrapControl 4 }
          cmcTcMasterPcu4                   OBJECT IDENTIFIER ::= { cmcTcMasterDevice4 10 }
          cmcTcMasterPcu4MibRev             OBJECT IDENTIFIER ::= { cmcTcMasterPcu4 1 }
          cmcTcMasterPcu4Values             OBJECT IDENTIFIER ::= { cmcTcMasterPcu4 2 }
          cmcTcMasterPcu4Status             OBJECT IDENTIFIER ::= { cmcTcMasterPcu4 3 }
          cmcTcMasterPcu4StatusTable1       OBJECT IDENTIFIER ::= { cmcTcMasterPcu4Status 6 }
          cmcTcMasterPcu4Setup              OBJECT IDENTIFIER ::= { cmcTcMasterPcu4 4 }
          cmcTcMasterPcu4SetupGeneral       OBJECT IDENTIFIER ::= { cmcTcMasterPcu4Setup 1 }
          cmcTcMasterPcu4TimerTable1        OBJECT IDENTIFIER ::= { cmcTcMasterPcu4SetupGeneral 8 }
          cmcTcMasterPcu4SetupDevice        OBJECT IDENTIFIER ::= { cmcTcMasterPcu4Setup 2 }
          cmcTcMasterPcu4SetupPower1        OBJECT IDENTIFIER ::= { cmcTcMasterPcu4SetupDevice 2 }
          cmcTcMasterPcu4SetupPower2        OBJECT IDENTIFIER ::= { cmcTcMasterPcu4SetupDevice 3 }
          cmcTcMasterPcu4SetupInput1        OBJECT IDENTIFIER ::= { cmcTcMasterPcu4SetupDevice 4 }
          cmcTcMasterPcu4SetupInput2        OBJECT IDENTIFIER ::= { cmcTcMasterPcu4SetupDevice 5 }
          cmcTcMasterPcu4SetupTemperature   OBJECT IDENTIFIER ::= { cmcTcMasterPcu4SetupDevice 6 }
          cmcTcMasterPcu4Setpoints          OBJECT IDENTIFIER ::= { cmcTcMasterPcu4 5 }
          cmcTcMasterPcu4Control            OBJECT IDENTIFIER ::= { cmcTcMasterPcu4 6 }
          cmcTcMasterPcu4TrapControl        OBJECT IDENTIFIER ::= { cmcTcMasterPcu4 7 }
          cmcTcMasterPcu4Traps              OBJECT IDENTIFIER ::= { cmcTcMasterPcu4TrapControl 7 }
          cmcTcMasterTc4                    OBJECT IDENTIFIER ::= { cmcTcMasterDevice4 11 }
          cmcTcMasterTc4MibRev              OBJECT IDENTIFIER ::= { cmcTcMasterTc4 1 }
          cmcTcMasterTc4Status              OBJECT IDENTIFIER ::= { cmcTcMasterTc4 2 }
          cmcTcMasterTc4StatusSensorUnit1   OBJECT IDENTIFIER ::= { cmcTcMasterTc4Status 3 }
          cmcTcMasterTc4StatusUnit1Sensors  OBJECT IDENTIFIER ::= { cmcTcMasterTc4StatusSensorUnit1 5 }
          cmcTcMasterTc4StatusUnit1Outputs  OBJECT IDENTIFIER ::= { cmcTcMasterTc4StatusSensorUnit1 6 }
          cmcTcMasterTc4StatusUnit1Msg      OBJECT IDENTIFIER ::= { cmcTcMasterTc4StatusSensorUnit1 7 }
          cmcTcMasterTc4StatusSensorUnit2   OBJECT IDENTIFIER ::= { cmcTcMasterTc4Status 4 }
          cmcTcMasterTc4StatusUnit2Sensors  OBJECT IDENTIFIER ::= { cmcTcMasterTc4StatusSensorUnit2 5 }
          cmcTcMasterTc4StatusUnit2Outputs  OBJECT IDENTIFIER ::= { cmcTcMasterTc4StatusSensorUnit2 6 }
          cmcTcMasterTc4StatusUnit2Msg      OBJECT IDENTIFIER ::= { cmcTcMasterTc4StatusSensorUnit2 7 }
          cmcTcMasterTc4StatusSensorUnit3   OBJECT IDENTIFIER ::= { cmcTcMasterTc4Status 5 }
          cmcTcMasterTc4StatusUnit3Sensors  OBJECT IDENTIFIER ::= { cmcTcMasterTc4StatusSensorUnit3 5 }
          cmcTcMasterTc4StatusUnit3Outputs  OBJECT IDENTIFIER ::= { cmcTcMasterTc4StatusSensorUnit3 6 }
          cmcTcMasterTc4StatusUnit3Msg      OBJECT IDENTIFIER ::= { cmcTcMasterTc4StatusSensorUnit3 7 }
          cmcTcMasterTc4StatusSensorUnit4   OBJECT IDENTIFIER ::= { cmcTcMasterTc4Status 6 }
          cmcTcMasterTc4StatusUnit4Sensors  OBJECT IDENTIFIER ::= { cmcTcMasterTc4StatusSensorUnit4 5 }
          cmcTcMasterTc4StatusUnit4Outputs  OBJECT IDENTIFIER ::= { cmcTcMasterTc4StatusSensorUnit4 6 }
          cmcTcMasterTc4StatusUnit4Msg      OBJECT IDENTIFIER ::= { cmcTcMasterTc4StatusSensorUnit4 7 }
          cmcTcMasterTc4StatusExtUnit       OBJECT IDENTIFIER ::= { cmcTcMasterTc4Status 7 }
          cmcTcMasterTc4Setup               OBJECT IDENTIFIER ::= { cmcTcMasterTc4 3 }
          cmcTcMasterTc4SetupGeneral        OBJECT IDENTIFIER ::= { cmcTcMasterTc4Setup 1 }
          cmcTcMasterTc4TimerTable1         OBJECT IDENTIFIER ::= { cmcTcMasterTc4SetupGeneral 8 }
          cmcTcMasterTc4TrapControl         OBJECT IDENTIFIER ::= { cmcTcMasterTc4 4 }
          cmcTcMasterTc4Traps               OBJECT IDENTIFIER ::= { cmcTcMasterTc4TrapControl 7 }
          cmcTcMasterTc4Control             OBJECT IDENTIFIER ::= { cmcTcMasterTc4 5 }
        cmcTcMasterDevice5                  OBJECT IDENTIFIER ::= { cmcTcMasterDevices 5 }
          cmcTcMasterCmc5                   OBJECT IDENTIFIER ::= { cmcTcMasterDevice5 8 }
          cmcTcMasterCmc5Values             OBJECT IDENTIFIER ::= { cmcTcMasterCmc5 1 }
          cmcTcMasterCmc5Table1             OBJECT IDENTIFIER ::= { cmcTcMasterCmc5Values 6 }
          cmcTcMasterCmc5Status             OBJECT IDENTIFIER ::= { cmcTcMasterCmc5 2 }
          cmcTcMasterCmc5Table              OBJECT IDENTIFIER ::= { cmcTcMasterCmc5Status 17 }
          cmcTcMasterCmc5Set                OBJECT IDENTIFIER ::= { cmcTcMasterCmc5 3 }
          cmcTcMasterCmc5RelayControl       OBJECT IDENTIFIER ::= { cmcTcMasterCmc5Set 5 }
          cmcTcMasterCmc5Setpoints          OBJECT IDENTIFIER ::= { cmcTcMasterCmc5 4 }
          cmcTcMasterCmc5TrapControl        OBJECT IDENTIFIER ::= { cmcTcMasterCmc5 5 }
          cmcTcMasterCmc5Traps              OBJECT IDENTIFIER ::= { cmcTcMasterCmc5TrapControl 4 }
          cmcTcMasterPcu5                   OBJECT IDENTIFIER ::= { cmcTcMasterDevice5 10 }
          cmcTcMasterPcu5MibRev             OBJECT IDENTIFIER ::= { cmcTcMasterPcu5 1 }
          cmcTcMasterPcu5Values             OBJECT IDENTIFIER ::= { cmcTcMasterPcu5 2 }
          cmcTcMasterPcu5Status             OBJECT IDENTIFIER ::= { cmcTcMasterPcu5 3 }
          cmcTcMasterPcu5StatusTable1       OBJECT IDENTIFIER ::= { cmcTcMasterPcu5Status 6 }
          cmcTcMasterPcu5Setup              OBJECT IDENTIFIER ::= { cmcTcMasterPcu5 4 }
          cmcTcMasterPcu5SetupGeneral       OBJECT IDENTIFIER ::= { cmcTcMasterPcu5Setup 1 }
          cmcTcMasterPcu5TimerTable1        OBJECT IDENTIFIER ::= { cmcTcMasterPcu5SetupGeneral 8 }
          cmcTcMasterPcu5SetupDevice        OBJECT IDENTIFIER ::= { cmcTcMasterPcu5Setup 2 }
          cmcTcMasterPcu5SetupPower1        OBJECT IDENTIFIER ::= { cmcTcMasterPcu5SetupDevice 2 }
          cmcTcMasterPcu5SetupPower2        OBJECT IDENTIFIER ::= { cmcTcMasterPcu5SetupDevice 3 }
          cmcTcMasterPcu5SetupInput1        OBJECT IDENTIFIER ::= { cmcTcMasterPcu5SetupDevice 4 }
          cmcTcMasterPcu5SetupInput2        OBJECT IDENTIFIER ::= { cmcTcMasterPcu5SetupDevice 5 }
          cmcTcMasterPcu5SetupTemperature   OBJECT IDENTIFIER ::= { cmcTcMasterPcu5SetupDevice 6 }
          cmcTcMasterPcu5Setpoints          OBJECT IDENTIFIER ::= { cmcTcMasterPcu5 5 }
          cmcTcMasterPcu5Control            OBJECT IDENTIFIER ::= { cmcTcMasterPcu5 6 }
          cmcTcMasterPcu5TrapControl        OBJECT IDENTIFIER ::= { cmcTcMasterPcu5 7 }
          cmcTcMasterPcu5Traps              OBJECT IDENTIFIER ::= { cmcTcMasterPcu5TrapControl 7 }
          cmcTcMasterTc5                    OBJECT IDENTIFIER ::= { cmcTcMasterDevice5 11 }
          cmcTcMasterTc5MibRev              OBJECT IDENTIFIER ::= { cmcTcMasterTc5 1 }
          cmcTcMasterTc5Status              OBJECT IDENTIFIER ::= { cmcTcMasterTc5 2 }
          cmcTcMasterTc5StatusSensorUnit1   OBJECT IDENTIFIER ::= { cmcTcMasterTc5Status 3 }
          cmcTcMasterTc5StatusUnit1Sensors  OBJECT IDENTIFIER ::= { cmcTcMasterTc5StatusSensorUnit1 5 }
          cmcTcMasterTc5StatusUnit1Outputs  OBJECT IDENTIFIER ::= { cmcTcMasterTc5StatusSensorUnit1 6 }
          cmcTcMasterTc5StatusUnit1Msg      OBJECT IDENTIFIER ::= { cmcTcMasterTc5StatusSensorUnit1 7 }
          cmcTcMasterTc5StatusSensorUnit2   OBJECT IDENTIFIER ::= { cmcTcMasterTc5Status 4 }
          cmcTcMasterTc5StatusUnit2Sensors  OBJECT IDENTIFIER ::= { cmcTcMasterTc5StatusSensorUnit2 5 }
          cmcTcMasterTc5StatusUnit2Outputs  OBJECT IDENTIFIER ::= { cmcTcMasterTc5StatusSensorUnit2 6 }
          cmcTcMasterTc5StatusUnit2Msg      OBJECT IDENTIFIER ::= { cmcTcMasterTc5StatusSensorUnit2 7 }
          cmcTcMasterTc5StatusSensorUnit3   OBJECT IDENTIFIER ::= { cmcTcMasterTc5Status 5 }
          cmcTcMasterTc5StatusUnit3Sensors  OBJECT IDENTIFIER ::= { cmcTcMasterTc5StatusSensorUnit3 5 }
          cmcTcMasterTc5StatusUnit3Outputs  OBJECT IDENTIFIER ::= { cmcTcMasterTc5StatusSensorUnit3 6 }
          cmcTcMasterTc5StatusUnit3Msg      OBJECT IDENTIFIER ::= { cmcTcMasterTc5StatusSensorUnit3 7 }
          cmcTcMasterTc5StatusSensorUnit4   OBJECT IDENTIFIER ::= { cmcTcMasterTc5Status 6 }
          cmcTcMasterTc5StatusUnit4Sensors  OBJECT IDENTIFIER ::= { cmcTcMasterTc5StatusSensorUnit4 5 }
          cmcTcMasterTc5StatusUnit4Outputs  OBJECT IDENTIFIER ::= { cmcTcMasterTc5StatusSensorUnit4 6 }
          cmcTcMasterTc5StatusUnit4Msg      OBJECT IDENTIFIER ::= { cmcTcMasterTc5StatusSensorUnit4 7 }
          cmcTcMasterTc5StatusExtUnit       OBJECT IDENTIFIER ::= { cmcTcMasterTc5Status 7 }
          cmcTcMasterTc5Setup               OBJECT IDENTIFIER ::= { cmcTcMasterTc5 3 }
          cmcTcMasterTc5SetupGeneral        OBJECT IDENTIFIER ::= { cmcTcMasterTc5Setup 1 }
          cmcTcMasterTc5TimerTable1         OBJECT IDENTIFIER ::= { cmcTcMasterTc5SetupGeneral 8 }
          cmcTcMasterTc5TrapControl         OBJECT IDENTIFIER ::= { cmcTcMasterTc5 4 }
          cmcTcMasterTc5Traps               OBJECT IDENTIFIER ::= { cmcTcMasterTc5TrapControl 7 }
          cmcTcMasterTc5Control             OBJECT IDENTIFIER ::= { cmcTcMasterTc5 5 }
        cmcTcMasterDevice6                  OBJECT IDENTIFIER ::= { cmcTcMasterDevices 6 }
          cmcTcMasterCmc6                   OBJECT IDENTIFIER ::= { cmcTcMasterDevice6 8 }
          cmcTcMasterCmc6Values             OBJECT IDENTIFIER ::= { cmcTcMasterCmc6 1 }
          cmcTcMasterCmc6Table1             OBJECT IDENTIFIER ::= { cmcTcMasterCmc6Values 6 }
          cmcTcMasterCmc6Status             OBJECT IDENTIFIER ::= { cmcTcMasterCmc6 2 }
          cmcTcMasterCmc6Table              OBJECT IDENTIFIER ::= { cmcTcMasterCmc6Status 17 }
          cmcTcMasterCmc6Set                OBJECT IDENTIFIER ::= { cmcTcMasterCmc6 3 }
          cmcTcMasterCmc6RelayControl       OBJECT IDENTIFIER ::= { cmcTcMasterCmc6Set 5 }
          cmcTcMasterCmc6Setpoints          OBJECT IDENTIFIER ::= { cmcTcMasterCmc6 4 }
          cmcTcMasterCmc6TrapControl        OBJECT IDENTIFIER ::= { cmcTcMasterCmc6 5 }
          cmcTcMasterCmc6Traps              OBJECT IDENTIFIER ::= { cmcTcMasterCmc6TrapControl 4 }
          cmcTcMasterPcu6                   OBJECT IDENTIFIER ::= { cmcTcMasterDevice6 10 }
          cmcTcMasterPcu6MibRev             OBJECT IDENTIFIER ::= { cmcTcMasterPcu6 1 }
          cmcTcMasterPcu6Values             OBJECT IDENTIFIER ::= { cmcTcMasterPcu6 2 }
          cmcTcMasterPcu6Status             OBJECT IDENTIFIER ::= { cmcTcMasterPcu6 3 }
          cmcTcMasterPcu6StatusTable1       OBJECT IDENTIFIER ::= { cmcTcMasterPcu6Status 6 }
          cmcTcMasterPcu6Setup              OBJECT IDENTIFIER ::= { cmcTcMasterPcu6 4 }
          cmcTcMasterPcu6SetupGeneral       OBJECT IDENTIFIER ::= { cmcTcMasterPcu6Setup 1 }
          cmcTcMasterPcu6TimerTable1        OBJECT IDENTIFIER ::= { cmcTcMasterPcu6SetupGeneral 8 }
          cmcTcMasterPcu6SetupDevice        OBJECT IDENTIFIER ::= { cmcTcMasterPcu6Setup 2 }
          cmcTcMasterPcu6SetupPower1        OBJECT IDENTIFIER ::= { cmcTcMasterPcu6SetupDevice 2 }
          cmcTcMasterPcu6SetupPower2        OBJECT IDENTIFIER ::= { cmcTcMasterPcu6SetupDevice 3 }
          cmcTcMasterPcu6SetupInput1        OBJECT IDENTIFIER ::= { cmcTcMasterPcu6SetupDevice 4 }
          cmcTcMasterPcu6SetupInput2        OBJECT IDENTIFIER ::= { cmcTcMasterPcu6SetupDevice 5 }
          cmcTcMasterPcu6SetupTemperature   OBJECT IDENTIFIER ::= { cmcTcMasterPcu6SetupDevice 6 }
          cmcTcMasterPcu6Setpoints          OBJECT IDENTIFIER ::= { cmcTcMasterPcu6 5 }
          cmcTcMasterPcu6Control            OBJECT IDENTIFIER ::= { cmcTcMasterPcu6 6 }
          cmcTcMasterPcu6TrapControl        OBJECT IDENTIFIER ::= { cmcTcMasterPcu6 7 }
          cmcTcMasterPcu6Traps              OBJECT IDENTIFIER ::= { cmcTcMasterPcu6TrapControl 7 }
          cmcTcMasterTc6                    OBJECT IDENTIFIER ::= { cmcTcMasterDevice6 11 }
          cmcTcMasterTc6MibRev              OBJECT IDENTIFIER ::= { cmcTcMasterTc6 1 }
          cmcTcMasterTc6Status              OBJECT IDENTIFIER ::= { cmcTcMasterTc6 2 }
          cmcTcMasterTc6StatusSensorUnit1   OBJECT IDENTIFIER ::= { cmcTcMasterTc6Status 3 }
          cmcTcMasterTc6StatusUnit1Sensors  OBJECT IDENTIFIER ::= { cmcTcMasterTc6StatusSensorUnit1 5 }
          cmcTcMasterTc6StatusUnit1Outputs  OBJECT IDENTIFIER ::= { cmcTcMasterTc6StatusSensorUnit1 6 }
          cmcTcMasterTc6StatusUnit1Msg      OBJECT IDENTIFIER ::= { cmcTcMasterTc6StatusSensorUnit1 7 }
          cmcTcMasterTc6StatusSensorUnit2   OBJECT IDENTIFIER ::= { cmcTcMasterTc6Status 4 }
          cmcTcMasterTc6StatusUnit2Sensors  OBJECT IDENTIFIER ::= { cmcTcMasterTc6StatusSensorUnit2 5 }
          cmcTcMasterTc6StatusUnit2Outputs  OBJECT IDENTIFIER ::= { cmcTcMasterTc6StatusSensorUnit2 6 }
          cmcTcMasterTc6StatusUnit2Msg      OBJECT IDENTIFIER ::= { cmcTcMasterTc6StatusSensorUnit2 7 }
          cmcTcMasterTc6StatusSensorUnit3   OBJECT IDENTIFIER ::= { cmcTcMasterTc6Status 5 }
          cmcTcMasterTc6StatusUnit3Sensors  OBJECT IDENTIFIER ::= { cmcTcMasterTc6StatusSensorUnit3 5 }
          cmcTcMasterTc6StatusUnit3Outputs  OBJECT IDENTIFIER ::= { cmcTcMasterTc6StatusSensorUnit3 6 }
          cmcTcMasterTc6StatusUnit3Msg      OBJECT IDENTIFIER ::= { cmcTcMasterTc6StatusSensorUnit3 7 }
          cmcTcMasterTc6StatusSensorUnit4   OBJECT IDENTIFIER ::= { cmcTcMasterTc6Status 6 }
          cmcTcMasterTc6StatusUnit4Sensors  OBJECT IDENTIFIER ::= { cmcTcMasterTc6StatusSensorUnit4 5 }
          cmcTcMasterTc6StatusUnit4Outputs  OBJECT IDENTIFIER ::= { cmcTcMasterTc6StatusSensorUnit4 6 }
          cmcTcMasterTc6StatusUnit4Msg      OBJECT IDENTIFIER ::= { cmcTcMasterTc6StatusSensorUnit4 7 }
          cmcTcMasterTc6StatusExtUnit       OBJECT IDENTIFIER ::= { cmcTcMasterTc6Status 7 }
          cmcTcMasterTc6Setup               OBJECT IDENTIFIER ::= { cmcTcMasterTc6 3 }
          cmcTcMasterTc6SetupGeneral        OBJECT IDENTIFIER ::= { cmcTcMasterTc6Setup 1 }
          cmcTcMasterTc6TimerTable1         OBJECT IDENTIFIER ::= { cmcTcMasterTc6SetupGeneral 8 }
          cmcTcMasterTc6TrapControl         OBJECT IDENTIFIER ::= { cmcTcMasterTc6 4 }
          cmcTcMasterTc6Traps               OBJECT IDENTIFIER ::= { cmcTcMasterTc6TrapControl 7 }
          cmcTcMasterTc6Control             OBJECT IDENTIFIER ::= { cmcTcMasterTc6 5 }
        cmcTcMasterDevice7                  OBJECT IDENTIFIER ::= { cmcTcMasterDevices 7 }
          cmcTcMasterCmc7                   OBJECT IDENTIFIER ::= { cmcTcMasterDevice7 8 }
          cmcTcMasterCmc7Values             OBJECT IDENTIFIER ::= { cmcTcMasterCmc7 1 }
          cmcTcMasterCmc7Table1             OBJECT IDENTIFIER ::= { cmcTcMasterCmc7Values 6 }
          cmcTcMasterCmc7Status             OBJECT IDENTIFIER ::= { cmcTcMasterCmc7 2 }
          cmcTcMasterCmc7Table              OBJECT IDENTIFIER ::= { cmcTcMasterCmc7Status 17 }
          cmcTcMasterCmc7Set                OBJECT IDENTIFIER ::= { cmcTcMasterCmc7 3 }
          cmcTcMasterCmc7RelayControl       OBJECT IDENTIFIER ::= { cmcTcMasterCmc7Set 5 }
          cmcTcMasterCmc7Setpoints          OBJECT IDENTIFIER ::= { cmcTcMasterCmc7 4 }
          cmcTcMasterCmc7TrapControl        OBJECT IDENTIFIER ::= { cmcTcMasterCmc7 5 }
          cmcTcMasterCmc7Traps              OBJECT IDENTIFIER ::= { cmcTcMasterCmc7TrapControl 4 }
          cmcTcMasterPcu7                   OBJECT IDENTIFIER ::= { cmcTcMasterDevice7 10 }
          cmcTcMasterPcu7MibRev             OBJECT IDENTIFIER ::= { cmcTcMasterPcu7 1 }
          cmcTcMasterPcu7Values             OBJECT IDENTIFIER ::= { cmcTcMasterPcu7 2 }
          cmcTcMasterPcu7Status             OBJECT IDENTIFIER ::= { cmcTcMasterPcu7 3 }
          cmcTcMasterPcu7StatusTable1       OBJECT IDENTIFIER ::= { cmcTcMasterPcu7Status 6 }
          cmcTcMasterPcu7Setup              OBJECT IDENTIFIER ::= { cmcTcMasterPcu7 4 }
          cmcTcMasterPcu7SetupGeneral       OBJECT IDENTIFIER ::= { cmcTcMasterPcu7Setup 1 }
          cmcTcMasterPcu7TimerTable1        OBJECT IDENTIFIER ::= { cmcTcMasterPcu7SetupGeneral 8 }
          cmcTcMasterPcu7SetupDevice        OBJECT IDENTIFIER ::= { cmcTcMasterPcu7Setup 2 }
          cmcTcMasterPcu7SetupPower1        OBJECT IDENTIFIER ::= { cmcTcMasterPcu7SetupDevice 2 }
          cmcTcMasterPcu7SetupPower2        OBJECT IDENTIFIER ::= { cmcTcMasterPcu7SetupDevice 3 }
          cmcTcMasterPcu7SetupInput1        OBJECT IDENTIFIER ::= { cmcTcMasterPcu7SetupDevice 4 }
          cmcTcMasterPcu7SetupInput2        OBJECT IDENTIFIER ::= { cmcTcMasterPcu7SetupDevice 5 }
          cmcTcMasterPcu7SetupTemperature   OBJECT IDENTIFIER ::= { cmcTcMasterPcu7SetupDevice 6 }
          cmcTcMasterPcu7Setpoints          OBJECT IDENTIFIER ::= { cmcTcMasterPcu7 5 }
          cmcTcMasterPcu7Control            OBJECT IDENTIFIER ::= { cmcTcMasterPcu7 6 }
          cmcTcMasterPcu7TrapControl        OBJECT IDENTIFIER ::= { cmcTcMasterPcu7 7 }    
          cmcTcMasterPcu7Traps              OBJECT IDENTIFIER ::= { cmcTcMasterPcu7TrapControl 7 }
          cmcTcMasterTc7                    OBJECT IDENTIFIER ::= { cmcTcMasterDevice7 11 }
          cmcTcMasterTc7MibRev              OBJECT IDENTIFIER ::= { cmcTcMasterTc7 1 }
          cmcTcMasterTc7Status              OBJECT IDENTIFIER ::= { cmcTcMasterTc7 2 }
          cmcTcMasterTc7StatusSensorUnit1   OBJECT IDENTIFIER ::= { cmcTcMasterTc7Status 3 }
          cmcTcMasterTc7StatusUnit1Sensors  OBJECT IDENTIFIER ::= { cmcTcMasterTc7StatusSensorUnit1 5 }
          cmcTcMasterTc7StatusUnit1Outputs  OBJECT IDENTIFIER ::= { cmcTcMasterTc7StatusSensorUnit1 6 }
          cmcTcMasterTc7StatusUnit1Msg      OBJECT IDENTIFIER ::= { cmcTcMasterTc7StatusSensorUnit1 7 }
          cmcTcMasterTc7StatusSensorUnit2   OBJECT IDENTIFIER ::= { cmcTcMasterTc7Status 4 }
          cmcTcMasterTc7StatusUnit2Sensors  OBJECT IDENTIFIER ::= { cmcTcMasterTc7StatusSensorUnit2 5 }
          cmcTcMasterTc7StatusUnit2Outputs  OBJECT IDENTIFIER ::= { cmcTcMasterTc7StatusSensorUnit2 6 }
          cmcTcMasterTc7StatusUnit2Msg      OBJECT IDENTIFIER ::= { cmcTcMasterTc7StatusSensorUnit2 7 }
          cmcTcMasterTc7StatusSensorUnit3   OBJECT IDENTIFIER ::= { cmcTcMasterTc7Status 5 }
          cmcTcMasterTc7StatusUnit3Sensors  OBJECT IDENTIFIER ::= { cmcTcMasterTc7StatusSensorUnit3 5 }
          cmcTcMasterTc7StatusUnit3Outputs  OBJECT IDENTIFIER ::= { cmcTcMasterTc7StatusSensorUnit3 6 }
          cmcTcMasterTc7StatusUnit3Msg      OBJECT IDENTIFIER ::= { cmcTcMasterTc7StatusSensorUnit3 7 }
          cmcTcMasterTc7StatusSensorUnit4   OBJECT IDENTIFIER ::= { cmcTcMasterTc7Status 6 }
          cmcTcMasterTc7StatusUnit4Sensors  OBJECT IDENTIFIER ::= { cmcTcMasterTc7StatusSensorUnit4 5 }
          cmcTcMasterTc7StatusUnit4Outputs  OBJECT IDENTIFIER ::= { cmcTcMasterTc7StatusSensorUnit4 6 }
          cmcTcMasterTc7StatusUnit4Msg      OBJECT IDENTIFIER ::= { cmcTcMasterTc7StatusSensorUnit4 7 }
          cmcTcMasterTc7StatusExtUnit       OBJECT IDENTIFIER ::= { cmcTcMasterTc7Status 7 }
          cmcTcMasterTc7Setup               OBJECT IDENTIFIER ::= { cmcTcMasterTc7 3 }
          cmcTcMasterTc7SetupGeneral        OBJECT IDENTIFIER ::= { cmcTcMasterTc7Setup 1 }
          cmcTcMasterTc7TimerTable1         OBJECT IDENTIFIER ::= { cmcTcMasterTc7SetupGeneral 8 }
          cmcTcMasterTc7TrapControl         OBJECT IDENTIFIER ::= { cmcTcMasterTc7 4 }
          cmcTcMasterTc7Traps               OBJECT IDENTIFIER ::= { cmcTcMasterTc7TrapControl 7 }
          cmcTcMasterTc7Control             OBJECT IDENTIFIER ::= { cmcTcMasterTc7 5 }
        cmcTcMasterDevice8                  OBJECT IDENTIFIER ::= { cmcTcMasterDevices 8 }
          cmcTcMasterCmc8                   OBJECT IDENTIFIER ::= { cmcTcMasterDevice8 8 }
          cmcTcMasterCmc8Values             OBJECT IDENTIFIER ::= { cmcTcMasterCmc8 1 }
          cmcTcMasterCmc8Table1             OBJECT IDENTIFIER ::= { cmcTcMasterCmc8Values 6 }
          cmcTcMasterCmc8Status             OBJECT IDENTIFIER ::= { cmcTcMasterCmc8 2 }
          cmcTcMasterCmc8Table              OBJECT IDENTIFIER ::= { cmcTcMasterCmc8Status 17 }
          cmcTcMasterCmc8Set                OBJECT IDENTIFIER ::= { cmcTcMasterCmc8 3 }
          cmcTcMasterCmc8RelayControl       OBJECT IDENTIFIER ::= { cmcTcMasterCmc8Set 5 }
          cmcTcMasterCmc8Setpoints          OBJECT IDENTIFIER ::= { cmcTcMasterCmc8 4 }
          cmcTcMasterCmc8TrapControl        OBJECT IDENTIFIER ::= { cmcTcMasterCmc8 5 }
          cmcTcMasterCmc8Traps              OBJECT IDENTIFIER ::= { cmcTcMasterCmc8TrapControl 4 }
          cmcTcMasterPcu8                   OBJECT IDENTIFIER ::= { cmcTcMasterDevice8 10 }
          cmcTcMasterPcu8MibRev             OBJECT IDENTIFIER ::= { cmcTcMasterPcu8 1 }
          cmcTcMasterPcu8Values             OBJECT IDENTIFIER ::= { cmcTcMasterPcu8 2 }
          cmcTcMasterPcu8Status             OBJECT IDENTIFIER ::= { cmcTcMasterPcu8 3 }
          cmcTcMasterPcu8StatusTable1       OBJECT IDENTIFIER ::= { cmcTcMasterPcu8Status 6 }
          cmcTcMasterPcu8Setup              OBJECT IDENTIFIER ::= { cmcTcMasterPcu8 4 }
          cmcTcMasterPcu8SetupGeneral       OBJECT IDENTIFIER ::= { cmcTcMasterPcu8Setup 1 }
          cmcTcMasterPcu8TimerTable1        OBJECT IDENTIFIER ::= { cmcTcMasterPcu8SetupGeneral 8 }
          cmcTcMasterPcu8SetupDevice        OBJECT IDENTIFIER ::= { cmcTcMasterPcu8Setup 2 }
          cmcTcMasterPcu8SetupPower1        OBJECT IDENTIFIER ::= { cmcTcMasterPcu8SetupDevice 2 }
          cmcTcMasterPcu8SetupPower2        OBJECT IDENTIFIER ::= { cmcTcMasterPcu8SetupDevice 3 }
          cmcTcMasterPcu8SetupInput1        OBJECT IDENTIFIER ::= { cmcTcMasterPcu8SetupDevice 4 }
          cmcTcMasterPcu8SetupInput2        OBJECT IDENTIFIER ::= { cmcTcMasterPcu8SetupDevice 5 }
          cmcTcMasterPcu8SetupTemperature   OBJECT IDENTIFIER ::= { cmcTcMasterPcu8SetupDevice 6 }
          cmcTcMasterPcu8Setpoints          OBJECT IDENTIFIER ::= { cmcTcMasterPcu8 5 }
          cmcTcMasterPcu8Control            OBJECT IDENTIFIER ::= { cmcTcMasterPcu8 6 }
          cmcTcMasterPcu8TrapControl        OBJECT IDENTIFIER ::= { cmcTcMasterPcu8 7 }
          cmcTcMasterPcu8Traps              OBJECT IDENTIFIER ::= { cmcTcMasterPcu8TrapControl 7 }
          cmcTcMasterTc8                    OBJECT IDENTIFIER ::= { cmcTcMasterDevice8 11 }
          cmcTcMasterTc8MibRev              OBJECT IDENTIFIER ::= { cmcTcMasterTc8 1 }
          cmcTcMasterTc8Status              OBJECT IDENTIFIER ::= { cmcTcMasterTc8 2 }
          cmcTcMasterTc8StatusSensorUnit1   OBJECT IDENTIFIER ::= { cmcTcMasterTc8Status 3 }
          cmcTcMasterTc8StatusUnit1Sensors  OBJECT IDENTIFIER ::= { cmcTcMasterTc8StatusSensorUnit1 5 }
          cmcTcMasterTc8StatusUnit1Outputs  OBJECT IDENTIFIER ::= { cmcTcMasterTc8StatusSensorUnit1 6 }
          cmcTcMasterTc8StatusUnit1Msg      OBJECT IDENTIFIER ::= { cmcTcMasterTc8StatusSensorUnit1 7 }
          cmcTcMasterTc8StatusSensorUnit2   OBJECT IDENTIFIER ::= { cmcTcMasterTc8Status 4 }
          cmcTcMasterTc8StatusUnit2Sensors  OBJECT IDENTIFIER ::= { cmcTcMasterTc8StatusSensorUnit2 5 }
          cmcTcMasterTc8StatusUnit2Outputs  OBJECT IDENTIFIER ::= { cmcTcMasterTc8StatusSensorUnit2 6 }
          cmcTcMasterTc8StatusUnit2Msg      OBJECT IDENTIFIER ::= { cmcTcMasterTc8StatusSensorUnit2 7 }
          cmcTcMasterTc8StatusSensorUnit3   OBJECT IDENTIFIER ::= { cmcTcMasterTc8Status 5 }
          cmcTcMasterTc8StatusUnit3Sensors  OBJECT IDENTIFIER ::= { cmcTcMasterTc8StatusSensorUnit3 5 }
          cmcTcMasterTc8StatusUnit3Outputs  OBJECT IDENTIFIER ::= { cmcTcMasterTc8StatusSensorUnit3 6 }
          cmcTcMasterTc8StatusUnit3Msg      OBJECT IDENTIFIER ::= { cmcTcMasterTc8StatusSensorUnit3 7 }
          cmcTcMasterTc8StatusSensorUnit4   OBJECT IDENTIFIER ::= { cmcTcMasterTc8Status 6 }
          cmcTcMasterTc8StatusUnit4Sensors  OBJECT IDENTIFIER ::= { cmcTcMasterTc8StatusSensorUnit4 5 }
          cmcTcMasterTc8StatusUnit4Outputs  OBJECT IDENTIFIER ::= { cmcTcMasterTc8StatusSensorUnit4 6 }
          cmcTcMasterTc8StatusUnit4Msg      OBJECT IDENTIFIER ::= { cmcTcMasterTc8StatusSensorUnit4 7 }
          cmcTcMasterTc8StatusExtUnit       OBJECT IDENTIFIER ::= { cmcTcMasterTc8Status 7 }
          cmcTcMasterTc8Setup               OBJECT IDENTIFIER ::= { cmcTcMasterTc8 3 }
          cmcTcMasterTc8SetupGeneral        OBJECT IDENTIFIER ::= { cmcTcMasterTc8Setup 1 }
          cmcTcMasterTc8TimerTable1         OBJECT IDENTIFIER ::= { cmcTcMasterTc8SetupGeneral 8 }
          cmcTcMasterTc8TrapControl         OBJECT IDENTIFIER ::= { cmcTcMasterTc8 4 }
          cmcTcMasterTc8Traps               OBJECT IDENTIFIER ::= { cmcTcMasterTc8TrapControl 7 }
          cmcTcMasterTc8Control             OBJECT IDENTIFIER ::= { cmcTcMasterTc8 5 }
        cmcTcMasterDevice9                  OBJECT IDENTIFIER ::= { cmcTcMasterDevices 9 }
          cmcTcMasterCmc9                   OBJECT IDENTIFIER ::= { cmcTcMasterDevice9 8 }
          cmcTcMasterCmc9Values             OBJECT IDENTIFIER ::= { cmcTcMasterCmc9 1 }
          cmcTcMasterCmc9Table1             OBJECT IDENTIFIER ::= { cmcTcMasterCmc9Values 6 }
          cmcTcMasterCmc9Status             OBJECT IDENTIFIER ::= { cmcTcMasterCmc9 2 }
          cmcTcMasterCmc9Table              OBJECT IDENTIFIER ::= { cmcTcMasterCmc9Status 17 }
          cmcTcMasterCmc9Set                OBJECT IDENTIFIER ::= { cmcTcMasterCmc9 3 }
          cmcTcMasterCmc9RelayControl       OBJECT IDENTIFIER ::= { cmcTcMasterCmc9Set 5 }
          cmcTcMasterCmc9Setpoints          OBJECT IDENTIFIER ::= { cmcTcMasterCmc9 4 }
          cmcTcMasterCmc9TrapControl        OBJECT IDENTIFIER ::= { cmcTcMasterCmc9 5 }
          cmcTcMasterCmc9Traps              OBJECT IDENTIFIER ::= { cmcTcMasterCmc9TrapControl 4 }
          cmcTcMasterPcu9                   OBJECT IDENTIFIER ::= { cmcTcMasterDevice9 10 }
          cmcTcMasterPcu9MibRev             OBJECT IDENTIFIER ::= { cmcTcMasterPcu9 1 }
          cmcTcMasterPcu9Values             OBJECT IDENTIFIER ::= { cmcTcMasterPcu9 2 }
          cmcTcMasterPcu9Status             OBJECT IDENTIFIER ::= { cmcTcMasterPcu9 3 }
          cmcTcMasterPcu9StatusTable1       OBJECT IDENTIFIER ::= { cmcTcMasterPcu9Status 6 }
          cmcTcMasterPcu9Setup              OBJECT IDENTIFIER ::= { cmcTcMasterPcu9 4 }
          cmcTcMasterPcu9SetupGeneral       OBJECT IDENTIFIER ::= { cmcTcMasterPcu9Setup 1 }
          cmcTcMasterPcu9TimerTable1        OBJECT IDENTIFIER ::= { cmcTcMasterPcu9SetupGeneral 8 }
          cmcTcMasterPcu9SetupDevice        OBJECT IDENTIFIER ::= { cmcTcMasterPcu9Setup 2 }
          cmcTcMasterPcu9SetupPower1        OBJECT IDENTIFIER ::= { cmcTcMasterPcu9SetupDevice 2 }
          cmcTcMasterPcu9SetupPower2        OBJECT IDENTIFIER ::= { cmcTcMasterPcu9SetupDevice 3 }
          cmcTcMasterPcu9SetupInput1        OBJECT IDENTIFIER ::= { cmcTcMasterPcu9SetupDevice 4 }
          cmcTcMasterPcu9SetupInput2        OBJECT IDENTIFIER ::= { cmcTcMasterPcu9SetupDevice 5 }
          cmcTcMasterPcu9SetupTemperature   OBJECT IDENTIFIER ::= { cmcTcMasterPcu9SetupDevice 6 }
          cmcTcMasterPcu9Setpoints          OBJECT IDENTIFIER ::= { cmcTcMasterPcu9 5 }
          cmcTcMasterPcu9Control            OBJECT IDENTIFIER ::= { cmcTcMasterPcu9 6 }
          cmcTcMasterPcu9TrapControl        OBJECT IDENTIFIER ::= { cmcTcMasterPcu9 7 }
          cmcTcMasterPcu9Traps              OBJECT IDENTIFIER ::= { cmcTcMasterPcu9TrapControl 7 }
          cmcTcMasterTc9                    OBJECT IDENTIFIER ::= { cmcTcMasterDevice9 11 }
          cmcTcMasterTc9MibRev              OBJECT IDENTIFIER ::= { cmcTcMasterTc9 1 }
          cmcTcMasterTc9Status              OBJECT IDENTIFIER ::= { cmcTcMasterTc9 2 }
          cmcTcMasterTc9StatusSensorUnit1   OBJECT IDENTIFIER ::= { cmcTcMasterTc9Status 3 }
          cmcTcMasterTc9StatusUnit1Sensors  OBJECT IDENTIFIER ::= { cmcTcMasterTc9StatusSensorUnit1 5 }
          cmcTcMasterTc9StatusUnit1Outputs  OBJECT IDENTIFIER ::= { cmcTcMasterTc9StatusSensorUnit1 6 }
          cmcTcMasterTc9StatusUnit1Msg      OBJECT IDENTIFIER ::= { cmcTcMasterTc9StatusSensorUnit1 7 }
          cmcTcMasterTc9StatusSensorUnit2   OBJECT IDENTIFIER ::= { cmcTcMasterTc9Status 4 }
          cmcTcMasterTc9StatusUnit2Sensors  OBJECT IDENTIFIER ::= { cmcTcMasterTc9StatusSensorUnit2 5 }
          cmcTcMasterTc9StatusUnit2Outputs  OBJECT IDENTIFIER ::= { cmcTcMasterTc9StatusSensorUnit2 6 }
          cmcTcMasterTc9StatusUnit2Msg      OBJECT IDENTIFIER ::= { cmcTcMasterTc9StatusSensorUnit2 7 }
          cmcTcMasterTc9StatusSensorUnit3   OBJECT IDENTIFIER ::= { cmcTcMasterTc9Status 5 }
          cmcTcMasterTc9StatusUnit3Sensors  OBJECT IDENTIFIER ::= { cmcTcMasterTc9StatusSensorUnit3 5 }
          cmcTcMasterTc9StatusUnit3Outputs  OBJECT IDENTIFIER ::= { cmcTcMasterTc9StatusSensorUnit3 6 }
          cmcTcMasterTc9StatusUnit3Msg      OBJECT IDENTIFIER ::= { cmcTcMasterTc9StatusSensorUnit3 7 }
          cmcTcMasterTc9StatusSensorUnit4   OBJECT IDENTIFIER ::= { cmcTcMasterTc9Status 6 }
          cmcTcMasterTc9StatusUnit4Sensors  OBJECT IDENTIFIER ::= { cmcTcMasterTc9StatusSensorUnit4 5 }
          cmcTcMasterTc9StatusUnit4Outputs  OBJECT IDENTIFIER ::= { cmcTcMasterTc9StatusSensorUnit4 6 }
          cmcTcMasterTc9StatusUnit4Msg      OBJECT IDENTIFIER ::= { cmcTcMasterTc9StatusSensorUnit4 7 }
          cmcTcMasterTc9StatusExtUnit       OBJECT IDENTIFIER ::= { cmcTcMasterTc9Status 7 }
          cmcTcMasterTc9Setup               OBJECT IDENTIFIER ::= { cmcTcMasterTc9 3 }
          cmcTcMasterTc9SetupGeneral        OBJECT IDENTIFIER ::= { cmcTcMasterTc9Setup 1 }
          cmcTcMasterTc9TimerTable1         OBJECT IDENTIFIER ::= { cmcTcMasterTc9SetupGeneral 8 }
          cmcTcMasterTc9TrapControl         OBJECT IDENTIFIER ::= { cmcTcMasterTc9 4 }
          cmcTcMasterTc9Traps               OBJECT IDENTIFIER ::= { cmcTcMasterTc9TrapControl 7 }
          cmcTcMasterTc9Control             OBJECT IDENTIFIER ::= { cmcTcMasterTc9 5 }
        cmcTcMasterDevice10                 OBJECT IDENTIFIER ::= { cmcTcMasterDevices 10 }
          cmcTcMasterCmc10                  OBJECT IDENTIFIER ::= { cmcTcMasterDevice10 8 }
          cmcTcMasterCmc10Values            OBJECT IDENTIFIER ::= { cmcTcMasterCmc10 1 }
          cmcTcMasterCmc10Table1            OBJECT IDENTIFIER ::= { cmcTcMasterCmc10Values 6 }
          cmcTcMasterCmc10Status            OBJECT IDENTIFIER ::= { cmcTcMasterCmc10 2 }
          cmcTcMasterCmc10Table             OBJECT IDENTIFIER ::= { cmcTcMasterCmc10Status 17 }
          cmcTcMasterCmc10Set               OBJECT IDENTIFIER ::= { cmcTcMasterCmc10 3 }
          cmcTcMasterCmc10RelayControl      OBJECT IDENTIFIER ::= { cmcTcMasterCmc10Set 5 }
          cmcTcMasterCmc10Setpoints         OBJECT IDENTIFIER ::= { cmcTcMasterCmc10 4 }
          cmcTcMasterCmc10TrapControl       OBJECT IDENTIFIER ::= { cmcTcMasterCmc10 5 }
          cmcTcMasterCmc10Traps             OBJECT IDENTIFIER ::= { cmcTcMasterCmc10TrapControl 4 }
          cmcTcMasterPcu10                  OBJECT IDENTIFIER ::= { cmcTcMasterDevice10 10 }
          cmcTcMasterPcu10MibRev            OBJECT IDENTIFIER ::= { cmcTcMasterPcu10 1 }
          cmcTcMasterPcu10Values            OBJECT IDENTIFIER ::= { cmcTcMasterPcu10 2 }
          cmcTcMasterPcu10Status            OBJECT IDENTIFIER ::= { cmcTcMasterPcu10 3 }
          cmcTcMasterPcu10StatusTable1      OBJECT IDENTIFIER ::= { cmcTcMasterPcu10Status 6 }
          cmcTcMasterPcu10Setup             OBJECT IDENTIFIER ::= { cmcTcMasterPcu10 4 }
          cmcTcMasterPcu10SetupGeneral      OBJECT IDENTIFIER ::= { cmcTcMasterPcu10Setup 1 }
          cmcTcMasterPcu10TimerTable1       OBJECT IDENTIFIER ::= { cmcTcMasterPcu10SetupGeneral 8 }
          cmcTcMasterPcu10SetupDevice       OBJECT IDENTIFIER ::= { cmcTcMasterPcu10Setup 2 }
          cmcTcMasterPcu10SetupPower1       OBJECT IDENTIFIER ::= { cmcTcMasterPcu10SetupDevice 2 }
          cmcTcMasterPcu10SetupPower2       OBJECT IDENTIFIER ::= { cmcTcMasterPcu10SetupDevice 3 }
          cmcTcMasterPcu10SetupInput1       OBJECT IDENTIFIER ::= { cmcTcMasterPcu10SetupDevice 4 }
          cmcTcMasterPcu10SetupInput2       OBJECT IDENTIFIER ::= { cmcTcMasterPcu10SetupDevice 5 }
          cmcTcMasterPcu10SetupTemperature  OBJECT IDENTIFIER ::= { cmcTcMasterPcu10SetupDevice 6 }
          cmcTcMasterPcu10Setpoints         OBJECT IDENTIFIER ::= { cmcTcMasterPcu10 5 }
          cmcTcMasterPcu10Control           OBJECT IDENTIFIER ::= { cmcTcMasterPcu10 6 }
          cmcTcMasterPcu10TrapControl       OBJECT IDENTIFIER ::= { cmcTcMasterPcu10 7 }
          cmcTcMasterPcu10Traps             OBJECT IDENTIFIER ::= { cmcTcMasterPcu10TrapControl 7 }
          cmcTcMasterTc10                   OBJECT IDENTIFIER ::= { cmcTcMasterDevice10 11 }
          cmcTcMasterTc10MibRev             OBJECT IDENTIFIER ::= { cmcTcMasterTc10 1 }
          cmcTcMasterTc10Status             OBJECT IDENTIFIER ::= { cmcTcMasterTc10 2 }
          cmcTcMasterTc10StatusSensorUnit1  OBJECT IDENTIFIER ::= { cmcTcMasterTc10Status 3 }
          cmcTcMasterTc10StatusUnit1Sensors OBJECT IDENTIFIER ::= { cmcTcMasterTc10StatusSensorUnit1 5 }
          cmcTcMasterTc10StatusUnit1Outputs OBJECT IDENTIFIER ::= { cmcTcMasterTc10StatusSensorUnit1 6 }
          cmcTcMasterTc10StatusUnit1Msg     OBJECT IDENTIFIER ::= { cmcTcMasterTc10StatusSensorUnit1 7 }
          cmcTcMasterTc10StatusSensorUnit2  OBJECT IDENTIFIER ::= { cmcTcMasterTc10Status 4 }
          cmcTcMasterTc10StatusUnit2Sensors OBJECT IDENTIFIER ::= { cmcTcMasterTc10StatusSensorUnit2 5 }
          cmcTcMasterTc10StatusUnit2Outputs OBJECT IDENTIFIER ::= { cmcTcMasterTc10StatusSensorUnit2 6 }
          cmcTcMasterTc10StatusUnit2Msg     OBJECT IDENTIFIER ::= { cmcTcMasterTc10StatusSensorUnit2 7 }
          cmcTcMasterTc10StatusSensorUnit3  OBJECT IDENTIFIER ::= { cmcTcMasterTc10Status 5 }
          cmcTcMasterTc10StatusUnit3Sensors OBJECT IDENTIFIER ::= { cmcTcMasterTc10StatusSensorUnit3 5 }
          cmcTcMasterTc10StatusUnit3Outputs OBJECT IDENTIFIER ::= { cmcTcMasterTc10StatusSensorUnit3 6 }
          cmcTcMasterTc10StatusUnit3Msg     OBJECT IDENTIFIER ::= { cmcTcMasterTc10StatusSensorUnit3 7 }
          cmcTcMasterTc10StatusSensorUnit4  OBJECT IDENTIFIER ::= { cmcTcMasterTc10Status 6 }
          cmcTcMasterTc10StatusUnit4Sensors OBJECT IDENTIFIER ::= { cmcTcMasterTc10StatusSensorUnit4 5 }
          cmcTcMasterTc10StatusUnit4Outputs OBJECT IDENTIFIER ::= { cmcTcMasterTc10StatusSensorUnit4 6 }
          cmcTcMasterTc10StatusUnit4Msg     OBJECT IDENTIFIER ::= { cmcTcMasterTc10StatusSensorUnit4 7 }
          cmcTcMasterTc10StatusExtUnit      OBJECT IDENTIFIER ::= { cmcTcMasterTc10Status 7 }
          cmcTcMasterTc10Setup              OBJECT IDENTIFIER ::= { cmcTcMasterTc10 3 }
          cmcTcMasterTc10SetupGeneral       OBJECT IDENTIFIER ::= { cmcTcMasterTc10Setup 1 }
          cmcTcMasterTc10TimerTable1        OBJECT IDENTIFIER ::= { cmcTcMasterTc10SetupGeneral 8 }
          cmcTcMasterTc10TrapControl        OBJECT IDENTIFIER ::= { cmcTcMasterTc10 4 }
          cmcTcMasterTc10Traps              OBJECT IDENTIFIER ::= { cmcTcMasterTc10TrapControl 7 }
          cmcTcMasterTc10Control            OBJECT IDENTIFIER ::= { cmcTcMasterTc10 5 }
      cmcTcMasterTrapControl                OBJECT IDENTIFIER ::= { cmcTcMaster 8 }
        cmcTcMasterTraps                    OBJECT IDENTIFIER ::= { cmcTcMasterTrapControl 2 }


--******************************************************************************
--TCM CMC-TC Manager DK7230.000
--******************************************************************************
--cmcTcMasterMibRev-group

  cmcTcMasterMibMajRev OBJECT-TYPE
    SYNTAX INTEGER (1..32000)
    ACCESS read-only
    STATUS mandatory
    DESCRIPTION
      "The Major Revision level.
       A change in the major revision level represents a major change
       in the architecture of the MIB. A change in the major revision
       level may indicate a significant change in the information,
       correct interpretation of data may require a MIB document
       with the same major revision level."
    ::= { cmcTcMasterMibRev 1 }

  cmcTcMasterMibMinRev OBJECT-TYPE
    SYNTAX INTEGER (0..32000)
    ACCESS read-only
    STATUS mandatory
    DESCRIPTION
      "The Minor Revision level.
       A change in the minor revision level may represent some minor
       additional support, no changes to any pre-existing information
       has occurred."
    ::= { cmcTcMasterMibRev 2 }

  cmcTcMasterMibCondition OBJECT-TYPE
    SYNTAX INTEGER {
      other (1),
      ok (2),
      degraded (3),
      failed (4)
    }
    ACCESS read-only
    STATUS mandatory
    DESCRIPTION
      "The overall condition (status) of the system represented by
       this MIB.
       (2) OK
       (3) a minor problem, warning condition (yellow LED on the Master unit)
       (4) a major problem (red LED on the Master unit)"
    ::= { cmcTcMasterMibRev 3 }

--cmcTcMasterValues-group

  cmcTcMasterValueTemperature OBJECT-TYPE
    SYNTAX INTEGER
    ACCESS read-only
    STATUS mandatory
    DESCRIPTION
      "Temperature of Master unit, measured on processor."
    ::= { cmcTcMasterValues 1 }

--cmcTcMasterStatus-group

  cmcTcMasterStatusTemperature OBJECT-TYPE
    SYNTAX INTEGER {
      ok(1),
      tooHigh(2),
      tooLow(3),
      warning(4),
      error(5)
    }
    ACCESS read-only
    STATUS mandatory
    DESCRIPTION
      "Status temperature of Master unit, OK/ too high/ too low
       (see setpoints of temperature of Master unit)"
    ::= { cmcTcMasterStatus 1 }

--cmcTcMasterSetupGeneral-group

  cmcTcMasterSetTempUnit OBJECT-TYPE
    SYNTAX INTEGER {
      celsius(1),
      fahrenheit(2)
    }
    ACCESS read-write
    STATUS mandatory
    DESCRIPTION
      "Unit of temperature values and setpoints, Celsius or Fahrenheit"
    ::= { cmcTcMasterSetupGeneral 1 }

  cmcTcMasterSetBeeper OBJECT-TYPE
    SYNTAX INTEGER {
      off(1),
      on(2)
    }
    ACCESS read-write
    STATUS mandatory
    DESCRIPTION
      "Audible alarm in the Master unit:
       (1): beeper is off (general)
       (2): beeper is on (Alarm)"
    ::= { cmcTcMasterSetupGeneral 2 }

  cmcTcMasterLogicRelay OBJECT-TYPE
    SYNTAX INTEGER {
      closeAtAlarm(1),
      openAtAlarm(2),
      off(3)
    }
    ACCESS read-write
    STATUS mandatory
    DESCRIPTION
      "Logic of alarm relay: 
       (1): Relay will pick up in case of an alarm
       (2): Relay will release in case of an alarm
       (3): Relay off (general)"
    ::= { cmcTcMasterSetupGeneral 3 }
 
  cmcTcMasterWebAccess OBJECT-TYPE
    SYNTAX INTEGER {
      viewOnly(1),
      fullAccess(2),
      off(3)
    }
    ACCESS read-write
    STATUS mandatory
    DESCRIPTION
      "Web access via HTTP: 
       (1): view only
       (2): full Access, read and set
       (3): Web disabled (general)"
    ::= { cmcTcMasterSetupGeneral 4 }
 
--SetupClock

  cmcTcMasterSetupDate OBJECT-TYPE
    SYNTAX DisplayString (SIZE (0..10))
    ACCESS read-write
    STATUS mandatory
    DESCRIPTION
      "actual Date in format DD.MM.YYYY"
    ::= { cmcTcMasterSetupGeneral 5 }

  cmcTcMasterSetupTime OBJECT-TYPE
    SYNTAX DisplayString (SIZE (0..8))
    ACCESS read-write
    STATUS mandatory
    DESCRIPTION
      "actual Time in format HH:MM:SS, HH (0-23), MM (0-59), SS (0-59)"
    ::= { cmcTcMasterSetupGeneral 6 }
 
--table for action definitions
 
  cmcTcMasterActionTableNumber OBJECT-TYPE
    SYNTAX INTEGER 
    ACCESS read-only
    STATUS mandatory
    DESCRIPTION
      "Number of action-table entries available on this unit"
    ::= { cmcTcMasterActionTable1 1 }

  cmcTcMasterActionTable OBJECT-TYPE
    SYNTAX SEQUENCE OF CmcTcMasterActionEntry
    ACCESS not-accessible
    STATUS mandatory
    DESCRIPTION
      "Headline of action-table"
    ::= { cmcTcMasterActionTable1 2 }

  cmcTcMasterActionEntry OBJECT-TYPE
    SYNTAX CmcTcMasterActionEntry
    ACCESS not-accessible
    STATUS mandatory
    DESCRIPTION
      "Entries of action-table"
    INDEX { cmcTcMasterActionIndex }
    ::= { cmcTcMasterActionTable 1 }

  CmcTcMasterActionEntry ::=
    SEQUENCE {
      cmcTcMasterActionIndex
        INTEGER,
      cmcTcMasterActionDef 
        DisplayString (SIZE (0..1000))                              
    }

    cmcTcMasterActionIndex OBJECT-TYPE
      SYNTAX INTEGER (1..32000)
      ACCESS read-only
      STATUS mandatory
      DESCRIPTION
        "Index for the list of action entries. Its value ranges
         between 1 and the value of cmcTcMasterActionTableNumber." 
      ::= { cmcTcMasterActionEntry 1 }

    cmcTcMasterActionDef OBJECT-TYPE
      SYNTAX DisplayString (SIZE (0..1000))
      ACCESS read-write
      STATUS mandatory
      DESCRIPTION
        "string that describes the definition 
         of the action"
      ::= { cmcTcMasterActionEntry 2 }

--cmcTcMasterSetupTemperature-group

  cmcTcMasterSetupTemperatureAvail OBJECT-TYPE
    SYNTAX INTEGER {
      notAvailable(1),
      available(2)
    }
    ACCESS read-only
    STATUS mandatory
    DESCRIPTION
      "Temp sensor 1:   
       (1) not available
       (2) available"
    ::= { cmcTcMasterSetupTemperature 1 }

  cmcTcMasterSetupTemperatureRelay OBJECT-TYPE
    SYNTAX INTEGER {
      disabled(1),
      enabled(2)
    }
    ACCESS read-write
    STATUS mandatory
    DESCRIPTION
      "Alert handling of Alarm Relay in case of an alarm condition
       of Temperature:  
       (1) no switching of Relays
       (2) Relay will switch"
    ::= { cmcTcMasterSetupTemperature 2 }

  cmcTcMasterSetupTemperatureBeeper OBJECT-TYPE
    SYNTAX INTEGER {
      disabled(1),
      enabled(2)
    }
    ACCESS read-write
    STATUS mandatory
    DESCRIPTION
      "Alert handling of beeper of in case of an alarm condition
       of Temperature: 
       (1) No Audible Alarm
       (2) Start Audible Alarm"
    ::= { cmcTcMasterSetupTemperature 3 }
  
--cmcTcMasterSetpoints-group

  cmcTcMasterSetpointHighTemperature OBJECT-TYPE
    SYNTAX INTEGER (0..200)
    ACCESS read-write
    STATUS mandatory
    DESCRIPTION
      "Setpoint high value alarm temperature "
    ::= { cmcTcMasterSetpoints 1 }

  cmcTcMasterSetpointLowTemperature OBJECT-TYPE
    SYNTAX INTEGER (0..200)
    ACCESS read-write
    STATUS mandatory
    DESCRIPTION
      "Setpoint low value alarm temperature "
    ::= { cmcTcMasterSetpoints 2 }
 
  cmcTcMasterSetpointTemperature OBJECT-TYPE
    SYNTAX INTEGER (0..200)
    ACCESS read-write
    STATUS mandatory
    DESCRIPTION
      "Setpoint temperature for temperature warning"
    ::= { cmcTcMasterSetpoints 3 }

--cmcTcMasterControl-group

  cmcTcMasterControlAlarmRelay OBJECT-TYPE
    SYNTAX INTEGER {
      relayOff(1),
      relayOn(2)
    }
    ACCESS read-write
    STATUS mandatory
    DESCRIPTION
      "Control of Alarm relay"
    ::= { cmcTcMasterControl 1 }

  cmcTcMasterClearAlarm OBJECT-TYPE
    SYNTAX INTEGER {
      noClear(1),
      clear(2)
    }
    ACCESS read-write
    STATUS mandatory
    DESCRIPTION
      "Clear alarm, beeper and relay"
    ::= { cmcTcMasterControl 2 }

--cmcTcMasterDevice1-group

  cmcTcMasterDev1Type OBJECT-TYPE
    SYNTAX INTEGER {
      other (0),
      cmc (1),
      pcu (3),
      tc (4)
    }
    ACCESS read-only
    STATUS mandatory
    DESCRIPTION
      "Type of device1"
    ::= { cmcTcMasterDevice1 1 }

  cmcTcMasterDev1Status OBJECT-TYPE
    SYNTAX INTEGER {
      other (1),
      notConnected (2),
      normal (3),
      minor (4),
      major (5),
      configChanged (6),
      connectionLost (10)
    }
    ACCESS read-only
    STATUS mandatory
    DESCRIPTION
      "Status of device1"
    ::= { cmcTcMasterDevice1 2 }

  cmcTcMasterDev1Descr OBJECT-TYPE
    SYNTAX DisplayString (SIZE (0..255))
    ACCESS read-only
    STATUS mandatory
    DESCRIPTION
      "A textual description of the entity.  This value
       should include the full name and version
       identification of the system's hardware type,
       software operating-system, and networking
       software.  It is mandatory that this only contain
       printable ASCII characters."
    ::= { cmcTcMasterDevice1 3 }

  cmcTcMasterDev1UpTime OBJECT-TYPE
    SYNTAX TimeTicks
    ACCESS read-only
    STATUS mandatory
    DESCRIPTION
      "The time (in hundredths of a second) since the
       network management portion of the system was last
       re-initialized."
    ::= { cmcTcMasterDevice1 4 }

  cmcTcMasterDev1Contact OBJECT-TYPE
    SYNTAX DisplayString (SIZE (0..255))
    ACCESS read-write
    STATUS mandatory
    DESCRIPTION
      "The textual identification of the contact person
       for this managed node, together with information
       on how to contact this person."
    ::= { cmcTcMasterDevice1 5 }

  cmcTcMasterDev1Name OBJECT-TYPE
    SYNTAX DisplayString (SIZE (0..255))
    ACCESS read-write
    STATUS mandatory
    DESCRIPTION
      "An administratively-assigned name for this
       managed node.  By convention, this is the node's
       fully-qualified domain name."
    ::= { cmcTcMasterDevice1 6 }

  cmcTcMasterDev1Location OBJECT-TYPE
    SYNTAX DisplayString (SIZE (0..255))
    ACCESS read-write
    STATUS mandatory
    DESCRIPTION
      "The physical location of this node (e.g.,
       `telephone closet, 3rd floor')."
    ::= { cmcTcMasterDevice1 7 }

--cmcTcMasterCmc1Values-group

  cmcTcMasterCmc1ValueTemperature1 OBJECT-TYPE
    SYNTAX INTEGER
    ACCESS read-only
    STATUS mandatory
    DESCRIPTION
      "Actual value of temperature 1 in deg C"
    ::= { cmcTcMasterCmc1Values 1 }

  cmcTcMasterCmc1ValueTemperature2 OBJECT-TYPE
    SYNTAX INTEGER
    ACCESS read-only
    STATUS mandatory
    DESCRIPTION
      "Actual value of temperature 2 in deg C"
    ::= { cmcTcMasterCmc1Values 2 }

  cmcTcMasterCmc1ValuePowerSupply OBJECT-TYPE
    SYNTAX INTEGER
    ACCESS read-only
    STATUS mandatory
    DESCRIPTION
      "Actual value of power supply in V"
    ::= { cmcTcMasterCmc1Values 3 }

  cmcTcMasterCmc1ValueAnalogAux1 OBJECT-TYPE
    SYNTAX INTEGER
    ACCESS read-only
    STATUS mandatory
    DESCRIPTION
      "Actual value of aux. analog input 1
      (4-20mA = 0-100%)"
    ::= { cmcTcMasterCmc1Values 4 }

  cmcTcMasterCmc1ValueAnalogAux2 OBJECT-TYPE
    SYNTAX INTEGER
    ACCESS read-only
    STATUS mandatory
    DESCRIPTION
      "Actual value of aux. analog input 2
      (4-20mA = 0-100%)"
    ::= { cmcTcMasterCmc1Values 5 }

--cmcTcMasterCmc1Values-table-group

  cmcTcMasterCmc1ValuesNumber OBJECT-TYPE
    SYNTAX INTEGER
    ACCESS read-only
    STATUS mandatory
    DESCRIPTION
      "Number of value-table entries"
    ::= { cmcTcMasterCmc1Table1 1 }

  cmcTcMasterCmc1ValuesTable OBJECT-TYPE
    SYNTAX SEQUENCE OF CmcTcMasterCmc1ValuesEntry
    ACCESS not-accessible
    STATUS mandatory
    DESCRIPTION
      "Headline of value-table"
    ::= { cmcTcMasterCmc1Table1 2 }

  cmcTcMasterCmc1ValuesEntry OBJECT-TYPE
    SYNTAX CmcTcMasterCmc1ValuesEntry
    ACCESS not-accessible
    STATUS mandatory
    DESCRIPTION
      "Entries of value-table"
    INDEX { cmcTcMasterCmc1ValuesIndex }
    ::= { cmcTcMasterCmc1ValuesTable 1 }

  CmcTcMasterCmc1ValuesEntry ::=
    SEQUENCE {
      cmcTcMasterCmc1ValuesIndex
        INTEGER,
      cmcTcMasterCmc1ValuesText
        DisplayString (SIZE (0..31)),
      cmcTcMasterCmc1ValuesValue
        INTEGER,
      cmcTcMasterCmc1ValuesStatus
        INTEGER,
      cmcTcMasterCmc1ValuesMaxValue
        INTEGER,
      cmcTcMasterCmc1ValuesMinValue
        INTEGER
    }

    cmcTcMasterCmc1ValuesIndex OBJECT-TYPE
      SYNTAX INTEGER (1..32000)
      ACCESS read-only
      STATUS mandatory
      DESCRIPTION
        "Index for the list of value entries. Its value ranges
        between 1 and the value of valuesNumber."
      ::= { cmcTcMasterCmc1ValuesEntry 1 }

    cmcTcMasterCmc1ValuesText OBJECT-TYPE
      SYNTAX DisplayString (SIZE (0..31))
      ACCESS read-write
      STATUS mandatory
      DESCRIPTION
        "Text of the entry in the value-table"
      ::= { cmcTcMasterCmc1ValuesEntry 2 }

    cmcTcMasterCmc1ValuesValue OBJECT-TYPE
      SYNTAX INTEGER
      ACCESS read-only
      STATUS mandatory
      DESCRIPTION
        "Actual value of the value-table"
      ::= { cmcTcMasterCmc1ValuesEntry 3 }

    cmcTcMasterCmc1ValuesStatus OBJECT-TYPE
      SYNTAX INTEGER {
        valueOK(1),
        valueTooLow(2),
        valueTooHigh(3),
        valueERROR(4),
        notAvail(5)
      }
      ACCESS read-only
      STATUS mandatory
      DESCRIPTION
        "Status of the value"
      ::= { cmcTcMasterCmc1ValuesEntry 4 }

    cmcTcMasterCmc1ValuesMaxValue OBJECT-TYPE
      SYNTAX INTEGER
      ACCESS read-write
      STATUS mandatory
      DESCRIPTION
        "Value for max. alarm"
      ::= { cmcTcMasterCmc1ValuesEntry 5 }

    cmcTcMasterCmc1ValuesMinValue OBJECT-TYPE
      SYNTAX INTEGER
      ACCESS read-write
      STATUS mandatory
      DESCRIPTION
        "Value for min. alarm"
      ::= { cmcTcMasterCmc1ValuesEntry 6 }

--cmcTcMasterCmc1status-group

  cmcTcMasterCmc1StatusTemperature1 OBJECT-TYPE
    SYNTAX DisplayString (SIZE (0..31))
    ACCESS read-only
    STATUS mandatory
    DESCRIPTION
      "Status temperature 1, OK/ too low/ too high
       (see setpoints of temperature 1)"
    ::= { cmcTcMasterCmc1Status 1 }

  cmcTcMasterCmc1StatusTemperature2 OBJECT-TYPE
    SYNTAX DisplayString (SIZE (0..31))
    ACCESS read-only
    STATUS mandatory
    DESCRIPTION
      "Status temperature 2, OK/ too low/ too high
       (see setpoints of temperature 2)"
    ::= { cmcTcMasterCmc1Status 2 }

  cmcTcMasterCmc1StatusFan1 OBJECT-TYPE
    SYNTAX DisplayString (SIZE (0..31))
    ACCESS read-only
    STATUS mandatory
    DESCRIPTION
      "Status fan 1, Stop/ running/ fault"
    ::= { cmcTcMasterCmc1Status 3 }

  cmcTcMasterCmc1StatusFan2 OBJECT-TYPE
    SYNTAX DisplayString (SIZE (0..31))
    ACCESS read-only
    STATUS mandatory
    DESCRIPTION
      "Status fan 2, Stop/ running/ fault"
    ::= { cmcTcMasterCmc1Status 4 }

  cmcTcMasterCmc1StatusHeating OBJECT-TYPE
    SYNTAX DisplayString (SIZE (0..31))
    ACCESS read-only
    STATUS mandatory
    DESCRIPTION
      "Status heating, On/Off"
    ::= { cmcTcMasterCmc1Status 5 }

  cmcTcMasterCmc1StatusPowerSupply OBJECT-TYPE
    SYNTAX DisplayString (SIZE (0..31))
    ACCESS read-only
    STATUS mandatory
    DESCRIPTION
      "Status power supply, OK/ too low/ too high
       (see setpoints of power supply)"
    ::= { cmcTcMasterCmc1Status 6 }

  cmcTcMasterCmc1StatusAnalogAux1 OBJECT-TYPE
    SYNTAX DisplayString (SIZE (0..31))
    ACCESS read-only
    STATUS mandatory
    DESCRIPTION
      "Status aux analog input 1, OK/ too low/ too high"
    ::= { cmcTcMasterCmc1Status 7 }

  cmcTcMasterCmc1StatusAnalogAux2 OBJECT-TYPE
    SYNTAX DisplayString (SIZE (0..31))
    ACCESS read-only
    STATUS mandatory
    DESCRIPTION
      "Status aux analog input 2, OK/ too low/ too high"
    ::= { cmcTcMasterCmc1Status 8 }

  cmcTcMasterCmc1StatusDoor OBJECT-TYPE
    SYNTAX DisplayString (SIZE (0..31))
    ACCESS read-only
    STATUS mandatory
    DESCRIPTION
      "Status door, open/closed/locked"
    ::= { cmcTcMasterCmc1Status 9 }

  cmcTcMasterCmc1StatusUps1 OBJECT-TYPE
    SYNTAX DisplayString (SIZE (0..31))
    ACCESS read-only
    STATUS mandatory
    DESCRIPTION
      "Status UPS 1, OK/ fault"
    ::= { cmcTcMasterCmc1Status 10 }

  cmcTcMasterCmc1StatusUps2 OBJECT-TYPE
    SYNTAX DisplayString (SIZE (0..31))
    ACCESS read-only
    STATUS mandatory
    DESCRIPTION
      "Status UPS 2, OK/ fault"
    ::= { cmcTcMasterCmc1Status 11 }

  cmcTcMasterCmc1StatusSmokeSensor OBJECT-TYPE
    SYNTAX DisplayString (SIZE (0..31))
    ACCESS read-only
    STATUS mandatory
    DESCRIPTION
      "Status smoke-sensor, OK/ smoke"
    ::= { cmcTcMasterCmc1Status 12 }

  cmcTcMasterCmc1StatusVibrationSensor OBJECT-TYPE
    SYNTAX DisplayString (SIZE (0..31))
    ACCESS read-only
    STATUS mandatory
    DESCRIPTION
      "Status vibration sensor, OK/ vibration"
    ::= { cmcTcMasterCmc1Status 13 }

  cmcTcMasterCmc1StatusMessage OBJECT-TYPE
    SYNTAX DisplayString (SIZE (0..31))
    ACCESS read-only
    STATUS mandatory
    DESCRIPTION
      "Message from CMC"
    ::= { cmcTcMasterCmc1Status 14 }

  cmcTcMasterCmc1ValueOperatingTime OBJECT-TYPE
    SYNTAX DisplayString (SIZE (0..31))
    ACCESS read-only
    STATUS mandatory
    DESCRIPTION
      "Operating time CMC-unit"
    ::= { cmcTcMasterCmc1Status 15 }

  cmcTcMasterCmc1StatusUnit OBJECT-TYPE
    SYNTAX INTEGER {
      unitCelsius(1),
      unitFahrenheit(2)
    }
    ACCESS read-only
    STATUS mandatory
    DESCRIPTION
      "Unit of temperature-values, Celsius or Fahrenheit"
   ::= { cmcTcMasterCmc1Status 16 }

--*******************************************************
--cmcTcMasterCmc1Status-table-group

  cmcTcMasterCmc1StatusNumber OBJECT-TYPE
    SYNTAX INTEGER 
    ACCESS read-only
    STATUS mandatory
    DESCRIPTION
      "Number of status-table entries"
    ::= { cmcTcMasterCmc1Table 1 }

  cmcTcMasterCmc1StatusTable OBJECT-TYPE
    SYNTAX SEQUENCE OF CmcTcMasterCmc1StatusEntry
    ACCESS not-accessible
    STATUS mandatory
    DESCRIPTION
      "Headline of table"
    ::= { cmcTcMasterCmc1Table 2 }

  cmcTcMasterCmc1StatusEntry OBJECT-TYPE
    SYNTAX CmcTcMasterCmc1StatusEntry
    ACCESS not-accessible
    STATUS mandatory
    DESCRIPTION
      "A list of status entries.  The number of
       entries is given by the value of cmcTcMasterCmc1StatusNumber." 
    INDEX { cmcTcMasterCmc1StatusIndex }
    ::= { cmcTcMasterCmc1StatusTable 1 }

  CmcTcMasterCmc1StatusEntry ::=
    SEQUENCE {
      cmcTcMasterCmc1StatusIndex
        INTEGER,
      cmcTcMasterCmc1StatusText
        DisplayString (SIZE (0..31)),
      cmcTcMasterCmc1StatusStatus
        INTEGER              
    }

    cmcTcMasterCmc1StatusIndex OBJECT-TYPE
      SYNTAX INTEGER (1..32000)
      ACCESS read-only
      STATUS mandatory
      DESCRIPTION
        "Index fo the list of status entries. Its value ranges
         between 1 and the value of cmcTcMasterCmc1StatusNumber." 
      ::= { cmcTcMasterCmc1StatusEntry 1 }

    cmcTcMasterCmc1StatusText OBJECT-TYPE
      SYNTAX DisplayString (SIZE (0..31))
      ACCESS read-write
      STATUS mandatory
      DESCRIPTION
        "Text of the entry in the status-table"
      ::= { cmcTcMasterCmc1StatusEntry 2 }

    cmcTcMasterCmc1StatusStatus OBJECT-TYPE
      SYNTAX INTEGER  {
        statusOK(1),
        alarm(2),
        security(3),
        notAvail(4)
      }
      ACCESS read-only
      STATUS mandatory
      DESCRIPTION
        "Status of the table entry"
      ::= { cmcTcMasterCmc1StatusEntry 3 }

--******************************************************************************

--cmcTCMasterCmc1Set-group

  cmcTcMasterCmc1StatusAccess OBJECT-TYPE
    SYNTAX DisplayString (SIZE (0..31))
    ACCESS read-write
    STATUS mandatory
    DESCRIPTION
      "Status access"
    ::= { cmcTcMasterCmc1Set 1 }

  cmcTcMasterCmc1SetDoor OBJECT-TYPE
    SYNTAX INTEGER {
      lockDoor(1),
      openDoorTime(2),
      openDoorAccess(3),
      openDoor(4)
    }
    ACCESS read-write
    STATUS mandatory
    DESCRIPTION
      "Set door, see table"
    ::= { cmcTcMasterCmc1Set 2 }

  cmcTcMasterCmc1SetMessage OBJECT-TYPE
    SYNTAX DisplayString (SIZE (0..31))
    ACCESS read-write
    STATUS mandatory
    DESCRIPTION
      "Set message"
    ::= { cmcTcMasterCmc1Set 3 }

  cmcTcMasterCmc1SetFault        OBJECT-TYPE
    SYNTAX INTEGER {
      clearFault(1),
      setFault(2)
    }
    ACCESS read-write
    STATUS mandatory
    DESCRIPTION
      "Set fault, see table"
    ::= { cmcTcMasterCmc1Set 4 }

--cmcTcMasterCmc1RelayControl-group

  cmcTcMasterCmc1RelaytableMaxNum OBJECT-TYPE
    SYNTAX INTEGER 
    ACCESS read-only
    STATUS mandatory
    DESCRIPTION
      "Number of table entries"
    ::= { cmcTcMasterCmc1RelayControl 1 }

  cmcTcMasterCmc1RelayTable OBJECT-TYPE
    SYNTAX SEQUENCE OF CmcTcMasterCmc1RelayEntry
    ACCESS not-accessible
    STATUS mandatory
    DESCRIPTION
      "Headline of table for relay control"
    ::= { cmcTcMasterCmc1RelayControl 2 }

  cmcTcMasterCmc1RelayEntry OBJECT-TYPE
    SYNTAX CmcTcMasterCmc1RelayEntry
    ACCESS not-accessible
    STATUS mandatory
    DESCRIPTION
      "Entries"
    INDEX { cmcTcMasterCmc1RelaytableIndex }
    ::= { cmcTcMasterCmc1RelayTable 1 }

  CmcTcMasterCmc1RelayEntry ::=
    SEQUENCE {
      cmcTcMasterCmc1RelaytableIndex
        INTEGER,
      cmcTcMasterCmc1RelaytableText
	DisplayString (SIZE (0..31)),
      cmcTcMasterCmc1RelaytableStatus
        INTEGER              
    }

    cmcTcMasterCmc1RelaytableIndex OBJECT-TYPE
      SYNTAX INTEGER (1..32000)
      ACCESS read-only
      STATUS mandatory
      DESCRIPTION
        "Index for the relay-table. Its value ranges
         between 1 and cmcTcMasterCmc1RelaytableMaxNum"
      ::= { cmcTcMasterCmc1RelayEntry 1 }

    cmcTcMasterCmc1RelaytableText OBJECT-TYPE
      SYNTAX DisplayString (SIZE (0..31))
      ACCESS read-write
      STATUS mandatory
      DESCRIPTION
        "Description-Text for each relay in the table"
      ::= { cmcTcMasterCmc1RelayEntry 2 }

    cmcTcMasterCmc1RelaytableStatus OBJECT-TYPE
      SYNTAX INTEGER  {
        relayOFF(1),
        relayON(2),
        notAvail(3)
      }
      ACCESS read-write
      STATUS mandatory
      DESCRIPTION
        "Status of relays in the table"
      ::= { cmcTcMasterCmc1RelayEntry 3 }

--cmcTcMasterCmc1Setpoints-group

  cmcTcMasterCmc1SetpointFan1 OBJECT-TYPE
    SYNTAX INTEGER 
    ACCESS read-write
    STATUS mandatory
    DESCRIPTION
      "Setpoint Fan 1 in C, Fan 1 will start
       if temperature 1 exceeds this value"
    ::= { cmcTcMasterCmc1Setpoints 1 }

  cmcTcMasterCmc1SetpointFan2 OBJECT-TYPE
    SYNTAX INTEGER 
    ACCESS read-write
    STATUS mandatory
    DESCRIPTION
      "Setpoint Fan 2 in C, Fan 2 will start
       if temperature 2 exceeds this value"
    ::= { cmcTcMasterCmc1Setpoints 2 }

  cmcTcMasterCmc1SetpointHeating OBJECT-TYPE
    SYNTAX INTEGER 
    ACCESS read-write
    STATUS mandatory
    DESCRIPTION
      "Setpoint heating in C, heating will start
       if lowest value of temperature 1 and 2 falls below this value"
    ::= { cmcTcMasterCmc1Setpoints 3 }

  cmcTcMasterCmc1SetpointHighTemperature1 OBJECT-TYPE
    SYNTAX INTEGER 
    ACCESS read-write
    STATUS mandatory
    DESCRIPTION
      "Setpoint high value alarm temperature 1"
    ::= { cmcTcMasterCmc1Setpoints 4 }

  cmcTcMasterCmc1SetpointLowTemperature1 OBJECT-TYPE
    SYNTAX INTEGER 
    ACCESS read-write
    STATUS mandatory
    DESCRIPTION
      "Setpoint low value alarm temperature 1"
    ::= { cmcTcMasterCmc1Setpoints 5 }

  cmcTcMasterCmc1SetpointHighTemperature2 OBJECT-TYPE
    SYNTAX INTEGER 
    ACCESS read-write
    STATUS mandatory
    DESCRIPTION
      "Setpoint high value alarm temperature 2"
    ::= { cmcTcMasterCmc1Setpoints 6 }

  cmcTcMasterCmc1SetpointLowTemperature2 OBJECT-TYPE
    SYNTAX INTEGER 
    ACCESS read-write
    STATUS mandatory
    DESCRIPTION
      "Setpoint low value alarm temperature 2"
    ::= { cmcTcMasterCmc1Setpoints 7 }

  cmcTcMasterCmc1SetpointHighVoltage OBJECT-TYPE
    SYNTAX INTEGER 
    ACCESS read-write
    STATUS mandatory
    DESCRIPTION
      "Setpoint high value supply voltage alarm"
    ::= { cmcTcMasterCmc1Setpoints 8 }

  cmcTcMasterCmc1SetpointLowVoltage OBJECT-TYPE
    SYNTAX INTEGER
    ACCESS read-write
    STATUS mandatory
    DESCRIPTION
      "Setpoint low value supply voltage alarm"
    ::= { cmcTcMasterCmc1Setpoints 9 }

  cmcTcMasterCmc1SetpointLowAux1 OBJECT-TYPE
    SYNTAX INTEGER 
    ACCESS read-write
    STATUS mandatory
    DESCRIPTION
      "Setpoint low value Aux input 1 alarm"
    ::= { cmcTcMasterCmc1Setpoints 10 }

  cmcTcMasterCmc1SetpointHighAux1 OBJECT-TYPE
    SYNTAX INTEGER 
    ACCESS read-write
    STATUS mandatory
    DESCRIPTION
      "Setpoint high value Aux input 1 alarm"
    ::= { cmcTcMasterCmc1Setpoints 11 }

  cmcTcMasterCmc1SetpointLowAux2 OBJECT-TYPE
    SYNTAX INTEGER 
    ACCESS read-write
    STATUS mandatory
    DESCRIPTION
      "Setpoint low value Aux input 2 alarm"
    ::= { cmcTcMasterCmc1Setpoints 12 }

  cmcTcMasterCmc1SetpointHighAux2 OBJECT-TYPE
    SYNTAX INTEGER 
    ACCESS read-write
    STATUS mandatory
    DESCRIPTION
      "Setpoint high value Aux input alarm"
    ::= { cmcTcMasterCmc1Setpoints 13 }

--cmcTcMasterCmc1TrapControl-group

  cmcTcMasterCmc1SetTrapRepeat OBJECT-TYPE
    SYNTAX INTEGER {
      disableTrapRepeat(1),
      enableTrapRepeat(2)
    }
    ACCESS read-write
    STATUS mandatory
    DESCRIPTION
      "Enable/disable repeating of traps. If enabled, traps will
       be repeated after a repeat time, set in setTrapRepeatTime.
       Repeating can be stopped by setting setTrapQuit to quitTrap"
    ::= { cmcTcMasterCmc1TrapControl 1 }

  cmcTcMasterCmc1SetTrapRepeatTime OBJECT-TYPE
    SYNTAX INTEGER 
    ACCESS read-write
    STATUS mandatory
    DESCRIPTION
      "Time value (sec) for trap-repeating, if setTrapRepeat is enabled"
    ::= { cmcTcMasterCmc1TrapControl 2 }

  cmcTcMasterCmc1SetTrapQuit OBJECT-TYPE
    SYNTAX INTEGER {
      quitTrap(1),
      quitTrapOK(2),
      noTrapToQuit(3),
      trapToQuit(4)
    }
    ACCESS read-write
    STATUS mandatory
    DESCRIPTION
      "Quit trap to stop repeating."
    ::= { cmcTcMasterCmc1TrapControl 3 }

--cmcTcMasterCmc1TrapTable-group

  cmcTcMasterCmc1TraptableNumber OBJECT-TYPE
    SYNTAX INTEGER 
    ACCESS read-only
    STATUS mandatory
    DESCRIPTION
      "Number of trapTable entries. The number of trap-receiver"
    ::= { cmcTcMasterCmc1Traps 1 }

  cmcTcMasterCmc1TrapTable OBJECT-TYPE
    SYNTAX SEQUENCE OF CmcTcMasterCmc1TrapEntry
    ACCESS not-accessible
    STATUS mandatory
    DESCRIPTION
      "A list of trap-receiver entries"
    ::= { cmcTcMasterCmc1Traps 2 }

  cmcTcMasterCmc1TrapEntry OBJECT-TYPE
    SYNTAX CmcTcMasterCmc1TrapEntry
    ACCESS not-accessible
    STATUS mandatory
    DESCRIPTION
      "Entries of trapTable"
    INDEX { cmcTcMasterCmc1TrapIndex }
    ::= { cmcTcMasterCmc1TrapTable 1 }

  CmcTcMasterCmc1TrapEntry ::=
    SEQUENCE {
      cmcTcMasterCmc1TrapIndex
        INTEGER,
      cmcTcMasterCmc1TrapStatus
        INTEGER,
      cmcTcMasterCmc1TrapIPaddress
        DisplayString
    }

    cmcTcMasterCmc1TrapIndex OBJECT-TYPE
      SYNTAX INTEGER (1..32000)
      ACCESS read-only
      STATUS mandatory
      DESCRIPTION
        "Index for the trap-receiver-table. Its value ranges between
         1 and the value of cmcTcMasterCmc1TraptableNumber "
      ::= { cmcTcMasterCmc1TrapEntry 1 }

    cmcTcMasterCmc1TrapStatus OBJECT-TYPE
      SYNTAX INTEGER  {
        enabled(1),
        disabled(2)
      }
      ACCESS read-write
      STATUS mandatory
      DESCRIPTION
        "Enable or disable trap receiver"
      ::= { cmcTcMasterCmc1TrapEntry 2 }

    cmcTcMasterCmc1TrapIPaddress OBJECT-TYPE
      SYNTAX DisplayString (SIZE (0..31))
      ACCESS read-write
      STATUS mandatory
      DESCRIPTION
        "IP-address of trap-receiver"
      ::= { cmcTcMasterCmc1TrapEntry 3 }

--cmcTcMasterPcu1MibRev-group
          
  cmcTcMasterPcu1MibMajRev OBJECT-TYPE
    SYNTAX INTEGER (1..32000)
    ACCESS read-only
    STATUS mandatory
    DESCRIPTION
      "The Major Revision level.
       A change in the major revision level represents a major change
       in the architecture of the MIB. A change in the major revision 
       level may indicate a significant change in the information,
       correct interpretation of data may require a MIB document
       with the same major revision level."
    ::= { cmcTcMasterPcu1MibRev 1 }

  cmcTcMasterPcu1MibMinRev OBJECT-TYPE
    SYNTAX INTEGER (0..32000)
    ACCESS read-only
    STATUS mandatory
    DESCRIPTION
      "The Minor Revision level.
       A change in the minor revision level may represent some minor
       additional support, no changes to any pre-existing information
       has occurred."
    ::= { cmcTcMasterPcu1MibRev 2 }

  cmcTcMasterPcu1MibCondition OBJECT-TYPE
    SYNTAX INTEGER {
      other (1),
      ok (2),
      degraded (3),
      failed (4)
    }
    ACCESS read-only
    STATUS mandatory
    DESCRIPTION
      "The overall condition (status) of the system represented by
       this MIB. 
       (2) OK
       (3) a minor problem, warning condition (yellow LED on PCU)
       (4) a major problem (red LED on PCU)"
    ::= { cmcTcMasterPcu1MibRev 3 }

--cmcTcMasterPcu1Values-group

  cmcTcMasterPcu1ValueEnergy1 OBJECT-TYPE
    SYNTAX INTEGER 
    ACCESS read-only
    STATUS mandatory
    DESCRIPTION
      "Total value of the Energy (Wh), measured on IEC input 1"
    ::= { cmcTcMasterPcu1Values 1 }

  cmcTcMasterPcu1ValueEnergy2 OBJECT-TYPE
    SYNTAX INTEGER 
    ACCESS read-only
    STATUS mandatory
    DESCRIPTION
      "Actual value of the Energy (Wh), measured on IEC input 2"
    ::= { cmcTcMasterPcu1Values 2 }

  cmcTcMasterPcu1ValueEnergy1Time OBJECT-TYPE
    SYNTAX INTEGER 
    ACCESS read-only
    STATUS mandatory
    DESCRIPTION
      "Actual value of the Energy (Wh), measured on IEC input 1, can be set to 0
       Value can be used to calculate the energy over a fixed time"
    ::= { cmcTcMasterPcu1Values 3 }

  cmcTcMasterPcu1ValueEnergy2Time OBJECT-TYPE
    SYNTAX INTEGER 
    ACCESS read-only
    STATUS mandatory
    DESCRIPTION
      "Actual value of the Energy (Wh), measured on IEC input 2, can be set to 0.
       Value can be used to calculate the energy over a fixed time"
    ::= { cmcTcMasterPcu1Values 4 }

  cmcTcMasterPcu1ValuePower1 OBJECT-TYPE
    SYNTAX INTEGER 
    ACCESS read-only
    STATUS mandatory
    DESCRIPTION
      "Calculated actual power 1 (W). Calculated from cmcTcMasterPcu1ValueEnergy1/time"
    ::= { cmcTcMasterPcu1Values 5 }
          
  cmcTcMasterPcu1ValuePower2 OBJECT-TYPE
    SYNTAX INTEGER 
    ACCESS read-only
    STATUS mandatory
    DESCRIPTION
      "Calculated actual power 2 (W). Calculated from cmcTcMasterPcu1ValueEnergy2/time"
    ::= { cmcTcMasterPcu1Values 6 }
          
  cmcTcMasterPcu1ValueTemperature OBJECT-TYPE
    SYNTAX INTEGER 
    ACCESS read-only
    STATUS mandatory
    DESCRIPTION
      "Actual value of temperature 1 in deg C or deg F"
    ::= { cmcTcMasterPcu1Values 7 }
          
--cmcTcMasterPcu1Status-group

  cmcTcMasterPcu1StatusInput1 OBJECT-TYPE
    SYNTAX INTEGER {
      false(1),
      true(2),
      pending(3),
      notAvail(4)
    }
    ACCESS read-only
    STATUS mandatory
    DESCRIPTION
      "Status of digital Input 1
       (1) digital signal is true (contact closed if setup is NO)
       (2) digital signal is false(contact opened if setup is NO),
       note setup of input (NO/NC)
       (3) digital input is pending, note setup of delay"
    ::= { cmcTcMasterPcu1Status 1 }

  cmcTcMasterPcu1StatusInput2 OBJECT-TYPE
    SYNTAX INTEGER {
      false(1),
      true(2),
      pending(3),
      notAvail(4)
    }
    ACCESS read-only
    STATUS mandatory
    DESCRIPTION
      "Status of digital Input 2
       (1) digital signal is true (contact closed if setup is NO)
       (2) digital signal is false(contact opened if setup is NO),
       note setup of input (NO/NC)
       (3) digital input is pending, note setup of delay"
    ::= { cmcTcMasterPcu1Status 2 }

  cmcTcMasterPcu1StatusPower1 OBJECT-TYPE
    SYNTAX INTEGER {
      ok(1),
      tooHigh(2),
      tooLow(3),
      warning(4),
      error(5),
      notAvail(6)
    }
    ACCESS read-only
    STATUS mandatory
    DESCRIPTION
      "Status Power 1, see setpoints"
    ::= { cmcTcMasterPcu1Status 3 }

  cmcTcMasterPcu1StatusPower2 OBJECT-TYPE
    SYNTAX INTEGER {
      ok(1),
      tooHigh(2),
      tooLow(3),
      warning(4),
      error(5),
      notAvail(6)
    }
    ACCESS read-only
    STATUS mandatory
    DESCRIPTION
      "Status Power 2, see setpoints"
    ::= { cmcTcMasterPcu1Status 4 }

  cmcTcMasterPcu1StatusTemperature OBJECT-TYPE
    SYNTAX INTEGER {
      ok(1),
      tooHigh(2),
      tooLow(3),
      warning(4),
      error(5)
    }
    ACCESS read-only
    STATUS mandatory
    DESCRIPTION
      "Status temperature 1, OK/ too high/ too low
       (see setpoints of temperature 1)"
    ::= { cmcTcMasterPcu1Status 5 }

--cmcTcMasterPcu1Status-table-group

  cmcTcMasterPcu1OutletsNumber OBJECT-TYPE
    SYNTAX INTEGER 
    ACCESS read-only
    STATUS mandatory
    DESCRIPTION
      "Number of value-table entries=number of outlets available on this unit"
    ::= { cmcTcMasterPcu1StatusTable1 1 }

  cmcTcMasterPcu1StatusTable OBJECT-TYPE
    SYNTAX SEQUENCE OF CmcTcMasterPcu1StatusEntry
    ACCESS not-accessible
    STATUS mandatory
    DESCRIPTION
      "Headline of status-table"
    ::= { cmcTcMasterPcu1StatusTable1 2 }

  cmcTcMasterPcu1StatusEntry OBJECT-TYPE
    SYNTAX CmcTcMasterPcu1StatusEntry
    ACCESS not-accessible
    STATUS mandatory
    DESCRIPTION
      "Entries of status-table"
    INDEX { cmcTcMasterPcu1StatusIndex }
    ::= { cmcTcMasterPcu1StatusTable 1 }

    CmcTcMasterPcu1StatusEntry ::=
      SEQUENCE {
        cmcTcMasterPcu1StatusIndex
          INTEGER,
        cmcTcMasterPcu1StatusText
          DisplayString (SIZE (0..31)),                
        cmcTcMasterPcu1StatusStatus
          INTEGER,
        cmcTcMasterPcu1ControlSNMP
          INTEGER,
        cmcTcMasterPcu1FrontSwitch
          INTEGER,
        cmcTcMasterPcu1Delay
          INTEGER,
        cmcTcMasterPcu1Input1
          INTEGER,
        cmcTcMasterPcu1Input2
          INTEGER,
        cmcTcMasterPcu1Temperature
          INTEGER,          
        cmcTcMasterPcu1Power
          INTEGER,          
        cmcTcMasterPcu1RestoreOutputStatus
          INTEGER           
      }

    cmcTcMasterPcu1StatusIndex OBJECT-TYPE
      SYNTAX INTEGER (1..32000)
      ACCESS read-only
      STATUS mandatory
      DESCRIPTION
        "Index for the list of value entries. Its value ranges
         between 1 and the value of cmcTcMasterPcu1OutletsNumber."
      ::= { cmcTcMasterPcu1StatusEntry 1 }

    cmcTcMasterPcu1StatusText OBJECT-TYPE
      SYNTAX DisplayString (SIZE (0..31))
      ACCESS read-write
      STATUS mandatory
      DESCRIPTION
        "Descriptional text for each outlet (entry in the table)"
      ::= { cmcTcMasterPcu1StatusEntry 2 }
              
    cmcTcMasterPcu1StatusStatus OBJECT-TYPE
      SYNTAX INTEGER {
        ok(1),
        onFrontKey(2),
        offFrontKey(3),
        onWEB(4),
        offWEB(5),
        onInput1(6),
        offInput1(7),
        onInput2(8),
        offInput2(9),
        onTemp(10),
        offTemp(11),
        onSNMP(12),
        offSNMP(13),
        onTimer(14),
        offTimer(15),
        onDelay(16),
        onConsole(17),
        offConsole(18),
        onReboot(19), 
        offReboot(20),
        onPower(21),
        offPower(22)
      }
      ACCESS read-only
      STATUS mandatory
      DESCRIPTION
        "Actual status of the outlet"
      ::= { cmcTcMasterPcu1StatusEntry 3 }

    cmcTcMasterPcu1ControlSNMP OBJECT-TYPE
      SYNTAX INTEGER  {
        on(1),
        off(2)
      }
      ACCESS read-write
      STATUS mandatory
      DESCRIPTION
        "Control via SNMP"
      ::= { cmcTcMasterPcu1StatusEntry 4 }

    cmcTcMasterPcu1FrontSwitch OBJECT-TYPE
      SYNTAX INTEGER {
        disabled(1),
        enabled(2)
      }
      ACCESS read-write
      STATUS mandatory
      DESCRIPTION
        "Control via front switch"
      ::= { cmcTcMasterPcu1StatusEntry 5 }
 
    cmcTcMasterPcu1Delay OBJECT-TYPE
      SYNTAX INTEGER (0..300)
      ACCESS read-write
      STATUS mandatory
      DESCRIPTION
        "Value for delay time in seconds.
         Value>0: Output is switched off for this time (in sec)"
      ::= { cmcTcMasterPcu1StatusEntry 6 }

    cmcTcMasterPcu1Input1 OBJECT-TYPE
      SYNTAX INTEGER {
        disabled(1),
        switchOn(2),
        switchOff(3),
        switchOnOff(4)
      }
      ACCESS read-write
      STATUS mandatory
      DESCRIPTION
        "Control via digital input 1
         (1): disabled
         (2): output is switched on in case of input 1 alarm
         (3): output is switched off in case of input 1 alarm
         (4): output has same status as input 1"
      ::= { cmcTcMasterPcu1StatusEntry 7 }

    cmcTcMasterPcu1Input2 OBJECT-TYPE
      SYNTAX INTEGER {
        disabled(1),
        switchOn(2),
        switchOff(3),
        switchOnOff(4)
      }
      ACCESS read-write
      STATUS mandatory
      DESCRIPTION
        "Control via digital input 2
         (1): disabled
         (2): output is switched on in case of input 2 alarm
         (3): output is switched off in case of input 2 alarm
         (4): output has same status as input 2"             
      ::= { cmcTcMasterPcu1StatusEntry 8 }

    cmcTcMasterPcu1Temperature OBJECT-TYPE
      SYNTAX INTEGER {
        disabled(1),
        switchOffAlarm(2),
        switchOnAlarm(3),
        switchOffSetpoint(4),
        switchOnSetpoint(5)
      }
      ACCESS read-write
      STATUS mandatory
      DESCRIPTION
        "Control via temperature alarm or setpoint
         (1): disabled
         (2): output is switched off in case of temperature alarm
         (3): output is switched on in case of temperature alarm
         (4): output is switched off if temperature setpoint (cmcTcMasterPcu1SetpointTemperature)
              is reached
         (5): output is switched on if temperature setpoint (cmcTcMasterPcu1SetpointTemperature)
              is reached"
      ::= { cmcTcMasterPcu1StatusEntry 9 }   
    
    cmcTcMasterPcu1Power OBJECT-TYPE
      SYNTAX INTEGER {
        disabled(1),
        switchOffAlarm(2),
        switchOffWarning(3),
        switchOnAlarm(4),
        switchOnWarning(5)
      }
      ACCESS read-write
      STATUS mandatory
      DESCRIPTION
        "Control via power setpoint
         (1): disabled
         (2): output is switched off upon power high alarm (cmcTcMasterPcu1SetpointHighPower1)
         (3): output is switched off upon power warning (cmcTcMasterPcu1SetpointWarningPower1)
         (4): output is switched on upon power alarm (cmcTcMasterPcu1SetpointHigh(Low)Power1)
         (5): output is switched on upon power warning (cmcTcMasterPcu1SetpointWarningPower1)             "
      ::= { cmcTcMasterPcu1StatusEntry 10 }                

    cmcTcMasterPcu1RestoreOutputStatus OBJECT-TYPE
      SYNTAX INTEGER {
        disabled(1),
        enabled(2)
      }
      ACCESS read-write
      STATUS mandatory
      DESCRIPTION
        "Save last output status and switch output to this status after reboot"
      ::= { cmcTcMasterPcu1StatusEntry 11 }
                
--cmcTcMasterPcu1SetupGeneral-group

  cmcTcMasterPcu1SetTempUnit OBJECT-TYPE
    SYNTAX INTEGER {
      celsius(1),
      fahrenheit(2)
    }
    ACCESS read-write
    STATUS mandatory
    DESCRIPTION
      "Unit of all temperature values and setpoints, Celsius or Fahrenheit"
    ::= { cmcTcMasterPcu1SetupGeneral 1 }

  cmcTcMasterPcu1SetBeeper OBJECT-TYPE
    SYNTAX INTEGER {
      off(1),
      on(2),
      enableClear(3)
    }
    ACCESS read-write
    STATUS mandatory
    DESCRIPTION
      "Audible alarm in PCU unit:
       (1): beeper is off (general)
       (2): beeper is on (Alarm)
       (3): enable Clear (cmcTcMasterPcu1ClearAlarm)"
    ::= { cmcTcMasterPcu1SetupGeneral 2 }

  cmcTcMasterPcu1LogicRelay OBJECT-TYPE
    SYNTAX INTEGER {
      closeAtAlarm(1),
      openAtAlarm(2),
      off(3),
      enableRemote(4)
    }
    ACCESS read-write
    STATUS mandatory
    DESCRIPTION
      "Logic of alarm relay: 
       (1): Relay will pick up in case of an alarm
       (2): Relay will release in case of an alarm
       (3): Relay off (general)
       (4): enable remote relay control (SNMP set)"
    ::= { cmcTcMasterPcu1SetupGeneral 3 }
 
  cmcTcMasterPcu1ClearRelay OBJECT-TYPE
    SYNTAX INTEGER {
      disabled(1),
      enabled(2)
    }
    ACCESS read-write
    STATUS mandatory
    DESCRIPTION
      "Enable clear of alarm relay: 
       (1): Relay cannot be cleared by cmcTcMasterPcu1ClearAlarm
       (2): Relay can be cleared by cmcTcMasterPcu1ClearAlarm"
    ::= { cmcTcMasterPcu1SetupGeneral 4 }                  

  cmcTcMasterPcu1WebAccess OBJECT-TYPE
    SYNTAX INTEGER {
      viewOnly(1),
      fullAccess(2),
      off(3)
    }
    ACCESS read-write
    STATUS mandatory
    DESCRIPTION
      "Web access via HTTP: 
       (1): view only
       (2): full Access, read and set
       (3): Web disabled (general)"
    ::= { cmcTcMasterPcu1SetupGeneral 5 }
 
  cmcTcMasterPcu1SetupDate OBJECT-TYPE
    SYNTAX DisplayString (SIZE (0..10))
    ACCESS read-write
    STATUS mandatory
    DESCRIPTION
      "actual Date in format DD.MM.YYYY"
    ::= { cmcTcMasterPcu1SetupGeneral 6 }

  cmcTcMasterPcu1SetupTime OBJECT-TYPE
    SYNTAX DisplayString (SIZE (0..8))
    ACCESS read-write
    STATUS mandatory
    DESCRIPTION
      "actual Time in format HH:MM:SS, HH (0-23), MM (0-59), SS (0-59)"
    ::= { cmcTcMasterPcu1SetupGeneral 7 }

--cmcTcMasterPcu1TimerTable1-group
 
  cmcTcMasterPcu1TimerNumber OBJECT-TYPE
    SYNTAX INTEGER 
    ACCESS read-only
    STATUS mandatory
    DESCRIPTION
      "Number of timers available on this unit"
    ::= { cmcTcMasterPcu1TimerTable1 1 }

  cmcTcMasterPcu1TimerTable OBJECT-TYPE
    SYNTAX SEQUENCE OF CmcTcMasterPcu1TimerEntry
    ACCESS not-accessible
    STATUS mandatory
    DESCRIPTION
      "Headline of timer-table"
    ::= { cmcTcMasterPcu1TimerTable1 2 }

  cmcTcMasterPcu1TimerEntry OBJECT-TYPE
    SYNTAX CmcTcMasterPcu1TimerEntry
    ACCESS not-accessible
    STATUS mandatory
    DESCRIPTION
      "Entries of timer-table"
    INDEX { cmcTcMasterPcu1TimerIndex }
    ::= { cmcTcMasterPcu1TimerTable 1 }

    CmcTcMasterPcu1TimerEntry ::=
      SEQUENCE {
        cmcTcMasterPcu1TimerIndex
          INTEGER,
        cmcTcMasterPcu1TimerStatus
          INTEGER,
        cmcTcMasterPcu1TimerDayOfWeek
          INTEGER,  
        cmcTcMasterPcu1TimeOn 
          DisplayString (SIZE (0..5)),                              
        cmcTcMasterPcu1TimeOff 
          DisplayString (SIZE (0..5)),                              
        cmcTcMasterPcu1TimeControl
          INTEGER,
        cmcTcMasterPcu1TimerOutput1
          INTEGER,
        cmcTcMasterPcu1TimerOutput2
          INTEGER         
      }

    cmcTcMasterPcu1TimerIndex OBJECT-TYPE
      SYNTAX INTEGER (1..32000)
      ACCESS read-only
      STATUS mandatory
      DESCRIPTION
        "Index for the list of timer entries. Its value ranges
         between 1 and the value of cmcTcMasterPcu1TimerNumber." 
      ::= { cmcTcMasterPcu1TimerEntry 1 }

    cmcTcMasterPcu1TimerStatus OBJECT-TYPE
      SYNTAX INTEGER {
        switchedOff(1),
        switchedOn(2),
        noTime(3) 
      }
      ACCESS read-only
      STATUS mandatory
      DESCRIPTION
        "Actual status of the timer"
      ::= { cmcTcMasterPcu1TimerEntry 2 }

    cmcTcMasterPcu1TimerDayOfWeek OBJECT-TYPE
      SYNTAX INTEGER {
        sun(1),
        mon(2),
        tue(3) ,
        wed(4),
        thu(5),
        fre(6),
        sat(7),
        sat-sun(8),
        mo-fr(9),
        mo-su(10)
      }
      ACCESS read-write
      STATUS mandatory
      DESCRIPTION
        "Day when the timer is active"
      ::= { cmcTcMasterPcu1TimerEntry 3 }
             
    cmcTcMasterPcu1TimeOn OBJECT-TYPE
      SYNTAX DisplayString (SIZE (0..5))
      ACCESS read-write
      STATUS mandatory
      DESCRIPTION
        "Time to switch on current outlet, 
         Format: HH:MM"
      ::= { cmcTcMasterPcu1TimerEntry 4 }

    cmcTcMasterPcu1TimeOff OBJECT-TYPE
      SYNTAX DisplayString (SIZE (0..5))
      ACCESS read-write
      STATUS mandatory
      DESCRIPTION
        "Time to switch off current outlet,
         Format: HH:MM"
      ::= { cmcTcMasterPcu1TimerEntry 5 }

    cmcTcMasterPcu1TimeControl OBJECT-TYPE
      SYNTAX INTEGER {
        disabled(1),
        enabled(2)
      }
      ACCESS read-write
      STATUS mandatory
      DESCRIPTION
        "Control via RTC"
      ::= { cmcTcMasterPcu1TimerEntry 6 }

    cmcTcMasterPcu1TimerOutput1 OBJECT-TYPE
      SYNTAX INTEGER 
      ACCESS read-write
      STATUS mandatory
      DESCRIPTION
        "Output which is controlled via timer"
      ::= { cmcTcMasterPcu1TimerEntry 7 }

    cmcTcMasterPcu1TimerOutput2 OBJECT-TYPE
      SYNTAX INTEGER 
      ACCESS read-write
      STATUS mandatory
      DESCRIPTION
        "Output which is controlled via timer"
      ::= { cmcTcMasterPcu1TimerEntry 8 }

--cmcTcMasterPcu1SetupPower1-group                     

  cmcTcMasterPcu1SetupPower1Avail OBJECT-TYPE
    SYNTAX INTEGER {
      notAvailable(1),
      available(2)
    }
    ACCESS read-write
    STATUS mandatory
    DESCRIPTION
      "Energy sensor 1 sensor:   
       (1) not available
       (2) available"
    ::= { cmcTcMasterPcu1SetupPower1 1 }

  cmcTcMasterPcu1SetupPower1Relay OBJECT-TYPE
    SYNTAX INTEGER {
      disabled(1),
      enabled(2)
    }
    ACCESS read-write
    STATUS mandatory
    DESCRIPTION
      "Alert handling of Alarm Relay in case of an alarm condition
       of Power 1:  
       (1) no switching of Relays
       (2) Relay will switch"
    ::= { cmcTcMasterPcu1SetupPower1 2 }

  cmcTcMasterPcu1SetupPower1Beeper OBJECT-TYPE
    SYNTAX INTEGER {
      disabled(1),
      enabled(2)
    }
    ACCESS read-write
    STATUS mandatory
    DESCRIPTION
      "Alert handling of beeper of in case of an alarm condition
       of Power 1: 
       (1) No Audible Alarm
       (2) Start Audible Alarm"
    ::= { cmcTcMasterPcu1SetupPower1 3 }

--cmcTcMasterPcu1SetupPower2-group                     

  cmcTcMasterPcu1SetupPower2Avail OBJECT-TYPE
    SYNTAX INTEGER {
      notAvailable(1),
      available(2)
    }
    ACCESS read-write
    STATUS mandatory
    DESCRIPTION
      "Energy sensor 2:   
       (1) not available
       (2) available"
    ::= { cmcTcMasterPcu1SetupPower2 1 }

  cmcTcMasterPcu1SetupPower2Relay OBJECT-TYPE
    SYNTAX INTEGER {
      disabled(1),
      enabled(2)
    }
    ACCESS read-write
    STATUS mandatory
    DESCRIPTION
      "Alert handling of Alarm Relay in case of an alarm condition
       of Power 2:  
       (1) no switching of Relay
       (2) Relay will switch"
    ::= { cmcTcMasterPcu1SetupPower2 2 }

  cmcTcMasterPcu1SetupPower2Beeper OBJECT-TYPE
    SYNTAX INTEGER {
      disabled(1),
      enabled(2)
    }
    ACCESS read-write
    STATUS mandatory
    DESCRIPTION
      "Alert handling of beeper of in case of an alarm condition
       of Power 2: 
       (1) No Audible Alarm
       (2) Start Audible Alarm"
    ::= { cmcTcMasterPcu1SetupPower2 3 }

--cmcTcMasterPcu1SetupInput1-group

  cmcTcMasterPcu1SetupInput1Avail OBJECT-TYPE
    SYNTAX INTEGER {
      notAvailable(1),
      available(2)
    }
    ACCESS read-write
    STATUS mandatory
    DESCRIPTION
      "Input 1 sensor:   
       (1) not available
       (2) available"
    ::= { cmcTcMasterPcu1SetupInput1 1 }

  cmcTcMasterPcu1SetupInput1Relay OBJECT-TYPE
    SYNTAX INTEGER {
      disabled(1),
      enabled(2)
    }
    ACCESS read-write
    STATUS mandatory
    DESCRIPTION
      "Alert handling of Alarm Relay in case of an alarm condition
       of Input 1:  
       (1) no switching of Relay
       (2) Relay will switch"
    ::= { cmcTcMasterPcu1SetupInput1 2 }

  cmcTcMasterPcu1SetupInput1Beeper OBJECT-TYPE
    SYNTAX INTEGER {
      disabled(1),
      enabled(2)
    }
    ACCESS read-write
    STATUS mandatory
    DESCRIPTION
      "Alert handling of beeper of in case of an alarm condition
       of Input 1: 
       (1) No Audible Alarm
       (2) Start Audible Alarm"
    ::= { cmcTcMasterPcu1SetupInput1 3 }

  cmcTcMasterPcu1SetupInput1Contact OBJECT-TYPE
    SYNTAX INTEGER {
      contactNO(1),
      contactNC(2),
      notAvail(3)
    }
    ACCESS read-write
    STATUS mandatory
    DESCRIPTION
      "Setup of digital input 1"
    ::= { cmcTcMasterPcu1SetupInput1 4 }

  cmcTcMasterPcu1SetupInput1Delay OBJECT-TYPE
    SYNTAX INTEGER (0..60)
    ACCESS read-write
    STATUS mandatory
    DESCRIPTION
      "Delay for changing of input state"
    ::= { cmcTcMasterPcu1SetupInput1 5 }

--cmcTcMasterPcu1SetupInput2-group

  cmcTcMasterPcu1SetupInput2Avail OBJECT-TYPE
    SYNTAX INTEGER {
      notAvailable(1),
      available(2)
    }
    ACCESS read-write
    STATUS mandatory
    DESCRIPTION
      "Input 2 sensor:   
       (2) available
       (1) not available"
    ::= { cmcTcMasterPcu1SetupInput2 1 }

  cmcTcMasterPcu1SetupInput2Relay OBJECT-TYPE
    SYNTAX INTEGER {
      disabled(1),
      enabled(2)
    }
    ACCESS read-write
    STATUS mandatory
    DESCRIPTION
      "Alert handling of Alarm Relay in case of an alarm condition
       of Input 1:  
       (1) no switching of Relays
       (2) Relay will switch"
    ::= { cmcTcMasterPcu1SetupInput2 2 }

  cmcTcMasterPcu1SetupInput2Beeper OBJECT-TYPE
    SYNTAX INTEGER {
      disabled(1),
      enabled(2)
    }
    ACCESS read-write
    STATUS mandatory
    DESCRIPTION
      "Alert handling of beeper of in case of an alarm condition
       of Input 2: 
       (1) No Audible Alarm
       (2) Start Audible Alarm"
    ::= { cmcTcMasterPcu1SetupInput2 3 }

  cmcTcMasterPcu1SetupInput2Contact OBJECT-TYPE
    SYNTAX INTEGER {
      contactNO(1),
      contactNC(2),
      notAvail(3)
    }
    ACCESS read-write
    STATUS mandatory
    DESCRIPTION
      "Setup of digital input 2"
    ::= { cmcTcMasterPcu1SetupInput2 4 }

  cmcTcMasterPcu1SetupInput2Delay OBJECT-TYPE
    SYNTAX INTEGER (0..60)
    ACCESS read-write
    STATUS mandatory
    DESCRIPTION
      "Delay for changing of input state"
    ::= { cmcTcMasterPcu1SetupInput2 5 }

--cmcTcMasterPcu1SetupTemperature-group                     

  cmcTcMasterPcu1SetupTemperatureAvail OBJECT-TYPE
    SYNTAX INTEGER {
      notAvailable(1),
      available(2)
    }
    ACCESS read-write
    STATUS mandatory
    DESCRIPTION
      "Temp sensor 1:   
       (1) not available
       (2) available"
    ::= { cmcTcMasterPcu1SetupTemperature 1 }

  cmcTcMasterPcu1SetupTemperatureRelay OBJECT-TYPE
    SYNTAX INTEGER {
      disabled(1),
      enabled(2)
    }
    ACCESS read-write
    STATUS mandatory
    DESCRIPTION
      "Alert handling of Alarm Relay in case of an alarm condition
       of Temperature:  
       (1) no switching of Relays
       (2) Relay will switch"
    ::= { cmcTcMasterPcu1SetupTemperature 2 }

  cmcTcMasterPcu1SetupTemperatureBeeper OBJECT-TYPE
    SYNTAX INTEGER {
      disabled(1),
      enabled(2)
    }
    ACCESS read-write
    STATUS mandatory
    DESCRIPTION
      "Alert handling of beeper of in case of an alarm condition
       of Temperature: 
       (1) No Audible Alarm
       (2) Start Audible Alarm"
    ::= { cmcTcMasterPcu1SetupTemperature 3 }

--cmcTcMasterPcu1SetupGeneral-group

  cmcTcMasterPcu1SetMessage OBJECT-TYPE
    SYNTAX DisplayString (SIZE (0..31))
    ACCESS read-write
    STATUS mandatory
    DESCRIPTION
      "Set message"
    ::= { cmcTcMasterPcu1SetupDevice 1 }

--cmcTcMasterPcu1Setpoints-group

  cmcTcMasterPcu1SetpointHighPower1 OBJECT-TYPE
    SYNTAX INTEGER 
    ACCESS read-write
    STATUS mandatory
    DESCRIPTION
      "Setpoint high value power consumption 1 alarm"
    ::= { cmcTcMasterPcu1Setpoints 1 }

  cmcTcMasterPcu1SetpointWarningPower1 OBJECT-TYPE
    SYNTAX INTEGER 
    ACCESS read-write
    STATUS mandatory
    DESCRIPTION
      "Setpoint warning value power consumption 1 alarm"
    ::= { cmcTcMasterPcu1Setpoints 2 }

  cmcTcMasterPcu1SetpointLowPower1 OBJECT-TYPE
    SYNTAX INTEGER
    ACCESS read-write
    STATUS mandatory
    DESCRIPTION
      "Setpoint low value power consumption 1 alarm"
    ::= { cmcTcMasterPcu1Setpoints 3 }

  cmcTcMasterPcu1SetpointHighPower2 OBJECT-TYPE
    SYNTAX INTEGER 
    ACCESS read-write
    STATUS mandatory
    DESCRIPTION
      "Setpoint high value power consumption 2 alarm"
    ::= { cmcTcMasterPcu1Setpoints 4 }

  cmcTcMasterPcu1SetpointWarningPower2 OBJECT-TYPE
    SYNTAX INTEGER 
    ACCESS read-write
    STATUS mandatory
    DESCRIPTION
      "Setpoint warning value power consumption 2 alarm"
    ::= { cmcTcMasterPcu1Setpoints 5 }

  cmcTcMasterPcu1SetpointLowPower2 OBJECT-TYPE
    SYNTAX INTEGER
    ACCESS read-write
    STATUS mandatory
    DESCRIPTION
      "Setpoint low value power consumption 2 alarm"
    ::= { cmcTcMasterPcu1Setpoints 6 }

  cmcTcMasterPcu1SetpointHighTemperature OBJECT-TYPE
    SYNTAX INTEGER (0..200)
    ACCESS read-write
    STATUS mandatory
    DESCRIPTION
      "Setpoint high value alarm temperature "
    ::= { cmcTcMasterPcu1Setpoints 7 }

  cmcTcMasterPcu1SetpointLowTemperature OBJECT-TYPE
    SYNTAX INTEGER (0..50)
    ACCESS read-write
    STATUS mandatory
    DESCRIPTION
      "Setpoint low value alarm temperature "
    ::= { cmcTcMasterPcu1Setpoints 8 }
 
  cmcTcMasterPcu1SetpointTemperature OBJECT-TYPE
    SYNTAX INTEGER (0..200)
    ACCESS read-write
    STATUS mandatory
    DESCRIPTION
      "Setpoint temperature for outlet control 
       and temperature warning"
    ::= { cmcTcMasterPcu1Setpoints 9 }

  cmcTcMasterPcu1SetpointTemperatureHyst OBJECT-TYPE
    SYNTAX INTEGER (0..15)
    ACCESS read-write
    STATUS mandatory
    DESCRIPTION
      "Hysteresis for cmcTcMasterPcu1SetpointTemperature"
    ::= { cmcTcMasterPcu1Setpoints 10 }
 
--cmcTcMasterPcu1Control-group

  cmcTcMasterPcu1ResetEnergy1 OBJECT-TYPE
    SYNTAX INTEGER {
      noReset(1),
      reset(2)
    }
    ACCESS read-write
    STATUS mandatory
    DESCRIPTION
      "Reset value of cmcTcMasterPcu1ValueEnergy1Time"
    ::= { cmcTcMasterPcu1Control 1 }

  cmcTcMasterPcu1ResetEnergy2 OBJECT-TYPE
    SYNTAX INTEGER {
      noReset(1),
      reset(2)
    }
    ACCESS read-write
    STATUS mandatory
    DESCRIPTION
      "Reset value of cmcTcMasterPcu1ValueEnergy2Time"
    ::= { cmcTcMasterPcu1Control 2 }

  cmcTcMasterPcu1ControlAlarmRelay OBJECT-TYPE
    SYNTAX INTEGER {
      relayOff(1),
      relayOn(2)
    }
    ACCESS read-write
    STATUS mandatory
    DESCRIPTION
      "Control of Alarm relay"
    ::= { cmcTcMasterPcu1Control 3 }

  cmcTcMasterPcu1ClearAlarm OBJECT-TYPE
    SYNTAX INTEGER {
      noClear(1),
      clear(2)
    }
    ACCESS read-write
    STATUS mandatory
    DESCRIPTION
      "Clear alarm, beeper and relay"
    ::= { cmcTcMasterPcu1Control 4 }

--cmcTcMasterPcu1TrapTable-group

  cmcTcMasterPcu1TrapTableNumber OBJECT-TYPE
    SYNTAX INTEGER 
    ACCESS read-only
    STATUS mandatory
    DESCRIPTION
      "Number of cmcTcMasterPcu1TrapTable entries. The number of trap-receivers avail."
    ::= { cmcTcMasterPcu1Traps 1 }

  cmcTcMasterPcu1TrapTable OBJECT-TYPE
    SYNTAX SEQUENCE OF CmcTcMasterPcu1TrapEntry
    ACCESS not-accessible
    STATUS mandatory
    DESCRIPTION
      "A list of trap-receiver entries"
    ::= { cmcTcMasterPcu1Traps 2 }

  cmcTcMasterPcu1TrapEntry OBJECT-TYPE
    SYNTAX CmcTcMasterPcu1TrapEntry
    ACCESS not-accessible
    STATUS mandatory
    DESCRIPTION
      "Entries of cmcTcMasterPcu1TrapTable"
    INDEX { cmcTcMasterPcu1TrapIndex }
    ::= { cmcTcMasterPcu1TrapTable 1 }

    CmcTcMasterPcu1TrapEntry ::=
      SEQUENCE {
        cmcTcMasterPcu1TrapIndex
          INTEGER,
        cmcTcMasterPcu1TrapStatus
          INTEGER,
        cmcTcMasterPcu1TrapIPaddress
          DisplayString
      }

    cmcTcMasterPcu1TrapIndex OBJECT-TYPE
      SYNTAX INTEGER (1..32000)
      ACCESS read-only
      STATUS mandatory
      DESCRIPTION
        "Index for the trap-receiver-table. Its value ranges between
         1 and the value of cmcTcMasterPcu1TrapTableNumber "
      ::= { cmcTcMasterPcu1TrapEntry 1 }

    cmcTcMasterPcu1TrapStatus OBJECT-TYPE
      SYNTAX INTEGER {
        disabled(1),
        enabled(2)
      }
      ACCESS read-write
      STATUS mandatory
      DESCRIPTION
        "Enable or disable trap receiver"
      ::= { cmcTcMasterPcu1TrapEntry 2 }

    cmcTcMasterPcu1TrapIPaddress OBJECT-TYPE
      SYNTAX DisplayString (SIZE (0..15))
      ACCESS read-write
      STATUS mandatory
      DESCRIPTION
        "IP-address of trap-receiver"
      ::= { cmcTcMasterPcu1TrapEntry 3 }

--cmcTcMasterTc1MibRev-group
          
  cmcTcMasterTc1MibMajRev OBJECT-TYPE
    SYNTAX INTEGER (1..32000)
    ACCESS read-only
    STATUS mandatory
    DESCRIPTION
      "The Major Revision level.
       A change in the major revision level represents a major change
       in the architecture of the MIB. A change in the major revision 
       level may indicate a significant change in the information,
       correct interpretation of data may require a MIB document
       with the same major revision level."
    ::= { cmcTcMasterTc1MibRev 1 }

  cmcTcMasterTc1MibMinRev OBJECT-TYPE
    SYNTAX INTEGER (0..32000)
    ACCESS read-only
    STATUS mandatory
    DESCRIPTION
      "The Minor Revision level.
       A change in the minor revision level may represent some minor
       additional support, no changes to any pre-existing information
       has occurred."
    ::= { cmcTcMasterTc1MibRev 2 }

  cmcTcMasterTc1MibCondition OBJECT-TYPE
    SYNTAX INTEGER {
      other (1),
      ok (2),
      degraded (3),
      failed (4),
      configChanged (5)
    }
    ACCESS read-only
    STATUS mandatory
    DESCRIPTION
      "The overall condition (status) of the system represented by
       this MIB. 
       (2) OK
       (3) a minor problem, warning condition (yellow LED on CMC-TC)
       (4) a major problem (red LED on CMC-TC)
       (5) configuration of sensor units changed or
           unit detected (red/yellow/green LED on CMC-TC)"
    ::= { cmcTcMasterTc1MibRev 3 }
          
--cmcTcMasterTc1Status-group

  cmcTcMasterTc1StatusDeviceCMC OBJECT-TYPE
    SYNTAX INTEGER {
      failed(1),
      ok(2)
    }
    ACCESS read-only
    STATUS mandatory
    DESCRIPTION
      "General Status of CMC-TC unit itself
       (1) failed
       (2) OK"
    ::= { cmcTcMasterTc1Status 1 }

  cmcTcMasterTc1UnitsConnected OBJECT-TYPE
    SYNTAX INTEGER 
    ACCESS read-only
    STATUS mandatory
    DESCRIPTION
      "Number of sensor units connected to the CMC-TC, Port 1 to 4"
    ::= { cmcTcMasterTc1Status 2 }

--unit 1

  cmcTcMasterTc1Unit1TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 1"
    ::= { cmcTcMasterTc1StatusSensorUnit1 1 }

  cmcTcMasterTc1Unit1Text OBJECT-TYPE
    SYNTAX DisplayString (SIZE (0..10))
    ACCESS read-write
    STATUS mandatory
    DESCRIPTION
      "Descriptional text for sensor unit connected to port 1"
    ::= { cmcTcMasterTc1StatusSensorUnit1 2 }

  cmcTcMasterTc1Unit1Serial OBJECT-TYPE
    SYNTAX INTEGER 
    ACCESS read-only
    STATUS mandatory
    DESCRIPTION
      "Serialnumber of sensor unit connected to port 1"
    ::= { cmcTcMasterTc1StatusSensorUnit1 3 }

  cmcTcMasterTc1Unit1Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 1
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc1StatusSensorUnit1 4 }

-- Sensors
              
  cmcTcMasterTc1Unit1NumberOfSensors OBJECT-TYPE
    SYNTAX INTEGER 
    ACCESS read-only
    STATUS mandatory
    DESCRIPTION
      "Number of sensors connected to sensor unit 1"
    ::= { cmcTcMasterTc1StatusUnit1Sensors 1 }

-- table with entry for each sensor available on this unit              

  cmcTcMasterTc1Unit1SensorTable OBJECT-TYPE
    SYNTAX SEQUENCE OF CmcTcMasterTc1Unit1SensorEntry
    ACCESS not-accessible
    STATUS mandatory
    DESCRIPTION
      "Headline of sensor table"
    ::= { cmcTcMasterTc1StatusUnit1Sensors 2 }

  cmcTcMasterTc1Unit1SensorEntry OBJECT-TYPE
    SYNTAX CmcTcMasterTc1Unit1SensorEntry
    ACCESS not-accessible
    STATUS mandatory
    DESCRIPTION
      "Entries of sensor table"
    INDEX { cmcTcMasterTc1Unit1SensorIndex }
    ::= { cmcTcMasterTc1Unit1SensorTable 1 }

    CmcTcMasterTc1Unit1SensorEntry ::=
      SEQUENCE {
        cmcTcMasterTc1Unit1SensorIndex
          INTEGER,
        cmcTcMasterTc1Unit1SensorType
          INTEGER,
        cmcTcMasterTc1Unit1SensorText
          DisplayString (SIZE (0..20)),                
        cmcTcMasterTc1Unit1SensorStatus
          INTEGER,
        cmcTcMasterTc1Unit1SensorValue
          INTEGER,
        cmcTcMasterTc1Unit1SensorSetHigh
          INTEGER,
        cmcTcMasterTc1Unit1SensorSetLow
          INTEGER,
        cmcTcMasterTc1Unit1SensorSetWarn
          INTEGER                
      }

    cmcTcMasterTc1Unit1SensorIndex OBJECT-TYPE
      SYNTAX INTEGER (1..32000)
      ACCESS read-only
      STATUS mandatory
      DESCRIPTION
        "Index for the list of value entries. Its value ranges
         between 1 and the value of cmcTcMasterTc1Unit1NumberOfSensors." 
      ::= { cmcTcMasterTc1Unit1SensorEntry 1 }

    cmcTcMasterTc1Unit1SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 1 to sensor[cmcTcMasterTc1Unit1SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc1Unit1SensorEntry 2 }

    cmcTcMasterTc1Unit1SensorText OBJECT-TYPE
      SYNTAX DisplayString (SIZE (0..20))
      ACCESS read-write
      STATUS mandatory
      DESCRIPTION
        "Descriptional text for each sensor (entry in the table)"
      ::= { cmcTcMasterTc1Unit1SensorEntry 3 }
              
    cmcTcMasterTc1Unit1SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc1Unit1SensorEntry 4 }

    cmcTcMasterTc1Unit1SensorValue OBJECT-TYPE
      SYNTAX INTEGER 
      ACCESS read-only
      STATUS mandatory
      DESCRIPTION
        "Value of sensor"
      ::= { cmcTcMasterTc1Unit1SensorEntry 5 }

    cmcTcMasterTc1Unit1SensorSetHigh OBJECT-TYPE
      SYNTAX INTEGER (0..300)
      ACCESS read-write
      STATUS mandatory
      DESCRIPTION
        "Value for high setpoint of sensor"
      ::= { cmcTcMasterTc1Unit1SensorEntry 6 }

    cmcTcMasterTc1Unit1SensorSetLow OBJECT-TYPE
      SYNTAX INTEGER (0..300)
      ACCESS read-write
      STATUS mandatory
      DESCRIPTION
        "Value for low setpoint of sensor,
         also used as alarm delay"
      ::= { cmcTcMasterTc1Unit1SensorEntry 7 }

    cmcTcMasterTc1Unit1SensorSetWarn OBJECT-TYPE
      SYNTAX INTEGER (0..300)
      ACCESS read-write
      STATUS mandatory
      DESCRIPTION
        "Value for warning setpoint of sensor, 
         also used as fan threshold"
      ::= { cmcTcMasterTc1Unit1SensorEntry 8 }
                
-- Outputs              

  cmcTcMasterTc1Unit1NumberOfOutputs OBJECT-TYPE
    SYNTAX INTEGER 
    ACCESS read-only
    STATUS mandatory
    DESCRIPTION
      "Number of outputs available on sensor unit 1"
    ::= { cmcTcMasterTc1StatusUnit1Outputs 1 }

-- table with entry for each output available on this unit              
                
  cmcTcMasterTc1Unit1OutputTable OBJECT-TYPE
    SYNTAX SEQUENCE OF CmcTcMasterTc1Unit1OutputEntry
    ACCESS not-accessible
    STATUS mandatory
    DESCRIPTION
      "Headline of output table"
    ::= { cmcTcMasterTc1StatusUnit1Outputs 2 }

  cmcTcMasterTc1Unit1OutputEntry OBJECT-TYPE
    SYNTAX CmcTcMasterTc1Unit1OutputEntry
    ACCESS not-accessible
    STATUS mandatory
    DESCRIPTION
      "Entries of output table"
    INDEX { cmcTcMasterTc1Unit1OutputIndex }
    ::= { cmcTcMasterTc1Unit1OutputTable 1 }

    CmcTcMasterTc1Unit1OutputEntry ::=
      SEQUENCE {
        cmcTcMasterTc1Unit1OutputIndex
          INTEGER,
        cmcTcMasterTc1Unit1OutputType
          INTEGER,
        cmcTcMasterTc1Unit1OutputText
          DisplayString (SIZE (0..20)),                
        cmcTcMasterTc1Unit1OutputStatus
          INTEGER,
        cmcTcMasterTc1Unit1OutputValue
          INTEGER,
        cmcTcMasterTc1Unit1OutputSet
          INTEGER,
        cmcTcMasterTc1Unit1OutputConfig
          INTEGER,                
        cmcTcMasterTc1Unit1OutputDelay
          INTEGER,
        cmcTcMasterTc1Unit1OutputTimeoutAction
          INTEGER
      }

    cmcTcMasterTc1Unit1OutputIndex OBJECT-TYPE
      SYNTAX INTEGER (1..32000)
      ACCESS read-only
      STATUS mandatory
      DESCRIPTION
        "Index for the list of output entries. Its value ranges
         between 1 and the value of cmcTcMasterTc1Unit1NumberOfOutputs." 
      ::= { cmcTcMasterTc1Unit1OutputEntry 1 }

    cmcTcMasterTc1Unit1OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 1 to output[cmcTcMasterTc1Unit1OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc1Unit1OutputEntry 2 }

    cmcTcMasterTc1Unit1OutputText OBJECT-TYPE
      SYNTAX DisplayString (SIZE (0..20))
      ACCESS read-write
      STATUS mandatory
      DESCRIPTION
        "Descriptional text for each output (entry in the table)"
      ::= { cmcTcMasterTc1Unit1OutputEntry 3 }
              
    cmcTcMasterTc1Unit1OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc1Unit1OutputEntry 4 }

    cmcTcMasterTc1Unit1OutputValue OBJECT-TYPE
      SYNTAX INTEGER (-32000..32000)
      ACCESS read-write
      STATUS mandatory
      DESCRIPTION
        "Value for output"
      ::= { cmcTcMasterTc1Unit1OutputEntry 5 }

    cmcTcMasterTc1Unit1OutputSet OBJECT-TYPE
      SYNTAX INTEGER {
        off (1),
        on (2),
        lock (3),
        unlock (4),
        unlockDelay (5)
      }
      ACCESS read-write
      STATUS mandatory
      DESCRIPTION
        "Command for output"
      ::= { cmcTcMasterTc1Unit1OutputEntry 6 }

    cmcTcMasterTc1Unit1OutputConfig OBJECT-TYPE
      SYNTAX INTEGER {
        disRemote (1),
        enRemote (2)
      }
      ACCESS read-write
      STATUS mandatory
      DESCRIPTION
        "Configuration for output
         1: 	disable remote control (e.g. keypad)
         2: 	enable remote control"
      ::= { cmcTcMasterTc1Unit1OutputEntry 7 }

    cmcTcMasterTc1Unit1OutputDelay OBJECT-TYPE
      SYNTAX INTEGER (0..999)
      ACCESS read-write
      STATUS mandatory
      DESCRIPTION
        "Unsigned Value for delay, 
         after this time the output will fall into the previous state"
      ::= { cmcTcMasterTc1Unit1OutputEntry 8 }

    cmcTcMasterTc1Unit1OutputTimeoutAction OBJECT-TYPE
      SYNTAX INTEGER {
        stay (1),
        off (2),
        on (3)
      }
      ACCESS read-write
      STATUS mandatory
      DESCRIPTION
        "State for output if timeout (RS422) occurs"
      ::= { cmcTcMasterTc1Unit1OutputEntry 9 }
 
-- Messages
              
  cmcTcMasterTc1Unit1NumberOfMsgs OBJECT-TYPE
    SYNTAX INTEGER 
    ACCESS read-only
    STATUS mandatory
    DESCRIPTION
      "Number of messages that can be created with sensor unit 1"
    ::= { cmcTcMasterTc1StatusUnit1Msg 1 }

-- table with entry for each alarm available on this unit               
                
  cmcTcMasterTc1Unit1MsgTable OBJECT-TYPE
    SYNTAX SEQUENCE OF CmcTcMasterTc1Unit1MsgEntry
    ACCESS not-accessible
    STATUS mandatory
    DESCRIPTION
      "Headline of message table"
    ::= { cmcTcMasterTc1StatusUnit1Msg 2 }

  cmcTcMasterTc1Unit1MsgEntry OBJECT-TYPE
    SYNTAX CmcTcMasterTc1Unit1MsgEntry
    ACCESS not-accessible
    STATUS mandatory
    DESCRIPTION
      "Entries of message table"
    INDEX { cmcTcMasterTc1Unit1MsgIndex }
    ::= { cmcTcMasterTc1Unit1MsgTable 1 }

    CmcTcMasterTc1Unit1MsgEntry ::=
      SEQUENCE {
        cmcTcMasterTc1Unit1MsgIndex
          INTEGER, 
        cmcTcMasterTc1Unit1MsgText
          DisplayString (SIZE (0..20)),                
        cmcTcMasterTc1Unit1MsgStatus
          INTEGER,                
        cmcTcMasterTc1Unit1MsgRelay
          INTEGER,
        cmcTcMasterTc1Unit1MsgBeeper
          INTEGER,
        cmcTcMasterTc1Unit1MsgTrap1
          INTEGER,
        cmcTcMasterTc1Unit1MsgTrap2
          INTEGER,
        cmcTcMasterTc1Unit1MsgTrap3
          INTEGER,
        cmcTcMasterTc1Unit1MsgTrap4
          INTEGER,   
        cmcTcMasterTc1Unit1MsgQuit
          INTEGER              
      }

    cmcTcMasterTc1Unit1MsgIndex OBJECT-TYPE
      SYNTAX INTEGER (1..32000)
      ACCESS read-only
      STATUS mandatory
      DESCRIPTION
        "Index for the list of message entries. Its value ranges
         between 1 and the value of cmcTcMasterTc1Unit1NumberOfMsgs." 
      ::= { cmcTcMasterTc1Unit1MsgEntry 1 }

    cmcTcMasterTc1Unit1MsgText OBJECT-TYPE
      SYNTAX DisplayString (SIZE (0..20))
      ACCESS read-write
      STATUS mandatory
      DESCRIPTION
        "Descriptional text for each message (entry in the table)"
      ::= { cmcTcMasterTc1Unit1MsgEntry 2 }
              
    cmcTcMasterTc1Unit1MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc1Unit1OutputSet)
         17: door is unlocked by WEB
         18: door is unlocked by timer
         19: no access, wrong keycode or cardnumber
         20: orientation of PSM-Unit is circuit 1
         21: orientation of PSM-Unit is circuit 2"
      ::= { cmcTcMasterTc1Unit1MsgEntry 3 }
        
    cmcTcMasterTc1Unit1MsgRelay OBJECT-TYPE
      SYNTAX INTEGER {
        disable (1),
        enable (2)
      }
      ACCESS read-write
      STATUS mandatory
      DESCRIPTION
        "Setup of Alarm relay for this message/alarm
         1:        no switching of alarm relay             
         2:        switching of alarm relay" 
      ::= { cmcTcMasterTc1Unit1MsgEntry 4 }

    cmcTcMasterTc1Unit1MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc1Unit1MsgEntry 5 }

    cmcTcMasterTc1Unit1MsgTrap1 OBJECT-TYPE
      SYNTAX INTEGER {
        disable (1),
        enable (2)
      }
      ACCESS read-write
      STATUS mandatory
      DESCRIPTION
        "Trap receiver 1 activated"
      ::= { cmcTcMasterTc1Unit1MsgEntry 6 }

    cmcTcMasterTc1Unit1MsgTrap2 OBJECT-TYPE
      SYNTAX INTEGER {
        disable (1),
        enable (2)
      }
      ACCESS read-write
      STATUS mandatory
      DESCRIPTION
        "Trap receiver 2 activated"
      ::= { cmcTcMasterTc1Unit1MsgEntry 7 }
 
    cmcTcMasterTc1Unit1MsgTrap3 OBJECT-TYPE
      SYNTAX INTEGER {
        disable (1),
        enable (2)
      }
      ACCESS read-write
      STATUS mandatory
      DESCRIPTION
        "Trap receiver 3 activated"
      ::= { cmcTcMasterTc1Unit1MsgEntry 8 }

    cmcTcMasterTc1Unit1MsgTrap4 OBJECT-TYPE
      SYNTAX INTEGER {
        disable (1),
        enable (2)
      }
      ACCESS read-write
      STATUS mandatory
      DESCRIPTION
        "Trap receiver 4 and Event Logging activated"
      ::= { cmcTcMasterTc1Unit1MsgEntry 9 }

    cmcTcMasterTc1Unit1MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc1Unit1MsgEntry 10 }

-- unit2

  cmcTcMasterTc1Unit2TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 2"
    ::= { cmcTcMasterTc1StatusSensorUnit2 1 }

  cmcTcMasterTc1Unit2Text OBJECT-TYPE
    SYNTAX DisplayString (SIZE (0..10))
    ACCESS read-write
    STATUS mandatory
    DESCRIPTION
      "Descriptional text for sensor unit connected to port 2"
    ::= { cmcTcMasterTc1StatusSensorUnit2 2 }

  cmcTcMasterTc1Unit2Serial OBJECT-TYPE
    SYNTAX INTEGER 
    ACCESS read-only
    STATUS mandatory
    DESCRIPTION
      "Serialnumber of sensor unit connected to port 2"
    ::= { cmcTcMasterTc1StatusSensorUnit2 3 }

  cmcTcMasterTc1Unit2Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 2
       (1) OK
       (2) error
       (3) configuration of sensor unit has changed, confirmation required
       (4) Quit from sensor unit to confirm configuration changes
       (5) timeout of sensor unit, confirmation required
       (6) sensor unit detected, needs to be confirmed
       (8) supply voltage is too low"              
    ::= { cmcTcMasterTc1StatusSensorUnit2 4 }

-- unit 2 table

-- Sensors              

  cmcTcMasterTc1Unit2NumberOfSensors OBJECT-TYPE
    SYNTAX INTEGER 
    ACCESS read-only
    STATUS mandatory
    DESCRIPTION
      "Number of sensors connected to sensor unit 2"
    ::= { cmcTcMasterTc1StatusUnit2Sensors 1 }

-- table with entry for each sensor available on this unit              

  cmcTcMasterTc1Unit2SensorTable OBJECT-TYPE
    SYNTAX SEQUENCE OF CmcTcMasterTc1Unit2SensorEntry
    ACCESS not-accessible
    STATUS mandatory
    DESCRIPTION
      "Headline of sensor table"
    ::= { cmcTcMasterTc1StatusUnit2Sensors 2 }

  cmcTcMasterTc1Unit2SensorEntry OBJECT-TYPE
    SYNTAX CmcTcMasterTc1Unit2SensorEntry
    ACCESS not-accessible
    STATUS mandatory
    DESCRIPTION
      "Entries of sensor table"
    INDEX { cmcTcMasterTc1Unit2SensorIndex }
    ::= { cmcTcMasterTc1Unit2SensorTable 1 }

    CmcTcMasterTc1Unit2SensorEntry ::=
      SEQUENCE {
        cmcTcMasterTc1Unit2SensorIndex
          INTEGER,
        cmcTcMasterTc1Unit2SensorType
          INTEGER,
        cmcTcMasterTc1Unit2SensorText
          DisplayString (SIZE (0..20)),                
        cmcTcMasterTc1Unit2SensorStatus
          INTEGER,
        cmcTcMasterTc1Unit2SensorValue
          INTEGER,
        cmcTcMasterTc1Unit2SensorSetHigh
          INTEGER,
        cmcTcMasterTc1Unit2SensorSetLow
          INTEGER,                 
        cmcTcMasterTc1Unit2SensorSetWarn
          INTEGER  
      }

    cmcTcMasterTc1Unit2SensorIndex OBJECT-TYPE
      SYNTAX INTEGER (1..32000)
      ACCESS read-only
      STATUS mandatory
      DESCRIPTION
        "Index for the list of value entries. Its value ranges
         between 1 and the value of cmcTcMasterTc1Unit2NumberOfSensors." 
      ::= { cmcTcMasterTc1Unit2SensorEntry 1 }

    cmcTcMasterTc1Unit2SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 2 to sensor[cmcTcMasterTc1Unit2SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc1Unit2SensorEntry 2 }
        
    cmcTcMasterTc1Unit2SensorText OBJECT-TYPE
      SYNTAX DisplayString (SIZE (0..20))
      ACCESS read-write
      STATUS mandatory
      DESCRIPTION
        "Descriptional text for each sensor (entry in the table)"
      ::= { cmcTcMasterTc1Unit2SensorEntry 3 }
              
    cmcTcMasterTc1Unit2SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc1Unit2SensorEntry 4 }

    cmcTcMasterTc1Unit2SensorValue OBJECT-TYPE
      SYNTAX INTEGER 
      ACCESS read-only
      STATUS mandatory
      DESCRIPTION
        "Value of sensor"
      ::= { cmcTcMasterTc1Unit2SensorEntry 5 }

    cmcTcMasterTc1Unit2SensorSetHigh OBJECT-TYPE
      SYNTAX INTEGER (0..300) 
      ACCESS read-write
      STATUS mandatory
      DESCRIPTION
        "Value for high setpoint of sensor"
      ::= { cmcTcMasterTc1Unit2SensorEntry 6 }

    cmcTcMasterTc1Unit2SensorSetLow OBJECT-TYPE
      SYNTAX INTEGER (0..300) 
      ACCESS read-write
      STATUS mandatory
      DESCRIPTION
        "Value for low setpoint of sensor,
         also used as alarm delay"
      ::= { cmcTcMasterTc1Unit2SensorEntry 7 }

    cmcTcMasterTc1Unit2SensorSetWarn OBJECT-TYPE
      SYNTAX INTEGER (0..300) 
      ACCESS read-write
      STATUS mandatory
      DESCRIPTION
        "Value for warning setpoint of sensor,
         also used as fan threshold"
      ::= { cmcTcMasterTc1Unit2SensorEntry 8 }

-- Outputs              

  cmcTcMasterTc1Unit2NumberOfOutputs OBJECT-TYPE
    SYNTAX INTEGER 
    ACCESS read-only
    STATUS mandatory
    DESCRIPTION
      "Number of outputs available on sensor unit 2"
    ::= { cmcTcMasterTc1StatusUnit2Outputs 1 }

-- table with entry for each output available on this unit              
                
  cmcTcMasterTc1Unit2OutputTable OBJECT-TYPE
    SYNTAX SEQUENCE OF CmcTcMasterTc1Unit2OutputEntry
    ACCESS not-accessible
    STATUS mandatory
    DESCRIPTION
      "Headline of output table"
    ::= { cmcTcMasterTc1StatusUnit2Outputs 2 }

  cmcTcMasterTc1Unit2OutputEntry OBJECT-TYPE
    SYNTAX CmcTcMasterTc1Unit2OutputEntry
    ACCESS not-accessible
    STATUS mandatory
    DESCRIPTION
      "Entries of output table"
    INDEX { cmcTcMasterTc1Unit2OutputIndex }
    ::= { cmcTcMasterTc1Unit2OutputTable 1 }

    CmcTcMasterTc1Unit2OutputEntry ::=
      SEQUENCE {
        cmcTcMasterTc1Unit2OutputIndex
          INTEGER,
        cmcTcMasterTc1Unit2OutputType
          INTEGER,
        cmcTcMasterTc1Unit2OutputText
          DisplayString (SIZE (0..20)),                
        cmcTcMasterTc1Unit2OutputStatus
          INTEGER,
        cmcTcMasterTc1Unit2OutputValue
          INTEGER,
        cmcTcMasterTc1Unit2OutputSet
          INTEGER,
        cmcTcMasterTc1Unit2OutputConfig
          INTEGER,                
        cmcTcMasterTc1Unit2OutputDelay
          INTEGER,
        cmcTcMasterTc1Unit2OutputTimeoutAction
          INTEGER
      }

    cmcTcMasterTc1Unit2OutputIndex OBJECT-TYPE
      SYNTAX INTEGER (1..32000)
      ACCESS read-only
      STATUS mandatory
      DESCRIPTION
        "Index for the list of output entries. Its value ranges
         between 1 and the value of cmcTcMasterTc1Unit2NumberOfOutputs." 
      ::= { cmcTcMasterTc1Unit2OutputEntry 1 }

    cmcTcMasterTc1Unit2OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 2 to output[cmcTcMasterTc1Unit2OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc1Unit2OutputEntry 2 }

        
    cmcTcMasterTc1Unit2OutputText OBJECT-TYPE
      SYNTAX DisplayString (SIZE (0..20))
      ACCESS read-write
      STATUS mandatory
      DESCRIPTION
        "Descriptional text for each output (entry in the table)"
      ::= { cmcTcMasterTc1Unit2OutputEntry 3 }
              
    cmcTcMasterTc1Unit2OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc1Unit2OutputEntry 4 }

    cmcTcMasterTc1Unit2OutputValue OBJECT-TYPE
      SYNTAX INTEGER (-32000..32000) 
      ACCESS read-write
      STATUS mandatory
      DESCRIPTION
        "Value for output"
      ::= { cmcTcMasterTc1Unit2OutputEntry 5 }

    cmcTcMasterTc1Unit2OutputSet OBJECT-TYPE
      SYNTAX INTEGER {
        off (1),
        on (2),
        lock (3),
        unlock (4),
        unlockDelay (5)
      }
      ACCESS read-write
      STATUS mandatory
      DESCRIPTION
        "Command for output"
      ::= { cmcTcMasterTc1Unit2OutputEntry 6 }

    cmcTcMasterTc1Unit2OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc1Unit2OutputEntry 7 }

    cmcTcMasterTc1Unit2OutputDelay OBJECT-TYPE
      SYNTAX INTEGER (0..999) 
      ACCESS read-write
      STATUS mandatory
      DESCRIPTION
        "Unsigned Value for delay, 
         after this time the output will fall into the previous state"
      ::= { cmcTcMasterTc1Unit2OutputEntry 8 }

    cmcTcMasterTc1Unit2OutputTimeoutAction OBJECT-TYPE
      SYNTAX INTEGER {
        stay (1),
        off (2),
        on (3)
      }
      ACCESS read-write
      STATUS mandatory
      DESCRIPTION
        "State for output if timeout (RS422) occurs"
      ::= { cmcTcMasterTc1Unit2OutputEntry 9 }

-- Messages
              
  cmcTcMasterTc1Unit2NumberOfMsgs OBJECT-TYPE
    SYNTAX INTEGER 
    ACCESS read-only
    STATUS mandatory
    DESCRIPTION
      "Number of messages that can be created with sensor unit 2"
    ::= { cmcTcMasterTc1StatusUnit2Msg 1 }

-- table with entry for each alarm available on this unit               
                
  cmcTcMasterTc1Unit2MsgTable OBJECT-TYPE
    SYNTAX SEQUENCE OF CmcTcMasterTc1Unit2MsgEntry
    ACCESS not-accessible
    STATUS mandatory
    DESCRIPTION
      "Headline of message table"
    ::= { cmcTcMasterTc1StatusUnit2Msg 2 }

  cmcTcMasterTc1Unit2MsgEntry OBJECT-TYPE
    SYNTAX CmcTcMasterTc1Unit2MsgEntry
    ACCESS not-accessible
    STATUS mandatory
    DESCRIPTION
      "Entries of message table"
    INDEX { cmcTcMasterTc1Unit2MsgIndex }
    ::= { cmcTcMasterTc1Unit2MsgTable 1 }

    CmcTcMasterTc1Unit2MsgEntry ::=
      SEQUENCE {
        cmcTcMasterTc1Unit2MsgIndex
          INTEGER,
        cmcTcMasterTc1Unit2MsgText
          DisplayString (SIZE (0..20)),
        cmcTcMasterTc1Unit2MsgStatus
          INTEGER, 
        cmcTcMasterTc1Unit2MsgRelay
          INTEGER,
        cmcTcMasterTc1Unit2MsgBeeper
          INTEGER,
        cmcTcMasterTc1Unit2MsgTrap1
          INTEGER,
        cmcTcMasterTc1Unit2MsgTrap2
          INTEGER,
        cmcTcMasterTc1Unit2MsgTrap3
          INTEGER,
        cmcTcMasterTc1Unit2MsgTrap4
          INTEGER,                 
        cmcTcMasterTc1Unit2MsgQuit
          INTEGER              
      }

    cmcTcMasterTc1Unit2MsgIndex OBJECT-TYPE
      SYNTAX INTEGER (1..32000)
      ACCESS read-only
      STATUS mandatory
      DESCRIPTION
        "Index for the list of message entries. Its value ranges
         between 1 and the value of cmcTcMasterTc1Unit2NumberOfMsgs." 
      ::= { cmcTcMasterTc1Unit2MsgEntry 1 }

    cmcTcMasterTc1Unit2MsgText OBJECT-TYPE
      SYNTAX DisplayString (SIZE (0..20))
      ACCESS read-write
      STATUS mandatory
      DESCRIPTION
        "Descriptional text for each message (entry in the table)"
      ::= { cmcTcMasterTc1Unit2MsgEntry 2 }

    cmcTcMasterTc1Unit2MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc1Unit2OutputSet)
         17: door is unlocked by WEB
         18: door is unlocked by timer
         19: no access, wrong keycode or cardnumber
         20: orientation of PSM-Unit is circuit 1
         21: orientation of PSM-Unit is circuit 2"
      ::= { cmcTcMasterTc1Unit2MsgEntry 3 }

    cmcTcMasterTc1Unit2MsgRelay OBJECT-TYPE
      SYNTAX INTEGER {
        disable (1),
        enable (2)
      }
      ACCESS read-write
      STATUS mandatory
      DESCRIPTION
        "Setup of Alarm relay for this alarm
         2:        no switching of alarm relay             
         1:        switching of alarm relay" 
      ::= { cmcTcMasterTc1Unit2MsgEntry 4 }

    cmcTcMasterTc1Unit2MsgBeeper OBJECT-TYPE
      SYNTAX INTEGER {
        disable (1),
        enable (2)
      }
      ACCESS read-write
      STATUS mandatory
      DESCRIPTION
        "Setup of Alarm beeper for this alarm
         2:        no audible alarm
         1:        audible alarm" 
      ::= { cmcTcMasterTc1Unit2MsgEntry 5 }

    cmcTcMasterTc1Unit2MsgTrap1 OBJECT-TYPE
      SYNTAX INTEGER {
        disable (1),
        enable (2)
      }
      ACCESS read-write
      STATUS mandatory
      DESCRIPTION
        "Trap receiver 1 activated"
      ::= { cmcTcMasterTc1Unit2MsgEntry 6 }

    cmcTcMasterTc1Unit2MsgTrap2 OBJECT-TYPE
      SYNTAX INTEGER {
        disable (1),
        enable (2)
      }
      ACCESS read-write
      STATUS mandatory
      DESCRIPTION
        "Trap receiver 2 activated"
      ::= { cmcTcMasterTc1Unit2MsgEntry 7 }
 
    cmcTcMasterTc1Unit2MsgTrap3 OBJECT-TYPE
      SYNTAX INTEGER {
        disable (1),
        enable (2)
      }
      ACCESS read-write
      STATUS mandatory
      DESCRIPTION
        "Trap receiver 3 activated"
      ::= { cmcTcMasterTc1Unit2MsgEntry 8 }

    cmcTcMasterTc1Unit2MsgTrap4 OBJECT-TYPE
      SYNTAX INTEGER {
        disable (1),
        enable (2)
      }
      ACCESS read-write
      STATUS mandatory
      DESCRIPTION
        "Trap receiver 4 and Event Logging activated"
      ::= { cmcTcMasterTc1Unit2MsgEntry 9 }

    cmcTcMasterTc1Unit2MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc1Unit2MsgEntry 10 }

-- unit 3
  cmcTcMasterTc1Unit3TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 3"
    ::= { cmcTcMasterTc1StatusSensorUnit3 1 }

  cmcTcMasterTc1Unit3Text OBJECT-TYPE
    SYNTAX DisplayString (SIZE (0..10))
    ACCESS read-write
    STATUS mandatory
    DESCRIPTION
      "Descriptional text for sensor unit connected to port 3"
    ::= { cmcTcMasterTc1StatusSensorUnit3 2 }

  cmcTcMasterTc1Unit3Serial OBJECT-TYPE
    SYNTAX INTEGER 
    ACCESS  read-only
    STATUS  mandatory
    DESCRIPTION
      "Serialnumber of sensor unit connected to port 3"
    ::= { cmcTcMasterTc1StatusSensorUnit3 3 }

  cmcTcMasterTc1Unit3Status OBJECT-TYPE
    SYNTAX INTEGER {
      ok(1),
      error(2),
      changed(3),
      quit(4),
      timeout(5),
      detected(6),
      notAvail(7),
      lowPower(8)
    }
    ACCESS  read-only
    STATUS  mandatory
    DESCRIPTION
      "General Status sensor unit connected to port 3
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc1StatusSensorUnit3 4 }

-- Sensors              

  cmcTcMasterTc1Unit3NumberOfSensors OBJECT-TYPE
    SYNTAX INTEGER 
    ACCESS read-only
    STATUS mandatory
    DESCRIPTION
      "Number of sensors connected to sensor unit 3"
    ::= { cmcTcMasterTc1StatusUnit3Sensors 1 }

-- table with entry for each sensor available on this unit              
        
  cmcTcMasterTc1Unit3SensorTable OBJECT-TYPE
    SYNTAX SEQUENCE OF CmcTcMasterTc1Unit3SensorEntry
    ACCESS not-accessible
    STATUS mandatory
    DESCRIPTION
      "Headline of sensor table"
    ::= { cmcTcMasterTc1StatusUnit3Sensors 2 }

  cmcTcMasterTc1Unit3SensorEntry OBJECT-TYPE
    SYNTAX CmcTcMasterTc1Unit3SensorEntry
    ACCESS not-accessible
    STATUS mandatory
    DESCRIPTION
      "Entries of sensor table"
    INDEX { cmcTcMasterTc1Unit3SensorIndex }
    ::= { cmcTcMasterTc1Unit3SensorTable 1 }

    CmcTcMasterTc1Unit3SensorEntry ::=
      SEQUENCE {
        cmcTcMasterTc1Unit3SensorIndex
          INTEGER,
        cmcTcMasterTc1Unit3SensorType
          INTEGER,
        cmcTcMasterTc1Unit3SensorText
          DisplayString (SIZE (0..20)),                
        cmcTcMasterTc1Unit3SensorStatus
          INTEGER,
        cmcTcMasterTc1Unit3SensorValue
          INTEGER,
        cmcTcMasterTc1Unit3SensorSetHigh
          INTEGER,
        cmcTcMasterTc1Unit3SensorSetLow
          INTEGER,                 
        cmcTcMasterTc1Unit3SensorSetWarn
          INTEGER  
      }

    cmcTcMasterTc1Unit3SensorIndex OBJECT-TYPE
      SYNTAX INTEGER (1..32000)
      ACCESS read-only
      STATUS mandatory
      DESCRIPTION
        "Index for the list of value entries. Its value ranges
         between 1 and the value of cmcTcMasterTc1Unit3NumberOfSensors." 
      ::= { cmcTcMasterTc1Unit3SensorEntry 1 }

    cmcTcMasterTc1Unit3SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 3 to sensor[cmcTcMasterTc1Unit3SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc1Unit3SensorEntry 2 }

    cmcTcMasterTc1Unit3SensorText OBJECT-TYPE
      SYNTAX DisplayString (SIZE (0..20))
      ACCESS read-write
      STATUS mandatory
      DESCRIPTION
        "Descriptional text for each sensor (entry in the table)"
      ::= { cmcTcMasterTc1Unit3SensorEntry 3 }
              
    cmcTcMasterTc1Unit3SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc1Unit3SensorEntry 4 }

    cmcTcMasterTc1Unit3SensorValue OBJECT-TYPE
      SYNTAX INTEGER 
      ACCESS read-only
      STATUS mandatory
      DESCRIPTION
        "Value of sensor"
      ::= { cmcTcMasterTc1Unit3SensorEntry 5 }

    cmcTcMasterTc1Unit3SensorSetHigh OBJECT-TYPE
      SYNTAX INTEGER (0..300) 
      ACCESS read-write
      STATUS mandatory
      DESCRIPTION
        "Value for high setpoint of sensor"
      ::= { cmcTcMasterTc1Unit3SensorEntry 6 }

    cmcTcMasterTc1Unit3SensorSetLow OBJECT-TYPE
      SYNTAX INTEGER (0..300) 
      ACCESS read-write
      STATUS mandatory
      DESCRIPTION
        "Value for low setpoint of sensor,
         also used as alarm delay"
      ::= { cmcTcMasterTc1Unit3SensorEntry 7 }

    cmcTcMasterTc1Unit3SensorSetWarn OBJECT-TYPE
      SYNTAX INTEGER (0..300) 
      ACCESS read-write
      STATUS mandatory
      DESCRIPTION
        "Value for warning setpoint of sensor,
         also used as fan threshold"
      ::= { cmcTcMasterTc1Unit3SensorEntry 8 }
                
-- Outputs              

  cmcTcMasterTc1Unit3NumberOfOutputs OBJECT-TYPE
    SYNTAX INTEGER 
    ACCESS read-only
    STATUS mandatory
    DESCRIPTION
      "Number of outputs available on sensor unit 3"
    ::= { cmcTcMasterTc1StatusUnit3Outputs 1 }

-- table with entry for each output available on this unit              
                
  cmcTcMasterTc1Unit3OutputTable OBJECT-TYPE
    SYNTAX SEQUENCE OF CmcTcMasterTc1Unit3OutputEntry
    ACCESS not-accessible
    STATUS mandatory
    DESCRIPTION
      "Headline of output table"
    ::= { cmcTcMasterTc1StatusUnit3Outputs 2 }

  cmcTcMasterTc1Unit3OutputEntry OBJECT-TYPE
    SYNTAX CmcTcMasterTc1Unit3OutputEntry
    ACCESS not-accessible
    STATUS mandatory
    DESCRIPTION
      "Entries of output table"
    INDEX { cmcTcMasterTc1Unit3OutputIndex }
    ::= { cmcTcMasterTc1Unit3OutputTable 1 }

    CmcTcMasterTc1Unit3OutputEntry ::=
      SEQUENCE {
        cmcTcMasterTc1Unit3OutputIndex
          INTEGER,
        cmcTcMasterTc1Unit3OutputType
          INTEGER,
        cmcTcMasterTc1Unit3OutputText
          DisplayString (SIZE (0..20)),                
        cmcTcMasterTc1Unit3OutputStatus
          INTEGER,
        cmcTcMasterTc1Unit3OutputValue
          INTEGER,
        cmcTcMasterTc1Unit3OutputSet
          INTEGER,
        cmcTcMasterTc1Unit3OutputConfig
          INTEGER,
        cmcTcMasterTc1Unit3OutputDelay
          INTEGER,
        cmcTcMasterTc1Unit3OutputTimeoutAction
          INTEGER
      }

    cmcTcMasterTc1Unit3OutputIndex OBJECT-TYPE
      SYNTAX INTEGER (1..32000)
      ACCESS read-only
      STATUS mandatory
      DESCRIPTION
        "Index for the list of output entries. Its value ranges
         between 1 and the value of cmcTcMasterTc1Unit3NumberOfOutputs." 
      ::= { cmcTcMasterTc1Unit3OutputEntry 1 }

    cmcTcMasterTc1Unit3OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 3 to output[cmcTcMasterTc1Unit3OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc1Unit3OutputEntry 2 }

        
    cmcTcMasterTc1Unit3OutputText OBJECT-TYPE
      SYNTAX DisplayString (SIZE (0..20))
      ACCESS read-write
      STATUS mandatory
      DESCRIPTION
        "Descriptional text for each output (entry in the table)"
      ::= { cmcTcMasterTc1Unit3OutputEntry 3 }
              
    cmcTcMasterTc1Unit3OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc1Unit3OutputEntry 4 }

    cmcTcMasterTc1Unit3OutputValue OBJECT-TYPE
      SYNTAX INTEGER (-32000..32000) 
      ACCESS read-write
      STATUS mandatory
      DESCRIPTION
        "Value for output"
      ::= { cmcTcMasterTc1Unit3OutputEntry 5 }

    cmcTcMasterTc1Unit3OutputSet OBJECT-TYPE
      SYNTAX INTEGER {
        off (1),
        on (2),
        lock (3),
        unlock (4),
        unlockDelay (5)
      }
      ACCESS read-write
      STATUS mandatory
      DESCRIPTION
        "Command for output"
      ::= { cmcTcMasterTc1Unit3OutputEntry 6 }

    cmcTcMasterTc1Unit3OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc1Unit3OutputEntry 7 }

    cmcTcMasterTc1Unit3OutputDelay OBJECT-TYPE
      SYNTAX INTEGER (0..999) 
      ACCESS read-write
      STATUS mandatory
      DESCRIPTION
        "Unsigned Value for delay, 
         after this time the output will fall into the previous state"
      ::= { cmcTcMasterTc1Unit3OutputEntry 8 }

    cmcTcMasterTc1Unit3OutputTimeoutAction OBJECT-TYPE
      SYNTAX INTEGER {
        stay (1),
        off (2),
        on (3)
      }
      ACCESS read-write
      STATUS mandatory
      DESCRIPTION
        "State for output if timeout (RS422) occurs"
      ::= { cmcTcMasterTc1Unit3OutputEntry 9 }

-- Messages
              
  cmcTcMasterTc1Unit3NumberOfMsgs OBJECT-TYPE
    SYNTAX INTEGER 
    ACCESS read-only
    STATUS mandatory
    DESCRIPTION
      "Number of messages that can be created with sensor unit 3"
    ::= { cmcTcMasterTc1StatusUnit3Msg 1 }

-- table with entry for each alarm available on this unit               
                
  cmcTcMasterTc1Unit3MsgTable OBJECT-TYPE
    SYNTAX SEQUENCE OF CmcTcMasterTc1Unit3MsgEntry
    ACCESS not-accessible
    STATUS mandatory
    DESCRIPTION
      "Headline of message table"
    ::= { cmcTcMasterTc1StatusUnit3Msg 2 }

  cmcTcMasterTc1Unit3MsgEntry OBJECT-TYPE
    SYNTAX CmcTcMasterTc1Unit3MsgEntry
    ACCESS not-accessible
    STATUS mandatory
    DESCRIPTION
      "Entries of message table"
    INDEX { cmcTcMasterTc1Unit3MsgIndex }
    ::= { cmcTcMasterTc1Unit3MsgTable 1 }

    CmcTcMasterTc1Unit3MsgEntry ::=
      SEQUENCE {
        cmcTcMasterTc1Unit3MsgIndex
          INTEGER,
        cmcTcMasterTc1Unit3MsgText
          DisplayString (SIZE (0..20)),
        cmcTcMasterTc1Unit3MsgStatus
          INTEGER, 
        cmcTcMasterTc1Unit3MsgRelay
          INTEGER,
        cmcTcMasterTc1Unit3MsgBeeper
          INTEGER,
        cmcTcMasterTc1Unit3MsgTrap1
          INTEGER,
        cmcTcMasterTc1Unit3MsgTrap2
          INTEGER,
        cmcTcMasterTc1Unit3MsgTrap3
          INTEGER,
        cmcTcMasterTc1Unit3MsgTrap4
          INTEGER,                 
        cmcTcMasterTc1Unit3MsgQuit
          INTEGER              
      }

    cmcTcMasterTc1Unit3MsgIndex OBJECT-TYPE
      SYNTAX INTEGER (1..32000)
      ACCESS read-only
      STATUS mandatory
      DESCRIPTION
        "Index for the list of message entries. Its value ranges
         between 1 and the value of cmcTcMasterTc1Unit3NumberOfMsgs." 
      ::= { cmcTcMasterTc1Unit3MsgEntry 1 }

    cmcTcMasterTc1Unit3MsgText OBJECT-TYPE
      SYNTAX DisplayString (SIZE (0..20))
      ACCESS read-write
      STATUS mandatory
      DESCRIPTION
        "Descriptional text for each message (entry in the table)"
      ::= { cmcTcMasterTc1Unit3MsgEntry 2 }

    cmcTcMasterTc1Unit3MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc1Unit3OutputSet)
         17: door is unlocked by WEB
         18: door is unlocked by timer
         19: no access, wrong keycode or cardnumber
         20: orientation of PSM-Unit is circuit 1
         21: orientation of PSM-Unit is circuit 2"
      ::= { cmcTcMasterTc1Unit3MsgEntry 3 }

    cmcTcMasterTc1Unit3MsgRelay OBJECT-TYPE
      SYNTAX INTEGER {
        disable (1),
        enable (2)
      }
      ACCESS read-write
      STATUS mandatory
      DESCRIPTION
        "Setup of Alarm relay for this alarm
         1:        no switching of alarm relay             
         2:        switching of alarm relay" 
      ::= { cmcTcMasterTc1Unit3MsgEntry 4 }

    cmcTcMasterTc1Unit3MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc1Unit3MsgEntry 5 }

    cmcTcMasterTc1Unit3MsgTrap1 OBJECT-TYPE
      SYNTAX INTEGER {
        disable (1),
        enable (2)
      }
      ACCESS read-write
      STATUS mandatory
      DESCRIPTION
        "Trap receiver 1 activated"
      ::= { cmcTcMasterTc1Unit3MsgEntry 6 }

    cmcTcMasterTc1Unit3MsgTrap2 OBJECT-TYPE
      SYNTAX INTEGER {
        disable (1),
        enable (2)
      }
      ACCESS read-write
      STATUS mandatory
      DESCRIPTION
        "Trap receiver 2 activated"
      ::= { cmcTcMasterTc1Unit3MsgEntry 7 }
 
    cmcTcMasterTc1Unit3MsgTrap3 OBJECT-TYPE
      SYNTAX INTEGER {
        disable (1),
        enable (2)
      }
      ACCESS read-write
      STATUS mandatory
      DESCRIPTION
        "Trap receiver 3 activated"
      ::= { cmcTcMasterTc1Unit3MsgEntry 8 }

    cmcTcMasterTc1Unit3MsgTrap4 OBJECT-TYPE
      SYNTAX INTEGER {
        disable (1),
        enable (2)
      }
      ACCESS read-write
      STATUS mandatory
      DESCRIPTION
        "Trap receiver 4 and Event Logging activated"
      ::= { cmcTcMasterTc1Unit3MsgEntry 9 }

    cmcTcMasterTc1Unit3MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc1Unit3MsgEntry 10 }

-- unit4

  cmcTcMasterTc1Unit4TypeOfDevice OBJECT-TYPE
    SYNTAX INTEGER {
      notAvail (1),
      unitIO (2),
      unitAccess (3),
      unitClimate (4),
      unitFCS (5),
      unitRTT (6),
      unitRLCP (7),
      unitPSM (8)
    }
    ACCESS  read-only
    STATUS  mandatory
    DESCRIPTION
      "Type of sensor unit connected to port 4"
    ::= { cmcTcMasterTc1StatusSensorUnit4 1 }

  cmcTcMasterTc1Unit4Text OBJECT-TYPE
    SYNTAX DisplayString (SIZE (0..10))
    ACCESS read-write
    STATUS mandatory
    DESCRIPTION
      "Descriptional text for sensor unit connected to port 4"
    ::= { cmcTcMasterTc1StatusSensorUnit4 2 }

  cmcTcMasterTc1Unit4Serial OBJECT-TYPE
    SYNTAX INTEGER 
    ACCESS read-only
    STATUS mandatory
    DESCRIPTION
      "Serialnumber of sensor unit connected to port 4"
    ::= { cmcTcMasterTc1StatusSensorUnit4 3 }

  cmcTcMasterTc1Unit4Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 4
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc1StatusSensorUnit4 4 }

-- Sensors
              
  cmcTcMasterTc1Unit4NumberOfSensors OBJECT-TYPE
    SYNTAX INTEGER 
    ACCESS read-only
    STATUS mandatory
    DESCRIPTION
      "Number of sensors connected to sensor unit 4"
    ::= { cmcTcMasterTc1StatusUnit4Sensors 1 }

-- table with entry for each sensor available on this unit              
                
  cmcTcMasterTc1Unit4SensorTable OBJECT-TYPE
    SYNTAX SEQUENCE OF CmcTcMasterTc1Unit4SensorEntry
    ACCESS not-accessible
    STATUS mandatory
    DESCRIPTION
      "Headline of sensor table"
    ::= { cmcTcMasterTc1StatusUnit4Sensors 2 }

  cmcTcMasterTc1Unit4SensorEntry OBJECT-TYPE
    SYNTAX CmcTcMasterTc1Unit4SensorEntry
    ACCESS not-accessible
    STATUS mandatory
    DESCRIPTION
      "Entries of sensor table"
    INDEX { cmcTcMasterTc1Unit4SensorIndex }
    ::= { cmcTcMasterTc1Unit4SensorTable 1 }

    CmcTcMasterTc1Unit4SensorEntry ::=
      SEQUENCE {
        cmcTcMasterTc1Unit4SensorIndex
          INTEGER,
        cmcTcMasterTc1Unit4SensorType
          INTEGER,
        cmcTcMasterTc1Unit4SensorText
          DisplayString (SIZE (0..20)),                
        cmcTcMasterTc1Unit4SensorStatus
          INTEGER,
        cmcTcMasterTc1Unit4SensorValue
          INTEGER,
        cmcTcMasterTc1Unit4SensorSetHigh
          INTEGER,
        cmcTcMasterTc1Unit4SensorSetLow
          INTEGER,                 
        cmcTcMasterTc1Unit4SensorSetWarn
          INTEGER  
      }

    cmcTcMasterTc1Unit4SensorIndex OBJECT-TYPE
      SYNTAX INTEGER (1..32000)
      ACCESS read-only
      STATUS mandatory
      DESCRIPTION
        "Index for the list of value entries. Its value ranges
         between 1 and the value of cmcTcMasterTc1Unit4NumberOfSensors." 
      ::= { cmcTcMasterTc1Unit4SensorEntry 1 }

    cmcTcMasterTc1Unit4SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 4 to sensor[cmcTcMasterTc1Unit4SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc1Unit4SensorEntry 2 }

    cmcTcMasterTc1Unit4SensorText OBJECT-TYPE
      SYNTAX DisplayString (SIZE (0..20))
      ACCESS read-write
      STATUS mandatory
      DESCRIPTION
        "Descriptional text for each sensor (entry in the table)"
      ::= { cmcTcMasterTc1Unit4SensorEntry 3 }
              
    cmcTcMasterTc1Unit4SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc1Unit4SensorEntry 4 }

    cmcTcMasterTc1Unit4SensorValue OBJECT-TYPE
      SYNTAX INTEGER 
      ACCESS read-only
      STATUS mandatory
      DESCRIPTION
        "Value of sensor"
      ::= { cmcTcMasterTc1Unit4SensorEntry 5 }

    cmcTcMasterTc1Unit4SensorSetHigh OBJECT-TYPE
      SYNTAX INTEGER (0..300) 
      ACCESS read-write
      STATUS mandatory
      DESCRIPTION
        "Value for high setpoint of sensor"
      ::= { cmcTcMasterTc1Unit4SensorEntry 6 }

    cmcTcMasterTc1Unit4SensorSetLow OBJECT-TYPE
      SYNTAX INTEGER (0..300) 
      ACCESS read-write
      STATUS mandatory
      DESCRIPTION
        "Value for low setpoint of sensor,
         also used as alarm delay"
      ::= { cmcTcMasterTc1Unit4SensorEntry 7 }

    cmcTcMasterTc1Unit4SensorSetWarn OBJECT-TYPE
      SYNTAX INTEGER (0..300) 
      ACCESS read-write
      STATUS mandatory
      DESCRIPTION
        "Value for warning setpoint of sensor,
         also used as fan threshold"
      ::= { cmcTcMasterTc1Unit4SensorEntry 8 }

-- Outputs              

  cmcTcMasterTc1Unit4NumberOfOutputs OBJECT-TYPE
    SYNTAX INTEGER 
    ACCESS read-only
    STATUS mandatory
    DESCRIPTION
      "Number of outputs available on sensor unit 4"
    ::= { cmcTcMasterTc1StatusUnit4Outputs 1 }

-- table with entry for each output available on this unit              
                
  cmcTcMasterTc1Unit4OutputTable OBJECT-TYPE
    SYNTAX SEQUENCE OF CmcTcMasterTc1Unit4OutputEntry
    ACCESS not-accessible
    STATUS mandatory
    DESCRIPTION
      "Headline of output table"
    ::= { cmcTcMasterTc1StatusUnit4Outputs 2 }

  cmcTcMasterTc1Unit4OutputEntry OBJECT-TYPE
    SYNTAX CmcTcMasterTc1Unit4OutputEntry
    ACCESS not-accessible
    STATUS mandatory
    DESCRIPTION
      "Entries of output table"
    INDEX { cmcTcMasterTc1Unit4OutputIndex }
    ::= { cmcTcMasterTc1Unit4OutputTable 1 }

    CmcTcMasterTc1Unit4OutputEntry ::=
      SEQUENCE {
        cmcTcMasterTc1Unit4OutputIndex
          INTEGER,
        cmcTcMasterTc1Unit4OutputType
          INTEGER,
        cmcTcMasterTc1Unit4OutputText
          DisplayString (SIZE (0..20)),                
        cmcTcMasterTc1Unit4OutputStatus
          INTEGER,
        cmcTcMasterTc1Unit4OutputValue
          INTEGER,
        cmcTcMasterTc1Unit4OutputSet
          INTEGER,
        cmcTcMasterTc1Unit4OutputConfig
          INTEGER,
        cmcTcMasterTc1Unit4OutputDelay
          INTEGER,
        cmcTcMasterTc1Unit4OutputTimeoutAction
          INTEGER
      }

    cmcTcMasterTc1Unit4OutputIndex OBJECT-TYPE
      SYNTAX INTEGER (1..32000)
      ACCESS read-only
      STATUS mandatory
      DESCRIPTION
        "Index for the list of output entries. Its value ranges
         between 1 and the value of cmcTcMasterTc1Unit4NumberOfOutputs." 
      ::= { cmcTcMasterTc1Unit4OutputEntry 1 }

    cmcTcMasterTc1Unit4OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 4 to output[cmcTcMasterTc1Unit4OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc1Unit4OutputEntry 2 }

    cmcTcMasterTc1Unit4OutputText OBJECT-TYPE
      SYNTAX DisplayString (SIZE (0..20))
      ACCESS read-write
      STATUS mandatory
      DESCRIPTION
        "Descriptional text for each output (entry in the table)"
      ::= { cmcTcMasterTc1Unit4OutputEntry 3 }
              
    cmcTcMasterTc1Unit4OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc1Unit4OutputEntry 4 }

    cmcTcMasterTc1Unit4OutputValue OBJECT-TYPE
      SYNTAX INTEGER (-32000..32000) 
      ACCESS read-write
      STATUS mandatory
      DESCRIPTION
        "Value for output"
      ::= { cmcTcMasterTc1Unit4OutputEntry 5 }

    cmcTcMasterTc1Unit4OutputSet OBJECT-TYPE
      SYNTAX INTEGER {
        off (1),
        on (2),
        lock (3),
        unlock (4),
        unlockDelay (5)
      }
      ACCESS read-write
      STATUS mandatory
      DESCRIPTION
        "Command for output"
      ::= { cmcTcMasterTc1Unit4OutputEntry 6 }

    cmcTcMasterTc1Unit4OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc1Unit4OutputEntry 7 }

    cmcTcMasterTc1Unit4OutputDelay OBJECT-TYPE
      SYNTAX INTEGER (0..999) 
      ACCESS read-write
      STATUS mandatory
      DESCRIPTION
        "Unsigned Value for delay, 
         after this time the output will fall into the previous state"
      ::= { cmcTcMasterTc1Unit4OutputEntry 8 }

    cmcTcMasterTc1Unit4OutputTimeoutAction OBJECT-TYPE
      SYNTAX INTEGER {
        stay (1),
        off (2),
        on (3)
      }
      ACCESS read-write
      STATUS mandatory
      DESCRIPTION
        "State for output if timeout (RS422) occurs"
      ::= { cmcTcMasterTc1Unit4OutputEntry 9 }

-- Messages
              
  cmcTcMasterTc1Unit4NumberOfMsgs OBJECT-TYPE
    SYNTAX INTEGER 
    ACCESS read-only
    STATUS mandatory
    DESCRIPTION
      "Number of messages that can be created with sensor unit 4"
    ::= { cmcTcMasterTc1StatusUnit4Msg 1 }

-- table with entry for each alarm available on this unit               
                
  cmcTcMasterTc1Unit4MsgTable OBJECT-TYPE
    SYNTAX SEQUENCE OF CmcTcMasterTc1Unit4MsgEntry
    ACCESS not-accessible
    STATUS mandatory
    DESCRIPTION
      "Headline of message table"
    ::= { cmcTcMasterTc1StatusUnit4Msg 2 }

  cmcTcMasterTc1Unit4MsgEntry OBJECT-TYPE
    SYNTAX CmcTcMasterTc1Unit4MsgEntry
    ACCESS not-accessible
    STATUS mandatory
    DESCRIPTION
      "Entries of message table"
    INDEX { cmcTcMasterTc1Unit4MsgIndex }
    ::= { cmcTcMasterTc1Unit4MsgTable 1 }

    CmcTcMasterTc1Unit4MsgEntry ::=
      SEQUENCE {
        cmcTcMasterTc1Unit4MsgIndex
          INTEGER,
        cmcTcMasterTc1Unit4MsgText
          DisplayString (SIZE (0..20)),                
        cmcTcMasterTc1Unit4MsgStatus
          INTEGER, 
        cmcTcMasterTc1Unit4MsgRelay
          INTEGER,
        cmcTcMasterTc1Unit4MsgBeeper
          INTEGER,
        cmcTcMasterTc1Unit4MsgTrap1
          INTEGER,
        cmcTcMasterTc1Unit4MsgTrap2
          INTEGER,
        cmcTcMasterTc1Unit4MsgTrap3
          INTEGER,
        cmcTcMasterTc1Unit4MsgTrap4
          INTEGER,                 
        cmcTcMasterTc1Unit4MsgQuit
          INTEGER              
      }

    cmcTcMasterTc1Unit4MsgIndex OBJECT-TYPE
      SYNTAX INTEGER (1..32000)
      ACCESS read-only
      STATUS mandatory
      DESCRIPTION
        "Index for the list of message entries. Its value ranges
         between 1 and the value of cmcTcMasterTc1Unit4NumberOfMsgs." 
      ::= { cmcTcMasterTc1Unit4MsgEntry 1 }

    cmcTcMasterTc1Unit4MsgText OBJECT-TYPE
      SYNTAX DisplayString (SIZE (0..20))
      ACCESS read-write
      STATUS mandatory
      DESCRIPTION
        "Descriptional text for each message (entry in the table)"
      ::= { cmcTcMasterTc1Unit4MsgEntry 2 }

    cmcTcMasterTc1Unit4MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc1Unit4OutputSet)
         17: door is unlocked by WEB
         18: door is unlocked by timer
         19: no access, wrong keycode or cardnumber
         20: orientation of PSM-Unit is circuit 1
         21: orientation of PSM-Unit is circuit 2"
      ::= { cmcTcMasterTc1Unit4MsgEntry 3 }

    cmcTcMasterTc1Unit4MsgRelay OBJECT-TYPE
      SYNTAX INTEGER {
        disable (1),
        enable (2)
      }
      ACCESS read-write
      STATUS mandatory
      DESCRIPTION
        "Setup of Alarm relay for this alarm
         1:        no switching of alarm relay             
         2:        switching of alarm relay" 
      ::= { cmcTcMasterTc1Unit4MsgEntry 4 }

    cmcTcMasterTc1Unit4MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc1Unit4MsgEntry 5 }

    cmcTcMasterTc1Unit4MsgTrap1 OBJECT-TYPE
      SYNTAX INTEGER {
        disable (1),
        enable (2)
      }
      ACCESS read-write
      STATUS mandatory
      DESCRIPTION
        "Trap receiver 1 activated"
      ::= { cmcTcMasterTc1Unit4MsgEntry 6 }

    cmcTcMasterTc1Unit4MsgTrap2 OBJECT-TYPE
      SYNTAX INTEGER {
        disable (1),
        enable (2)
      }
      ACCESS read-write
      STATUS mandatory
      DESCRIPTION
        "Trap receiver 2 activated"
      ::= { cmcTcMasterTc1Unit4MsgEntry 7 }
 
    cmcTcMasterTc1Unit4MsgTrap3 OBJECT-TYPE
      SYNTAX INTEGER {
        disable (1),
        enable (2)
      }
      ACCESS read-write
      STATUS mandatory
      DESCRIPTION
        "Trap receiver 3 activated"
      ::= { cmcTcMasterTc1Unit4MsgEntry 8 }

    cmcTcMasterTc1Unit4MsgTrap4 OBJECT-TYPE
      SYNTAX INTEGER {
        disable (1),
        enable (2)
      }
      ACCESS read-write
      STATUS mandatory
      DESCRIPTION
        "Trap receiver 4 and Event Logging activated"
      ::= { cmcTcMasterTc1Unit4MsgEntry 9 }

    cmcTcMasterTc1Unit4MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc1Unit4MsgEntry 10 }

--Status extension unit

  cmcTcMasterTc1ValuesRelay OBJECT-TYPE
    SYNTAX INTEGER {
      disable (1),
      enable (2)
    }
    ACCESS read-write
    STATUS mandatory
    DESCRIPTION
      "Setup of Alarm relay for alarm ext. unit(s)
       1:        no switching of alarm relay             
       2:        switching of alarm relay" 
    ::= { cmcTcMasterTc1StatusExtUnit 1 }

  cmcTcMasterTc1ValuesBeeper OBJECT-TYPE
    SYNTAX INTEGER {
      disable (1),
      enable (2)
    }
    ACCESS read-write
    STATUS mandatory
    DESCRIPTION
      "Setup of Alarm beeper for alarm ext. unit(s)
       1:        no audible alarm
       2:        audible alarm" 
    ::= { cmcTcMasterTc1StatusExtUnit 2 }

  cmcTcMasterTc1ValuesTrap1 OBJECT-TYPE
    SYNTAX INTEGER {
      disable (1),
      enable (2)
    }
    ACCESS read-write
    STATUS mandatory
    DESCRIPTION
      "Trap receiver 1 activated"
    ::= { cmcTcMasterTc1StatusExtUnit 3 }

  cmcTcMasterTc1ValuesTrap2 OBJECT-TYPE
    SYNTAX INTEGER {
      disable (1),
      enable (2)
    }
    ACCESS read-write
    STATUS mandatory
    DESCRIPTION
      "Trap receiver 2 activated"
    ::= { cmcTcMasterTc1StatusExtUnit 4 }
 
  cmcTcMasterTc1ValuesTrap3 OBJECT-TYPE
    SYNTAX INTEGER {
      disable (1),
      enable (2)
    }
    ACCESS read-write
    STATUS mandatory
    DESCRIPTION
      "Trap receiver 3 activated"
    ::= { cmcTcMasterTc1StatusExtUnit 5 }

  cmcTcMasterTc1ValuesTrap4 OBJECT-TYPE
    SYNTAX INTEGER {
      disable (1),
      enable (2)
    }
    ACCESS read-write
    STATUS mandatory
    DESCRIPTION
      "Trap receiver 4 and Event Logging activated"
    ::= { cmcTcMasterTc1StatusExtUnit 6 }
 
  cmcTcMasterTc1NumberOfValues OBJECT-TYPE
    SYNTAX INTEGER 
    ACCESS  read-only
    STATUS  mandatory
    DESCRIPTION
      "Number of values availabel on extension units connected to the CMC-TC"
    ::= { cmcTcMasterTc1StatusExtUnit 7 }

-- table with entry for each value available on extension units              

  cmcTcMasterTc1ValuesTable OBJECT-TYPE
    SYNTAX SEQUENCE OF CmcTcMasterTc1ValuesEntry
    ACCESS not-accessible
    STATUS mandatory
    DESCRIPTION
      "Headline of values-table"
    ::= { cmcTcMasterTc1StatusExtUnit 8 }

  cmcTcMasterTc1ValuesEntry OBJECT-TYPE
    SYNTAX CmcTcMasterTc1ValuesEntry
    ACCESS not-accessible
    STATUS mandatory
    DESCRIPTION
      "Entries of values-table"
    INDEX { cmcTcMasterTc1ValuesIndex }
    ::= { cmcTcMasterTc1ValuesTable 1 }

    CmcTcMasterTc1ValuesEntry ::=
      SEQUENCE {
        cmcTcMasterTc1ValuesIndex
          INTEGER,
        cmcTcMasterTc1ValuesText
          DisplayString (SIZE (0..20)),                
        cmcTcMasterTc1ValuesStatus
          INTEGER,
        cmcTcMasterTc1ValuesValue
          INTEGER,
        cmcTcMasterTc1ValuesSetHigh
          INTEGER,
        cmcTcMasterTc1ValuesSetLow
          INTEGER
      }

    cmcTcMasterTc1ValuesIndex OBJECT-TYPE
      SYNTAX INTEGER (1..32000)
      ACCESS read-only
      STATUS mandatory
      DESCRIPTION
        "Index for the list of value entries. Its value ranges
         between 1 and the value of cmcTcMasterTc1NumberOfValues." 
      ::= { cmcTcMasterTc1ValuesEntry 1 }

        
    cmcTcMasterTc1ValuesText OBJECT-TYPE
      SYNTAX DisplayString (SIZE (0..20))
      ACCESS read-write
      STATUS mandatory
      DESCRIPTION
        "Descriptional text for each value (entry in the table)
         of the extension card"
      ::= { cmcTcMasterTc1ValuesEntry 2 }
              
    cmcTcMasterTc1ValuesStatus OBJECT-TYPE
      SYNTAX INTEGER {
        notAvail(1),
        lost(2),
        changed(3),
        ok(4),
        tooLow(5),
        tooHigh(6),
        error(7)
      }
      ACCESS read-only
      STATUS mandatory
      DESCRIPTION
        "Actual status of the value of the extension card"
      ::= { cmcTcMasterTc1ValuesEntry 3 }

    cmcTcMasterTc1ValuesValue OBJECT-TYPE
      SYNTAX INTEGER 
      ACCESS read-only
      STATUS mandatory
      DESCRIPTION
        "Value of sensor"
      ::= { cmcTcMasterTc1ValuesEntry 4 }

    cmcTcMasterTc1ValuesSetHigh OBJECT-TYPE
      SYNTAX INTEGER (0..255)
      ACCESS read-write
      STATUS mandatory
      DESCRIPTION
        "Value for high setpoint of sensor"
      ::= { cmcTcMasterTc1ValuesEntry 5 }

    cmcTcMasterTc1ValuesSetLow OBJECT-TYPE
      SYNTAX INTEGER (0..255)
      ACCESS read-write
      STATUS mandatory
      DESCRIPTION
        "Value for low setpoint of sensor"
      ::= { cmcTcMasterTc1ValuesEntry 6 }

--cmcTcMasterTc1SetupGeneral-group

  cmcTcMasterTc1SetTempUnit OBJECT-TYPE
    SYNTAX INTEGER {
      celsius(1),
      fahrenheit(2)
    }
    ACCESS read-write
    STATUS mandatory
    DESCRIPTION
      "Unit of all temperature values and setpoints, Celsius or Fahrenheit"
   ::= { cmcTcMasterTc1SetupGeneral 1 }

  cmcTcMasterTc1SetBeeper OBJECT-TYPE
    SYNTAX INTEGER {
      off(1),
      on(2)
    }
    ACCESS read-write
    STATUS mandatory
    DESCRIPTION
      "Audible alarm in CMC-TC unit:
       (2): beeper is on
       (1): beeper is off (general)"
    ::= { cmcTcMasterTc1SetupGeneral 2 }


  cmcTcMasterTc1QuitRelay OBJECT-TYPE
    SYNTAX INTEGER {
      disabled(1),
      enabled(2)
    }
    ACCESS read-write
    STATUS mandatory
    DESCRIPTION
      "Enable or disable acknowledging currently active alarm relay 
       (with 'C' on CMC-TC)."
    ::= { cmcTcMasterTc1SetupGeneral 3 }

  cmcTcMasterTc1LogicRelay OBJECT-TYPE
    SYNTAX INTEGER {
      closeAtAlarm(1),
      openAtAlarm(2),
      off(3)
    }
    ACCESS read-write
    STATUS mandatory
    DESCRIPTION
      "Logic of alarm relay: 
       (1) Relay will pick up in case of an alarm
       (2) Relay will release in case of an alarm
       (3) Relay off (general)"
    ::= { cmcTcMasterTc1SetupGeneral 4 }

  cmcTcMasterTc1WebAccess OBJECT-TYPE
    SYNTAX INTEGER {
      viewOnly(1),
      fullAccess(2),
      off(3)
    }
    ACCESS read-write
    STATUS mandatory
    DESCRIPTION
      "Web access via HTTP: 
       (1) view only
       (2) full Access, read and set
       (3) Web disabled (general)"
    ::= { cmcTcMasterTc1SetupGeneral 5 }
 
  cmcTcMasterTc1SetupDate OBJECT-TYPE
    SYNTAX DisplayString (SIZE (0..10))
    ACCESS read-write
    STATUS mandatory
    DESCRIPTION
      "actual Date in format DD.MM.YYYY"
    ::= { cmcTcMasterTc1SetupGeneral 6 }

  cmcTcMasterTc1SetupTime OBJECT-TYPE
    SYNTAX DisplayString (SIZE (0..8))
    ACCESS read-write
    STATUS mandatory
    DESCRIPTION
      "actual Time in format HH:MM:SS, HH (0-23), MM (0-59), SS (0-59)"
    ::= { cmcTcMasterTc1SetupGeneral 7 }
 
-- table for timer function
 
  cmcTcMasterTc1TimerNumber OBJECT-TYPE
    SYNTAX INTEGER 
    ACCESS read-only
    STATUS mandatory
    DESCRIPTION
      "Number of timers available on this unit"
    ::= { cmcTcMasterTc1TimerTable1 1 }

  cmcTcMasterTc1TimerTable OBJECT-TYPE
    SYNTAX SEQUENCE OF CmcTcMasterTc1TimerEntry
    ACCESS not-accessible
    STATUS mandatory
    DESCRIPTION
      "Headline of timer-table"
    ::= { cmcTcMasterTc1TimerTable1 2 }

  cmcTcMasterTc1TimerEntry OBJECT-TYPE
    SYNTAX CmcTcMasterTc1TimerEntry
    ACCESS not-accessible
    STATUS mandatory
    DESCRIPTION
      "Entries of timer-table"
    INDEX { cmcTcMasterTc1TimerIndex }
    ::= { cmcTcMasterTc1TimerTable 1 }

    CmcTcMasterTc1TimerEntry ::=
      SEQUENCE {
        cmcTcMasterTc1TimerIndex
          INTEGER,
        cmcTcMasterTc1TimerStatus
          INTEGER,
        cmcTcMasterTc1TimerDayOfWeek
          INTEGER,  
        cmcTcMasterTc1TimeOn 
          DisplayString (SIZE (0..5)),                              
        cmcTcMasterTc1TimeOff 
          DisplayString (SIZE (0..5)),                              
        cmcTcMasterTc1TimeControl
          INTEGER,
        cmcTcMasterTc1TimerFunction
           INTEGER
      }

    cmcTcMasterTc1TimerIndex OBJECT-TYPE
      SYNTAX INTEGER (1..32000)
      ACCESS read-only
      STATUS mandatory
      DESCRIPTION
        "Index for the list of timer entries. Its value ranges
         between 1 and the value of cmcTcMasterTc1TimerNumber." 
      ::= { cmcTcMasterTc1TimerEntry 1 }

    cmcTcMasterTc1TimerStatus OBJECT-TYPE
      SYNTAX INTEGER {
        switchedOff(1),
        switchedOn(2),
        noTime(3) 
      }
      ACCESS read-only
      STATUS mandatory
      DESCRIPTION
        "Actual status of the timer"
      ::= { cmcTcMasterTc1TimerEntry 2 }

    cmcTcMasterTc1TimerDayOfWeek OBJECT-TYPE
      SYNTAX INTEGER {
        sun(1),
        mon(2),
        tue(3) ,
        wed(4),
        thu(5),
        fri(6),
        sat(7),
        sat-sun(8),
        mon-fri(9),
        mon-sun(10)
      }
      ACCESS read-write
      STATUS mandatory
      DESCRIPTION
        "Selection of day of week for timer to switch"
      ::= { cmcTcMasterTc1TimerEntry 3 }
             
    cmcTcMasterTc1TimeOn OBJECT-TYPE
      SYNTAX DisplayString (SIZE (0..5))
      ACCESS read-write
      STATUS mandatory
      DESCRIPTION
        "Time to switch on current function, 
         Format: HH:MM"
      ::= { cmcTcMasterTc1TimerEntry 4 }

    cmcTcMasterTc1TimeOff OBJECT-TYPE
      SYNTAX DisplayString (SIZE (0..5))
      ACCESS read-write
      STATUS mandatory
      DESCRIPTION
        "Time to switch off current function,
         Format: HH:MM"
      ::= { cmcTcMasterTc1TimerEntry 5 }

    cmcTcMasterTc1TimeControl OBJECT-TYPE
      SYNTAX INTEGER  {
        disabled(1),
        enabled(2)
      }
      ACCESS read-write
      STATUS mandatory
      DESCRIPTION
        "Control via RTC"
      ::= { cmcTcMasterTc1TimerEntry 6 }

    cmcTcMasterTc1TimerFunction OBJECT-TYPE
      SYNTAX INTEGER {
        disKeypad1-1 (1),
        disKeypad2-1 (2),
        disKeypad1-2 (3),
        disKeypad2-2 (4),
        disKeypad1-3 (5),
        disKeypad2-3 (6),
        disKeypad1-4 (7),
        disKeypad2-4 (8),
        unlDoor1-1 (9),
        unlDoor2-1 (10),
        unlDoor1-2 (11),
        unlDoor2-2 (12),
        unlDoor1-3 (13),
        unlDoor2-3 (14),
        unlDoor1-4 (15),
        unlDoor2-5 (16),
        disTrapRec1 (17),
        disTrapRec2 (18),
        disTrapRec3 (19),
        disTrapRec4 (20),
        disSMS (21),
        schedule1 (22),
        schedule2 (23),
        schedule3 (24),
        schedule4 (25)
      }
      ACCESS read-write
      STATUS mandatory
      DESCRIPTION
        "Function which is controlled via timer
         1:     unlock via keypad 1 on unit 1 or remote input lock 1 is disabled
         2:     unlock via keypad 2 on unit 1 or remote input lock 2 is disabled
         3      unlock via keypad 1 on unit 2 or remote input lock 1 is disabled
         4:     unlock via keypad 2 on unit 2 or remote input lock 2 is disabled
         5:     unlock via keypad 1 on unit 3 or remote input lock 1 is disabled
         6:     unlock via keypad 2 on unit 3 or remote input lock 2 is disabled
         7:     unlock via keypad 1 on unit 4 or remote input lock 1 is disabled
         8:     unlock via keypad 2 on unit 4 or remote input lock 2 is disabled
         9:     Lock of door 1 on unit 1 will be unlocked
         10:    Lock of door 2 on unit 1 will be unlocked
         11:    Lock of door 1 on unit 2 will be unlocked
         12:    Lock of door 2 on unit 2 will be unlocked
         13:    Lock of door 1 on unit 3 will be unlocked
         14:    Lock of door 2 on unit 3 will be unlocked
         15:    Lock of door 1 on unit 4 will be unlocked
         16:    Lock of door 2 on unit 4 will be unlocked
         17-20: sending Traps to this Trap receiver will be disabled
         21:    sending SMS will be disabled
         22-25: Scheduled alarm off"
      ::= { cmcTcMasterTc1TimerEntry 7 }

--cmcTcMasterTc1TrapTable-group

  cmcTcMasterTc1TraptableNumber OBJECT-TYPE
    SYNTAX INTEGER 
    ACCESS read-only
    STATUS mandatory
    DESCRIPTION
      "Number of trapTable entries. The number of trap-receiver"
    ::= { cmcTcMasterTc1Traps 1 }

  cmcTcMasterTc1TrapTableTable OBJECT-TYPE    
    SYNTAX SEQUENCE OF CmcTcMasterTc1TrapTableEntry
    ACCESS not-accessible
    STATUS mandatory
    DESCRIPTION
     "A list of trap-receiver entries"
    ::= { cmcTcMasterTc1Traps 2 }

  cmcTcMasterTc1TrapTableEntry OBJECT-TYPE
    SYNTAX CmcTcMasterTc1TrapTableEntry
    ACCESS not-accessible
    STATUS mandatory
    DESCRIPTION
      "Entries of cmcTcMasterTc1TrapTable"
    INDEX   { cmcTcMasterTc1TrapIndex }
    ::= { cmcTcMasterTc1TrapTableTable 1 }      
              
    CmcTcMasterTc1TrapTableEntry ::=
      SEQUENCE {
        cmcTcMasterTc1TrapIndex
          INTEGER,
        cmcTcMasterTc1TrapStatus
          INTEGER,
        cmcTcMasterTc1TrapIPaddress
          DisplayString
      }

    cmcTcMasterTc1TrapIndex OBJECT-TYPE
      SYNTAX INTEGER (1..32000)
      ACCESS read-only
      STATUS mandatory
      DESCRIPTION
        "Index for the trap-receiver-table. Its value ranges between
         1 and the value of cmcTcMasterTc1TraptableNumber "
      ::= { cmcTcMasterTc1TrapTableEntry 1 }

    cmcTcMasterTc1TrapStatus OBJECT-TYPE
      SYNTAX INTEGER {
        disabled(1),
        enabled(2)
      }
      ACCESS read-write
      STATUS mandatory
      DESCRIPTION
        "Enable or disable trap receiver"
      ::= { cmcTcMasterTc1TrapTableEntry 2 }

    cmcTcMasterTc1TrapIPaddress OBJECT-TYPE
      SYNTAX DisplayString (SIZE (0..15))
      ACCESS read-write
      STATUS mandatory
      DESCRIPTION
        "IP-address of trap-receiver"
      ::= { cmcTcMasterTc1TrapTableEntry 3 }

--cmcTcMasterTc1Control-group (Added in Version 1.1)

  cmcTcMasterTc1QuitUnit OBJECT-TYPE
    SYNTAX INTEGER {
      noQuit(1),
      quit(2),
    }
    ACCESS read-write
    STATUS mandatory
    DESCRIPTION
      "Command to quit (acknowledge) alarms of CMC-TC unit.
       Setting to 'quit' (2) will have same result as pressing 'C' on Units.
       Variable is automatically set back to 'noQuit' (1)."
    ::= { cmcTcMasterTc1Control 1 }

--cmcTcMasterDevice2-group

  cmcTcMasterDev2Type OBJECT-TYPE
    SYNTAX INTEGER {
      other (0),
      cmc (1),
      pcu (3),
      tc (4)
    }
    ACCESS read-only
    STATUS mandatory
    DESCRIPTION
      "Type of device2"
    ::= { cmcTcMasterDevice2 1 }

  cmcTcMasterDev2Status OBJECT-TYPE
    SYNTAX INTEGER {
      other (1),
      notConnected (2),
      normal (3),
      minor (4),
      major (5),
      configChanged (6),
      connectionLost (10)
    }
    ACCESS read-only
    STATUS mandatory
    DESCRIPTION
      "Status of device2"
    ::= { cmcTcMasterDevice2 2 }

  cmcTcMasterDev2Descr OBJECT-TYPE
    SYNTAX DisplayString (SIZE (0..255))
    ACCESS read-only
    STATUS mandatory
    DESCRIPTION
      "A textual description of the entity.  This value
       should include the full name and version
       identification of the system's hardware type,
       software operating-system, and networking
       software.  It is mandatory that this only contain
       printable ASCII characters."
    ::= { cmcTcMasterDevice2 3 }

  cmcTcMasterDev2UpTime OBJECT-TYPE
    SYNTAX TimeTicks
    ACCESS read-only
    STATUS mandatory
    DESCRIPTION
      "The time (in hundredths of a second) since the
       network management portion of the system was last
       re-initialized."
    ::= { cmcTcMasterDevice2 4 }

  cmcTcMasterDev2Contact OBJECT-TYPE
    SYNTAX DisplayString (SIZE (0..255))
    ACCESS read-write
    STATUS mandatory
    DESCRIPTION
      "The textual identification of the contact person
       for this managed node, together with information
       on how to contact this person."
    ::= { cmcTcMasterDevice2 5 }

  cmcTcMasterDev2Name OBJECT-TYPE
    SYNTAX DisplayString (SIZE (0..255))
    ACCESS read-write
    STATUS mandatory
    DESCRIPTION
      "An administratively-assigned name for this
       managed node.  By convention, this is the node's
       fully-qualified domain name."
    ::= { cmcTcMasterDevice2 6 }

  cmcTcMasterDev2Location OBJECT-TYPE
    SYNTAX DisplayString (SIZE (0..255))
    ACCESS read-write
    STATUS mandatory
    DESCRIPTION
      "The physical location of this node (e.g.,
       `telephone closet, 3rd floor')."
    ::= { cmcTcMasterDevice2 7 }

--cmcTcMasterCmc2Values-group

  cmcTcMasterCmc2ValueTemperature1 OBJECT-TYPE
    SYNTAX INTEGER
    ACCESS read-only
    STATUS mandatory
    DESCRIPTION
      "Actual value of temperature 1 in deg C"
    ::= { cmcTcMasterCmc2Values 1 }

  cmcTcMasterCmc2ValueTemperature2 OBJECT-TYPE
    SYNTAX INTEGER
    ACCESS read-only
    STATUS mandatory
    DESCRIPTION
      "Actual value of temperature 2 in deg C"
    ::= { cmcTcMasterCmc2Values 2 }

  cmcTcMasterCmc2ValuePowerSupply OBJECT-TYPE
    SYNTAX INTEGER
    ACCESS read-only
    STATUS mandatory
    DESCRIPTION
      "Actual value of power supply in V"
    ::= { cmcTcMasterCmc2Values 3 }

  cmcTcMasterCmc2ValueAnalogAux1 OBJECT-TYPE
    SYNTAX INTEGER
    ACCESS read-only
    STATUS mandatory
    DESCRIPTION
      "Actual value of aux. analog input 1
      (4-20mA = 0-100%)"
    ::= { cmcTcMasterCmc2Values 4 }

  cmcTcMasterCmc2ValueAnalogAux2 OBJECT-TYPE
    SYNTAX INTEGER
    ACCESS read-only
    STATUS mandatory
    DESCRIPTION
      "Actual value of aux. analog input 2
      (4-20mA = 0-100%)"
    ::= { cmcTcMasterCmc2Values 5 }

--cmcTcMasterCmc2Values-table-group

  cmcTcMasterCmc2ValuesNumber OBJECT-TYPE
    SYNTAX INTEGER
    ACCESS read-only
    STATUS mandatory
    DESCRIPTION
      "Number of value-table entries"
    ::= { cmcTcMasterCmc2Table1 1 }

  cmcTcMasterCmc2ValuesTable OBJECT-TYPE
    SYNTAX SEQUENCE OF CmcTcMasterCmc2ValuesEntry
    ACCESS not-accessible
    STATUS mandatory
    DESCRIPTION
      "Headline of value-table"
    ::= { cmcTcMasterCmc2Table1 2 }

  cmcTcMasterCmc2ValuesEntry OBJECT-TYPE
    SYNTAX CmcTcMasterCmc2ValuesEntry
    ACCESS not-accessible
    STATUS mandatory
    DESCRIPTION
      "Entries of value-table"
    INDEX { cmcTcMasterCmc2ValuesIndex }
    ::= { cmcTcMasterCmc2ValuesTable 1 }

  CmcTcMasterCmc2ValuesEntry ::=
    SEQUENCE {
      cmcTcMasterCmc2ValuesIndex
        INTEGER,
      cmcTcMasterCmc2ValuesText
        DisplayString (SIZE (0..31)),
      cmcTcMasterCmc2ValuesValue
        INTEGER,
      cmcTcMasterCmc2ValuesStatus
        INTEGER,
      cmcTcMasterCmc2ValuesMaxValue
        INTEGER,
      cmcTcMasterCmc2ValuesMinValue
        INTEGER
    }

    cmcTcMasterCmc2ValuesIndex OBJECT-TYPE
      SYNTAX INTEGER (1..32000)
      ACCESS read-only
      STATUS mandatory
      DESCRIPTION
        "Index for the list of value entries. Its value ranges
        between 1 and the value of valuesNumber."
      ::= { cmcTcMasterCmc2ValuesEntry 1 }

    cmcTcMasterCmc2ValuesText OBJECT-TYPE
      SYNTAX DisplayString (SIZE (0..31))
      ACCESS read-write
      STATUS mandatory
      DESCRIPTION
        "Text of the entry in the value-table"
      ::= { cmcTcMasterCmc2ValuesEntry 2 }

    cmcTcMasterCmc2ValuesValue OBJECT-TYPE
      SYNTAX INTEGER
      ACCESS read-only
      STATUS mandatory
      DESCRIPTION
        "Actual value of the value-table"
      ::= { cmcTcMasterCmc2ValuesEntry 3 }

    cmcTcMasterCmc2ValuesStatus OBJECT-TYPE
      SYNTAX INTEGER {
        valueOK(1),
        valueTooLow(2),
        valueTooHigh(3),
        valueERROR(4),
        notAvail(5)
      }
      ACCESS read-only
      STATUS mandatory
      DESCRIPTION
        "Status of the value"
      ::= { cmcTcMasterCmc2ValuesEntry 4 }

    cmcTcMasterCmc2ValuesMaxValue OBJECT-TYPE
      SYNTAX INTEGER
      ACCESS read-write
      STATUS mandatory
      DESCRIPTION
        "Value for max. alarm"
      ::= { cmcTcMasterCmc2ValuesEntry 5 }

    cmcTcMasterCmc2ValuesMinValue OBJECT-TYPE
      SYNTAX INTEGER
      ACCESS read-write
      STATUS mandatory
      DESCRIPTION
        "Value for min. alarm"
      ::= { cmcTcMasterCmc2ValuesEntry 6 }

--cmcTcMasterCmc2status-group

  cmcTcMasterCmc2StatusTemperature1 OBJECT-TYPE
    SYNTAX DisplayString (SIZE (0..31))
    ACCESS read-only
    STATUS mandatory
    DESCRIPTION
      "Status temperature 1, OK/ too low/ too high
       (see setpoints of temperature 1)"
    ::= { cmcTcMasterCmc2Status 1 }

  cmcTcMasterCmc2StatusTemperature2 OBJECT-TYPE
    SYNTAX DisplayString (SIZE (0..31))
    ACCESS read-only
    STATUS mandatory
    DESCRIPTION
      "Status temperature 2, OK/ too low/ too high
       (see setpoints of temperature 2)"
    ::= { cmcTcMasterCmc2Status 2 }

  cmcTcMasterCmc2StatusFan1 OBJECT-TYPE
    SYNTAX DisplayString (SIZE (0..31))
    ACCESS read-only
    STATUS mandatory
    DESCRIPTION
      "Status fan 1, Stop/ running/ fault"
    ::= { cmcTcMasterCmc2Status 3 }

  cmcTcMasterCmc2StatusFan2 OBJECT-TYPE
    SYNTAX DisplayString (SIZE (0..31))
    ACCESS read-only
    STATUS mandatory
    DESCRIPTION
      "Status fan 2, Stop/ running/ fault"
    ::= { cmcTcMasterCmc2Status 4 }

  cmcTcMasterCmc2StatusHeating OBJECT-TYPE
    SYNTAX DisplayString (SIZE (0..31))
    ACCESS read-only
    STATUS mandatory
    DESCRIPTION
      "Status heating, On/Off"
    ::= { cmcTcMasterCmc2Status 5 }

  cmcTcMasterCmc2StatusPowerSupply OBJECT-TYPE
    SYNTAX DisplayString (SIZE (0..31))
    ACCESS read-only
    STATUS mandatory
    DESCRIPTION
      "Status power supply, OK/ too low/ too high
       (see setpoints of power supply)"
    ::= { cmcTcMasterCmc2Status 6 }

  cmcTcMasterCmc2StatusAnalogAux1 OBJECT-TYPE
    SYNTAX DisplayString (SIZE (0..31))
    ACCESS read-only
    STATUS mandatory
    DESCRIPTION
      "Status aux analog input 1, OK/ too low/ too high"
    ::= { cmcTcMasterCmc2Status 7 }

  cmcTcMasterCmc2StatusAnalogAux2 OBJECT-TYPE
    SYNTAX DisplayString (SIZE (0..31))
    ACCESS read-only
    STATUS mandatory
    DESCRIPTION
      "Status aux analog input 2, OK/ too low/ too high"
    ::= { cmcTcMasterCmc2Status 8 }

  cmcTcMasterCmc2StatusDoor OBJECT-TYPE
    SYNTAX DisplayString (SIZE (0..31))
    ACCESS read-only
    STATUS mandatory
    DESCRIPTION
      "Status door, open/closed/locked"
    ::= { cmcTcMasterCmc2Status 9 }

  cmcTcMasterCmc2StatusUps1 OBJECT-TYPE
    SYNTAX DisplayString (SIZE (0..31))
    ACCESS read-only
    STATUS mandatory
    DESCRIPTION
      "Status UPS 1, OK/ fault"
    ::= { cmcTcMasterCmc2Status 10 }

  cmcTcMasterCmc2StatusUps2 OBJECT-TYPE
    SYNTAX DisplayString (SIZE (0..31))
    ACCESS read-only
    STATUS mandatory
    DESCRIPTION
      "Status UPS 2, OK/ fault"
    ::= { cmcTcMasterCmc2Status 11 }

  cmcTcMasterCmc2StatusSmokeSensor OBJECT-TYPE
    SYNTAX DisplayString (SIZE (0..31))
    ACCESS read-only
    STATUS mandatory
    DESCRIPTION
      "Status smoke-sensor, OK/ smoke"
    ::= { cmcTcMasterCmc2Status 12 }

  cmcTcMasterCmc2StatusVibrationSensor OBJECT-TYPE
    SYNTAX DisplayString (SIZE (0..31))
    ACCESS read-only
    STATUS mandatory
    DESCRIPTION
      "Status vibration sensor, OK/ vibration"
    ::= { cmcTcMasterCmc2Status 13 }

  cmcTcMasterCmc2StatusMessage OBJECT-TYPE
    SYNTAX DisplayString (SIZE (0..31))
    ACCESS read-only
    STATUS mandatory
    DESCRIPTION
      "Message from CMC"
    ::= { cmcTcMasterCmc2Status 14 }

  cmcTcMasterCmc2ValueOperatingTime OBJECT-TYPE
    SYNTAX DisplayString (SIZE (0..31))
    ACCESS read-only
    STATUS mandatory
    DESCRIPTION
      "Operating time CMC-unit"
    ::= { cmcTcMasterCmc2Status 15 }

  cmcTcMasterCmc2StatusUnit OBJECT-TYPE
    SYNTAX INTEGER {
      unitCelsius(1),
      unitFahrenheit(2)
    }
    ACCESS read-only
    STATUS mandatory
    DESCRIPTION
      "Unit of temperature-values, Celsius or Fahrenheit"
   ::= { cmcTcMasterCmc2Status 16 }


--cmcTcMasterCmc2Status-table-group

  cmcTcMasterCmc2StatusNumber OBJECT-TYPE
    SYNTAX INTEGER 
    ACCESS read-only
    STATUS mandatory
    DESCRIPTION
      "Number of status-table entries"
    ::= { cmcTcMasterCmc2Table 1 }

  cmcTcMasterCmc2StatusTable OBJECT-TYPE
    SYNTAX SEQUENCE OF CmcTcMasterCmc2StatusEntry
    ACCESS not-accessible
    STATUS mandatory
    DESCRIPTION
      "Headline of table"
    ::= { cmcTcMasterCmc2Table 2 }

  cmcTcMasterCmc2StatusEntry OBJECT-TYPE
    SYNTAX CmcTcMasterCmc2StatusEntry
    ACCESS not-accessible
    STATUS mandatory
    DESCRIPTION
      "A list of status entries.  The number of
       entries is given by the value of cmcTcMasterCmc2StatusNumber." 
    INDEX { cmcTcMasterCmc2StatusIndex }
    ::= { cmcTcMasterCmc2StatusTable 1 }

  CmcTcMasterCmc2StatusEntry ::=
    SEQUENCE {
      cmcTcMasterCmc2StatusIndex
        INTEGER,
      cmcTcMasterCmc2StatusText
        DisplayString (SIZE (0..31)),
      cmcTcMasterCmc2StatusStatus
        INTEGER              
    }

    cmcTcMasterCmc2StatusIndex OBJECT-TYPE
      SYNTAX INTEGER (1..32000)
      ACCESS read-only
      STATUS mandatory
      DESCRIPTION
        "Index fo the list of status entries. Its value ranges
         between 1 and the value of cmcTcMasterCmc2StatusNumber." 
      ::= { cmcTcMasterCmc2StatusEntry 1 }

    cmcTcMasterCmc2StatusText OBJECT-TYPE
      SYNTAX DisplayString (SIZE (0..31))
      ACCESS read-write
      STATUS mandatory
      DESCRIPTION
        "Text of the entry in the status-table"
      ::= { cmcTcMasterCmc2StatusEntry 2 }

    cmcTcMasterCmc2StatusStatus OBJECT-TYPE
      SYNTAX INTEGER  {
        statusOK(1),
        alarm(2),
        security(3),
        notAvail(4)
      }
      ACCESS read-only
      STATUS mandatory
      DESCRIPTION
        "Status of the table entry"
      ::= { cmcTcMasterCmc2StatusEntry 3 }

--******************************************************************************

--cmcTCMasterCmc2Set-group

  cmcTcMasterCmc2StatusAccess OBJECT-TYPE
    SYNTAX DisplayString (SIZE (0..31))
    ACCESS read-write
    STATUS mandatory
    DESCRIPTION
      "Status access"
    ::= { cmcTcMasterCmc2Set 1 }

  cmcTcMasterCmc2SetDoor OBJECT-TYPE
    SYNTAX INTEGER {
      lockDoor(1),
      openDoorTime(2),
      openDoorAccess(3),
      openDoor(4)
    }
    ACCESS read-write
    STATUS mandatory
    DESCRIPTION
      "Set door, see table"
    ::= { cmcTcMasterCmc2Set 2 }

  cmcTcMasterCmc2SetMessage OBJECT-TYPE
    SYNTAX DisplayString (SIZE (0..31))
    ACCESS read-write
    STATUS mandatory
    DESCRIPTION
      "Set message"
    ::= { cmcTcMasterCmc2Set 3 }

  cmcTcMasterCmc2SetFault        OBJECT-TYPE
    SYNTAX INTEGER {
      clearFault(1),
      setFault(2)
    }
    ACCESS read-write
    STATUS mandatory
    DESCRIPTION
      "Set fault, see table"
    ::= { cmcTcMasterCmc2Set 4 }

--cmcTcMasterCmc2RelayControl-group

  cmcTcMasterCmc2RelaytableMaxNum OBJECT-TYPE
    SYNTAX INTEGER 
    ACCESS read-only
    STATUS mandatory
    DESCRIPTION
      "Number of table entries"
    ::= { cmcTcMasterCmc2RelayControl 1 }

  cmcTcMasterCmc2RelayTable OBJECT-TYPE
    SYNTAX SEQUENCE OF CmcTcMasterCmc2RelayEntry
    ACCESS not-accessible
    STATUS mandatory
    DESCRIPTION
      "Headline of table for relay control"
    ::= { cmcTcMasterCmc2RelayControl 2 }

  cmcTcMasterCmc2RelayEntry OBJECT-TYPE
    SYNTAX CmcTcMasterCmc2RelayEntry
    ACCESS not-accessible
    STATUS mandatory
    DESCRIPTION
      "Entries"
    INDEX { cmcTcMasterCmc2RelaytableIndex }
    ::= { cmcTcMasterCmc2RelayTable 1 }

  CmcTcMasterCmc2RelayEntry ::=
    SEQUENCE {
      cmcTcMasterCmc2RelaytableIndex
        INTEGER,
      cmcTcMasterCmc2RelaytableText
	DisplayString (SIZE (0..31)),
      cmcTcMasterCmc2RelaytableStatus
        INTEGER              
    }

    cmcTcMasterCmc2RelaytableIndex OBJECT-TYPE
      SYNTAX INTEGER (1..32000)
      ACCESS read-only
      STATUS mandatory
      DESCRIPTION
        "Index for the relay-table. Its value ranges
         between 1 and cmcTcMasterCmc2RelaytableMaxNum"
      ::= { cmcTcMasterCmc2RelayEntry 1 }

    cmcTcMasterCmc2RelaytableText OBJECT-TYPE
      SYNTAX DisplayString (SIZE (0..31))
      ACCESS read-write
      STATUS mandatory
      DESCRIPTION
        "Description-Text for each relay in the table"
      ::= { cmcTcMasterCmc2RelayEntry 2 }

    cmcTcMasterCmc2RelaytableStatus OBJECT-TYPE
      SYNTAX INTEGER  {
        relayOFF(1),
        relayON(2),
        notAvail(3)
      }
      ACCESS read-write
      STATUS mandatory
      DESCRIPTION
        "Status of relays in the table"
      ::= { cmcTcMasterCmc2RelayEntry 3 }

--cmcTcMasterCmc2Setpoints-group

  cmcTcMasterCmc2SetpointFan1 OBJECT-TYPE
    SYNTAX INTEGER 
    ACCESS read-write
    STATUS mandatory
    DESCRIPTION
      "Setpoint Fan 1 in C, Fan 1 will start
       if temperature 1 exceeds this value"
    ::= { cmcTcMasterCmc2Setpoints 1 }

  cmcTcMasterCmc2SetpointFan2 OBJECT-TYPE
    SYNTAX INTEGER 
    ACCESS read-write
    STATUS mandatory
    DESCRIPTION
      "Setpoint Fan 2 in C, Fan 2 will start
       if temperature 2 exceeds this value"
    ::= { cmcTcMasterCmc2Setpoints 2 }

  cmcTcMasterCmc2SetpointHeating OBJECT-TYPE
    SYNTAX INTEGER 
    ACCESS read-write
    STATUS mandatory
    DESCRIPTION
      "Setpoint heating in C, heating will start
       if lowest value of temperature 1 and 2 falls below this value"
    ::= { cmcTcMasterCmc2Setpoints 3 }

  cmcTcMasterCmc2SetpointHighTemperature1 OBJECT-TYPE
    SYNTAX INTEGER 
    ACCESS read-write
    STATUS mandatory
    DESCRIPTION
      "Setpoint high value alarm temperature 1"
    ::= { cmcTcMasterCmc2Setpoints 4 }

  cmcTcMasterCmc2SetpointLowTemperature1 OBJECT-TYPE
    SYNTAX INTEGER 
    ACCESS read-write
    STATUS mandatory
    DESCRIPTION
      "Setpoint low value alarm temperature 1"
    ::= { cmcTcMasterCmc2Setpoints 5 }

  cmcTcMasterCmc2SetpointHighTemperature2 OBJECT-TYPE
    SYNTAX INTEGER 
    ACCESS read-write
    STATUS mandatory
    DESCRIPTION
      "Setpoint high value alarm temperature 2"
    ::= { cmcTcMasterCmc2Setpoints 6 }

  cmcTcMasterCmc2SetpointLowTemperature2 OBJECT-TYPE
    SYNTAX INTEGER 
    ACCESS read-write
    STATUS mandatory
    DESCRIPTION
      "Setpoint low value alarm temperature 2"
    ::= { cmcTcMasterCmc2Setpoints 7 }

  cmcTcMasterCmc2SetpointHighVoltage OBJECT-TYPE
    SYNTAX INTEGER 
    ACCESS read-write
    STATUS mandatory
    DESCRIPTION
      "Setpoint high value supply voltage alarm"
    ::= { cmcTcMasterCmc2Setpoints 8 }

  cmcTcMasterCmc2SetpointLowVoltage OBJECT-TYPE
    SYNTAX INTEGER
    ACCESS read-write
    STATUS mandatory
    DESCRIPTION
      "Setpoint low value supply voltage alarm"
    ::= { cmcTcMasterCmc2Setpoints 9 }

  cmcTcMasterCmc2SetpointLowAux1 OBJECT-TYPE
    SYNTAX INTEGER 
    ACCESS read-write
    STATUS mandatory
    DESCRIPTION
      "Setpoint low value Aux input 1 alarm"
    ::= { cmcTcMasterCmc2Setpoints 10 }

  cmcTcMasterCmc2SetpointHighAux1 OBJECT-TYPE
    SYNTAX INTEGER 
    ACCESS read-write
    STATUS mandatory
    DESCRIPTION
      "Setpoint high value Aux input 1 alarm"
    ::= { cmcTcMasterCmc2Setpoints 11 }

  cmcTcMasterCmc2SetpointLowAux2 OBJECT-TYPE
    SYNTAX INTEGER 
    ACCESS read-write
    STATUS mandatory
    DESCRIPTION
      "Setpoint low value Aux input 2 alarm"
    ::= { cmcTcMasterCmc2Setpoints 12 }

  cmcTcMasterCmc2SetpointHighAux2 OBJECT-TYPE
    SYNTAX INTEGER 
    ACCESS read-write
    STATUS mandatory
    DESCRIPTION
      "Setpoint high value Aux input alarm"
    ::= { cmcTcMasterCmc2Setpoints 13 }

--cmcTcMasterCmc2TrapControl-group

  cmcTcMasterCmc2SetTrapRepeat OBJECT-TYPE
    SYNTAX INTEGER {
      disableTrapRepeat(1),
      enableTrapRepeat(2)
    }
    ACCESS read-write
    STATUS mandatory
    DESCRIPTION
      "Enable/disable repeating of traps. If enabled, traps will
       be repeated after a repeat time, set in setTrapRepeatTime.
       Repeating can be stopped by setting setTrapQuit to quitTrap"
    ::= { cmcTcMasterCmc2TrapControl 1 }

  cmcTcMasterCmc2SetTrapRepeatTime OBJECT-TYPE
    SYNTAX INTEGER 
    ACCESS read-write
    STATUS mandatory
    DESCRIPTION
      "Time value (sec) for trap-repeating, if setTrapRepeat is enabled"
    ::= { cmcTcMasterCmc2TrapControl 2 }

  cmcTcMasterCmc2SetTrapQuit OBJECT-TYPE
    SYNTAX INTEGER {
      quitTrap(1),
      quitTrapOK(2),
      noTrapToQuit(3),
      trapToQuit(4)
    }
    ACCESS read-write
    STATUS mandatory
    DESCRIPTION
      "Quit trap to stop repeating."
    ::= { cmcTcMasterCmc2TrapControl 3 }

--cmcTcMasterCmc2TrapTable-group

  cmcTcMasterCmc2TraptableNumber OBJECT-TYPE
    SYNTAX INTEGER 
    ACCESS read-only
    STATUS mandatory
    DESCRIPTION
      "Number of trapTable entries. The number of trap-receiver"
    ::= { cmcTcMasterCmc2Traps 1 }

  cmcTcMasterCmc2TrapTable OBJECT-TYPE
    SYNTAX SEQUENCE OF CmcTcMasterCmc2TrapEntry
    ACCESS not-accessible
    STATUS mandatory
    DESCRIPTION
      "A list of trap-receiver entries"
    ::= { cmcTcMasterCmc2Traps 2 }

  cmcTcMasterCmc2TrapEntry OBJECT-TYPE
    SYNTAX CmcTcMasterCmc2TrapEntry
    ACCESS not-accessible
    STATUS mandatory
    DESCRIPTION
      "Entries of trapTable"
    INDEX { cmcTcMasterCmc2TrapIndex }
    ::= { cmcTcMasterCmc2TrapTable 1 }

  CmcTcMasterCmc2TrapEntry ::=
    SEQUENCE {
      cmcTcMasterCmc2TrapIndex
        INTEGER,
      cmcTcMasterCmc2TrapStatus
        INTEGER,
      cmcTcMasterCmc2TrapIPaddress
        DisplayString
    }

    cmcTcMasterCmc2TrapIndex OBJECT-TYPE
      SYNTAX INTEGER (1..32000)
      ACCESS read-only
      STATUS mandatory
      DESCRIPTION
        "Index for the trap-receiver-table. Its value ranges between
         1 and the value of cmcTcMasterCmc2TraptableNumber "
      ::= { cmcTcMasterCmc2TrapEntry 1 }

    cmcTcMasterCmc2TrapStatus OBJECT-TYPE
      SYNTAX INTEGER  {
        enabled(1),
        disabled(2)
      }
      ACCESS read-write
      STATUS mandatory
      DESCRIPTION
        "Enable or disable trap receiver"
      ::= { cmcTcMasterCmc2TrapEntry 2 }

    cmcTcMasterCmc2TrapIPaddress OBJECT-TYPE
      SYNTAX DisplayString (SIZE (0..31))
      ACCESS read-write
      STATUS mandatory
      DESCRIPTION
        "IP-address of trap-receiver"
      ::= { cmcTcMasterCmc2TrapEntry 3 }

--cmcTcMasterPcu2MibRev-group
          
  cmcTcMasterPcu2MibMajRev OBJECT-TYPE
    SYNTAX INTEGER (1..32000)
    ACCESS read-only
    STATUS mandatory
    DESCRIPTION
      "The Major Revision level.
       A change in the major revision level represents a major change
       in the architecture of the MIB. A change in the major revision 
       level may indicate a significant change in the information,
       correct interpretation of data may require a MIB document
       with the same major revision level."
    ::= { cmcTcMasterPcu2MibRev 1 }

  cmcTcMasterPcu2MibMinRev OBJECT-TYPE
    SYNTAX INTEGER (0..32000)
    ACCESS read-only
    STATUS mandatory
    DESCRIPTION
      "The Minor Revision level.
       A change in the minor revision level may represent some minor
       additional support, no changes to any pre-existing information
       has occurred."
    ::= { cmcTcMasterPcu2MibRev 2 }

  cmcTcMasterPcu2MibCondition OBJECT-TYPE
    SYNTAX INTEGER {
      other (1),
      ok (2),
      degraded (3),
      failed (4)
    }
    ACCESS read-only
    STATUS mandatory
    DESCRIPTION
      "The overall condition (status) of the system represented by
       this MIB. 
       (2) OK
       (3) a minor problem, warning condition (yellow LED on PCU)
       (4) a major problem (red LED on PCU)"
    ::= { cmcTcMasterPcu2MibRev 3 }

--cmcTcMasterPcu2Values-group

  cmcTcMasterPcu2ValueEnergy1 OBJECT-TYPE
    SYNTAX INTEGER 
    ACCESS read-only
    STATUS mandatory
    DESCRIPTION
      "Total value of the Energy (Wh), measured on IEC input 1"
    ::= { cmcTcMasterPcu2Values 1 }

  cmcTcMasterPcu2ValueEnergy2 OBJECT-TYPE
    SYNTAX INTEGER 
    ACCESS read-only
    STATUS mandatory
    DESCRIPTION
      "Actual value of the Energy (Wh), measured on IEC input 2"
    ::= { cmcTcMasterPcu2Values 2 }

  cmcTcMasterPcu2ValueEnergy1Time OBJECT-TYPE
    SYNTAX INTEGER 
    ACCESS read-only
    STATUS mandatory
    DESCRIPTION
      "Actual value of the Energy (Wh), measured on IEC input 1, can be set to 0
       Value can be used to calculate the energy over a fixed time"
    ::= { cmcTcMasterPcu2Values 3 }

  cmcTcMasterPcu2ValueEnergy2Time OBJECT-TYPE
    SYNTAX INTEGER 
    ACCESS read-only
    STATUS mandatory
    DESCRIPTION
      "Actual value of the Energy (Wh), measured on IEC input 2, can be set to 0.
       Value can be used to calculate the energy over a fixed time"
    ::= { cmcTcMasterPcu2Values 4 }

  cmcTcMasterPcu2ValuePower1 OBJECT-TYPE
    SYNTAX INTEGER 
    ACCESS read-only
    STATUS mandatory
    DESCRIPTION
      "Calculated actual power 1 (W). Calculated from cmcTcMasterPcu2ValueEnergy1/time"
    ::= { cmcTcMasterPcu2Values 5 }
          
  cmcTcMasterPcu2ValuePower2 OBJECT-TYPE
    SYNTAX INTEGER 
    ACCESS read-only
    STATUS mandatory
    DESCRIPTION
      "Calculated actual power 2 (W). Calculated from cmcTcMasterPcu2ValueEnergy2/time"
    ::= { cmcTcMasterPcu2Values 6 }
          
  cmcTcMasterPcu2ValueTemperature OBJECT-TYPE
    SYNTAX INTEGER 
    ACCESS read-only
    STATUS mandatory
    DESCRIPTION
      "Actual value of temperature 1 in deg C or deg F"
    ::= { cmcTcMasterPcu2Values 7 }
          
--cmcTcMasterPcu2Status-group

  cmcTcMasterPcu2StatusInput1 OBJECT-TYPE
    SYNTAX INTEGER {
      false(1),
      true(2),
      pending(3),
      notAvail(4)
    }
    ACCESS read-only
    STATUS mandatory
    DESCRIPTION
      "Status of digital Input 1
       (1) digital signal is true (contact closed if setup is NO)
       (2) digital signal is false(contact opened if setup is NO),
       note setup of input (NO/NC)
       (3) digital input is pending, note setup of delay"
    ::= { cmcTcMasterPcu2Status 1 }

  cmcTcMasterPcu2StatusInput2 OBJECT-TYPE
    SYNTAX INTEGER {
      false(1),
      true(2),
      pending(3),
      notAvail(4)
    }
    ACCESS read-only
    STATUS mandatory
    DESCRIPTION
      "Status of digital Input 2
       (1) digital signal is true (contact closed if setup is NO)
       (2) digital signal is false(contact opened if setup is NO),
       note setup of input (NO/NC)
       (3) digital input is pending, note setup of delay"
    ::= { cmcTcMasterPcu2Status 2 }

  cmcTcMasterPcu2StatusPower1 OBJECT-TYPE
    SYNTAX INTEGER {
      ok(1),
      tooHigh(2),
      tooLow(3),
      warning(4),
      error(5),
      notAvail(6)
    }
    ACCESS read-only
    STATUS mandatory
    DESCRIPTION
      "Status Power 1, see setpoints"
    ::= { cmcTcMasterPcu2Status 3 }

  cmcTcMasterPcu2StatusPower2 OBJECT-TYPE
    SYNTAX INTEGER {
      ok(1),
      tooHigh(2),
      tooLow(3),
      warning(4),
      error(5),
      notAvail(6)
    }
    ACCESS read-only
    STATUS mandatory
    DESCRIPTION
      "Status Power 2, see setpoints"
    ::= { cmcTcMasterPcu2Status 4 }

  cmcTcMasterPcu2StatusTemperature OBJECT-TYPE
    SYNTAX INTEGER {
      ok(1),
      tooHigh(2),
      tooLow(3),
      warning(4),
      error(5)
    }
    ACCESS read-only
    STATUS mandatory
    DESCRIPTION
      "Status temperature 1, OK/ too high/ too low
       (see setpoints of temperature 1)"
    ::= { cmcTcMasterPcu2Status 5 }

--cmcTcMasterPcu2Status-table-group

  cmcTcMasterPcu2OutletsNumber OBJECT-TYPE
    SYNTAX INTEGER 
    ACCESS read-only
    STATUS mandatory
    DESCRIPTION
      "Number of value-table entries=number of outlets available on this unit"
    ::= { cmcTcMasterPcu2StatusTable1 1 }

  cmcTcMasterPcu2StatusTable OBJECT-TYPE
    SYNTAX SEQUENCE OF CmcTcMasterPcu2StatusEntry
    ACCESS not-accessible
    STATUS mandatory
    DESCRIPTION
      "Headline of status-table"
    ::= { cmcTcMasterPcu2StatusTable1 2 }

  cmcTcMasterPcu2StatusEntry OBJECT-TYPE
    SYNTAX CmcTcMasterPcu2StatusEntry
    ACCESS not-accessible
    STATUS mandatory
    DESCRIPTION
      "Entries of status-table"
    INDEX { cmcTcMasterPcu2StatusIndex }
    ::= { cmcTcMasterPcu2StatusTable 1 }

    CmcTcMasterPcu2StatusEntry ::=
      SEQUENCE {
        cmcTcMasterPcu2StatusIndex
          INTEGER,
        cmcTcMasterPcu2StatusText
          DisplayString (SIZE (0..31)),                
        cmcTcMasterPcu2StatusStatus
          INTEGER,
        cmcTcMasterPcu2ControlSNMP
          INTEGER,
        cmcTcMasterPcu2FrontSwitch
          INTEGER,
        cmcTcMasterPcu2Delay
          INTEGER,
        cmcTcMasterPcu2Input1
          INTEGER,
        cmcTcMasterPcu2Input2
          INTEGER,
        cmcTcMasterPcu2Temperature
          INTEGER,          
        cmcTcMasterPcu2Power
          INTEGER,          
        cmcTcMasterPcu2RestoreOutputStatus
          INTEGER           
      }

    cmcTcMasterPcu2StatusIndex OBJECT-TYPE
      SYNTAX INTEGER (1..32000)
      ACCESS read-only
      STATUS mandatory
      DESCRIPTION
        "Index for the list of value entries. Its value ranges
         between 1 and the value of cmcTcMasterPcu2OutletsNumber."
      ::= { cmcTcMasterPcu2StatusEntry 1 }

    cmcTcMasterPcu2StatusText OBJECT-TYPE
      SYNTAX DisplayString (SIZE (0..31))
      ACCESS read-write
      STATUS mandatory
      DESCRIPTION
        "Descriptional text for each outlet (entry in the table)"
      ::= { cmcTcMasterPcu2StatusEntry 2 }
              
    cmcTcMasterPcu2StatusStatus OBJECT-TYPE
      SYNTAX INTEGER {
        ok(1),
        onFrontKey(2),
        offFrontKey(3),
        onWEB(4),
        offWEB(5),
        onInput1(6),
        offInput1(7),
        onInput2(8),
        offInput2(9),
        onTemp(10),
        offTemp(11),
        onSNMP(12),
        offSNMP(13),
        onTimer(14),
        offTimer(15),
        onDelay(16),
        onConsole(17),
        offConsole(18),
        onReboot(19), 
        offReboot(20),
        onPower(21),
        offPower(22)
      }
      ACCESS read-only
      STATUS mandatory
      DESCRIPTION
        "Actual status of the outlet"
      ::= { cmcTcMasterPcu2StatusEntry 3 }

    cmcTcMasterPcu2ControlSNMP OBJECT-TYPE
      SYNTAX INTEGER  {
        on(1),
        off(2)
      }
      ACCESS read-write
      STATUS mandatory
      DESCRIPTION
        "Control via SNMP"
      ::= { cmcTcMasterPcu2StatusEntry 4 }

    cmcTcMasterPcu2FrontSwitch OBJECT-TYPE
      SYNTAX INTEGER {
        disabled(1),
        enabled(2)
      }
      ACCESS read-write
      STATUS mandatory
      DESCRIPTION
        "Control via front switch"
      ::= { cmcTcMasterPcu2StatusEntry 5 }
 
    cmcTcMasterPcu2Delay OBJECT-TYPE
      SYNTAX INTEGER (0..300)
      ACCESS read-write
      STATUS mandatory
      DESCRIPTION
        "Value for delay time in seconds.
         Value>0: Output is switched off for this time (in sec)"
      ::= { cmcTcMasterPcu2StatusEntry 6 }

    cmcTcMasterPcu2Input1 OBJECT-TYPE
      SYNTAX INTEGER {
        disabled(1),
        switchOn(2),
        switchOff(3),
        switchOnOff(4)
      }
      ACCESS read-write
      STATUS mandatory
      DESCRIPTION
        "Control via digital input 1
         (1): disabled
         (2): output is switched on in case of input 1 alarm
         (3): output is switched off in case of input 1 alarm
         (4): output has same status as input 1"
      ::= { cmcTcMasterPcu2StatusEntry 7 }

    cmcTcMasterPcu2Input2 OBJECT-TYPE
      SYNTAX INTEGER {
        disabled(1),
        switchOn(2),
        switchOff(3),
        switchOnOff(4)
      }
      ACCESS read-write
      STATUS mandatory
      DESCRIPTION
        "Control via digital input 2
         (1): disabled
         (2): output is switched on in case of input 2 alarm
         (3): output is switched off in case of input 2 alarm
         (4): output has same status as input 2"             
      ::= { cmcTcMasterPcu2StatusEntry 8 }

    cmcTcMasterPcu2Temperature OBJECT-TYPE
      SYNTAX INTEGER {
        disabled(1),
        switchOffAlarm(2),
        switchOnAlarm(3),
        switchOffSetpoint(4),
        switchOnSetpoint(5)
      }
      ACCESS read-write
      STATUS mandatory
      DESCRIPTION
        "Control via temperature alarm or setpoint
         (1): disabled
         (2): output is switched off in case of temperature alarm
         (3): output is switched on in case of temperature alarm
         (4): output is switched off if temperature setpoint (cmcTcMasterPcu2SetpointTemperature)
              is reached
         (5): output is switched on if temperature setpoint (cmcTcMasterPcu2SetpointTemperature)
              is reached"
      ::= { cmcTcMasterPcu2StatusEntry 9 }   
    
    cmcTcMasterPcu2Power OBJECT-TYPE
      SYNTAX INTEGER {
        disabled(1),
        switchOffAlarm(2),
        switchOffWarning(3),
        switchOnAlarm(4),
        switchOnWarning(5)
      }
      ACCESS read-write
      STATUS mandatory
      DESCRIPTION
        "Control via power setpoint
         (1): disabled
         (2): output is switched off upon power high alarm (cmcTcMasterPcu2SetpointHighPower1)
         (3): output is switched off upon power warning (cmcTcMasterPcu2SetpointWarningPower1)
         (4): output is switched on upon power alarm (cmcTcMasterPcu2SetpointHigh(Low)Power1)
         (5): output is switched on upon power warning (cmcTcMasterPcu2SetpointWarningPower1)             "
      ::= { cmcTcMasterPcu2StatusEntry 10 }                

    cmcTcMasterPcu2RestoreOutputStatus OBJECT-TYPE
      SYNTAX INTEGER {
        disabled(1),
        enabled(2)
      }
      ACCESS read-write
      STATUS mandatory
      DESCRIPTION
        "Save last output status and switch output to this status after reboot"
      ::= { cmcTcMasterPcu2StatusEntry 11 }
                
--cmcTcMasterPcu2SetupGeneral-group

  cmcTcMasterPcu2SetTempUnit OBJECT-TYPE
    SYNTAX INTEGER {
      celsius(1),
      fahrenheit(2)
    }
    ACCESS read-write
    STATUS mandatory
    DESCRIPTION
      "Unit of all temperature values and setpoints, Celsius or Fahrenheit"
    ::= { cmcTcMasterPcu2SetupGeneral 1 }

  cmcTcMasterPcu2SetBeeper OBJECT-TYPE
    SYNTAX INTEGER {
      off(1),
      on(2),
      enableClear(3)
    }
    ACCESS read-write
    STATUS mandatory
    DESCRIPTION
      "Audible alarm in PCU unit:
       (1): beeper is off (general)
       (2): beeper is on (Alarm)
       (3): enable Clear (cmcTcMasterPcu2ClearAlarm)"
    ::= { cmcTcMasterPcu2SetupGeneral 2 }

  cmcTcMasterPcu2LogicRelay OBJECT-TYPE
    SYNTAX INTEGER {
      closeAtAlarm(1),
      openAtAlarm(2),
      off(3),
      enableRemote(4)
    }
    ACCESS read-write
    STATUS mandatory
    DESCRIPTION
      "Logic of alarm relay: 
       (1): Relay will pick up in case of an alarm
       (2): Relay will release in case of an alarm
       (3): Relay off (general)
       (4): enable remote relay control (SNMP set)"
    ::= { cmcTcMasterPcu2SetupGeneral 3 }
 
  cmcTcMasterPcu2ClearRelay OBJECT-TYPE
    SYNTAX INTEGER {
      disabled(1),
      enabled(2)
    }
    ACCESS read-write
    STATUS mandatory
    DESCRIPTION
      "Enable clear of alarm relay: 
       (1): Relay cannot be cleared by cmcTcMasterPcu2ClearAlarm
       (2): Relay can be cleared by cmcTcMasterPcu2ClearAlarm"
    ::= { cmcTcMasterPcu2SetupGeneral 4 }                  

  cmcTcMasterPcu2WebAccess OBJECT-TYPE
    SYNTAX INTEGER {
      viewOnly(1),
      fullAccess(2),
      off(3)
    }
    ACCESS read-write
    STATUS mandatory
    DESCRIPTION
      "Web access via HTTP: 
       (1): view only
       (2): full Access, read and set
       (3): Web disabled (general)"
    ::= { cmcTcMasterPcu2SetupGeneral 5 }
 
  cmcTcMasterPcu2SetupDate OBJECT-TYPE
    SYNTAX DisplayString (SIZE (0..10))
    ACCESS read-write
    STATUS mandatory
    DESCRIPTION
      "actual Date in format DD.MM.YYYY"
    ::= { cmcTcMasterPcu2SetupGeneral 6 }

  cmcTcMasterPcu2SetupTime OBJECT-TYPE
    SYNTAX DisplayString (SIZE (0..8))
    ACCESS read-write
    STATUS mandatory
    DESCRIPTION
      "actual Time in format HH:MM:SS, HH (0-23), MM (0-59), SS (0-59)"
    ::= { cmcTcMasterPcu2SetupGeneral 7 }

--cmcTcMasterPcu2TimerTable1-group
 
  cmcTcMasterPcu2TimerNumber OBJECT-TYPE
    SYNTAX INTEGER 
    ACCESS read-only
    STATUS mandatory
    DESCRIPTION
      "Number of timers available on this unit"
    ::= { cmcTcMasterPcu2TimerTable1 1 }

  cmcTcMasterPcu2TimerTable OBJECT-TYPE
    SYNTAX SEQUENCE OF CmcTcMasterPcu2TimerEntry
    ACCESS not-accessible
    STATUS mandatory
    DESCRIPTION
      "Headline of timer-table"
    ::= { cmcTcMasterPcu2TimerTable1 2 }

  cmcTcMasterPcu2TimerEntry OBJECT-TYPE
    SYNTAX CmcTcMasterPcu2TimerEntry
    ACCESS not-accessible
    STATUS mandatory
    DESCRIPTION
      "Entries of timer-table"
    INDEX { cmcTcMasterPcu2TimerIndex }
    ::= { cmcTcMasterPcu2TimerTable 1 }

    CmcTcMasterPcu2TimerEntry ::=
      SEQUENCE {
        cmcTcMasterPcu2TimerIndex
          INTEGER,
        cmcTcMasterPcu2TimerStatus
          INTEGER,
        cmcTcMasterPcu2TimerDayOfWeek
          INTEGER,  
        cmcTcMasterPcu2TimeOn 
          DisplayString (SIZE (0..5)),                              
        cmcTcMasterPcu2TimeOff 
          DisplayString (SIZE (0..5)),                              
        cmcTcMasterPcu2TimeControl
          INTEGER,
        cmcTcMasterPcu2TimerOutput1
          INTEGER,
        cmcTcMasterPcu2TimerOutput2
          INTEGER         
      }

    cmcTcMasterPcu2TimerIndex OBJECT-TYPE
      SYNTAX INTEGER (1..32000)
      ACCESS read-only
      STATUS mandatory
      DESCRIPTION
        "Index for the list of timer entries. Its value ranges
         between 1 and the value of cmcTcMasterPcu2TimerNumber." 
      ::= { cmcTcMasterPcu2TimerEntry 1 }

    cmcTcMasterPcu2TimerStatus OBJECT-TYPE
      SYNTAX INTEGER {
        switchedOff(1),
        switchedOn(2),
        noTime(3) 
      }
      ACCESS read-only
      STATUS mandatory
      DESCRIPTION
        "Actual status of the timer"
      ::= { cmcTcMasterPcu2TimerEntry 2 }

    cmcTcMasterPcu2TimerDayOfWeek OBJECT-TYPE
      SYNTAX INTEGER {
        sun(1),
        mon(2),
        tue(3) ,
        wed(4),
        thu(5),
        fre(6),
        sat(7),
        sat-sun(8),
        mo-fr(9),
        mo-su(10)
      }
      ACCESS read-write
      STATUS mandatory
      DESCRIPTION
        "Day when the timer is active"
      ::= { cmcTcMasterPcu2TimerEntry 3 }
             
    cmcTcMasterPcu2TimeOn OBJECT-TYPE
      SYNTAX DisplayString (SIZE (0..5))
      ACCESS read-write
      STATUS mandatory
      DESCRIPTION
        "Time to switch on current outlet, 
         Format: HH:MM"
      ::= { cmcTcMasterPcu2TimerEntry 4 }

    cmcTcMasterPcu2TimeOff OBJECT-TYPE
      SYNTAX DisplayString (SIZE (0..5))
      ACCESS read-write
      STATUS mandatory
      DESCRIPTION
        "Time to switch off current outlet,
         Format: HH:MM"
      ::= { cmcTcMasterPcu2TimerEntry 5 }

    cmcTcMasterPcu2TimeControl OBJECT-TYPE
      SYNTAX INTEGER {
        disabled(1),
        enabled(2)
      }
      ACCESS read-write
      STATUS mandatory
      DESCRIPTION
        "Control via RTC"
      ::= { cmcTcMasterPcu2TimerEntry 6 }

    cmcTcMasterPcu2TimerOutput1 OBJECT-TYPE
      SYNTAX INTEGER 
      ACCESS read-write
      STATUS mandatory
      DESCRIPTION
        "Output which is controlled via timer"
      ::= { cmcTcMasterPcu2TimerEntry 7 }

    cmcTcMasterPcu2TimerOutput2 OBJECT-TYPE
      SYNTAX INTEGER 
      ACCESS read-write
      STATUS mandatory
      DESCRIPTION
        "Output which is controlled via timer"
      ::= { cmcTcMasterPcu2TimerEntry 8 }

--cmcTcMasterPcu2SetupPower1-group                     

  cmcTcMasterPcu2SetupPower1Avail OBJECT-TYPE
    SYNTAX INTEGER {
      notAvailable(1),
      available(2)
    }
    ACCESS read-write
    STATUS mandatory
    DESCRIPTION
      "Energy sensor 1 sensor:   
       (1) not available
       (2) available"
    ::= { cmcTcMasterPcu2SetupPower1 1 }

  cmcTcMasterPcu2SetupPower1Relay OBJECT-TYPE
    SYNTAX INTEGER {
      disabled(1),
      enabled(2)
    }
    ACCESS read-write
    STATUS mandatory
    DESCRIPTION
      "Alert handling of Alarm Relay in case of an alarm condition
       of Power 1:  
       (1) no switching of Relays
       (2) Relay will switch"
    ::= { cmcTcMasterPcu2SetupPower1 2 }

  cmcTcMasterPcu2SetupPower1Beeper OBJECT-TYPE
    SYNTAX INTEGER {
      disabled(1),
      enabled(2)
    }
    ACCESS read-write
    STATUS mandatory
    DESCRIPTION
      "Alert handling of beeper of in case of an alarm condition
       of Power 1: 
       (1) No Audible Alarm
       (2) Start Audible Alarm"
    ::= { cmcTcMasterPcu2SetupPower1 3 }

--cmcTcMasterPcu2SetupPower2-group                     

  cmcTcMasterPcu2SetupPower2Avail OBJECT-TYPE
    SYNTAX INTEGER {
      notAvailable(1),
      available(2)
    }
    ACCESS read-write
    STATUS mandatory
    DESCRIPTION
      "Energy sensor 2:   
       (1) not available
       (2) available"
    ::= { cmcTcMasterPcu2SetupPower2 1 }

  cmcTcMasterPcu2SetupPower2Relay OBJECT-TYPE
    SYNTAX INTEGER {
      disabled(1),
      enabled(2)
    }
    ACCESS read-write
    STATUS mandatory
    DESCRIPTION
      "Alert handling of Alarm Relay in case of an alarm condition
       of Power 2:  
       (1) no switching of Relay
       (2) Relay will switch"
    ::= { cmcTcMasterPcu2SetupPower2 2 }

  cmcTcMasterPcu2SetupPower2Beeper OBJECT-TYPE
    SYNTAX INTEGER {
      disabled(1),
      enabled(2)
    }
    ACCESS read-write
    STATUS mandatory
    DESCRIPTION
      "Alert handling of beeper of in case of an alarm condition
       of Power 2: 
       (1) No Audible Alarm
       (2) Start Audible Alarm"
    ::= { cmcTcMasterPcu2SetupPower2 3 }

--cmcTcMasterPcu2SetupInput1-group

  cmcTcMasterPcu2SetupInput1Avail OBJECT-TYPE
    SYNTAX INTEGER {
      notAvailable(1),
      available(2)
    }
    ACCESS read-write
    STATUS mandatory
    DESCRIPTION
      "Input 1 sensor:   
       (1) not available
       (2) available"
    ::= { cmcTcMasterPcu2SetupInput1 1 }

  cmcTcMasterPcu2SetupInput1Relay OBJECT-TYPE
    SYNTAX INTEGER {
      disabled(1),
      enabled(2)
    }
    ACCESS read-write
    STATUS mandatory
    DESCRIPTION
      "Alert handling of Alarm Relay in case of an alarm condition
       of Input 1:  
       (1) no switching of Relay
       (2) Relay will switch"
    ::= { cmcTcMasterPcu2SetupInput1 2 }

  cmcTcMasterPcu2SetupInput1Beeper OBJECT-TYPE
    SYNTAX INTEGER {
      disabled(1),
      enabled(2)
    }
    ACCESS read-write
    STATUS mandatory
    DESCRIPTION
      "Alert handling of beeper of in case of an alarm condition
       of Input 1: 
       (1) No Audible Alarm
       (2) Start Audible Alarm"
    ::= { cmcTcMasterPcu2SetupInput1 3 }

  cmcTcMasterPcu2SetupInput1Contact OBJECT-TYPE
    SYNTAX INTEGER {
      contactNO(1),
      contactNC(2),
      notAvail(3)
    }
    ACCESS read-write
    STATUS mandatory
    DESCRIPTION
      "Setup of digital input 1"
    ::= { cmcTcMasterPcu2SetupInput1 4 }

  cmcTcMasterPcu2SetupInput1Delay OBJECT-TYPE
    SYNTAX INTEGER (0..60)
    ACCESS read-write
    STATUS mandatory
    DESCRIPTION
      "Delay for changing of input state"
    ::= { cmcTcMasterPcu2SetupInput1 5 }

--cmcTcMasterPcu2SetupInput2-group

  cmcTcMasterPcu2SetupInput2Avail OBJECT-TYPE
    SYNTAX INTEGER {
      notAvailable(1),
      available(2)
    }
    ACCESS read-write
    STATUS mandatory
    DESCRIPTION
      "Input 2 sensor:   
       (2) available
       (1) not available"
    ::= { cmcTcMasterPcu2SetupInput2 1 }

  cmcTcMasterPcu2SetupInput2Relay OBJECT-TYPE
    SYNTAX INTEGER {
      disabled(1),
      enabled(2)
    }
    ACCESS read-write
    STATUS mandatory
    DESCRIPTION
      "Alert handling of Alarm Relay in case of an alarm condition
       of Input 1:  
       (1) no switching of Relays
       (2) Relay will switch"
    ::= { cmcTcMasterPcu2SetupInput2 2 }

  cmcTcMasterPcu2SetupInput2Beeper OBJECT-TYPE
    SYNTAX INTEGER {
      disabled(1),
      enabled(2)
    }
    ACCESS read-write
    STATUS mandatory
    DESCRIPTION
      "Alert handling of beeper of in case of an alarm condition
       of Input 2: 
       (1) No Audible Alarm
       (2) Start Audible Alarm"
    ::= { cmcTcMasterPcu2SetupInput2 3 }

  cmcTcMasterPcu2SetupInput2Contact OBJECT-TYPE
    SYNTAX INTEGER {
      contactNO(1),
      contactNC(2),
      notAvail(3)
    }
    ACCESS read-write
    STATUS mandatory
    DESCRIPTION
      "Setup of digital input 2"
    ::= { cmcTcMasterPcu2SetupInput2 4 }

  cmcTcMasterPcu2SetupInput2Delay OBJECT-TYPE
    SYNTAX INTEGER (0..60)
    ACCESS read-write
    STATUS mandatory
    DESCRIPTION
      "Delay for changing of input state"
    ::= { cmcTcMasterPcu2SetupInput2 5 }

--cmcTcMasterPcu2SetupTemperature-group                     

  cmcTcMasterPcu2SetupTemperatureAvail OBJECT-TYPE
    SYNTAX INTEGER {
      notAvailable(1),
      available(2)
    }
    ACCESS read-write
    STATUS mandatory
    DESCRIPTION
      "Temp sensor 1:   
       (1) not available
       (2) available"
    ::= { cmcTcMasterPcu2SetupTemperature 1 }

  cmcTcMasterPcu2SetupTemperatureRelay OBJECT-TYPE
    SYNTAX INTEGER {
      disabled(1),
      enabled(2)
    }
    ACCESS read-write
    STATUS mandatory
    DESCRIPTION
      "Alert handling of Alarm Relay in case of an alarm condition
       of Temperature:  
       (1) no switching of Relays
       (2) Relay will switch"
    ::= { cmcTcMasterPcu2SetupTemperature 2 }

  cmcTcMasterPcu2SetupTemperatureBeeper OBJECT-TYPE
    SYNTAX INTEGER {
      disabled(1),
      enabled(2)
    }
    ACCESS read-write
    STATUS mandatory
    DESCRIPTION
      "Alert handling of beeper of in case of an alarm condition
       of Temperature: 
       (1) No Audible Alarm
       (2) Start Audible Alarm"
    ::= { cmcTcMasterPcu2SetupTemperature 3 }

--cmcTcMasterPcu2SetupGeneral-group

  cmcTcMasterPcu2SetMessage OBJECT-TYPE
    SYNTAX DisplayString (SIZE (0..31))
    ACCESS read-write
    STATUS mandatory
    DESCRIPTION
      "Set message"
    ::= { cmcTcMasterPcu2SetupDevice 1 }

--cmcTcMasterPcu2Setpoints-group

  cmcTcMasterPcu2SetpointHighPower1 OBJECT-TYPE
    SYNTAX INTEGER 
    ACCESS read-write
    STATUS mandatory
    DESCRIPTION
      "Setpoint high value power consumption 1 alarm"
    ::= { cmcTcMasterPcu2Setpoints 1 }

  cmcTcMasterPcu2SetpointWarningPower1 OBJECT-TYPE
    SYNTAX INTEGER 
    ACCESS read-write
    STATUS mandatory
    DESCRIPTION
      "Setpoint warning value power consumption 1 alarm"
    ::= { cmcTcMasterPcu2Setpoints 2 }

  cmcTcMasterPcu2SetpointLowPower1 OBJECT-TYPE
    SYNTAX INTEGER
    ACCESS read-write
    STATUS mandatory
    DESCRIPTION
      "Setpoint low value power consumption 1 alarm"
    ::= { cmcTcMasterPcu2Setpoints 3 }

  cmcTcMasterPcu2SetpointHighPower2 OBJECT-TYPE
    SYNTAX INTEGER 
    ACCESS read-write
    STATUS mandatory
    DESCRIPTION
      "Setpoint high value power consumption 2 alarm"
    ::= { cmcTcMasterPcu2Setpoints 4 }

  cmcTcMasterPcu2SetpointWarningPower2 OBJECT-TYPE
    SYNTAX INTEGER 
    ACCESS read-write
    STATUS mandatory
    DESCRIPTION
      "Setpoint warning value power consumption 2 alarm"
    ::= { cmcTcMasterPcu2Setpoints 5 }

  cmcTcMasterPcu2SetpointLowPower2 OBJECT-TYPE
    SYNTAX INTEGER
    ACCESS read-write
    STATUS mandatory
    DESCRIPTION
      "Setpoint low value power consumption 2 alarm"
    ::= { cmcTcMasterPcu2Setpoints 6 }

  cmcTcMasterPcu2SetpointHighTemperature OBJECT-TYPE
    SYNTAX INTEGER (0..200)
    ACCESS read-write
    STATUS mandatory
    DESCRIPTION
      "Setpoint high value alarm temperature "
    ::= { cmcTcMasterPcu2Setpoints 7 }

  cmcTcMasterPcu2SetpointLowTemperature OBJECT-TYPE
    SYNTAX INTEGER (0..50)
    ACCESS read-write
    STATUS mandatory
    DESCRIPTION
      "Setpoint low value alarm temperature "
    ::= { cmcTcMasterPcu2Setpoints 8 }
 
  cmcTcMasterPcu2SetpointTemperature OBJECT-TYPE
    SYNTAX INTEGER (0..200)
    ACCESS read-write
    STATUS mandatory
    DESCRIPTION
      "Setpoint temperature for outlet control 
       and temperature warning"
    ::= { cmcTcMasterPcu2Setpoints 9 }

  cmcTcMasterPcu2SetpointTemperatureHyst OBJECT-TYPE
    SYNTAX INTEGER (0..15)
    ACCESS read-write
    STATUS mandatory
    DESCRIPTION
      "Hysteresis for cmcTcMasterPcu2SetpointTemperature"
    ::= { cmcTcMasterPcu2Setpoints 10 }
 
--cmcTcMasterPcu2Control-group

  cmcTcMasterPcu2ResetEnergy1 OBJECT-TYPE
    SYNTAX INTEGER {
      noReset(1),
      reset(2)
    }
    ACCESS read-write
    STATUS mandatory
    DESCRIPTION
      "Reset value of cmcTcMasterPcu2ValueEnergy1Time"
    ::= { cmcTcMasterPcu2Control 1 }

  cmcTcMasterPcu2ResetEnergy2 OBJECT-TYPE
    SYNTAX INTEGER {
      noReset(1),
      reset(2)
    }
    ACCESS read-write
    STATUS mandatory
    DESCRIPTION
      "Reset value of cmcTcMasterPcu2ValueEnergy2Time"
    ::= { cmcTcMasterPcu2Control 2 }

  cmcTcMasterPcu2ControlAlarmRelay OBJECT-TYPE
    SYNTAX INTEGER {
      relayOff(1),
      relayOn(2)
    }
    ACCESS read-write
    STATUS mandatory
    DESCRIPTION
      "Control of Alarm relay"
    ::= { cmcTcMasterPcu2Control 3 }

  cmcTcMasterPcu2ClearAlarm OBJECT-TYPE
    SYNTAX INTEGER {
      noClear(1),
      clear(2)
    }
    ACCESS read-write
    STATUS mandatory
    DESCRIPTION
      "Clear alarm, beeper and relay"
    ::= { cmcTcMasterPcu2Control 4 }

--cmcTcMasterPcu2TrapTable-group

  cmcTcMasterPcu2TrapTableNumber OBJECT-TYPE
    SYNTAX INTEGER 
    ACCESS read-only
    STATUS mandatory
    DESCRIPTION
      "Number of cmcTcMasterPcu2TrapTable entries. The number of trap-receivers avail."
    ::= { cmcTcMasterPcu2Traps 1 }

  cmcTcMasterPcu2TrapTable OBJECT-TYPE
    SYNTAX SEQUENCE OF CmcTcMasterPcu2TrapEntry
    ACCESS not-accessible
    STATUS mandatory
    DESCRIPTION
      "A list of trap-receiver entries"
    ::= { cmcTcMasterPcu2Traps 2 }

  cmcTcMasterPcu2TrapEntry OBJECT-TYPE
    SYNTAX CmcTcMasterPcu2TrapEntry
    ACCESS not-accessible
    STATUS mandatory
    DESCRIPTION
      "Entries of cmcTcMasterPcu2TrapTable"
    INDEX { cmcTcMasterPcu2TrapIndex }
    ::= { cmcTcMasterPcu2TrapTable 1 }

    CmcTcMasterPcu2TrapEntry ::=
      SEQUENCE {
        cmcTcMasterPcu2TrapIndex
          INTEGER,
        cmcTcMasterPcu2TrapStatus
          INTEGER,
        cmcTcMasterPcu2TrapIPaddress
          DisplayString
      }

    cmcTcMasterPcu2TrapIndex OBJECT-TYPE
      SYNTAX INTEGER (1..32000)
      ACCESS read-only
      STATUS mandatory
      DESCRIPTION
        "Index for the trap-receiver-table. Its value ranges between
         1 and the value of cmcTcMasterPcu2TrapTableNumber "
      ::= { cmcTcMasterPcu2TrapEntry 1 }

    cmcTcMasterPcu2TrapStatus OBJECT-TYPE
      SYNTAX INTEGER {
        disabled(1),
        enabled(2)
      }
      ACCESS read-write
      STATUS mandatory
      DESCRIPTION
        "Enable or disable trap receiver"
      ::= { cmcTcMasterPcu2TrapEntry 2 }

    cmcTcMasterPcu2TrapIPaddress OBJECT-TYPE
      SYNTAX DisplayString (SIZE (0..15))
      ACCESS read-write
      STATUS mandatory
      DESCRIPTION
        "IP-address of trap-receiver"
      ::= { cmcTcMasterPcu2TrapEntry 3 }

--cmcTcMasterTc2MibRev-group
          
  cmcTcMasterTc2MibMajRev OBJECT-TYPE
    SYNTAX INTEGER (1..32000)
    ACCESS read-only
    STATUS mandatory
    DESCRIPTION
      "The Major Revision level.
       A change in the major revision level represents a major change
       in the architecture of the MIB. A change in the major revision 
       level may indicate a significant change in the information,
       correct interpretation of data may require a MIB document
       with the same major revision level."
    ::= { cmcTcMasterTc2MibRev 1 }

  cmcTcMasterTc2MibMinRev OBJECT-TYPE
    SYNTAX INTEGER (0..32000)
    ACCESS read-only
    STATUS mandatory
    DESCRIPTION
      "The Minor Revision level.
       A change in the minor revision level may represent some minor
       additional support, no changes to any pre-existing information
       has occurred."
    ::= { cmcTcMasterTc2MibRev 2 }

  cmcTcMasterTc2MibCondition OBJECT-TYPE
    SYNTAX INTEGER {
      other (1),
      ok (2),
      degraded (3),
      failed (4),
      configChanged (5)
    }
    ACCESS read-only
    STATUS mandatory
    DESCRIPTION
      "The overall condition (status) of the system represented by
       this MIB. 
       (2) OK
       (3) a minor problem, warning condition (yellow LED on CMC-TC)
       (4) a major problem (red LED on CMC-TC)
       (5) configuration of sensor units changed or
           unit detected (red/yellow/green LED on CMC-TC)"
    ::= { cmcTcMasterTc2MibRev 3 }
          
--cmcTcMasterTc2Status-group

  cmcTcMasterTc2StatusDeviceCMC OBJECT-TYPE
    SYNTAX INTEGER {
      failed(1),
      ok(2)
    }
    ACCESS read-only
    STATUS mandatory
    DESCRIPTION
      "General Status of CMC-TC unit itself
       (1) failed
       (2) OK"
    ::= { cmcTcMasterTc2Status 1 }

  cmcTcMasterTc2UnitsConnected OBJECT-TYPE
    SYNTAX INTEGER 
    ACCESS read-only
    STATUS mandatory
    DESCRIPTION
      "Number of sensor units connected to the CMC-TC, Port 1 to 4"
    ::= { cmcTcMasterTc2Status 2 }

--unit 1

  cmcTcMasterTc2Unit1TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 1"
    ::= { cmcTcMasterTc2StatusSensorUnit1 1 }

  cmcTcMasterTc2Unit1Text OBJECT-TYPE
    SYNTAX DisplayString (SIZE (0..10))
    ACCESS read-write
    STATUS mandatory
    DESCRIPTION
      "Descriptional text for sensor unit connected to port 1"
    ::= { cmcTcMasterTc2StatusSensorUnit1 2 }

  cmcTcMasterTc2Unit1Serial OBJECT-TYPE
    SYNTAX INTEGER 
    ACCESS read-only
    STATUS mandatory
    DESCRIPTION
      "Serialnumber of sensor unit connected to port 1"
    ::= { cmcTcMasterTc2StatusSensorUnit1 3 }

  cmcTcMasterTc2Unit1Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 1
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc2StatusSensorUnit1 4 }

-- Sensors
              
  cmcTcMasterTc2Unit1NumberOfSensors OBJECT-TYPE
    SYNTAX INTEGER 
    ACCESS read-only
    STATUS mandatory
    DESCRIPTION
      "Number of sensors connected to sensor unit 1"
    ::= { cmcTcMasterTc2StatusUnit1Sensors 1 }

-- table with entry for each sensor available on this unit              

  cmcTcMasterTc2Unit1SensorTable OBJECT-TYPE
    SYNTAX SEQUENCE OF CmcTcMasterTc2Unit1SensorEntry
    ACCESS not-accessible
    STATUS mandatory
    DESCRIPTION
      "Headline of sensor table"
    ::= { cmcTcMasterTc2StatusUnit1Sensors 2 }

  cmcTcMasterTc2Unit1SensorEntry OBJECT-TYPE
    SYNTAX CmcTcMasterTc2Unit1SensorEntry
    ACCESS not-accessible
    STATUS mandatory
    DESCRIPTION
      "Entries of sensor table"
    INDEX { cmcTcMasterTc2Unit1SensorIndex }
    ::= { cmcTcMasterTc2Unit1SensorTable 1 }

    CmcTcMasterTc2Unit1SensorEntry ::=
      SEQUENCE {
        cmcTcMasterTc2Unit1SensorIndex
          INTEGER,
        cmcTcMasterTc2Unit1SensorType
          INTEGER,
        cmcTcMasterTc2Unit1SensorText
          DisplayString (SIZE (0..20)),                
        cmcTcMasterTc2Unit1SensorStatus
          INTEGER,
        cmcTcMasterTc2Unit1SensorValue
          INTEGER,
        cmcTcMasterTc2Unit1SensorSetHigh
          INTEGER,
        cmcTcMasterTc2Unit1SensorSetLow
          INTEGER,
        cmcTcMasterTc2Unit1SensorSetWarn
          INTEGER                
      }

    cmcTcMasterTc2Unit1SensorIndex OBJECT-TYPE
      SYNTAX INTEGER (1..32000)
      ACCESS read-only
      STATUS mandatory
      DESCRIPTION
        "Index for the list of value entries. Its value ranges
         between 1 and the value of cmcTcMasterTc2Unit1NumberOfSensors." 
      ::= { cmcTcMasterTc2Unit1SensorEntry 1 }

    cmcTcMasterTc2Unit1SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 1 to sensor[cmcTcMasterTc2Unit1SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc2Unit1SensorEntry 2 }

    cmcTcMasterTc2Unit1SensorText OBJECT-TYPE
      SYNTAX DisplayString (SIZE (0..20))
      ACCESS read-write
      STATUS mandatory
      DESCRIPTION
        "Descriptional text for each sensor (entry in the table)"
      ::= { cmcTcMasterTc2Unit1SensorEntry 3 }
              
    cmcTcMasterTc2Unit1SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc2Unit1SensorEntry 4 }

    cmcTcMasterTc2Unit1SensorValue OBJECT-TYPE
      SYNTAX INTEGER 
      ACCESS read-only
      STATUS mandatory
      DESCRIPTION
        "Value of sensor"
      ::= { cmcTcMasterTc2Unit1SensorEntry 5 }

    cmcTcMasterTc2Unit1SensorSetHigh OBJECT-TYPE
      SYNTAX INTEGER (0..300) 
      ACCESS read-write
      STATUS mandatory
      DESCRIPTION
        "Value for high setpoint of sensor"
      ::= { cmcTcMasterTc2Unit1SensorEntry 6 }

    cmcTcMasterTc2Unit1SensorSetLow OBJECT-TYPE
      SYNTAX INTEGER (0..300) 
      ACCESS read-write
      STATUS mandatory
      DESCRIPTION
        "Value for low setpoint of sensor,
         also used as alarm delay"
      ::= { cmcTcMasterTc2Unit1SensorEntry 7 }

    cmcTcMasterTc2Unit1SensorSetWarn OBJECT-TYPE
      SYNTAX INTEGER (0..300) 
      ACCESS read-write
      STATUS mandatory
      DESCRIPTION
        "Value for warning setpoint of sensor, 
         also used as fan threshold"
      ::= { cmcTcMasterTc2Unit1SensorEntry 8 }
                
-- Outputs              

  cmcTcMasterTc2Unit1NumberOfOutputs OBJECT-TYPE
    SYNTAX INTEGER 
    ACCESS read-only
    STATUS mandatory
    DESCRIPTION
      "Number of outputs available on sensor unit 1"
    ::= { cmcTcMasterTc2StatusUnit1Outputs 1 }

-- table with entry for each output available on this unit              
                
  cmcTcMasterTc2Unit1OutputTable OBJECT-TYPE
    SYNTAX SEQUENCE OF CmcTcMasterTc2Unit1OutputEntry
    ACCESS not-accessible
    STATUS mandatory
    DESCRIPTION
      "Headline of output table"
    ::= { cmcTcMasterTc2StatusUnit1Outputs 2 }

  cmcTcMasterTc2Unit1OutputEntry OBJECT-TYPE
    SYNTAX CmcTcMasterTc2Unit1OutputEntry
    ACCESS not-accessible
    STATUS mandatory
    DESCRIPTION
      "Entries of output table"
    INDEX { cmcTcMasterTc2Unit1OutputIndex }
    ::= { cmcTcMasterTc2Unit1OutputTable 1 }

    CmcTcMasterTc2Unit1OutputEntry ::=
      SEQUENCE {
        cmcTcMasterTc2Unit1OutputIndex
          INTEGER,
        cmcTcMasterTc2Unit1OutputType
          INTEGER,
        cmcTcMasterTc2Unit1OutputText
          DisplayString (SIZE (0..20)),                
        cmcTcMasterTc2Unit1OutputStatus
          INTEGER,
        cmcTcMasterTc2Unit1OutputValue
          INTEGER,
        cmcTcMasterTc2Unit1OutputSet
          INTEGER,
        cmcTcMasterTc2Unit1OutputConfig
          INTEGER,                
        cmcTcMasterTc2Unit1OutputDelay
          INTEGER,
        cmcTcMasterTc2Unit1OutputTimeoutAction
          INTEGER
      }

    cmcTcMasterTc2Unit1OutputIndex OBJECT-TYPE
      SYNTAX INTEGER (1..32000)
      ACCESS read-only
      STATUS mandatory
      DESCRIPTION
        "Index for the list of output entries. Its value ranges
         between 1 and the value of cmcTcMasterTc2Unit1NumberOfOutputs." 
      ::= { cmcTcMasterTc2Unit1OutputEntry 1 }

    cmcTcMasterTc2Unit1OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 1 to output[cmcTcMasterTc2Unit1OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc2Unit1OutputEntry 2 }

    cmcTcMasterTc2Unit1OutputText OBJECT-TYPE
      SYNTAX DisplayString (SIZE (0..20))
      ACCESS read-write
      STATUS mandatory
      DESCRIPTION
        "Descriptional text for each output (entry in the table)"
      ::= { cmcTcMasterTc2Unit1OutputEntry 3 }
              
    cmcTcMasterTc2Unit1OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc2Unit1OutputEntry 4 }

    cmcTcMasterTc2Unit1OutputValue OBJECT-TYPE
      SYNTAX INTEGER (-32000..32000) 
      ACCESS read-write
      STATUS mandatory
      DESCRIPTION
        "Value for output"
      ::= { cmcTcMasterTc2Unit1OutputEntry 5 }

    cmcTcMasterTc2Unit1OutputSet OBJECT-TYPE
      SYNTAX INTEGER {
        off (1),
        on (2),
        lock (3),
        unlock (4),
        unlockDelay (5)
      }
      ACCESS read-write
      STATUS mandatory
      DESCRIPTION
        "Command for output"
      ::= { cmcTcMasterTc2Unit1OutputEntry 6 }

    cmcTcMasterTc2Unit1OutputConfig OBJECT-TYPE
      SYNTAX INTEGER {
        disRemote (1),
        enRemote (2)
      }
      ACCESS read-write
      STATUS mandatory
      DESCRIPTION
        "Configuration for output
         1: 	disable remote control (e.g. keypad)
         2: 	enable remote control"
      ::= { cmcTcMasterTc2Unit1OutputEntry 7 }

    cmcTcMasterTc2Unit1OutputDelay OBJECT-TYPE
      SYNTAX INTEGER (0..999) 
      ACCESS read-write
      STATUS mandatory
      DESCRIPTION
        "Unsigned Value for delay, 
         after this time the output will fall into the previous state"
      ::= { cmcTcMasterTc2Unit1OutputEntry 8 }

    cmcTcMasterTc2Unit1OutputTimeoutAction OBJECT-TYPE
      SYNTAX INTEGER {
        stay (1),
        off (2),
        on (3)
      }
      ACCESS read-write
      STATUS mandatory
      DESCRIPTION
        "State for output if timeout (RS422) occurs"
      ::= { cmcTcMasterTc2Unit1OutputEntry 9 }
 
-- Messages
              
  cmcTcMasterTc2Unit1NumberOfMsgs OBJECT-TYPE
    SYNTAX INTEGER 
    ACCESS read-only
    STATUS mandatory
    DESCRIPTION
      "Number of messages that can be created with sensor unit 1"
    ::= { cmcTcMasterTc2StatusUnit1Msg 1 }

-- table with entry for each alarm available on this unit               
                
  cmcTcMasterTc2Unit1MsgTable OBJECT-TYPE
    SYNTAX SEQUENCE OF CmcTcMasterTc2Unit1MsgEntry
    ACCESS not-accessible
    STATUS mandatory
    DESCRIPTION
      "Headline of message table"
    ::= { cmcTcMasterTc2StatusUnit1Msg 2 }

  cmcTcMasterTc2Unit1MsgEntry OBJECT-TYPE
    SYNTAX CmcTcMasterTc2Unit1MsgEntry
    ACCESS not-accessible
    STATUS mandatory
    DESCRIPTION
      "Entries of message table"
    INDEX { cmcTcMasterTc2Unit1MsgIndex }
    ::= { cmcTcMasterTc2Unit1MsgTable 1 }

    CmcTcMasterTc2Unit1MsgEntry ::=
      SEQUENCE {
        cmcTcMasterTc2Unit1MsgIndex
          INTEGER, 
        cmcTcMasterTc2Unit1MsgText
          DisplayString (SIZE (0..20)),                
        cmcTcMasterTc2Unit1MsgStatus
          INTEGER,                
        cmcTcMasterTc2Unit1MsgRelay
          INTEGER,
        cmcTcMasterTc2Unit1MsgBeeper
          INTEGER,
        cmcTcMasterTc2Unit1MsgTrap1
          INTEGER,
        cmcTcMasterTc2Unit1MsgTrap2
          INTEGER,
        cmcTcMasterTc2Unit1MsgTrap3
          INTEGER,
        cmcTcMasterTc2Unit1MsgTrap4
          INTEGER,                 
        cmcTcMasterTc2Unit1MsgQuit
          INTEGER              
      }

    cmcTcMasterTc2Unit1MsgIndex OBJECT-TYPE
      SYNTAX INTEGER (1..32000)
      ACCESS read-only
      STATUS mandatory
      DESCRIPTION
        "Index for the list of message entries. Its value ranges
         between 1 and the value of cmcTcMasterTc2Unit1NumberOfMsgs." 
      ::= { cmcTcMasterTc2Unit1MsgEntry 1 }

    cmcTcMasterTc2Unit1MsgText OBJECT-TYPE
      SYNTAX DisplayString (SIZE (0..20))
      ACCESS read-write
      STATUS mandatory
      DESCRIPTION
        "Descriptional text for each message (entry in the table)"
      ::= { cmcTcMasterTc2Unit1MsgEntry 2 }
              
    cmcTcMasterTc2Unit1MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc2Unit1OutputSet)
         17: door is unlocked by WEB
         18: door is unlocked by timer
         19: no access, wrong keycode or cardnumber
         20: orientation of PSM-Unit is circuit 1
         21: orientation of PSM-Unit is circuit 2"
      ::= { cmcTcMasterTc2Unit1MsgEntry 3 }
        
    cmcTcMasterTc2Unit1MsgRelay OBJECT-TYPE
      SYNTAX INTEGER {
        disable (1),
        enable (2)
      }
      ACCESS read-write
      STATUS mandatory
      DESCRIPTION
        "Setup of Alarm relay for this message/alarm
         1:        no switching of alarm relay             
         2:        switching of alarm relay" 
      ::= { cmcTcMasterTc2Unit1MsgEntry 4 }

    cmcTcMasterTc2Unit1MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc2Unit1MsgEntry 5 }

    cmcTcMasterTc2Unit1MsgTrap1 OBJECT-TYPE
      SYNTAX INTEGER {
        disable (1),
        enable (2)
      }
      ACCESS read-write
      STATUS mandatory
      DESCRIPTION
        "Trap receiver 1 activated"
      ::= { cmcTcMasterTc2Unit1MsgEntry 6 }

    cmcTcMasterTc2Unit1MsgTrap2 OBJECT-TYPE
      SYNTAX INTEGER {
        disable (1),
        enable (2)
      }
      ACCESS read-write
      STATUS mandatory
      DESCRIPTION
        "Trap receiver 2 activated"
      ::= { cmcTcMasterTc2Unit1MsgEntry 7 }
 
    cmcTcMasterTc2Unit1MsgTrap3 OBJECT-TYPE
      SYNTAX INTEGER {
        disable (1),
        enable (2)
      }
      ACCESS read-write
      STATUS mandatory
      DESCRIPTION
        "Trap receiver 3 activated"
      ::= { cmcTcMasterTc2Unit1MsgEntry 8 }

    cmcTcMasterTc2Unit1MsgTrap4 OBJECT-TYPE
      SYNTAX INTEGER {
        disable (1),
        enable (2)
      }
      ACCESS read-write
      STATUS mandatory
      DESCRIPTION
        "Trap receiver 4 and Event Logging activated"
      ::= { cmcTcMasterTc2Unit1MsgEntry 9 }

    cmcTcMasterTc2Unit1MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc2Unit1MsgEntry 10 }

-- unit2

  cmcTcMasterTc2Unit2TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 2"
    ::= { cmcTcMasterTc2StatusSensorUnit2 1 }

  cmcTcMasterTc2Unit2Text OBJECT-TYPE
    SYNTAX DisplayString (SIZE (0..10))
    ACCESS read-write
    STATUS mandatory
    DESCRIPTION
      "Descriptional text for sensor unit connected to port 2"
    ::= { cmcTcMasterTc2StatusSensorUnit2 2 }

  cmcTcMasterTc2Unit2Serial OBJECT-TYPE
    SYNTAX INTEGER 
    ACCESS read-only
    STATUS mandatory
    DESCRIPTION
      "Serialnumber of sensor unit connected to port 2"
    ::= { cmcTcMasterTc2StatusSensorUnit2 3 }

  cmcTcMasterTc2Unit2Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 2
       (1) OK
       (2) error
       (3) configuration of sensor unit has changed, confirmation required
       (4) Quit from sensor unit to confirm configuration changes
       (5) timeout of sensor unit, confirmation required
       (6) sensor unit detected, needs to be confirmed
       (8) supply voltage is too low"              
    ::= { cmcTcMasterTc2StatusSensorUnit2 4 }

-- unit 2 table

-- Sensors              

  cmcTcMasterTc2Unit2NumberOfSensors OBJECT-TYPE
    SYNTAX INTEGER 
    ACCESS read-only
    STATUS mandatory
    DESCRIPTION
      "Number of sensors connected to sensor unit 2"
    ::= { cmcTcMasterTc2StatusUnit2Sensors 1 }

-- table with entry for each sensor available on this unit              

  cmcTcMasterTc2Unit2SensorTable OBJECT-TYPE
    SYNTAX SEQUENCE OF CmcTcMasterTc2Unit2SensorEntry
    ACCESS not-accessible
    STATUS mandatory
    DESCRIPTION
      "Headline of sensor table"
    ::= { cmcTcMasterTc2StatusUnit2Sensors 2 }

  cmcTcMasterTc2Unit2SensorEntry OBJECT-TYPE
    SYNTAX CmcTcMasterTc2Unit2SensorEntry
    ACCESS not-accessible
    STATUS mandatory
    DESCRIPTION
      "Entries of sensor table"
    INDEX { cmcTcMasterTc2Unit2SensorIndex }
    ::= { cmcTcMasterTc2Unit2SensorTable 1 }

    CmcTcMasterTc2Unit2SensorEntry ::=
      SEQUENCE {
        cmcTcMasterTc2Unit2SensorIndex
          INTEGER,
        cmcTcMasterTc2Unit2SensorType
          INTEGER,
        cmcTcMasterTc2Unit2SensorText
          DisplayString (SIZE (0..20)),                
        cmcTcMasterTc2Unit2SensorStatus
          INTEGER,
        cmcTcMasterTc2Unit2SensorValue
          INTEGER,
        cmcTcMasterTc2Unit2SensorSetHigh
          INTEGER,
        cmcTcMasterTc2Unit2SensorSetLow
          INTEGER,                 
        cmcTcMasterTc2Unit2SensorSetWarn
          INTEGER  
      }

    cmcTcMasterTc2Unit2SensorIndex OBJECT-TYPE
      SYNTAX INTEGER (1..32000)
      ACCESS read-only
      STATUS mandatory
      DESCRIPTION
        "Index for the list of value entries. Its value ranges
         between 1 and the value of cmcTcMasterTc2Unit2NumberOfSensors." 
      ::= { cmcTcMasterTc2Unit2SensorEntry 1 }

    cmcTcMasterTc2Unit2SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 2 to sensor[cmcTcMasterTc2Unit2SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc2Unit2SensorEntry 2 }
        
    cmcTcMasterTc2Unit2SensorText OBJECT-TYPE
      SYNTAX DisplayString (SIZE (0..20))
      ACCESS read-write
      STATUS mandatory
      DESCRIPTION
        "Descriptional text for each sensor (entry in the table)"
      ::= { cmcTcMasterTc2Unit2SensorEntry 3 }
              
    cmcTcMasterTc2Unit2SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc2Unit2SensorEntry 4 }

    cmcTcMasterTc2Unit2SensorValue OBJECT-TYPE
      SYNTAX INTEGER 
      ACCESS read-only
      STATUS mandatory
      DESCRIPTION
        "Value of sensor"
      ::= { cmcTcMasterTc2Unit2SensorEntry 5 }

    cmcTcMasterTc2Unit2SensorSetHigh OBJECT-TYPE
      SYNTAX INTEGER (0..300) 
      ACCESS read-write
      STATUS mandatory
      DESCRIPTION
        "Value for high setpoint of sensor"
      ::= { cmcTcMasterTc2Unit2SensorEntry 6 }

    cmcTcMasterTc2Unit2SensorSetLow OBJECT-TYPE
      SYNTAX INTEGER (0..300) 
      ACCESS read-write
      STATUS mandatory
      DESCRIPTION
        "Value for low setpoint of sensor,
         also used as alarm delay"
      ::= { cmcTcMasterTc2Unit2SensorEntry 7 }

    cmcTcMasterTc2Unit2SensorSetWarn OBJECT-TYPE
      SYNTAX INTEGER (0..300) 
      ACCESS read-write
      STATUS mandatory
      DESCRIPTION
        "Value for warning setpoint of sensor,
         also used as fan threshold"
      ::= { cmcTcMasterTc2Unit2SensorEntry 8 }

-- Outputs              

  cmcTcMasterTc2Unit2NumberOfOutputs OBJECT-TYPE
    SYNTAX INTEGER 
    ACCESS read-only
    STATUS mandatory
    DESCRIPTION
      "Number of outputs available on sensor unit 2"
    ::= { cmcTcMasterTc2StatusUnit2Outputs 1 }

-- table with entry for each output available on this unit              
                
  cmcTcMasterTc2Unit2OutputTable OBJECT-TYPE
    SYNTAX SEQUENCE OF CmcTcMasterTc2Unit2OutputEntry
    ACCESS not-accessible
    STATUS mandatory
    DESCRIPTION
      "Headline of output table"
    ::= { cmcTcMasterTc2StatusUnit2Outputs 2 }

  cmcTcMasterTc2Unit2OutputEntry OBJECT-TYPE
    SYNTAX CmcTcMasterTc2Unit2OutputEntry
    ACCESS not-accessible
    STATUS mandatory
    DESCRIPTION
      "Entries of output table"
    INDEX { cmcTcMasterTc2Unit2OutputIndex }
    ::= { cmcTcMasterTc2Unit2OutputTable 1 }

    CmcTcMasterTc2Unit2OutputEntry ::=
      SEQUENCE {
        cmcTcMasterTc2Unit2OutputIndex
          INTEGER,
        cmcTcMasterTc2Unit2OutputType
          INTEGER,
        cmcTcMasterTc2Unit2OutputText
          DisplayString (SIZE (0..20)),                
        cmcTcMasterTc2Unit2OutputStatus
          INTEGER,
        cmcTcMasterTc2Unit2OutputValue
          INTEGER,
        cmcTcMasterTc2Unit2OutputSet
          INTEGER,
        cmcTcMasterTc2Unit2OutputConfig
          INTEGER,                
        cmcTcMasterTc2Unit2OutputDelay
          INTEGER,
        cmcTcMasterTc2Unit2OutputTimeoutAction
          INTEGER
      }

    cmcTcMasterTc2Unit2OutputIndex OBJECT-TYPE
      SYNTAX INTEGER (1..32000)
      ACCESS read-only
      STATUS mandatory
      DESCRIPTION
        "Index for the list of output entries. Its value ranges
         between 1 and the value of cmcTcMasterTc2Unit2NumberOfOutputs." 
      ::= { cmcTcMasterTc2Unit2OutputEntry 1 }

    cmcTcMasterTc2Unit2OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 2 to output[cmcTcMasterTc2Unit2OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc2Unit2OutputEntry 2 }

        
    cmcTcMasterTc2Unit2OutputText OBJECT-TYPE
      SYNTAX DisplayString (SIZE (0..20))
      ACCESS read-write
      STATUS mandatory
      DESCRIPTION
        "Descriptional text for each output (entry in the table)"
      ::= { cmcTcMasterTc2Unit2OutputEntry 3 }
              
    cmcTcMasterTc2Unit2OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc2Unit2OutputEntry 4 }

    cmcTcMasterTc2Unit2OutputValue OBJECT-TYPE
      SYNTAX INTEGER (-32000..32000) 
      ACCESS read-write
      STATUS mandatory
      DESCRIPTION
        "Value for output"
      ::= { cmcTcMasterTc2Unit2OutputEntry 5 }

    cmcTcMasterTc2Unit2OutputSet OBJECT-TYPE
      SYNTAX INTEGER {
        off (1),
        on (2),
        lock (3),
        unlock (4),
        unlockDelay (5)
      }
      ACCESS read-write
      STATUS mandatory
      DESCRIPTION
        "Command for output"
      ::= { cmcTcMasterTc2Unit2OutputEntry 6 }

    cmcTcMasterTc2Unit2OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc2Unit2OutputEntry 7 }

    cmcTcMasterTc2Unit2OutputDelay OBJECT-TYPE
      SYNTAX INTEGER (0..999) 
      ACCESS read-write
      STATUS mandatory
      DESCRIPTION
        "Unsigned Value for delay, 
         after this time the output will fall into the previous state"
      ::= { cmcTcMasterTc2Unit2OutputEntry 8 }

    cmcTcMasterTc2Unit2OutputTimeoutAction OBJECT-TYPE
      SYNTAX INTEGER {
        stay (1),
        off (2),
        on (3)
      }
      ACCESS read-write
      STATUS mandatory
      DESCRIPTION
        "State for output if timeout (RS422) occurs"
      ::= { cmcTcMasterTc2Unit2OutputEntry 9 }

-- Messages
              
  cmcTcMasterTc2Unit2NumberOfMsgs OBJECT-TYPE
    SYNTAX INTEGER 
    ACCESS read-only
    STATUS mandatory
    DESCRIPTION
      "Number of messages that can be created with sensor unit 2"
    ::= { cmcTcMasterTc2StatusUnit2Msg 1 }

-- table with entry for each alarm available on this unit               
                
  cmcTcMasterTc2Unit2MsgTable OBJECT-TYPE
    SYNTAX SEQUENCE OF CmcTcMasterTc2Unit2MsgEntry
    ACCESS not-accessible
    STATUS mandatory
    DESCRIPTION
      "Headline of message table"
    ::= { cmcTcMasterTc2StatusUnit2Msg 2 }

  cmcTcMasterTc2Unit2MsgEntry OBJECT-TYPE
    SYNTAX CmcTcMasterTc2Unit2MsgEntry
    ACCESS not-accessible
    STATUS mandatory
    DESCRIPTION
      "Entries of message table"
    INDEX { cmcTcMasterTc2Unit2MsgIndex }
    ::= { cmcTcMasterTc2Unit2MsgTable 1 }

    CmcTcMasterTc2Unit2MsgEntry ::=
      SEQUENCE {
        cmcTcMasterTc2Unit2MsgIndex
          INTEGER,
        cmcTcMasterTc2Unit2MsgText
          DisplayString (SIZE (0..20)),
        cmcTcMasterTc2Unit2MsgStatus
          INTEGER, 
        cmcTcMasterTc2Unit2MsgRelay
          INTEGER,
        cmcTcMasterTc2Unit2MsgBeeper
          INTEGER,
        cmcTcMasterTc2Unit2MsgTrap1
          INTEGER,
        cmcTcMasterTc2Unit2MsgTrap2
          INTEGER,
        cmcTcMasterTc2Unit2MsgTrap3
          INTEGER,
        cmcTcMasterTc2Unit2MsgTrap4
          INTEGER,                 
        cmcTcMasterTc2Unit2MsgQuit
          INTEGER              
      }

    cmcTcMasterTc2Unit2MsgIndex OBJECT-TYPE
      SYNTAX INTEGER (1..32000)
      ACCESS read-only
      STATUS mandatory
      DESCRIPTION
        "Index for the list of message entries. Its value ranges
         between 1 and the value of cmcTcMasterTc2Unit2NumberOfMsgs." 
      ::= { cmcTcMasterTc2Unit2MsgEntry 1 }

    cmcTcMasterTc2Unit2MsgText OBJECT-TYPE
      SYNTAX DisplayString (SIZE (0..20))
      ACCESS read-write
      STATUS mandatory
      DESCRIPTION
        "Descriptional text for each message (entry in the table)"
      ::= { cmcTcMasterTc2Unit2MsgEntry 2 }

    cmcTcMasterTc2Unit2MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc2Unit2OutputSet)
         17: door is unlocked by WEB
         18: door is unlocked by timer
         19: no access, wrong keycode or cardnumber
         20: orientation of PSM-Unit is circuit 1
         21: orientation of PSM-Unit is circuit 2"
      ::= { cmcTcMasterTc2Unit2MsgEntry 3 }

    cmcTcMasterTc2Unit2MsgRelay OBJECT-TYPE
      SYNTAX INTEGER {
        disable (1),
        enable (2)
      }
      ACCESS read-write
      STATUS mandatory
      DESCRIPTION
        "Setup of Alarm relay for this alarm
         2:        no switching of alarm relay             
         1:        switching of alarm relay" 
      ::= { cmcTcMasterTc2Unit2MsgEntry 4 }

    cmcTcMasterTc2Unit2MsgBeeper OBJECT-TYPE
      SYNTAX INTEGER {
        disable (1),
        enable (2)
      }
      ACCESS read-write
      STATUS mandatory
      DESCRIPTION
        "Setup of Alarm beeper for this alarm
         2:        no audible alarm
         1:        audible alarm" 
      ::= { cmcTcMasterTc2Unit2MsgEntry 5 }

    cmcTcMasterTc2Unit2MsgTrap1 OBJECT-TYPE
      SYNTAX INTEGER {
        disable (1),
        enable (2)
      }
      ACCESS read-write
      STATUS mandatory
      DESCRIPTION
        "Trap receiver 1 activated"
      ::= { cmcTcMasterTc2Unit2MsgEntry 6 }

    cmcTcMasterTc2Unit2MsgTrap2 OBJECT-TYPE
      SYNTAX INTEGER {
        disable (1),
        enable (2)
      }
      ACCESS read-write
      STATUS mandatory
      DESCRIPTION
        "Trap receiver 2 activated"
      ::= { cmcTcMasterTc2Unit2MsgEntry 7 }
 
    cmcTcMasterTc2Unit2MsgTrap3 OBJECT-TYPE
      SYNTAX INTEGER {
        disable (1),
        enable (2)
      }
      ACCESS read-write
      STATUS mandatory
      DESCRIPTION
        "Trap receiver 3 activated"
      ::= { cmcTcMasterTc2Unit2MsgEntry 8 }

    cmcTcMasterTc2Unit2MsgTrap4 OBJECT-TYPE
      SYNTAX INTEGER {
        disable (1),
        enable (2)
      }
      ACCESS read-write
      STATUS mandatory
      DESCRIPTION
        "Trap receiver 4 and Event Logging activated"
      ::= { cmcTcMasterTc2Unit2MsgEntry 9 }

    cmcTcMasterTc2Unit2MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc2Unit2MsgEntry 10 }

-- unit 3
  cmcTcMasterTc2Unit3TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 3"
    ::= { cmcTcMasterTc2StatusSensorUnit3 1 }

  cmcTcMasterTc2Unit3Text OBJECT-TYPE
    SYNTAX DisplayString (SIZE (0..10))
    ACCESS read-write
    STATUS mandatory
    DESCRIPTION
      "Descriptional text for sensor unit connected to port 3"
    ::= { cmcTcMasterTc2StatusSensorUnit3 2 }

  cmcTcMasterTc2Unit3Serial OBJECT-TYPE
    SYNTAX INTEGER 
    ACCESS  read-only
    STATUS  mandatory
    DESCRIPTION
      "Serialnumber of sensor unit connected to port 3"
    ::= { cmcTcMasterTc2StatusSensorUnit3 3 }

  cmcTcMasterTc2Unit3Status OBJECT-TYPE
    SYNTAX INTEGER {
      ok(1),
      error(2),
      changed(3),
      quit(4),
      timeout(5),
      detected(6),
      notAvail(7),
      lowPower(8)
    }
    ACCESS  read-only
    STATUS  mandatory
    DESCRIPTION
      "General Status sensor unit connected to port 3
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc2StatusSensorUnit3 4 }

-- Sensors              

  cmcTcMasterTc2Unit3NumberOfSensors OBJECT-TYPE
    SYNTAX INTEGER 
    ACCESS read-only
    STATUS mandatory
    DESCRIPTION
      "Number of sensors connected to sensor unit 3"
    ::= { cmcTcMasterTc2StatusUnit3Sensors 1 }

-- table with entry for each sensor available on this unit              
        
  cmcTcMasterTc2Unit3SensorTable OBJECT-TYPE
    SYNTAX SEQUENCE OF CmcTcMasterTc2Unit3SensorEntry
    ACCESS not-accessible
    STATUS mandatory
    DESCRIPTION
      "Headline of sensor table"
    ::= { cmcTcMasterTc2StatusUnit3Sensors 2 }

  cmcTcMasterTc2Unit3SensorEntry OBJECT-TYPE
    SYNTAX CmcTcMasterTc2Unit3SensorEntry
    ACCESS not-accessible
    STATUS mandatory
    DESCRIPTION
      "Entries of sensor table"
    INDEX { cmcTcMasterTc2Unit3SensorIndex }
    ::= { cmcTcMasterTc2Unit3SensorTable 1 }

    CmcTcMasterTc2Unit3SensorEntry ::=
      SEQUENCE {
        cmcTcMasterTc2Unit3SensorIndex
          INTEGER,
        cmcTcMasterTc2Unit3SensorType
          INTEGER,
        cmcTcMasterTc2Unit3SensorText
          DisplayString (SIZE (0..20)),                
        cmcTcMasterTc2Unit3SensorStatus
          INTEGER,
        cmcTcMasterTc2Unit3SensorValue
          INTEGER,
        cmcTcMasterTc2Unit3SensorSetHigh
          INTEGER,
        cmcTcMasterTc2Unit3SensorSetLow
          INTEGER,                 
        cmcTcMasterTc2Unit3SensorSetWarn
          INTEGER  
      }

    cmcTcMasterTc2Unit3SensorIndex OBJECT-TYPE
      SYNTAX INTEGER (1..32000)
      ACCESS read-only
      STATUS mandatory
      DESCRIPTION
        "Index for the list of value entries. Its value ranges
         between 1 and the value of cmcTcMasterTc2Unit3NumberOfSensors." 
      ::= { cmcTcMasterTc2Unit3SensorEntry 1 }

    cmcTcMasterTc2Unit3SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 3 to sensor[cmcTcMasterTc2Unit3SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc2Unit3SensorEntry 2 }

    cmcTcMasterTc2Unit3SensorText OBJECT-TYPE
      SYNTAX DisplayString (SIZE (0..20))
      ACCESS read-write
      STATUS mandatory
      DESCRIPTION
        "Descriptional text for each sensor (entry in the table)"
      ::= { cmcTcMasterTc2Unit3SensorEntry 3 }
              
    cmcTcMasterTc2Unit3SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc2Unit3SensorEntry 4 }

    cmcTcMasterTc2Unit3SensorValue OBJECT-TYPE
      SYNTAX INTEGER 
      ACCESS read-only
      STATUS mandatory
      DESCRIPTION
        "Value of sensor"
      ::= { cmcTcMasterTc2Unit3SensorEntry 5 }

    cmcTcMasterTc2Unit3SensorSetHigh OBJECT-TYPE
      SYNTAX INTEGER (0..300) 
      ACCESS read-write
      STATUS mandatory
      DESCRIPTION
        "Value for high setpoint of sensor"
      ::= { cmcTcMasterTc2Unit3SensorEntry 6 }

    cmcTcMasterTc2Unit3SensorSetLow OBJECT-TYPE
      SYNTAX INTEGER (0..300) 
      ACCESS read-write
      STATUS mandatory
      DESCRIPTION
        "Value for low setpoint of sensor,
         also used as alarm delay"
      ::= { cmcTcMasterTc2Unit3SensorEntry 7 }

    cmcTcMasterTc2Unit3SensorSetWarn OBJECT-TYPE
      SYNTAX INTEGER (0..300) 
      ACCESS read-write
      STATUS mandatory
      DESCRIPTION
        "Value for warning setpoint of sensor,
         also used as fan threshold"
      ::= { cmcTcMasterTc2Unit3SensorEntry 8 }
                
-- Outputs              

  cmcTcMasterTc2Unit3NumberOfOutputs OBJECT-TYPE
    SYNTAX INTEGER 
    ACCESS read-only
    STATUS mandatory
    DESCRIPTION
      "Number of outputs available on sensor unit 3"
    ::= { cmcTcMasterTc2StatusUnit3Outputs 1 }

-- table with entry for each output available on this unit              
                
  cmcTcMasterTc2Unit3OutputTable OBJECT-TYPE
    SYNTAX SEQUENCE OF CmcTcMasterTc2Unit3OutputEntry
    ACCESS not-accessible
    STATUS mandatory
    DESCRIPTION
      "Headline of output table"
    ::= { cmcTcMasterTc2StatusUnit3Outputs 2 }

  cmcTcMasterTc2Unit3OutputEntry OBJECT-TYPE
    SYNTAX CmcTcMasterTc2Unit3OutputEntry
    ACCESS not-accessible
    STATUS mandatory
    DESCRIPTION
      "Entries of output table"
    INDEX { cmcTcMasterTc2Unit3OutputIndex }
    ::= { cmcTcMasterTc2Unit3OutputTable 1 }

    CmcTcMasterTc2Unit3OutputEntry ::=
      SEQUENCE {
        cmcTcMasterTc2Unit3OutputIndex
          INTEGER,
        cmcTcMasterTc2Unit3OutputType
          INTEGER,
        cmcTcMasterTc2Unit3OutputText
          DisplayString (SIZE (0..20)),                
        cmcTcMasterTc2Unit3OutputStatus
          INTEGER,
        cmcTcMasterTc2Unit3OutputValue
          INTEGER,
        cmcTcMasterTc2Unit3OutputSet
          INTEGER,
        cmcTcMasterTc2Unit3OutputConfig
          INTEGER,
        cmcTcMasterTc2Unit3OutputDelay
          INTEGER,
        cmcTcMasterTc2Unit3OutputTimeoutAction
          INTEGER
      }

    cmcTcMasterTc2Unit3OutputIndex OBJECT-TYPE
      SYNTAX INTEGER (1..32000)
      ACCESS read-only
      STATUS mandatory
      DESCRIPTION
        "Index for the list of output entries. Its value ranges
         between 1 and the value of cmcTcMasterTc2Unit3NumberOfOutputs." 
      ::= { cmcTcMasterTc2Unit3OutputEntry 1 }

    cmcTcMasterTc2Unit3OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 3 to output[cmcTcMasterTc2Unit3OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc2Unit3OutputEntry 2 }

        
    cmcTcMasterTc2Unit3OutputText OBJECT-TYPE
      SYNTAX DisplayString (SIZE (0..20))
      ACCESS read-write
      STATUS mandatory
      DESCRIPTION
        "Descriptional text for each output (entry in the table)"
      ::= { cmcTcMasterTc2Unit3OutputEntry 3 }
              
    cmcTcMasterTc2Unit3OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc2Unit3OutputEntry 4 }

    cmcTcMasterTc2Unit3OutputValue OBJECT-TYPE
      SYNTAX INTEGER (-32000..32000) 
      ACCESS read-write
      STATUS mandatory
      DESCRIPTION
        "Value for output"
      ::= { cmcTcMasterTc2Unit3OutputEntry 5 }

    cmcTcMasterTc2Unit3OutputSet OBJECT-TYPE
      SYNTAX INTEGER {
        off (1),
        on (2),
        lock (3),
        unlock (4),
        unlockDelay (5)
      }
      ACCESS read-write
      STATUS mandatory
      DESCRIPTION
        "Command for output"
      ::= { cmcTcMasterTc2Unit3OutputEntry 6 }

    cmcTcMasterTc2Unit3OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc2Unit3OutputEntry 7 }

    cmcTcMasterTc2Unit3OutputDelay OBJECT-TYPE
      SYNTAX INTEGER (0..999) 
      ACCESS read-write
      STATUS mandatory
      DESCRIPTION
        "Unsigned Value for delay, 
         after this time the output will fall into the previous state"
      ::= { cmcTcMasterTc2Unit3OutputEntry 8 }

    cmcTcMasterTc2Unit3OutputTimeoutAction OBJECT-TYPE
      SYNTAX INTEGER {
        stay (1),
        off (2),
        on (3)
      }
      ACCESS read-write
      STATUS mandatory
      DESCRIPTION
        "State for output if timeout (RS422) occurs"
      ::= { cmcTcMasterTc2Unit3OutputEntry 9 }

-- Messages
              
  cmcTcMasterTc2Unit3NumberOfMsgs OBJECT-TYPE
    SYNTAX INTEGER 
    ACCESS read-only
    STATUS mandatory
    DESCRIPTION
      "Number of messages that can be created with sensor unit 3"
    ::= { cmcTcMasterTc2StatusUnit3Msg 1 }

-- table with entry for each alarm available on this unit               
                
  cmcTcMasterTc2Unit3MsgTable OBJECT-TYPE
    SYNTAX SEQUENCE OF CmcTcMasterTc2Unit3MsgEntry
    ACCESS not-accessible
    STATUS mandatory
    DESCRIPTION
      "Headline of message table"
    ::= { cmcTcMasterTc2StatusUnit3Msg 2 }

  cmcTcMasterTc2Unit3MsgEntry OBJECT-TYPE
    SYNTAX CmcTcMasterTc2Unit3MsgEntry
    ACCESS not-accessible
    STATUS mandatory
    DESCRIPTION
      "Entries of message table"
    INDEX { cmcTcMasterTc2Unit3MsgIndex }
    ::= { cmcTcMasterTc2Unit3MsgTable 1 }

    CmcTcMasterTc2Unit3MsgEntry ::=
      SEQUENCE {
        cmcTcMasterTc2Unit3MsgIndex
          INTEGER,
        cmcTcMasterTc2Unit3MsgText
          DisplayString (SIZE (0..20)),
        cmcTcMasterTc2Unit3MsgStatus
          INTEGER, 
        cmcTcMasterTc2Unit3MsgRelay
          INTEGER,
        cmcTcMasterTc2Unit3MsgBeeper
          INTEGER,
        cmcTcMasterTc2Unit3MsgTrap1
          INTEGER,
        cmcTcMasterTc2Unit3MsgTrap2
          INTEGER,
        cmcTcMasterTc2Unit3MsgTrap3
          INTEGER,
        cmcTcMasterTc2Unit3MsgTrap4
          INTEGER,                 
        cmcTcMasterTc2Unit3MsgQuit
          INTEGER              
      }

    cmcTcMasterTc2Unit3MsgIndex OBJECT-TYPE
      SYNTAX INTEGER (1..32000)
      ACCESS read-only
      STATUS mandatory
      DESCRIPTION
        "Index for the list of message entries. Its value ranges
         between 1 and the value of cmcTcMasterTc2Unit3NumberOfMsgs." 
      ::= { cmcTcMasterTc2Unit3MsgEntry 1 }

    cmcTcMasterTc2Unit3MsgText OBJECT-TYPE
      SYNTAX DisplayString (SIZE (0..20))
      ACCESS read-write
      STATUS mandatory
      DESCRIPTION
        "Descriptional text for each message (entry in the table)"
      ::= { cmcTcMasterTc2Unit3MsgEntry 2 }

    cmcTcMasterTc2Unit3MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc2Unit3OutputSet)
         17: door is unlocked by WEB
         18: door is unlocked by timer
         19: no access, wrong keycode or cardnumber
         20: orientation of PSM-Unit is circuit 1
         21: orientation of PSM-Unit is circuit 2"
      ::= { cmcTcMasterTc2Unit3MsgEntry 3 }

    cmcTcMasterTc2Unit3MsgRelay OBJECT-TYPE
      SYNTAX INTEGER {
        disable (1),
        enable (2)
      }
      ACCESS read-write
      STATUS mandatory
      DESCRIPTION
        "Setup of Alarm relay for this alarm
         1:        no switching of alarm relay             
         2:        switching of alarm relay" 
      ::= { cmcTcMasterTc2Unit3MsgEntry 4 }

    cmcTcMasterTc2Unit3MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc2Unit3MsgEntry 5 }

    cmcTcMasterTc2Unit3MsgTrap1 OBJECT-TYPE
      SYNTAX INTEGER {
        disable (1),
        enable (2)
      }
      ACCESS read-write
      STATUS mandatory
      DESCRIPTION
        "Trap receiver 1 activated"
      ::= { cmcTcMasterTc2Unit3MsgEntry 6 }

    cmcTcMasterTc2Unit3MsgTrap2 OBJECT-TYPE
      SYNTAX INTEGER {
        disable (1),
        enable (2)
      }
      ACCESS read-write
      STATUS mandatory
      DESCRIPTION
        "Trap receiver 2 activated"
      ::= { cmcTcMasterTc2Unit3MsgEntry 7 }
 
    cmcTcMasterTc2Unit3MsgTrap3 OBJECT-TYPE
      SYNTAX INTEGER {
        disable (1),
        enable (2)
      }
      ACCESS read-write
      STATUS mandatory
      DESCRIPTION
        "Trap receiver 3 activated"
      ::= { cmcTcMasterTc2Unit3MsgEntry 8 }

    cmcTcMasterTc2Unit3MsgTrap4 OBJECT-TYPE
      SYNTAX INTEGER {
        disable (1),
        enable (2)
      }
      ACCESS read-write
      STATUS mandatory
      DESCRIPTION
        "Trap receiver 4 and Event Logging activated"
      ::= { cmcTcMasterTc2Unit3MsgEntry 9 }

    cmcTcMasterTc2Unit3MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc2Unit3MsgEntry 10 }

-- unit4

  cmcTcMasterTc2Unit4TypeOfDevice OBJECT-TYPE
    SYNTAX INTEGER {
      notAvail (1),
      unitIO (2),
      unitAccess (3),
      unitClimate (4),
      unitFCS (5),
      unitRTT (6),
      unitRLCP (7),
      unitPSM (8)
    }
    ACCESS  read-only
    STATUS  mandatory
    DESCRIPTION
      "Type of sensor unit connected to port 4"
    ::= { cmcTcMasterTc2StatusSensorUnit4 1 }

  cmcTcMasterTc2Unit4Text OBJECT-TYPE
    SYNTAX DisplayString (SIZE (0..10))
    ACCESS read-write
    STATUS mandatory
    DESCRIPTION
      "Descriptional text for sensor unit connected to port 4"
    ::= { cmcTcMasterTc2StatusSensorUnit4 2 }

  cmcTcMasterTc2Unit4Serial OBJECT-TYPE
    SYNTAX INTEGER 
    ACCESS read-only
    STATUS mandatory
    DESCRIPTION
      "Serialnumber of sensor unit connected to port 4"
    ::= { cmcTcMasterTc2StatusSensorUnit4 3 }

  cmcTcMasterTc2Unit4Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 4
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc2StatusSensorUnit4 4 }

-- Sensors
              
  cmcTcMasterTc2Unit4NumberOfSensors OBJECT-TYPE
    SYNTAX INTEGER 
    ACCESS read-only
    STATUS mandatory
    DESCRIPTION
      "Number of sensors connected to sensor unit 4"
    ::= { cmcTcMasterTc2StatusUnit4Sensors 1 }

-- table with entry for each sensor available on this unit              
                
  cmcTcMasterTc2Unit4SensorTable OBJECT-TYPE
    SYNTAX SEQUENCE OF CmcTcMasterTc2Unit4SensorEntry
    ACCESS not-accessible
    STATUS mandatory
    DESCRIPTION
      "Headline of sensor table"
    ::= { cmcTcMasterTc2StatusUnit4Sensors 2 }

  cmcTcMasterTc2Unit4SensorEntry OBJECT-TYPE
    SYNTAX CmcTcMasterTc2Unit4SensorEntry
    ACCESS not-accessible
    STATUS mandatory
    DESCRIPTION
      "Entries of sensor table"
    INDEX { cmcTcMasterTc2Unit4SensorIndex }
    ::= { cmcTcMasterTc2Unit4SensorTable 1 }

    CmcTcMasterTc2Unit4SensorEntry ::=
      SEQUENCE {
        cmcTcMasterTc2Unit4SensorIndex
          INTEGER,
        cmcTcMasterTc2Unit4SensorType
          INTEGER,
        cmcTcMasterTc2Unit4SensorText
          DisplayString (SIZE (0..20)),                
        cmcTcMasterTc2Unit4SensorStatus
          INTEGER,
        cmcTcMasterTc2Unit4SensorValue
          INTEGER,
        cmcTcMasterTc2Unit4SensorSetHigh
          INTEGER,
        cmcTcMasterTc2Unit4SensorSetLow
          INTEGER,                 
        cmcTcMasterTc2Unit4SensorSetWarn
          INTEGER  
      }

    cmcTcMasterTc2Unit4SensorIndex OBJECT-TYPE
      SYNTAX INTEGER (1..32000)
      ACCESS read-only
      STATUS mandatory
      DESCRIPTION
        "Index for the list of value entries. Its value ranges
         between 1 and the value of cmcTcMasterTc2Unit4NumberOfSensors." 
      ::= { cmcTcMasterTc2Unit4SensorEntry 1 }

    cmcTcMasterTc2Unit4SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 4 to sensor[cmcTcMasterTc2Unit4SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCPT-Unit
         30:       actual current*10, PSM-Unit
         31:       status PSM-Unit
         32:       position PSM-Unit, normal/reversed = circuit 1/2" 
      ::= { cmcTcMasterTc2Unit4SensorEntry 2 }

    cmcTcMasterTc2Unit4SensorText OBJECT-TYPE
      SYNTAX DisplayString (SIZE (0..20))
      ACCESS read-write
      STATUS mandatory
      DESCRIPTION
        "Descriptional text for each sensor (entry in the table)"
      ::= { cmcTcMasterTc2Unit4SensorEntry 3 }
              
    cmcTcMasterTc2Unit4SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc2Unit4SensorEntry 4 }

    cmcTcMasterTc2Unit4SensorValue OBJECT-TYPE
      SYNTAX INTEGER 
      ACCESS read-only
      STATUS mandatory
      DESCRIPTION
        "Value of sensor"
      ::= { cmcTcMasterTc2Unit4SensorEntry 5 }

    cmcTcMasterTc2Unit4SensorSetHigh OBJECT-TYPE
      SYNTAX INTEGER (0..300) 
      ACCESS read-write
      STATUS mandatory
      DESCRIPTION
        "Value for high setpoint of sensor"
      ::= { cmcTcMasterTc2Unit4SensorEntry 6 }

    cmcTcMasterTc2Unit4SensorSetLow OBJECT-TYPE
      SYNTAX INTEGER (0..300) 
      ACCESS read-write
      STATUS mandatory
      DESCRIPTION
        "Value for low setpoint of sensor,
         also used as alarm delay"
      ::= { cmcTcMasterTc2Unit4SensorEntry 7 }

    cmcTcMasterTc2Unit4SensorSetWarn OBJECT-TYPE
      SYNTAX INTEGER (0..300) 
      ACCESS read-write
      STATUS mandatory
      DESCRIPTION
        "Value for warning setpoint of sensor,
         also used as fan threshold"
      ::= { cmcTcMasterTc2Unit4SensorEntry 8 }

-- Outputs              

  cmcTcMasterTc2Unit4NumberOfOutputs OBJECT-TYPE
    SYNTAX INTEGER 
    ACCESS read-only
    STATUS mandatory
    DESCRIPTION
      "Number of outputs available on sensor unit 4"
    ::= { cmcTcMasterTc2StatusUnit4Outputs 1 }

-- table with entry for each output available on this unit              
                
  cmcTcMasterTc2Unit4OutputTable OBJECT-TYPE
    SYNTAX SEQUENCE OF CmcTcMasterTc2Unit4OutputEntry
    ACCESS not-accessible
    STATUS mandatory
    DESCRIPTION
      "Headline of output table"
    ::= { cmcTcMasterTc2StatusUnit4Outputs 2 }

  cmcTcMasterTc2Unit4OutputEntry OBJECT-TYPE
    SYNTAX CmcTcMasterTc2Unit4OutputEntry
    ACCESS not-accessible
    STATUS mandatory
    DESCRIPTION
      "Entries of output table"
    INDEX { cmcTcMasterTc2Unit4OutputIndex }
    ::= { cmcTcMasterTc2Unit4OutputTable 1 }

    CmcTcMasterTc2Unit4OutputEntry ::=
      SEQUENCE {
        cmcTcMasterTc2Unit4OutputIndex
          INTEGER,
        cmcTcMasterTc2Unit4OutputType
          INTEGER,
        cmcTcMasterTc2Unit4OutputText
          DisplayString (SIZE (0..20)),                
        cmcTcMasterTc2Unit4OutputStatus
          INTEGER,
        cmcTcMasterTc2Unit4OutputValue
          INTEGER,
        cmcTcMasterTc2Unit4OutputSet
          INTEGER,
        cmcTcMasterTc2Unit4OutputConfig
          INTEGER,
        cmcTcMasterTc2Unit4OutputDelay
          INTEGER,
        cmcTcMasterTc2Unit4OutputTimeoutAction
          INTEGER
      }

    cmcTcMasterTc2Unit4OutputIndex OBJECT-TYPE
      SYNTAX INTEGER (1..32000)
      ACCESS read-only
      STATUS mandatory
      DESCRIPTION
        "Index for the list of output entries. Its value ranges
         between 1 and the value of cmcTcMasterTc2Unit4NumberOfOutputs." 
      ::= { cmcTcMasterTc2Unit4OutputEntry 1 }

    cmcTcMasterTc2Unit4OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 4 to output[cmcTcMasterTc2Unit4OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc2Unit4OutputEntry 2 }

    cmcTcMasterTc2Unit4OutputText OBJECT-TYPE
      SYNTAX DisplayString (SIZE (0..20))
      ACCESS read-write
      STATUS mandatory
      DESCRIPTION
        "Descriptional text for each output (entry in the table)"
      ::= { cmcTcMasterTc2Unit4OutputEntry 3 }
              
    cmcTcMasterTc2Unit4OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc2Unit4OutputEntry 4 }

    cmcTcMasterTc2Unit4OutputValue OBJECT-TYPE
      SYNTAX INTEGER (-32000..32000) 
      ACCESS read-write
      STATUS mandatory
      DESCRIPTION
        "Value for output"
      ::= { cmcTcMasterTc2Unit4OutputEntry 5 }

    cmcTcMasterTc2Unit4OutputSet OBJECT-TYPE
      SYNTAX INTEGER {
        off (1),
        on (2),
        lock (3),
        unlock (4),
        unlockDelay (5)
      }
      ACCESS read-write
      STATUS mandatory
      DESCRIPTION
        "Command for output"
      ::= { cmcTcMasterTc2Unit4OutputEntry 6 }

    cmcTcMasterTc2Unit4OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc2Unit4OutputEntry 7 }

    cmcTcMasterTc2Unit4OutputDelay OBJECT-TYPE
      SYNTAX INTEGER (0..999) 
      ACCESS read-write
      STATUS mandatory
      DESCRIPTION
        "Unsigned Value for delay, 
         after this time the output will fall into the previous state"
      ::= { cmcTcMasterTc2Unit4OutputEntry 8 }

    cmcTcMasterTc2Unit4OutputTimeoutAction OBJECT-TYPE
      SYNTAX INTEGER {
        stay (1),
        off (2),
        on (3)
      }
      ACCESS read-write
      STATUS mandatory
      DESCRIPTION
        "State for output if timeout (RS422) occurs"
      ::= { cmcTcMasterTc2Unit4OutputEntry 9 }

-- Messages
              
  cmcTcMasterTc2Unit4NumberOfMsgs OBJECT-TYPE
    SYNTAX INTEGER 
    ACCESS read-only
    STATUS mandatory
    DESCRIPTION
      "Number of messages that can be created with sensor unit 4"
    ::= { cmcTcMasterTc2StatusUnit4Msg 1 }

-- table with entry for each alarm available on this unit               
                
  cmcTcMasterTc2Unit4MsgTable OBJECT-TYPE
    SYNTAX SEQUENCE OF CmcTcMasterTc2Unit4MsgEntry
    ACCESS not-accessible
    STATUS mandatory
    DESCRIPTION
      "Headline of message table"
    ::= { cmcTcMasterTc2StatusUnit4Msg 2 }

  cmcTcMasterTc2Unit4MsgEntry OBJECT-TYPE
    SYNTAX CmcTcMasterTc2Unit4MsgEntry
    ACCESS not-accessible
    STATUS mandatory
    DESCRIPTION
      "Entries of message table"
    INDEX { cmcTcMasterTc2Unit4MsgIndex }
    ::= { cmcTcMasterTc2Unit4MsgTable 1 }

    CmcTcMasterTc2Unit4MsgEntry ::=
      SEQUENCE {
        cmcTcMasterTc2Unit4MsgIndex
          INTEGER,
        cmcTcMasterTc2Unit4MsgText
          DisplayString (SIZE (0..20)),                
        cmcTcMasterTc2Unit4MsgStatus
          INTEGER, 
        cmcTcMasterTc2Unit4MsgRelay
          INTEGER,
        cmcTcMasterTc2Unit4MsgBeeper
          INTEGER,
        cmcTcMasterTc2Unit4MsgTrap1
          INTEGER,
        cmcTcMasterTc2Unit4MsgTrap2
          INTEGER,
        cmcTcMasterTc2Unit4MsgTrap3
          INTEGER,
        cmcTcMasterTc2Unit4MsgTrap4
          INTEGER,                 
        cmcTcMasterTc2Unit4MsgQuit
          INTEGER              
      }

    cmcTcMasterTc2Unit4MsgIndex OBJECT-TYPE
      SYNTAX INTEGER (1..32000)
      ACCESS read-only
      STATUS mandatory
      DESCRIPTION
        "Index for the list of message entries. Its value ranges
         between 1 and the value of cmcTcMasterTc2Unit4NumberOfMsgs." 
      ::= { cmcTcMasterTc2Unit4MsgEntry 1 }

    cmcTcMasterTc2Unit4MsgText OBJECT-TYPE
      SYNTAX DisplayString (SIZE (0..20))
      ACCESS read-write
      STATUS mandatory
      DESCRIPTION
        "Descriptional text for each message (entry in the table)"
      ::= { cmcTcMasterTc2Unit4MsgEntry 2 }

    cmcTcMasterTc2Unit4MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc2Unit4OutputSet)
         17: door is unlocked by WEB
         18: door is unlocked by timer
         19: no access, wrong keycode or cardnumber
         20: orientation of PSM-Unit is circuit 1
         21: orientation of PSM-Unit is circuit 2"
      ::= { cmcTcMasterTc2Unit4MsgEntry 3 }

    cmcTcMasterTc2Unit4MsgRelay OBJECT-TYPE
      SYNTAX INTEGER {
        disable (1),
        enable (2)
      }
      ACCESS read-write
      STATUS mandatory
      DESCRIPTION
        "Setup of Alarm relay for this alarm
         1:        no switching of alarm relay             
         2:        switching of alarm relay" 
      ::= { cmcTcMasterTc2Unit4MsgEntry 4 }

    cmcTcMasterTc2Unit4MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc2Unit4MsgEntry 5 }

    cmcTcMasterTc2Unit4MsgTrap1 OBJECT-TYPE
      SYNTAX INTEGER {
        disable (1),
        enable (2)
      }
      ACCESS read-write
      STATUS mandatory
      DESCRIPTION
        "Trap receiver 1 activated"
      ::= { cmcTcMasterTc2Unit4MsgEntry 6 }

    cmcTcMasterTc2Unit4MsgTrap2 OBJECT-TYPE
      SYNTAX INTEGER {
        disable (1),
        enable (2)
      }
      ACCESS read-write
      STATUS mandatory
      DESCRIPTION
        "Trap receiver 2 activated"
      ::= { cmcTcMasterTc2Unit4MsgEntry 7 }
 
    cmcTcMasterTc2Unit4MsgTrap3 OBJECT-TYPE
      SYNTAX INTEGER {
        disable (1),
        enable (2)
      }
      ACCESS read-write
      STATUS mandatory
      DESCRIPTION
        "Trap receiver 3 activated"
      ::= { cmcTcMasterTc2Unit4MsgEntry 8 }

    cmcTcMasterTc2Unit4MsgTrap4 OBJECT-TYPE
      SYNTAX INTEGER {
        disable (1),
        enable (2)
      }
      ACCESS read-write
      STATUS mandatory
      DESCRIPTION
        "Trap receiver 4 and Event Logging activated"
      ::= { cmcTcMasterTc2Unit4MsgEntry 9 }

    cmcTcMasterTc2Unit4MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc2Unit4MsgEntry 10 }

--Status extension unit

  cmcTcMasterTc2ValuesRelay OBJECT-TYPE
    SYNTAX INTEGER {
      disable (1),
      enable (2)
    }
    ACCESS read-write
    STATUS mandatory
    DESCRIPTION
      "Setup of Alarm relay for alarm ext. unit(s)
       1:        no switching of alarm relay             
       2:        switching of alarm relay" 
    ::= { cmcTcMasterTc2StatusExtUnit 1 }

  cmcTcMasterTc2ValuesBeeper OBJECT-TYPE
    SYNTAX INTEGER {
      disable (1),
      enable (2)
    }
    ACCESS read-write
    STATUS mandatory
    DESCRIPTION
      "Setup of Alarm beeper for alarm ext. unit(s)
       1:        no audible alarm
       2:        audible alarm" 
    ::= { cmcTcMasterTc2StatusExtUnit 2 }

  cmcTcMasterTc2ValuesTrap1 OBJECT-TYPE
    SYNTAX INTEGER {
      disable (1),
      enable (2)
    }
    ACCESS read-write
    STATUS mandatory
    DESCRIPTION
      "Trap receiver 1 activated"
    ::= { cmcTcMasterTc2StatusExtUnit 3 }

  cmcTcMasterTc2ValuesTrap2 OBJECT-TYPE
    SYNTAX INTEGER {
      disable (1),
      enable (2)
    }
    ACCESS read-write
    STATUS mandatory
    DESCRIPTION
      "Trap receiver 2 activated"
    ::= { cmcTcMasterTc2StatusExtUnit 4 }
 
  cmcTcMasterTc2ValuesTrap3 OBJECT-TYPE
    SYNTAX INTEGER {
      disable (1),
      enable (2)
    }
    ACCESS read-write
    STATUS mandatory
    DESCRIPTION
      "Trap receiver 3 activated"
    ::= { cmcTcMasterTc2StatusExtUnit 5 }

  cmcTcMasterTc2ValuesTrap4 OBJECT-TYPE
    SYNTAX INTEGER {
      disable (1),
      enable (2)
    }
    ACCESS read-write
    STATUS mandatory
    DESCRIPTION
      "Trap receiver 4 and Event Logging activated"
    ::= { cmcTcMasterTc2StatusExtUnit 6 }
 
  cmcTcMasterTc2NumberOfValues OBJECT-TYPE
    SYNTAX INTEGER 
    ACCESS  read-only
    STATUS  mandatory
    DESCRIPTION
      "Number of values availabel on extension units connected to the CMC-TC"
    ::= { cmcTcMasterTc2StatusExtUnit 7 }

-- table with entry for each value available on extension units              

  cmcTcMasterTc2ValuesTable OBJECT-TYPE
    SYNTAX SEQUENCE OF CmcTcMasterTc2ValuesEntry
    ACCESS not-accessible
    STATUS mandatory
    DESCRIPTION
      "Headline of values-table"
    ::= { cmcTcMasterTc2StatusExtUnit 8 }

  cmcTcMasterTc2ValuesEntry OBJECT-TYPE
    SYNTAX CmcTcMasterTc2ValuesEntry
    ACCESS not-accessible
    STATUS mandatory
    DESCRIPTION
      "Entries of values-table"
    INDEX { cmcTcMasterTc2ValuesIndex }
    ::= { cmcTcMasterTc2ValuesTable 1 }

    CmcTcMasterTc2ValuesEntry ::=
      SEQUENCE {
        cmcTcMasterTc2ValuesIndex
          INTEGER,
        cmcTcMasterTc2ValuesText
          DisplayString (SIZE (0..20)),                
        cmcTcMasterTc2ValuesStatus
          INTEGER,
        cmcTcMasterTc2ValuesValue
          INTEGER,
        cmcTcMasterTc2ValuesSetHigh
          INTEGER,
        cmcTcMasterTc2ValuesSetLow
          INTEGER
      }

    cmcTcMasterTc2ValuesIndex OBJECT-TYPE
      SYNTAX INTEGER (1..32000)
      ACCESS read-only
      STATUS mandatory
      DESCRIPTION
        "Index for the list of value entries. Its value ranges
         between 1 and the value of cmcTcMasterTc2NumberOfValues." 
      ::= { cmcTcMasterTc2ValuesEntry 1 }

        
    cmcTcMasterTc2ValuesText OBJECT-TYPE
      SYNTAX DisplayString (SIZE (0..20))
      ACCESS read-write
      STATUS mandatory
      DESCRIPTION
        "Descriptional text for each value (entry in the table)
         of the extension card"
      ::= { cmcTcMasterTc2ValuesEntry 2 }
              
    cmcTcMasterTc2ValuesStatus OBJECT-TYPE
      SYNTAX INTEGER {
        notAvail(1),
        lost(2),
        changed(3),
        ok(4),
        tooLow(5),
        tooHigh(6),
        error(7)
      }
      ACCESS read-only
      STATUS mandatory
      DESCRIPTION
        "Actual status of the value of the extension card"
      ::= { cmcTcMasterTc2ValuesEntry 3 }

    cmcTcMasterTc2ValuesValue OBJECT-TYPE
      SYNTAX INTEGER 
      ACCESS read-only
      STATUS mandatory
      DESCRIPTION
        "Value of sensor"
      ::= { cmcTcMasterTc2ValuesEntry 4 }

    cmcTcMasterTc2ValuesSetHigh OBJECT-TYPE
      SYNTAX INTEGER (0..255) 
      ACCESS read-write
      STATUS mandatory
      DESCRIPTION
        "Value for high setpoint of sensor"
      ::= { cmcTcMasterTc2ValuesEntry 5 }

    cmcTcMasterTc2ValuesSetLow OBJECT-TYPE
      SYNTAX INTEGER (0..255) 
      ACCESS read-write
      STATUS mandatory
      DESCRIPTION
        "Value for low setpoint of sensor"
      ::= { cmcTcMasterTc2ValuesEntry 6 }

--cmcTcMasterTc2SetupGeneral-group

  cmcTcMasterTc2SetTempUnit OBJECT-TYPE
    SYNTAX INTEGER {
      celsius(1),
      fahrenheit(2)
    }
    ACCESS read-write
    STATUS mandatory
    DESCRIPTION
      "Unit of all temperature values and setpoints, Celsius or Fahrenheit"
   ::= { cmcTcMasterTc2SetupGeneral 1 }

  cmcTcMasterTc2SetBeeper OBJECT-TYPE
    SYNTAX INTEGER {
      off(1),
      on(2)
    }
    ACCESS read-write
    STATUS mandatory
    DESCRIPTION
      "Audible alarm in CMC-TC unit:
       (2): beeper is on
       (1): beeper is off (general)"
    ::= { cmcTcMasterTc2SetupGeneral 2 }


  cmcTcMasterTc2QuitRelay OBJECT-TYPE
    SYNTAX INTEGER {
      disabled(1),
      enabled(2)
    }
    ACCESS read-write
    STATUS mandatory
    DESCRIPTION
      "Enable or disable acknowledging currently active alarm relay 
       (with 'C' on CMC-TC)."
    ::= { cmcTcMasterTc2SetupGeneral 3 }

  cmcTcMasterTc2LogicRelay OBJECT-TYPE
    SYNTAX INTEGER {
      closeAtAlarm(1),
      openAtAlarm(2),
      off(3)
    }
    ACCESS read-write
    STATUS mandatory
    DESCRIPTION
      "Logic of alarm relay: 
       (1) Relay will pick up in case of an alarm
       (2) Relay will release in case of an alarm
       (3) Relay off (general)"
    ::= { cmcTcMasterTc2SetupGeneral 4 }

  cmcTcMasterTc2WebAccess OBJECT-TYPE
    SYNTAX INTEGER {
      viewOnly(1),
      fullAccess(2),
      off(3)
    }
    ACCESS read-write
    STATUS mandatory
    DESCRIPTION
      "Web access via HTTP: 
       (1) view only
       (2) full Access, read and set
       (3) Web disabled (general)"
    ::= { cmcTcMasterTc2SetupGeneral 5 }
 
  cmcTcMasterTc2SetupDate OBJECT-TYPE
    SYNTAX DisplayString (SIZE (0..10))
    ACCESS read-write
    STATUS mandatory
    DESCRIPTION
      "actual Date in format DD.MM.YYYY"
    ::= { cmcTcMasterTc2SetupGeneral 6 }

  cmcTcMasterTc2SetupTime OBJECT-TYPE
    SYNTAX DisplayString (SIZE (0..8))
    ACCESS read-write
    STATUS mandatory
    DESCRIPTION
      "actual Time in format HH:MM:SS, HH (0-23), MM (0-59), SS (0-59)"
    ::= { cmcTcMasterTc2SetupGeneral 7 }
 
-- table for timer function
 
  cmcTcMasterTc2TimerNumber OBJECT-TYPE
    SYNTAX INTEGER 
    ACCESS read-only
    STATUS mandatory
    DESCRIPTION
      "Number of timers available on this unit"
    ::= { cmcTcMasterTc2TimerTable1 1 }

  cmcTcMasterTc2TimerTable OBJECT-TYPE
    SYNTAX SEQUENCE OF CmcTcMasterTc2TimerEntry
    ACCESS not-accessible
    STATUS mandatory
    DESCRIPTION
      "Headline of timer-table"
    ::= { cmcTcMasterTc2TimerTable1 2 }

  cmcTcMasterTc2TimerEntry OBJECT-TYPE
    SYNTAX CmcTcMasterTc2TimerEntry
    ACCESS not-accessible
    STATUS mandatory
    DESCRIPTION
      "Entries of timer-table"
    INDEX { cmcTcMasterTc2TimerIndex }
    ::= { cmcTcMasterTc2TimerTable 1 }

    CmcTcMasterTc2TimerEntry ::=
      SEQUENCE {
        cmcTcMasterTc2TimerIndex
          INTEGER,
        cmcTcMasterTc2TimerStatus
          INTEGER,
        cmcTcMasterTc2TimerDayOfWeek
          INTEGER,  
        cmcTcMasterTc2TimeOn 
          DisplayString (SIZE (0..5)),                              
        cmcTcMasterTc2TimeOff 
          DisplayString (SIZE (0..5)),                              
        cmcTcMasterTc2TimeControl
          INTEGER,
        cmcTcMasterTc2TimerFunction
           INTEGER
      }

    cmcTcMasterTc2TimerIndex OBJECT-TYPE
      SYNTAX INTEGER (1..32000)
      ACCESS read-only
      STATUS mandatory
      DESCRIPTION
        "Index for the list of timer entries. Its value ranges
         between 1 and the value of cmcTcMasterTc2TimerNumber." 
      ::= { cmcTcMasterTc2TimerEntry 1 }

    cmcTcMasterTc2TimerStatus OBJECT-TYPE
      SYNTAX INTEGER {
        switchedOff(1),
        switchedOn(2),
        noTime(3) 
      }
      ACCESS read-only
      STATUS mandatory
      DESCRIPTION
        "Actual status of the timer"
      ::= { cmcTcMasterTc2TimerEntry 2 }

    cmcTcMasterTc2TimerDayOfWeek OBJECT-TYPE
      SYNTAX INTEGER {
        sun(1),
        mon(2),
        tue(3) ,
        wed(4),
        thu(5),
        fri(6),
        sat(7),
        sat-sun(8),
        mon-fri(9),
        mon-sun(10)
      }
      ACCESS read-write
      STATUS mandatory
      DESCRIPTION
        "Selection of day of week for timer to switch"
      ::= { cmcTcMasterTc2TimerEntry 3 }
             
    cmcTcMasterTc2TimeOn OBJECT-TYPE
      SYNTAX DisplayString (SIZE (0..5))
      ACCESS read-write
      STATUS mandatory
      DESCRIPTION
        "Time to switch on current function, 
         Format: HH:MM"
      ::= { cmcTcMasterTc2TimerEntry 4 }

    cmcTcMasterTc2TimeOff OBJECT-TYPE
      SYNTAX DisplayString (SIZE (0..5))
      ACCESS read-write
      STATUS mandatory
      DESCRIPTION
        "Time to switch off current function,
         Format: HH:MM"
      ::= { cmcTcMasterTc2TimerEntry 5 }

    cmcTcMasterTc2TimeControl OBJECT-TYPE
      SYNTAX INTEGER  {
        disabled(1),
        enabled(2)
      }
      ACCESS read-write
      STATUS mandatory
      DESCRIPTION
        "Control via RTC"
      ::= { cmcTcMasterTc2TimerEntry 6 }

    cmcTcMasterTc2TimerFunction OBJECT-TYPE
      SYNTAX INTEGER {
        disKeypad1-1 (1),
        disKeypad2-1 (2),
        disKeypad1-2 (3),
        disKeypad2-2 (4),
        disKeypad1-3 (5),
        disKeypad2-3 (6),
        disKeypad1-4 (7),
        disKeypad2-4 (8),
        unlDoor1-1 (9),
        unlDoor2-1 (10),
        unlDoor1-2 (11),
        unlDoor2-2 (12),
        unlDoor1-3 (13),
        unlDoor2-3 (14),
        unlDoor1-4 (15),
        unlDoor2-5 (16),
        disTrapRec1 (17),
        disTrapRec2 (18),
        disTrapRec3 (19),
        disTrapRec4 (20),
        disSMS (21),
        schedule1 (22),
        schedule2 (23),
        schedule3 (24),
        schedule4 (25)
      }
      ACCESS read-write
      STATUS mandatory
      DESCRIPTION
        "Function which is controlled via timer
         1:     unlock via keypad 1 on unit 1 or remote input lock 1 is disabled
         2:     unlock via keypad 2 on unit 1 or remote input lock 2 is disabled
         3      unlock via keypad 1 on unit 2 or remote input lock 1 is disabled
         4:     unlock via keypad 2 on unit 2 or remote input lock 2 is disabled
         5:     unlock via keypad 1 on unit 3 or remote input lock 1 is disabled
         6:     unlock via keypad 2 on unit 3 or remote input lock 2 is disabled
         7:     unlock via keypad 1 on unit 4 or remote input lock 1 is disabled
         8:     unlock via keypad 2 on unit 4 or remote input lock 2 is disabled
         9:     Lock of door 1 on unit 1 will be unlocked
         10:    Lock of door 2 on unit 1 will be unlocked
         11:    Lock of door 1 on unit 2 will be unlocked
         12:    Lock of door 2 on unit 2 will be unlocked
         13:    Lock of door 1 on unit 3 will be unlocked
         14:    Lock of door 2 on unit 3 will be unlocked
         15:    Lock of door 1 on unit 4 will be unlocked
         16:    Lock of door 2 on unit 4 will be unlocked
         17-20: sending Traps to this Trap receiver will be disabled
         21:    sending SMS will be disabled
         22-25: Scheduled alarm off"
      ::= { cmcTcMasterTc2TimerEntry 7 }

--cmcTcMasterTc2TrapTable-group

  cmcTcMasterTc2TraptableNumber OBJECT-TYPE
    SYNTAX INTEGER 
    ACCESS read-only
    STATUS mandatory
    DESCRIPTION
      "Number of trapTable entries. The number of trap-receiver"
    ::= { cmcTcMasterTc2Traps 1 }

  cmcTcMasterTc2TrapTableTable OBJECT-TYPE    
    SYNTAX SEQUENCE OF CmcTcMasterTc2TrapTableEntry
    ACCESS not-accessible
    STATUS mandatory
    DESCRIPTION
     "A list of trap-receiver entries"
    ::= { cmcTcMasterTc2Traps 2 }

  cmcTcMasterTc2TrapTableEntry OBJECT-TYPE
    SYNTAX CmcTcMasterTc2TrapTableEntry
    ACCESS not-accessible
    STATUS mandatory
    DESCRIPTION
      "Entries of cmcTcMasterTc2TrapTable"
    INDEX   { cmcTcMasterTc2TrapIndex }
    ::= { cmcTcMasterTc2TrapTableTable 1 }      
              
    CmcTcMasterTc2TrapTableEntry ::=
      SEQUENCE {
        cmcTcMasterTc2TrapIndex
          INTEGER,
        cmcTcMasterTc2TrapStatus
          INTEGER,
        cmcTcMasterTc2TrapIPaddress
          DisplayString
      }

    cmcTcMasterTc2TrapIndex OBJECT-TYPE
      SYNTAX INTEGER (1..32000)
      ACCESS read-only
      STATUS mandatory
      DESCRIPTION
        "Index for the trap-receiver-table. Its value ranges between
         1 and the value of cmcTcMasterTc2TraptableNumber "
      ::= { cmcTcMasterTc2TrapTableEntry 1 }

    cmcTcMasterTc2TrapStatus OBJECT-TYPE
      SYNTAX INTEGER {
        disabled(1),
        enabled(2)
      }
      ACCESS read-write
      STATUS mandatory
      DESCRIPTION
        "Enable or disable trap receiver"
      ::= { cmcTcMasterTc2TrapTableEntry 2 }

    cmcTcMasterTc2TrapIPaddress OBJECT-TYPE
      SYNTAX DisplayString (SIZE (0..15))
      ACCESS read-write
      STATUS mandatory
      DESCRIPTION
        "IP-address of trap-receiver"
      ::= { cmcTcMasterTc2TrapTableEntry 3 }

--cmcTcMasterTc2Control-group (Added in Version 1.1)

  cmcTcMasterTc2QuitUnit OBJECT-TYPE
    SYNTAX INTEGER {
      noQuit(1),
      quit(2),
    }
    ACCESS read-write
    STATUS mandatory
    DESCRIPTION
      "Command to quit (acknowledge) alarms of CMC-TC unit.
       Setting to 'quit' (2) will have same result as pressing 'C' on Units.
       Variable is automatically set back to 'noQuit' (1)."
    ::= { cmcTcMasterTc2Control 1 }

--cmcTcMasterDevice3-group

  cmcTcMasterDev3Type OBJECT-TYPE
    SYNTAX INTEGER {
      other (0),
      cmc (1),
      pcu (3),
      tc (4)
    }
    ACCESS read-only
    STATUS mandatory
    DESCRIPTION
      "Type of device3"
    ::= { cmcTcMasterDevice3 1 }

  cmcTcMasterDev3Status OBJECT-TYPE
    SYNTAX INTEGER {
      other (1),
      notConnected (2),
      normal (3),
      minor (4),
      major (5),
      configChanged (6),
      connectionLost (10)
    }
    ACCESS read-only
    STATUS mandatory
    DESCRIPTION
      "Status of device3"
    ::= { cmcTcMasterDevice3 2 }

  cmcTcMasterDev3Descr OBJECT-TYPE
    SYNTAX DisplayString (SIZE (0..255))
    ACCESS read-only
    STATUS mandatory
    DESCRIPTION
      "A textual description of the entity.  This value
       should include the full name and version
       identification of the system's hardware type,
       software operating-system, and networking
       software.  It is mandatory that this only contain
       printable ASCII characters."
    ::= { cmcTcMasterDevice3 3 }

  cmcTcMasterDev3UpTime OBJECT-TYPE
    SYNTAX TimeTicks
    ACCESS read-only
    STATUS mandatory
    DESCRIPTION
      "The time (in hundredths of a second) since the
       network management portion of the system was last
       re-initialized."
    ::= { cmcTcMasterDevice3 4 }

  cmcTcMasterDev3Contact OBJECT-TYPE
    SYNTAX DisplayString (SIZE (0..255))
    ACCESS read-write
    STATUS mandatory
    DESCRIPTION
      "The textual identification of the contact person
       for this managed node, together with information
       on how to contact this person."
    ::= { cmcTcMasterDevice3 5 }

  cmcTcMasterDev3Name OBJECT-TYPE
    SYNTAX DisplayString (SIZE (0..255))
    ACCESS read-write
    STATUS mandatory
    DESCRIPTION
      "An administratively-assigned name for this
       managed node.  By convention, this is the node's
       fully-qualified domain name."
    ::= { cmcTcMasterDevice3 6 }

  cmcTcMasterDev3Location OBJECT-TYPE
    SYNTAX DisplayString (SIZE (0..255))
    ACCESS read-write
    STATUS mandatory
    DESCRIPTION
      "The physical location of this node (e.g.,
       `telephone closet, 3rd floor')."
    ::= { cmcTcMasterDevice3 7 }

--cmcTcMasterCmc3Values-group

  cmcTcMasterCmc3ValueTemperature1 OBJECT-TYPE
    SYNTAX INTEGER
    ACCESS read-only
    STATUS mandatory
    DESCRIPTION
      "Actual value of temperature 1 in deg C"
    ::= { cmcTcMasterCmc3Values 1 }

  cmcTcMasterCmc3ValueTemperature2 OBJECT-TYPE
    SYNTAX INTEGER
    ACCESS read-only
    STATUS mandatory
    DESCRIPTION
      "Actual value of temperature 2 in deg C"
    ::= { cmcTcMasterCmc3Values 2 }

  cmcTcMasterCmc3ValuePowerSupply OBJECT-TYPE
    SYNTAX INTEGER
    ACCESS read-only
    STATUS mandatory
    DESCRIPTION
      "Actual value of power supply in V"
    ::= { cmcTcMasterCmc3Values 3 }

  cmcTcMasterCmc3ValueAnalogAux1 OBJECT-TYPE
    SYNTAX INTEGER
    ACCESS read-only
    STATUS mandatory
    DESCRIPTION
      "Actual value of aux. analog input 1
      (4-20mA = 0-100%)"
    ::= { cmcTcMasterCmc3Values 4 }

  cmcTcMasterCmc3ValueAnalogAux2 OBJECT-TYPE
    SYNTAX INTEGER
    ACCESS read-only
    STATUS mandatory
    DESCRIPTION
      "Actual value of aux. analog input 2
      (4-20mA = 0-100%)"
    ::= { cmcTcMasterCmc3Values 5 }

--cmcTcMasterCmc3Values-table-group

  cmcTcMasterCmc3ValuesNumber OBJECT-TYPE
    SYNTAX INTEGER
    ACCESS read-only
    STATUS mandatory
    DESCRIPTION
      "Number of value-table entries"
    ::= { cmcTcMasterCmc3Table1 1 }

  cmcTcMasterCmc3ValuesTable OBJECT-TYPE
    SYNTAX SEQUENCE OF CmcTcMasterCmc3ValuesEntry
    ACCESS not-accessible
    STATUS mandatory
    DESCRIPTION
      "Headline of value-table"
    ::= { cmcTcMasterCmc3Table1 2 }

  cmcTcMasterCmc3ValuesEntry OBJECT-TYPE
    SYNTAX CmcTcMasterCmc3ValuesEntry
    ACCESS not-accessible
    STATUS mandatory
    DESCRIPTION
      "Entries of value-table"
    INDEX { cmcTcMasterCmc3ValuesIndex }
    ::= { cmcTcMasterCmc3ValuesTable 1 }

  CmcTcMasterCmc3ValuesEntry ::=
    SEQUENCE {
      cmcTcMasterCmc3ValuesIndex
        INTEGER,
      cmcTcMasterCmc3ValuesText
        DisplayString (SIZE (0..31)),
      cmcTcMasterCmc3ValuesValue
        INTEGER,
      cmcTcMasterCmc3ValuesStatus
        INTEGER,
      cmcTcMasterCmc3ValuesMaxValue
        INTEGER,
      cmcTcMasterCmc3ValuesMinValue
        INTEGER
    }

    cmcTcMasterCmc3ValuesIndex OBJECT-TYPE
      SYNTAX INTEGER (1..32000)
      ACCESS read-only
      STATUS mandatory
      DESCRIPTION
        "Index for the list of value entries. Its value ranges
        between 1 and the value of valuesNumber."
      ::= { cmcTcMasterCmc3ValuesEntry 1 }

    cmcTcMasterCmc3ValuesText OBJECT-TYPE
      SYNTAX DisplayString (SIZE (0..31))
      ACCESS read-write
      STATUS mandatory
      DESCRIPTION
        "Text of the entry in the value-table"
      ::= { cmcTcMasterCmc3ValuesEntry 2 }

    cmcTcMasterCmc3ValuesValue OBJECT-TYPE
      SYNTAX INTEGER
      ACCESS read-only
      STATUS mandatory
      DESCRIPTION
        "Actual value of the value-table"
      ::= { cmcTcMasterCmc3ValuesEntry 3 }

    cmcTcMasterCmc3ValuesStatus OBJECT-TYPE
      SYNTAX INTEGER {
        valueOK(1),
        valueTooLow(2),
        valueTooLigh(3),
        valueERROR(4),
        notAvail(5)
      }
      ACCESS read-only
      STATUS mandatory
      DESCRIPTION
        "Status of the value"
      ::= { cmcTcMasterCmc3ValuesEntry 4 }

    cmcTcMasterCmc3ValuesMaxValue OBJECT-TYPE
      SYNTAX INTEGER
      ACCESS read-write
      STATUS mandatory
      DESCRIPTION
        "Value for max. alarm"
      ::= { cmcTcMasterCmc3ValuesEntry 5 }

    cmcTcMasterCmc3ValuesMinValue OBJECT-TYPE
      SYNTAX INTEGER
      ACCESS read-write
      STATUS mandatory
      DESCRIPTION
        "Value for min. alarm"
      ::= { cmcTcMasterCmc3ValuesEntry 6 }

--cmcTcMasterCmc3status-group

  cmcTcMasterCmc3StatusTemperature1 OBJECT-TYPE
    SYNTAX DisplayString (SIZE (0..31))
    ACCESS read-only
    STATUS mandatory
    DESCRIPTION
      "Status temperature 1, OK/ too low/ too high
       (see setpoints of temperature 1)"
    ::= { cmcTcMasterCmc3Status 1 }

  cmcTcMasterCmc3StatusTemperature2 OBJECT-TYPE
    SYNTAX DisplayString (SIZE (0..31))
    ACCESS read-only
    STATUS mandatory
    DESCRIPTION
      "Status temperature 2, OK/ too low/ too high
       (see setpoints of temperature 2)"
    ::= { cmcTcMasterCmc3Status 2 }

  cmcTcMasterCmc3StatusFan1 OBJECT-TYPE
    SYNTAX DisplayString (SIZE (0..31))
    ACCESS read-only
    STATUS mandatory
    DESCRIPTION
      "Status fan 1, Stop/ running/ fault"
    ::= { cmcTcMasterCmc3Status 3 }

  cmcTcMasterCmc3StatusFan2 OBJECT-TYPE
    SYNTAX DisplayString (SIZE (0..31))
    ACCESS read-only
    STATUS mandatory
    DESCRIPTION
      "Status fan 2, Stop/ running/ fault"
    ::= { cmcTcMasterCmc3Status 4 }

  cmcTcMasterCmc3StatusHeating OBJECT-TYPE
    SYNTAX DisplayString (SIZE (0..31))
    ACCESS read-only
    STATUS mandatory
    DESCRIPTION
      "Status heating, On/Off"
    ::= { cmcTcMasterCmc3Status 5 }

  cmcTcMasterCmc3StatusPowerSupply OBJECT-TYPE
    SYNTAX DisplayString (SIZE (0..31))
    ACCESS read-only
    STATUS mandatory
    DESCRIPTION
      "Status power supply, OK/ too low/ too high
       (see setpoints of power supply)"
    ::= { cmcTcMasterCmc3Status 6 }

  cmcTcMasterCmc3StatusAnalogAux1 OBJECT-TYPE
    SYNTAX DisplayString (SIZE (0..31))
    ACCESS read-only
    STATUS mandatory
    DESCRIPTION
      "Status aux analog input 1, OK/ too low/ too high"
    ::= { cmcTcMasterCmc3Status 7 }

  cmcTcMasterCmc3StatusAnalogAux2 OBJECT-TYPE
    SYNTAX DisplayString (SIZE (0..31))
    ACCESS read-only
    STATUS mandatory
    DESCRIPTION
      "Status aux analog input 2, OK/ too low/ too high"
    ::= { cmcTcMasterCmc3Status 8 }

  cmcTcMasterCmc3StatusDoor OBJECT-TYPE
    SYNTAX DisplayString (SIZE (0..31))
    ACCESS read-only
    STATUS mandatory
    DESCRIPTION
      "Status door, open/closed/locked"
    ::= { cmcTcMasterCmc3Status 9 }

  cmcTcMasterCmc3StatusUps1 OBJECT-TYPE
    SYNTAX DisplayString (SIZE (0..31))
    ACCESS read-only
    STATUS mandatory
    DESCRIPTION
      "Status UPS 1, OK/ fault"
    ::= { cmcTcMasterCmc3Status 10 }

  cmcTcMasterCmc3StatusUps2 OBJECT-TYPE
    SYNTAX DisplayString (SIZE (0..31))
    ACCESS read-only
    STATUS mandatory
    DESCRIPTION
      "Status UPS 2, OK/ fault"
    ::= { cmcTcMasterCmc3Status 11 }

  cmcTcMasterCmc3StatusSmokeSensor OBJECT-TYPE
    SYNTAX DisplayString (SIZE (0..31))
    ACCESS read-only
    STATUS mandatory
    DESCRIPTION
      "Status smoke-sensor, OK/ smoke"
    ::= { cmcTcMasterCmc3Status 12 }

  cmcTcMasterCmc3StatusVibrationSensor OBJECT-TYPE
    SYNTAX DisplayString (SIZE (0..31))
    ACCESS read-only
    STATUS mandatory
    DESCRIPTION
      "Status vibration sensor, OK/ vibration"
    ::= { cmcTcMasterCmc3Status 13 }

  cmcTcMasterCmc3StatusMessage OBJECT-TYPE
    SYNTAX DisplayString (SIZE (0..31))
    ACCESS read-only
    STATUS mandatory
    DESCRIPTION
      "Message from CMC"
    ::= { cmcTcMasterCmc3Status 14 }

  cmcTcMasterCmc3ValueOperatingTime OBJECT-TYPE
    SYNTAX DisplayString (SIZE (0..31))
    ACCESS read-only
    STATUS mandatory
    DESCRIPTION
      "Operating time CMC-unit"
    ::= { cmcTcMasterCmc3Status 15 }

  cmcTcMasterCmc3StatusUnit OBJECT-TYPE
    SYNTAX INTEGER {
      unitCelsius(1),
      unitFahrenheit(2)
    }
    ACCESS read-only
    STATUS mandatory
    DESCRIPTION
      "Unit of temperature-values, Celsius or Fahrenheit"
   ::= { cmcTcMasterCmc3Status 16 }


--cmcTcMasterCmc3Status-table-group

  cmcTcMasterCmc3StatusNumber OBJECT-TYPE
    SYNTAX INTEGER 
    ACCESS read-only
    STATUS mandatory
    DESCRIPTION
      "Number of status-table entries"
    ::= { cmcTcMasterCmc3Table 1 }

  cmcTcMasterCmc3StatusTable OBJECT-TYPE
    SYNTAX SEQUENCE OF CmcTcMasterCmc3StatusEntry
    ACCESS not-accessible
    STATUS mandatory
    DESCRIPTION
      "Headline of table"
    ::= { cmcTcMasterCmc3Table 2 }

  cmcTcMasterCmc3StatusEntry OBJECT-TYPE
    SYNTAX CmcTcMasterCmc3StatusEntry
    ACCESS not-accessible
    STATUS mandatory
    DESCRIPTION
      "A list of status entries.  The number of
       entries is given by the value of cmcTcMasterCmc3StatusNumber." 
    INDEX { cmcTcMasterCmc3StatusIndex }
    ::= { cmcTcMasterCmc3StatusTable 1 }

  CmcTcMasterCmc3StatusEntry ::=
    SEQUENCE {
      cmcTcMasterCmc3StatusIndex
        INTEGER,
      cmcTcMasterCmc3StatusText
        DisplayString (SIZE (0..31)),
      cmcTcMasterCmc3StatusStatus
        INTEGER              
    }

    cmcTcMasterCmc3StatusIndex OBJECT-TYPE
      SYNTAX INTEGER (1..32000)
      ACCESS read-only
      STATUS mandatory
      DESCRIPTION
        "Index fo the list of status entries. Its value ranges
         between 1 and the value of cmcTcMasterCmc3StatusNumber." 
      ::= { cmcTcMasterCmc3StatusEntry 1 }

    cmcTcMasterCmc3StatusText OBJECT-TYPE
      SYNTAX DisplayString (SIZE (0..31))
      ACCESS read-write
      STATUS mandatory
      DESCRIPTION
        "Text of the entry in the status-table"
      ::= { cmcTcMasterCmc3StatusEntry 2 }

    cmcTcMasterCmc3StatusStatus OBJECT-TYPE
      SYNTAX INTEGER  {
        statusOK(1),
        alarm(2),
        security(3),
        notAvail(4)
      }
      ACCESS read-only
      STATUS mandatory
      DESCRIPTION
        "Status of the table entry"
      ::= { cmcTcMasterCmc3StatusEntry 3 }

--******************************************************************************

--cmcTCMasterCmc3Set-group

  cmcTcMasterCmc3StatusAccess OBJECT-TYPE
    SYNTAX DisplayString (SIZE (0..31))
    ACCESS read-write
    STATUS mandatory
    DESCRIPTION
      "Status access"
    ::= { cmcTcMasterCmc3Set 1 }

  cmcTcMasterCmc3SetDoor OBJECT-TYPE
    SYNTAX INTEGER {
      lockDoor(1),
      openDoorTime(2),
      openDoorAccess(3),
      openDoor(4)
    }
    ACCESS read-write
    STATUS mandatory
    DESCRIPTION
      "Set door, see table"
    ::= { cmcTcMasterCmc3Set 2 }

  cmcTcMasterCmc3SetMessage OBJECT-TYPE
    SYNTAX DisplayString (SIZE (0..31))
    ACCESS read-write
    STATUS mandatory
    DESCRIPTION
      "Set message"
    ::= { cmcTcMasterCmc3Set 3 }

  cmcTcMasterCmc3SetFault        OBJECT-TYPE
    SYNTAX INTEGER {
      clearFault(1),
      setFault(2)
    }
    ACCESS read-write
    STATUS mandatory
    DESCRIPTION
      "Set fault, see table"
    ::= { cmcTcMasterCmc3Set 4 }

--cmcTcMasterCmc3RelayControl-group-----------------------------------------------------------------

  cmcTcMasterCmc3RelaytableMaxNum OBJECT-TYPE
    SYNTAX INTEGER 
    ACCESS read-only
    STATUS mandatory
    DESCRIPTION
      "Number of table entries"
    ::= { cmcTcMasterCmc3RelayControl 1 }

  cmcTcMasterCmc3RelayTable OBJECT-TYPE
    SYNTAX SEQUENCE OF CmcTcMasterCmc3RelayEntry
    ACCESS not-accessible
    STATUS mandatory
    DESCRIPTION
      "Headline of table for relay control"
    ::= { cmcTcMasterCmc3RelayControl 2 }

  cmcTcMasterCmc3RelayEntry OBJECT-TYPE
    SYNTAX CmcTcMasterCmc3RelayEntry
    ACCESS not-accessible
    STATUS mandatory
    DESCRIPTION
      "Entries"
    INDEX { cmcTcMasterCmc3RelaytableIndex }
    ::= { cmcTcMasterCmc3RelayTable 1 }

  CmcTcMasterCmc3RelayEntry ::=
    SEQUENCE {
      cmcTcMasterCmc3RelaytableIndex
        INTEGER,
      cmcTcMasterCmc3RelaytableText
	DisplayString (SIZE (0..31)),
      cmcTcMasterCmc3RelaytableStatus
        INTEGER              
    }

    cmcTcMasterCmc3RelaytableIndex OBJECT-TYPE
      SYNTAX INTEGER (1..32000)
      ACCESS read-only
      STATUS mandatory
      DESCRIPTION
        "Index for the relay-table. Its value ranges
         between 1 and cmcTcMasterCmc3RelaytableMaxNum"
      ::= { cmcTcMasterCmc3RelayEntry 1 }

    cmcTcMasterCmc3RelaytableText OBJECT-TYPE
      SYNTAX DisplayString (SIZE (0..31))
      ACCESS read-write
      STATUS mandatory
      DESCRIPTION
        "Description-Text for each relay in the table"
      ::= { cmcTcMasterCmc3RelayEntry 2 }

    cmcTcMasterCmc3RelaytableStatus OBJECT-TYPE
      SYNTAX INTEGER  {
        relayOFF(1),
        relayON(2),
        notAvail(3)
      }
      ACCESS read-write
      STATUS mandatory
      DESCRIPTION
        "Status of relays in the table"
      ::= { cmcTcMasterCmc3RelayEntry 3 }

--cmcTcMasterCmc3Setpoints-group

  cmcTcMasterCmc3SetpointFan1 OBJECT-TYPE
    SYNTAX INTEGER 
    ACCESS read-write
    STATUS mandatory
    DESCRIPTION
      "Setpoint Fan 1 in C, Fan 1 will start
       if temperature 1 exceeds this value"
    ::= { cmcTcMasterCmc3Setpoints 1 }

  cmcTcMasterCmc3SetpointFan2 OBJECT-TYPE
    SYNTAX INTEGER 
    ACCESS read-write
    STATUS mandatory
    DESCRIPTION
      "Setpoint Fan 2 in C, Fan 2 will start
       if temperature 2 exceeds this value"
    ::= { cmcTcMasterCmc3Setpoints 2 }

  cmcTcMasterCmc3SetpointHeating OBJECT-TYPE
    SYNTAX INTEGER 
    ACCESS read-write
    STATUS mandatory
    DESCRIPTION
      "Setpoint heating in C, heating will start
       if lowest value of temperature 1 and 2 falls below this value"
    ::= { cmcTcMasterCmc3Setpoints 3 }

  cmcTcMasterCmc3SetpointHighTemperature1 OBJECT-TYPE
    SYNTAX INTEGER 
    ACCESS read-write
    STATUS mandatory
    DESCRIPTION
      "Setpoint high value alarm temperature 1"
    ::= { cmcTcMasterCmc3Setpoints 4 }

  cmcTcMasterCmc3SetpointLowTemperature1 OBJECT-TYPE
    SYNTAX INTEGER 
    ACCESS read-write
    STATUS mandatory
    DESCRIPTION
      "Setpoint low value alarm temperature 1"
    ::= { cmcTcMasterCmc3Setpoints 5 }

  cmcTcMasterCmc3SetpointHighTemperature2 OBJECT-TYPE
    SYNTAX INTEGER 
    ACCESS read-write
    STATUS mandatory
    DESCRIPTION
      "Setpoint high value alarm temperature 2"
    ::= { cmcTcMasterCmc3Setpoints 6 }

  cmcTcMasterCmc3SetpointLowTemperature2 OBJECT-TYPE
    SYNTAX INTEGER 
    ACCESS read-write
    STATUS mandatory
    DESCRIPTION
      "Setpoint low value alarm temperature 2"
    ::= { cmcTcMasterCmc3Setpoints 7 }

  cmcTcMasterCmc3SetpointHighVoltage OBJECT-TYPE
    SYNTAX INTEGER 
    ACCESS read-write
    STATUS mandatory
    DESCRIPTION
      "Setpoint high value supply voltage alarm"
    ::= { cmcTcMasterCmc3Setpoints 8 }

  cmcTcMasterCmc3SetpointLowVoltage OBJECT-TYPE
    SYNTAX INTEGER
    ACCESS read-write
    STATUS mandatory
    DESCRIPTION
      "Setpoint low value supply voltage alarm"
    ::= { cmcTcMasterCmc3Setpoints 9 }

  cmcTcMasterCmc3SetpointLowAux1 OBJECT-TYPE
    SYNTAX INTEGER 
    ACCESS read-write
    STATUS mandatory
    DESCRIPTION
      "Setpoint low value Aux input 1 alarm"
    ::= { cmcTcMasterCmc3Setpoints 10 }

  cmcTcMasterCmc3SetpointHighAux1 OBJECT-TYPE
    SYNTAX INTEGER 
    ACCESS read-write
    STATUS mandatory
    DESCRIPTION
      "Setpoint high value Aux input 1 alarm"
    ::= { cmcTcMasterCmc3Setpoints 11 }

  cmcTcMasterCmc3SetpointLowAux2 OBJECT-TYPE
    SYNTAX INTEGER 
    ACCESS read-write
    STATUS mandatory
    DESCRIPTION
      "Setpoint low value Aux input 2 alarm"
    ::= { cmcTcMasterCmc3Setpoints 12 }

  cmcTcMasterCmc3SetpointHighAux2 OBJECT-TYPE
    SYNTAX INTEGER 
    ACCESS read-write
    STATUS mandatory
    DESCRIPTION
      "Setpoint high value Aux input alarm"
    ::= { cmcTcMasterCmc3Setpoints 13 }

--cmcTcMasterCmc3TrapControl-group

  cmcTcMasterCmc3SetTrapRepeat OBJECT-TYPE
    SYNTAX INTEGER {
      disableTrapRepeat(1),
      enableTrapRepeat(2)
    }
    ACCESS read-write
    STATUS mandatory
    DESCRIPTION
      "Enable/disable repeating of traps. If enabled, traps will
       be repeated after a repeat time, set in setTrapRepeatTime.
       Repeating can be stopped by setting setTrapQuit to quitTrap"
    ::= { cmcTcMasterCmc3TrapControl 1 }

  cmcTcMasterCmc3SetTrapRepeatTime OBJECT-TYPE
    SYNTAX INTEGER 
    ACCESS read-write
    STATUS mandatory
    DESCRIPTION
      "Time value (sec) for trap-repeating, if setTrapRepeat is enabled"
    ::= { cmcTcMasterCmc3TrapControl 2 }

  cmcTcMasterCmc3SetTrapQuit OBJECT-TYPE
    SYNTAX INTEGER {
      quitTrap(1),
      quitTrapOK(2),
      noTrapToQuit(3),
      trapToQuit(4)
    }
    ACCESS read-write
    STATUS mandatory
    DESCRIPTION
      "Quit trap to stop repeating."
    ::= { cmcTcMasterCmc3TrapControl 3 }

--cmcTcMasterCmc3TrapTable-group

  cmcTcMasterCmc3TraptableNumber OBJECT-TYPE
    SYNTAX INTEGER 
    ACCESS read-only
    STATUS mandatory
    DESCRIPTION
      "Number of trapTable entries. The number of trap-receiver"
    ::= { cmcTcMasterCmc3Traps 1 }

  cmcTcMasterCmc3TrapTable OBJECT-TYPE
    SYNTAX SEQUENCE OF CmcTcMasterCmc3TrapEntry
    ACCESS not-accessible
    STATUS mandatory
    DESCRIPTION
      "A list of trap-receiver entries"
    ::= { cmcTcMasterCmc3Traps 2 }

  cmcTcMasterCmc3TrapEntry OBJECT-TYPE
    SYNTAX CmcTcMasterCmc3TrapEntry
    ACCESS not-accessible
    STATUS mandatory
    DESCRIPTION
      "Entries of trapTable"
    INDEX { cmcTcMasterCmc3TrapIndex }
    ::= { cmcTcMasterCmc3TrapTable 1 }

  CmcTcMasterCmc3TrapEntry ::=
    SEQUENCE {
      cmcTcMasterCmc3TrapIndex
        INTEGER,
      cmcTcMasterCmc3TrapStatus
        INTEGER,
      cmcTcMasterCmc3TrapIPaddress
        DisplayString
    }

    cmcTcMasterCmc3TrapIndex OBJECT-TYPE
      SYNTAX INTEGER (1..32000)
      ACCESS read-only
      STATUS mandatory
      DESCRIPTION
        "Index for the trap-receiver-table. Its value ranges between
         1 and the value of cmcTcMasterCmc3TraptableNumber "
      ::= { cmcTcMasterCmc3TrapEntry 1 }

    cmcTcMasterCmc3TrapStatus OBJECT-TYPE
      SYNTAX INTEGER  {
        enabled(1),
        disabled(2)
      }
      ACCESS read-write
      STATUS mandatory
      DESCRIPTION
        "Enable or disable trap receiver"
      ::= { cmcTcMasterCmc3TrapEntry 2 }

    cmcTcMasterCmc3TrapIPaddress OBJECT-TYPE
      SYNTAX DisplayString (SIZE (0..31))
      ACCESS read-write
      STATUS mandatory
      DESCRIPTION
        "IP-address of trap-receiver"
      ::= { cmcTcMasterCmc3TrapEntry 3 }

--cmcTcMasterPcu3MibRev-group
          
  cmcTcMasterPcu3MibMajRev OBJECT-TYPE
    SYNTAX INTEGER (1..32000)
    ACCESS read-only
    STATUS mandatory
    DESCRIPTION
      "The Major Revision level.
       A change in the major revision level represents a major change
       in the architecture of the MIB. A change in the major revision 
       level may indicate a significant change in the information,
       correct interpretation of data may require a MIB document
       with the same major revision level."
    ::= { cmcTcMasterPcu3MibRev 1 }

  cmcTcMasterPcu3MibMinRev OBJECT-TYPE
    SYNTAX INTEGER (0..32000)
    ACCESS read-only
    STATUS mandatory
    DESCRIPTION
      "The Minor Revision level.
       A change in the minor revision level may represent some minor
       additional support, no changes to any pre-existing information
       has occurred."
    ::= { cmcTcMasterPcu3MibRev 2 }

  cmcTcMasterPcu3MibCondition OBJECT-TYPE
    SYNTAX INTEGER {
      other (1),
      ok (2),
      degraded (3),
      failed (4)
    }
    ACCESS read-only
    STATUS mandatory
    DESCRIPTION
      "The overall condition (status) of the system represented by
       this MIB. 
       (2) OK
       (3) a minor problem, warning condition (yellow LED on PCU)
       (4) a major problem (red LED on PCU)"
    ::= { cmcTcMasterPcu3MibRev 3 }

--cmcTcMasterPcu3Values-group

  cmcTcMasterPcu3ValueEnergy1 OBJECT-TYPE
    SYNTAX INTEGER 
    ACCESS read-only
    STATUS mandatory
    DESCRIPTION
      "Total value of the Energy (Wh), measured on IEC input 1"
    ::= { cmcTcMasterPcu3Values 1 }

  cmcTcMasterPcu3ValueEnergy2 OBJECT-TYPE
    SYNTAX INTEGER 
    ACCESS read-only
    STATUS mandatory
    DESCRIPTION
      "Actual value of the Energy (Wh), measured on IEC input 2"
    ::= { cmcTcMasterPcu3Values 2 }

  cmcTcMasterPcu3ValueEnergy1Time OBJECT-TYPE
    SYNTAX INTEGER 
    ACCESS read-only
    STATUS mandatory
    DESCRIPTION
      "Actual value of the Energy (Wh), measured on IEC input 1, can be set to 0
       Value can be used to calculate the energy over a fixed time"
    ::= { cmcTcMasterPcu3Values 3 }

  cmcTcMasterPcu3ValueEnergy2Time OBJECT-TYPE
    SYNTAX INTEGER 
    ACCESS read-only
    STATUS mandatory
    DESCRIPTION
      "Actual value of the Energy (Wh), measured on IEC input 2, can be set to 0.
       Value can be used to calculate the energy over a fixed time"
    ::= { cmcTcMasterPcu3Values 4 }

  cmcTcMasterPcu3ValuePower1 OBJECT-TYPE
    SYNTAX INTEGER 
    ACCESS read-only
    STATUS mandatory
    DESCRIPTION
      "Calculated actual power 1 (W). Calculated from cmcTcMasterPcu3ValueEnergy1/time"
    ::= { cmcTcMasterPcu3Values 5 }
          
  cmcTcMasterPcu3ValuePower2 OBJECT-TYPE
    SYNTAX INTEGER 
    ACCESS read-only
    STATUS mandatory
    DESCRIPTION
      "Calculated actual power 2 (W). Calculated from cmcTcMasterPcu3ValueEnergy2/time"
    ::= { cmcTcMasterPcu3Values 6 }
          
  cmcTcMasterPcu3ValueTemperature OBJECT-TYPE
    SYNTAX INTEGER 
    ACCESS read-only
    STATUS mandatory
    DESCRIPTION
      "Actual value of temperature 1 in deg C or deg F"
    ::= { cmcTcMasterPcu3Values 7 }
          
--cmcTcMasterPcu3Status-group

  cmcTcMasterPcu3StatusInput1 OBJECT-TYPE
    SYNTAX INTEGER {
      false(1),
      true(2),
      pending(3),
      notAvail(4)
    }
    ACCESS read-only
    STATUS mandatory
    DESCRIPTION
      "Status of digital Input 1
       (1) digital signal is true (contact closed if setup is NO)
       (2) digital signal is false(contact opened if setup is NO),
       note setup of input (NO/NC)
       (3) digital input is pending, note setup of delay"
    ::= { cmcTcMasterPcu3Status 1 }

  cmcTcMasterPcu3StatusInput2 OBJECT-TYPE
    SYNTAX INTEGER {
      false(1),
      true(2),
      pending(3),
      notAvail(4)
    }
    ACCESS read-only
    STATUS mandatory
    DESCRIPTION
      "Status of digital Input 2
       (1) digital signal is true (contact closed if setup is NO)
       (2) digital signal is false(contact opened if setup is NO),
       note setup of input (NO/NC)
       (3) digital input is pending, note setup of delay"
    ::= { cmcTcMasterPcu3Status 2 }

  cmcTcMasterPcu3StatusPower1 OBJECT-TYPE
    SYNTAX INTEGER {
      ok(1),
      tooHigh(2),
      tooLow(3),
      warning(4),
      error(5),
      notAvail(6)
    }
    ACCESS read-only
    STATUS mandatory
    DESCRIPTION
      "Status Power 1, see setpoints"
    ::= { cmcTcMasterPcu3Status 3 }

  cmcTcMasterPcu3StatusPower2 OBJECT-TYPE
    SYNTAX INTEGER {
      ok(1),
      tooHigh(2),
      tooLow(3),
      warning(4),
      error(5),
      notAvail(6)
    }
    ACCESS read-only
    STATUS mandatory
    DESCRIPTION
      "Status Power 2, see setpoints"
    ::= { cmcTcMasterPcu3Status 4 }

  cmcTcMasterPcu3StatusTemperature OBJECT-TYPE
    SYNTAX INTEGER {
      ok(1),
      tooHigh(2),
      tooLow(3),
      warning(4),
      error(5)
    }
    ACCESS read-only
    STATUS mandatory
    DESCRIPTION
      "Status temperature 1, OK/ too high/ too low
       (see setpoints of temperature 1)"
    ::= { cmcTcMasterPcu3Status 5 }

--cmcTcMasterPcu3Status-table-group

  cmcTcMasterPcu3OutletsNumber OBJECT-TYPE
    SYNTAX INTEGER 
    ACCESS read-only
    STATUS mandatory
    DESCRIPTION
      "Number of value-table entries=number of outlets available on this unit"
    ::= { cmcTcMasterPcu3StatusTable1 1 }

  cmcTcMasterPcu3StatusTable OBJECT-TYPE
    SYNTAX SEQUENCE OF CmcTcMasterPcu3StatusEntry
    ACCESS not-accessible
    STATUS mandatory
    DESCRIPTION
      "Headline of status-table"
    ::= { cmcTcMasterPcu3StatusTable1 2 }

  cmcTcMasterPcu3StatusEntry OBJECT-TYPE
    SYNTAX CmcTcMasterPcu3StatusEntry
    ACCESS not-accessible
    STATUS mandatory
    DESCRIPTION
      "Entries of status-table"
    INDEX { cmcTcMasterPcu3StatusIndex }
    ::= { cmcTcMasterPcu3StatusTable 1 }

    CmcTcMasterPcu3StatusEntry ::=
      SEQUENCE {
        cmcTcMasterPcu3StatusIndex
          INTEGER,
        cmcTcMasterPcu3StatusText
          DisplayString (SIZE (0..31)),                
        cmcTcMasterPcu3StatusStatus
          INTEGER,
        cmcTcMasterPcu3ControlSNMP
          INTEGER,
        cmcTcMasterPcu3FrontSwitch
          INTEGER,
        cmcTcMasterPcu3Delay
          INTEGER,
        cmcTcMasterPcu3Input1
          INTEGER,
        cmcTcMasterPcu3Input2
          INTEGER,
        cmcTcMasterPcu3Temperature
          INTEGER,          
        cmcTcMasterPcu3Power
          INTEGER,          
        cmcTcMasterPcu3RestoreOutputStatus
          INTEGER           
      }

    cmcTcMasterPcu3StatusIndex OBJECT-TYPE
      SYNTAX INTEGER (1..32000)
      ACCESS read-only
      STATUS mandatory
      DESCRIPTION
        "Index for the list of value entries. Its value ranges
         between 1 and the value of cmcTcMasterPcu3OutletsNumber."
      ::= { cmcTcMasterPcu3StatusEntry 1 }

    cmcTcMasterPcu3StatusText OBJECT-TYPE
      SYNTAX DisplayString (SIZE (0..31))
      ACCESS read-write
      STATUS mandatory
      DESCRIPTION
        "Descriptional text for each outlet (entry in the table)"
      ::= { cmcTcMasterPcu3StatusEntry 2 }
              
    cmcTcMasterPcu3StatusStatus OBJECT-TYPE
      SYNTAX INTEGER {
        ok(1),
        onFrontKey(2),
        offFrontKey(3),
        onWEB(4),
        offWEB(5),
        onInput1(6),
        offInput1(7),
        onInput2(8),
        offInput2(9),
        onTemp(10),
        offTemp(11),
        onSNMP(12),
        offSNMP(13),
        onTimer(14),
        offTimer(15),
        onDelay(16),
        onConsole(17),
        offConsole(18),
        onReboot(19), 
        offReboot(20),
        onPower(21),
        offPower(22)

      }
      ACCESS read-only
      STATUS mandatory
      DESCRIPTION
        "Actual status of the outlet"
      ::= { cmcTcMasterPcu3StatusEntry 3 }

    cmcTcMasterPcu3ControlSNMP OBJECT-TYPE
      SYNTAX INTEGER  {
        on(1),
        off(2)
      }
      ACCESS read-write
      STATUS mandatory
      DESCRIPTION
        "Control via SNMP"
      ::= { cmcTcMasterPcu3StatusEntry 4 }

    cmcTcMasterPcu3FrontSwitch OBJECT-TYPE
      SYNTAX INTEGER {
        disabled(1),
        enabled(2)
      }
      ACCESS read-write
      STATUS mandatory
      DESCRIPTION
        "Control via front switch"
      ::= { cmcTcMasterPcu3StatusEntry 5 }
 
    cmcTcMasterPcu3Delay OBJECT-TYPE
      SYNTAX INTEGER (0..300)
      ACCESS read-write
      STATUS mandatory
      DESCRIPTION
        "Value for delay time in seconds.
         Value>0: Output is switched off for this time (in sec)"
      ::= { cmcTcMasterPcu3StatusEntry 6 }

    cmcTcMasterPcu3Input1 OBJECT-TYPE
      SYNTAX INTEGER {
        disabled(1),
        switchOn(2),
        switchOff(3),
        switchOnOff(4)
      }
      ACCESS read-write
      STATUS mandatory
      DESCRIPTION
        "Control via digital input 1
         (1): disabled
         (2): output is switched on in case of input 1 alarm
         (3): output is switched off in case of input 1 alarm
         (4): output has same status as input 1"
      ::= { cmcTcMasterPcu3StatusEntry 7 }

    cmcTcMasterPcu3Input2 OBJECT-TYPE
      SYNTAX INTEGER {
        disabled(1),
        switchOn(2),
        switchOff(3),
        switchOnOff(4)
      }
      ACCESS read-write
      STATUS mandatory
      DESCRIPTION
        "Control via digital input 2
         (1): disabled
         (2): output is switched on in case of input 2 alarm
         (3): output is switched off in case of input 2 alarm
         (4): output has same status as input 2"             
      ::= { cmcTcMasterPcu3StatusEntry 8 }

    cmcTcMasterPcu3Temperature OBJECT-TYPE
      SYNTAX INTEGER {
        disabled(1),
        switchOffAlarm(2),
        switchOnAlarm(3),
        switchOffSetpoint(4),
        switchOnSetpoint(5)
      }
      ACCESS read-write
      STATUS mandatory
      DESCRIPTION
        "Control via temperature alarm or setpoint
         (1): disabled
         (2): output is switched off in case of temperature alarm
         (3): output is switched on in case of temperature alarm
         (4): output is switched off if temperature setpoint (cmcTcMasterPcu3SetpointTemperature)
              is reached
         (5): output is switched on if temperature setpoint (cmcTcMasterPcu3SetpointTemperature)
              is reached"
      ::= { cmcTcMasterPcu3StatusEntry 9 }   
    
    cmcTcMasterPcu3Power OBJECT-TYPE
      SYNTAX INTEGER {
        disabled(1),
        switchOffAlarm(2),
        switchOffWarning(3),
        switchOnAlarm(4),
        switchOnWarning(5)
      }
      ACCESS read-write
      STATUS mandatory
      DESCRIPTION
        "Control via power setpoint
         (1): disabled
         (2): output is switched off upon power high alarm (cmcTcMasterPcu3SetpointHighPower1)
         (3): output is switched off upon power warning (cmcTcMasterPcu3SetpointWarningPower1)
         (4): output is switched on upon power alarm (cmcTcMasterPcu3SetpointHigh(Low)Power1)
         (5): output is switched on upon power warning (cmcTcMasterPcu3SetpointWarningPower1)             "
      ::= { cmcTcMasterPcu3StatusEntry 10 }                

    cmcTcMasterPcu3RestoreOutputStatus OBJECT-TYPE
      SYNTAX INTEGER {
        disabled(1),
        enabled(2)
      }
      ACCESS read-write
      STATUS mandatory
      DESCRIPTION
        "Save last output status and switch output to this status after reboot"
      ::= { cmcTcMasterPcu3StatusEntry 11 }
                
--cmcTcMasterPcu3SetupGeneral-group

  cmcTcMasterPcu3SetTempUnit OBJECT-TYPE
    SYNTAX INTEGER {
      celsius(1),
      fahrenheit(2)
    }
    ACCESS read-write
    STATUS mandatory
    DESCRIPTION
      "Unit of all temperature values and setpoints, Celsius or Fahrenheit"
    ::= { cmcTcMasterPcu3SetupGeneral 1 }

  cmcTcMasterPcu3SetBeeper OBJECT-TYPE
    SYNTAX INTEGER {
      off(1),
      on(2),
      enableClear(3)
    }
    ACCESS read-write
    STATUS mandatory
    DESCRIPTION
      "Audible alarm in PCU unit:
       (1): beeper is off (general)
       (2): beeper is on (Alarm)
       (3): enable Clear (cmcTcMasterPcu3ClearAlarm)"
    ::= { cmcTcMasterPcu3SetupGeneral 2 }

  cmcTcMasterPcu3LogicRelay OBJECT-TYPE
    SYNTAX INTEGER {
      closeAtAlarm(1),
      openAtAlarm(2),
      off(3),
      enableRemote(4)
    }
    ACCESS read-write
    STATUS mandatory
    DESCRIPTION
      "Logic of alarm relay: 
       (1): Relay will pick up in case of an alarm
       (2): Relay will release in case of an alarm
       (3): Relay off (general)
       (4): enable remote relay control (SNMP set)"
    ::= { cmcTcMasterPcu3SetupGeneral 3 }
 
  cmcTcMasterPcu3ClearRelay OBJECT-TYPE
    SYNTAX INTEGER {
      disabled(1),
      enabled(2)
    }
    ACCESS read-write
    STATUS mandatory
    DESCRIPTION
      "Enable clear of alarm relay: 
       (1): Relay cannot be cleared by cmcTcMasterPcu3ClearAlarm
       (2): Relay can be cleared by cmcTcMasterPcu3ClearAlarm"
    ::= { cmcTcMasterPcu3SetupGeneral 4 }                  

  cmcTcMasterPcu3WebAccess OBJECT-TYPE
    SYNTAX INTEGER {
      viewOnly(1),
      fullAccess(2),
      off(3)
    }
    ACCESS read-write
    STATUS mandatory
    DESCRIPTION
      "Web access via HTTP: 
       (1): view only
       (2): full Access, read and set
       (3): Web disabled (general)"
    ::= { cmcTcMasterPcu3SetupGeneral 5 }
 
  cmcTcMasterPcu3SetupDate OBJECT-TYPE
    SYNTAX DisplayString (SIZE (0..10))
    ACCESS read-write
    STATUS mandatory
    DESCRIPTION
      "actual Date in format DD.MM.YYYY"
    ::= { cmcTcMasterPcu3SetupGeneral 6 }

  cmcTcMasterPcu3SetupTime OBJECT-TYPE
    SYNTAX DisplayString (SIZE (0..8))
    ACCESS read-write
    STATUS mandatory
    DESCRIPTION
      "actual Time in format HH:MM:SS, HH (0-23), MM (0-59), SS (0-59)"
    ::= { cmcTcMasterPcu3SetupGeneral 7 }

--cmcTcMasterPcu3TimerTable1-group
 
  cmcTcMasterPcu3TimerNumber OBJECT-TYPE
    SYNTAX INTEGER 
    ACCESS read-only
    STATUS mandatory
    DESCRIPTION
      "Number of timers available on this unit"
    ::= { cmcTcMasterPcu3TimerTable1 1 }

  cmcTcMasterPcu3TimerTable OBJECT-TYPE
    SYNTAX SEQUENCE OF CmcTcMasterPcu3TimerEntry
    ACCESS not-accessible
    STATUS mandatory
    DESCRIPTION
      "Headline of timer-table"
    ::= { cmcTcMasterPcu3TimerTable1 2 }

  cmcTcMasterPcu3TimerEntry OBJECT-TYPE
    SYNTAX CmcTcMasterPcu3TimerEntry
    ACCESS not-accessible
    STATUS mandatory
    DESCRIPTION
      "Entries of timer-table"
    INDEX { cmcTcMasterPcu3TimerIndex }
    ::= { cmcTcMasterPcu3TimerTable 1 }

    CmcTcMasterPcu3TimerEntry ::=
      SEQUENCE {
        cmcTcMasterPcu3TimerIndex
          INTEGER,
        cmcTcMasterPcu3TimerStatus
          INTEGER,
        cmcTcMasterPcu3TimerDayOfWeek
          INTEGER,  
        cmcTcMasterPcu3TimeOn 
          DisplayString (SIZE (0..5)),                              
        cmcTcMasterPcu3TimeOff 
          DisplayString (SIZE (0..5)),                              
        cmcTcMasterPcu3TimeControl
          INTEGER,
        cmcTcMasterPcu3TimerOutput1
          INTEGER,
        cmcTcMasterPcu3TimerOutput2
          INTEGER         
      }

    cmcTcMasterPcu3TimerIndex OBJECT-TYPE
      SYNTAX INTEGER (1..32000)
      ACCESS read-only
      STATUS mandatory
      DESCRIPTION
        "Index for the list of timer entries. Its value ranges
         between 1 and the value of cmcTcMasterPcu3TimerNumber." 
      ::= { cmcTcMasterPcu3TimerEntry 1 }

    cmcTcMasterPcu3TimerStatus OBJECT-TYPE
      SYNTAX INTEGER {
        switchedOff(1),
        switchedOn(2),
        noTime(3) 
      }
      ACCESS read-only
      STATUS mandatory
      DESCRIPTION
        "Actual status of the timer"
      ::= { cmcTcMasterPcu3TimerEntry 2 }

    cmcTcMasterPcu3TimerDayOfWeek OBJECT-TYPE
      SYNTAX INTEGER {
        sun(1),
        mon(2),
        tue(3) ,
        wed(4),
        thu(5),
        fre(6),
        sat(7),
        sat-sun(8),
        mo-fr(9),
        mo-su(10)
      }
      ACCESS read-write
      STATUS mandatory
      DESCRIPTION
        "Day when the timer is active"
      ::= { cmcTcMasterPcu3TimerEntry 3 }
             
    cmcTcMasterPcu3TimeOn OBJECT-TYPE
      SYNTAX DisplayString (SIZE (0..5))
      ACCESS read-write
      STATUS mandatory
      DESCRIPTION
        "Time to switch on current outlet, 
         Format: HH:MM"
      ::= { cmcTcMasterPcu3TimerEntry 4 }

    cmcTcMasterPcu3TimeOff OBJECT-TYPE
      SYNTAX DisplayString (SIZE (0..5))
      ACCESS read-write
      STATUS mandatory
      DESCRIPTION
        "Time to switch off current outlet,
         Format: HH:MM"
      ::= { cmcTcMasterPcu3TimerEntry 5 }

    cmcTcMasterPcu3TimeControl OBJECT-TYPE
      SYNTAX INTEGER {
        disabled(1),
        enabled(2)
      }
      ACCESS read-write
      STATUS mandatory
      DESCRIPTION
        "Control via RTC"
      ::= { cmcTcMasterPcu3TimerEntry 6 }

    cmcTcMasterPcu3TimerOutput1 OBJECT-TYPE
      SYNTAX INTEGER 
      ACCESS read-write
      STATUS mandatory
      DESCRIPTION
        "Output which is controlled via timer"
      ::= { cmcTcMasterPcu3TimerEntry 7 }

    cmcTcMasterPcu3TimerOutput2 OBJECT-TYPE
      SYNTAX INTEGER 
      ACCESS read-write
      STATUS mandatory
      DESCRIPTION
        "Output which is controlled via timer"
      ::= { cmcTcMasterPcu3TimerEntry 8 }

--cmcTcMasterPcu3SetupPower1-group                     

  cmcTcMasterPcu3SetupPower1Avail OBJECT-TYPE
    SYNTAX INTEGER {
      notAvailable(1),
      available(2)
    }
    ACCESS read-write
    STATUS mandatory
    DESCRIPTION
      "Energy sensor 1 sensor:   
       (1) not available
       (2) available"
    ::= { cmcTcMasterPcu3SetupPower1 1 }

  cmcTcMasterPcu3SetupPower1Relay OBJECT-TYPE
    SYNTAX INTEGER {
      disabled(1),
      enabled(2)
    }
    ACCESS read-write
    STATUS mandatory
    DESCRIPTION
      "Alert handling of Alarm Relay in case of an alarm condition
       of Power 1:  
       (1) no switching of Relays
       (2) Relay will switch"
    ::= { cmcTcMasterPcu3SetupPower1 2 }

  cmcTcMasterPcu3SetupPower1Beeper OBJECT-TYPE
    SYNTAX INTEGER {
      disabled(1),
      enabled(2)
    }
    ACCESS read-write
    STATUS mandatory
    DESCRIPTION
      "Alert handling of beeper of in case of an alarm condition
       of Power 1: 
       (1) No Audible Alarm
       (2) Start Audible Alarm"
    ::= { cmcTcMasterPcu3SetupPower1 3 }

--cmcTcMasterPcu3SetupPower2-group                     

  cmcTcMasterPcu3SetupPower2Avail OBJECT-TYPE
    SYNTAX INTEGER {
      notAvailable(1),
      available(2)
    }
    ACCESS read-write
    STATUS mandatory
    DESCRIPTION
      "Energy sensor 2:   
       (1) not available
       (2) available"
    ::= { cmcTcMasterPcu3SetupPower2 1 }

  cmcTcMasterPcu3SetupPower2Relay OBJECT-TYPE
    SYNTAX INTEGER {
      disabled(1),
      enabled(2)
    }
    ACCESS read-write
    STATUS mandatory
    DESCRIPTION
      "Alert handling of Alarm Relay in case of an alarm condition
       of Power 2:  
       (1) no switching of Relay
       (2) Relay will switch"
    ::= { cmcTcMasterPcu3SetupPower2 2 }

  cmcTcMasterPcu3SetupPower2Beeper OBJECT-TYPE
    SYNTAX INTEGER {
      disabled(1),
      enabled(2)
    }
    ACCESS read-write
    STATUS mandatory
    DESCRIPTION
      "Alert handling of beeper of in case of an alarm condition
       of Power 2: 
       (1) No Audible Alarm
       (2) Start Audible Alarm"
    ::= { cmcTcMasterPcu3SetupPower2 3 }

--cmcTcMasterPcu3SetupInput1-group

  cmcTcMasterPcu3SetupInput1Avail OBJECT-TYPE
    SYNTAX INTEGER {
      notAvailable(1),
      available(2)
    }
    ACCESS read-write
    STATUS mandatory
    DESCRIPTION
      "Input 1 sensor:   
       (1) not available
       (2) available"
    ::= { cmcTcMasterPcu3SetupInput1 1 }

  cmcTcMasterPcu3SetupInput1Relay OBJECT-TYPE
    SYNTAX INTEGER {
      disabled(1),
      enabled(2)
    }
    ACCESS read-write
    STATUS mandatory
    DESCRIPTION
      "Alert handling of Alarm Relay in case of an alarm condition
       of Input 1:  
       (1) no switching of Relay
       (2) Relay will switch"
    ::= { cmcTcMasterPcu3SetupInput1 2 }

  cmcTcMasterPcu3SetupInput1Beeper OBJECT-TYPE
    SYNTAX INTEGER {
      disabled(1),
      enabled(2)
    }
    ACCESS read-write
    STATUS mandatory
    DESCRIPTION
      "Alert handling of beeper of in case of an alarm condition
       of Input 1: 
       (1) No Audible Alarm
       (2) Start Audible Alarm"
    ::= { cmcTcMasterPcu3SetupInput1 3 }

  cmcTcMasterPcu3SetupInput1Contact OBJECT-TYPE
    SYNTAX INTEGER {
      contactNO(1),
      contactNC(2),
      notAvail(3)
    }
    ACCESS read-write
    STATUS mandatory
    DESCRIPTION
      "Setup of digital input 1"
    ::= { cmcTcMasterPcu3SetupInput1 4 }

  cmcTcMasterPcu3SetupInput1Delay OBJECT-TYPE
    SYNTAX INTEGER (0..60)
    ACCESS read-write
    STATUS mandatory
    DESCRIPTION
      "Delay for changing of input state"
    ::= { cmcTcMasterPcu3SetupInput1 5 }

--cmcTcMasterPcu3SetupInput2-group

  cmcTcMasterPcu3SetupInput2Avail OBJECT-TYPE
    SYNTAX INTEGER {
      notAvailable(1),
      available(2)
    }
    ACCESS read-write
    STATUS mandatory
    DESCRIPTION
      "Input 2 sensor:   
       (2) available
       (1) not available"
    ::= { cmcTcMasterPcu3SetupInput2 1 }

  cmcTcMasterPcu3SetupInput2Relay OBJECT-TYPE
    SYNTAX INTEGER {
      disabled(1),
      enabled(2)
    }
    ACCESS read-write
    STATUS mandatory
    DESCRIPTION
      "Alert handling of Alarm Relay in case of an alarm condition
       of Input 1:  
       (1) no switching of Relays
       (2) Relay will switch"
    ::= { cmcTcMasterPcu3SetupInput2 2 }

  cmcTcMasterPcu3SetupInput2Beeper OBJECT-TYPE
    SYNTAX INTEGER {
      disabled(1),
      enabled(2)
    }
    ACCESS read-write
    STATUS mandatory
    DESCRIPTION
      "Alert handling of beeper of in case of an alarm condition
       of Input 2: 
       (1) No Audible Alarm
       (2) Start Audible Alarm"
    ::= { cmcTcMasterPcu3SetupInput2 3 }

  cmcTcMasterPcu3SetupInput2Contact OBJECT-TYPE
    SYNTAX INTEGER {
      contactNO(1),
      contactNC(2),
      notAvail(3)
    }
    ACCESS read-write
    STATUS mandatory
    DESCRIPTION
      "Setup of digital input 2"
    ::= { cmcTcMasterPcu3SetupInput2 4 }

  cmcTcMasterPcu3SetupInput2Delay OBJECT-TYPE
    SYNTAX INTEGER (0..60)
    ACCESS read-write
    STATUS mandatory
    DESCRIPTION
      "Delay for changing of input state"
    ::= { cmcTcMasterPcu3SetupInput2 5 }

--cmcTcMasterPcu3SetupTemperature-group                     

  cmcTcMasterPcu3SetupTemperatureAvail OBJECT-TYPE
    SYNTAX INTEGER {
      notAvailable(1),
      available(2)
    }
    ACCESS read-write
    STATUS mandatory
    DESCRIPTION
      "Temp sensor 1:   
       (1) not available
       (2) available"
    ::= { cmcTcMasterPcu3SetupTemperature 1 }

  cmcTcMasterPcu3SetupTemperatureRelay OBJECT-TYPE
    SYNTAX INTEGER {
      disabled(1),
      enabled(2)
    }
    ACCESS read-write
    STATUS mandatory
    DESCRIPTION
      "Alert handling of Alarm Relay in case of an alarm condition
       of Temperature:  
       (1) no switching of Relays
       (2) Relay will switch"
    ::= { cmcTcMasterPcu3SetupTemperature 2 }

  cmcTcMasterPcu3SetupTemperatureBeeper OBJECT-TYPE
    SYNTAX INTEGER {
      disabled(1),
      enabled(2)
    }
    ACCESS read-write
    STATUS mandatory
    DESCRIPTION
      "Alert handling of beeper of in case of an alarm condition
       of Temperature: 
       (1) No Audible Alarm
       (2) Start Audible Alarm"
    ::= { cmcTcMasterPcu3SetupTemperature 3 }

--cmcTcMasterPcu3SetupGeneral-group

  cmcTcMasterPcu3SetMessage OBJECT-TYPE
    SYNTAX DisplayString (SIZE (0..31))
    ACCESS read-write
    STATUS mandatory
    DESCRIPTION
      "Set message"
    ::= { cmcTcMasterPcu3SetupDevice 1 }

--cmcTcMasterPcu3Setpoints-group

  cmcTcMasterPcu3SetpointHighPower1 OBJECT-TYPE
    SYNTAX INTEGER 
    ACCESS read-write
    STATUS mandatory
    DESCRIPTION
      "Setpoint high value power consumption 1 alarm"
    ::= { cmcTcMasterPcu3Setpoints 1 }

  cmcTcMasterPcu3SetpointWarningPower1 OBJECT-TYPE
    SYNTAX INTEGER 
    ACCESS read-write
    STATUS mandatory
    DESCRIPTION
      "Setpoint warning value power consumption 1 alarm"
    ::= { cmcTcMasterPcu3Setpoints 2 }

  cmcTcMasterPcu3SetpointLowPower1 OBJECT-TYPE
    SYNTAX INTEGER
    ACCESS read-write
    STATUS mandatory
    DESCRIPTION
      "Setpoint low value power consumption 1 alarm"
    ::= { cmcTcMasterPcu3Setpoints 3 }

  cmcTcMasterPcu3SetpointHighPower2 OBJECT-TYPE
    SYNTAX INTEGER 
    ACCESS read-write
    STATUS mandatory
    DESCRIPTION
      "Setpoint high value power consumption 2 alarm"
    ::= { cmcTcMasterPcu3Setpoints 4 }

  cmcTcMasterPcu3SetpointWarningPower2 OBJECT-TYPE
    SYNTAX INTEGER 
    ACCESS read-write
    STATUS mandatory
    DESCRIPTION
      "Setpoint warning value power consumption 2 alarm"
    ::= { cmcTcMasterPcu3Setpoints 5 }

  cmcTcMasterPcu3SetpointLowPower2 OBJECT-TYPE
    SYNTAX INTEGER
    ACCESS read-write
    STATUS mandatory
    DESCRIPTION
      "Setpoint low value power consumption 2 alarm"
    ::= { cmcTcMasterPcu3Setpoints 6 }

  cmcTcMasterPcu3SetpointHighTemperature OBJECT-TYPE
    SYNTAX INTEGER (0..200)
    ACCESS read-write
    STATUS mandatory
    DESCRIPTION
      "Setpoint high value alarm temperature "
    ::= { cmcTcMasterPcu3Setpoints 7 }

  cmcTcMasterPcu3SetpointLowTemperature OBJECT-TYPE
    SYNTAX INTEGER (0..50)
    ACCESS read-write
    STATUS mandatory
    DESCRIPTION
      "Setpoint low value alarm temperature "
    ::= { cmcTcMasterPcu3Setpoints 8 }
 
  cmcTcMasterPcu3SetpointTemperature OBJECT-TYPE
    SYNTAX INTEGER (0..200)
    ACCESS read-write
    STATUS mandatory
    DESCRIPTION
      "Setpoint temperature for outlet control 
       and temperature warning"
    ::= { cmcTcMasterPcu3Setpoints 9 }

  cmcTcMasterPcu3SetpointTemperatureHyst OBJECT-TYPE
    SYNTAX INTEGER (0..15)
    ACCESS read-write
    STATUS mandatory
    DESCRIPTION
      "Hysteresis for cmcTcMasterPcu3SetpointTemperature"
    ::= { cmcTcMasterPcu3Setpoints 10 }
 
--cmcTcMasterPcu3Control-group

  cmcTcMasterPcu3ResetEnergy1 OBJECT-TYPE
    SYNTAX INTEGER {
      noReset(1),
      reset(2)
    }
    ACCESS read-write
    STATUS mandatory
    DESCRIPTION
      "Reset value of cmcTcMasterPcu3ValueEnergy1Time"
    ::= { cmcTcMasterPcu3Control 1 }

  cmcTcMasterPcu3ResetEnergy2 OBJECT-TYPE
    SYNTAX INTEGER {
      noReset(1),
      reset(2)
    }
    ACCESS read-write
    STATUS mandatory
    DESCRIPTION
      "Reset value of cmcTcMasterPcu3ValueEnergy2Time"
    ::= { cmcTcMasterPcu3Control 2 }

  cmcTcMasterPcu3ControlAlarmRelay OBJECT-TYPE
    SYNTAX INTEGER {
      relayOff(1),
      relayOn(2)
    }
    ACCESS read-write
    STATUS mandatory
    DESCRIPTION
      "Control of Alarm relay"
    ::= { cmcTcMasterPcu3Control 3 }

  cmcTcMasterPcu3ClearAlarm OBJECT-TYPE
    SYNTAX INTEGER {
      noClear(1),
      clear(2)
    }
    ACCESS read-write
    STATUS mandatory
    DESCRIPTION
      "Clear alarm, beeper and relay"
    ::= { cmcTcMasterPcu3Control 4 }

--cmcTcMasterPcu3TrapTable-group

  cmcTcMasterPcu3TrapTableNumber OBJECT-TYPE
    SYNTAX INTEGER 
    ACCESS read-only
    STATUS mandatory
    DESCRIPTION
      "Number of cmcTcMasterPcu3TrapTable entries. The number of trap-receivers avail."
    ::= { cmcTcMasterPcu3Traps 1 }

  cmcTcMasterPcu3TrapTable OBJECT-TYPE
    SYNTAX SEQUENCE OF CmcTcMasterPcu3TrapEntry
    ACCESS not-accessible
    STATUS mandatory
    DESCRIPTION
      "A list of trap-receiver entries"
    ::= { cmcTcMasterPcu3Traps 2 }

  cmcTcMasterPcu3TrapEntry OBJECT-TYPE
    SYNTAX CmcTcMasterPcu3TrapEntry
    ACCESS not-accessible
    STATUS mandatory
    DESCRIPTION
      "Entries of cmcTcMasterPcu3TrapTable"
    INDEX { cmcTcMasterPcu3TrapIndex }
    ::= { cmcTcMasterPcu3TrapTable 1 }

    CmcTcMasterPcu3TrapEntry ::=
      SEQUENCE {
        cmcTcMasterPcu3TrapIndex
          INTEGER,
        cmcTcMasterPcu3TrapStatus
          INTEGER,
        cmcTcMasterPcu3TrapIPaddress
          DisplayString
      }

    cmcTcMasterPcu3TrapIndex OBJECT-TYPE
      SYNTAX INTEGER (1..32000)
      ACCESS read-only
      STATUS mandatory
      DESCRIPTION
        "Index for the trap-receiver-table. Its value ranges between
         1 and the value of cmcTcMasterPcu3TrapTableNumber "
      ::= { cmcTcMasterPcu3TrapEntry 1 }

    cmcTcMasterPcu3TrapStatus OBJECT-TYPE
      SYNTAX INTEGER {
        disabled(1),
        enabled(2)
      }
      ACCESS read-write
      STATUS mandatory
      DESCRIPTION
        "Enable or disable trap receiver"
      ::= { cmcTcMasterPcu3TrapEntry 2 }

    cmcTcMasterPcu3TrapIPaddress OBJECT-TYPE
      SYNTAX DisplayString (SIZE (0..15))
      ACCESS read-write
      STATUS mandatory
      DESCRIPTION
        "IP-address of trap-receiver"
      ::= { cmcTcMasterPcu3TrapEntry 3 }

--cmcTcMasterTc3MibRev-group
          
  cmcTcMasterTc3MibMajRev OBJECT-TYPE
    SYNTAX INTEGER (1..32000)
    ACCESS read-only
    STATUS mandatory
    DESCRIPTION
      "The Major Revision level.
       A change in the major revision level represents a major change
       in the architecture of the MIB. A change in the major revision 
       level may indicate a significant change in the information,
       correct interpretation of data may require a MIB document
       with the same major revision level."
    ::= { cmcTcMasterTc3MibRev 1 }

  cmcTcMasterTc3MibMinRev OBJECT-TYPE
    SYNTAX INTEGER (0..32000)
    ACCESS read-only
    STATUS mandatory
    DESCRIPTION
      "The Minor Revision level.
       A change in the minor revision level may represent some minor
       additional support, no changes to any pre-existing information
       has occurred."
    ::= { cmcTcMasterTc3MibRev 2 }

  cmcTcMasterTc3MibCondition OBJECT-TYPE
    SYNTAX INTEGER {
      other (1),
      ok (2),
      degraded (3),
      failed (4),
      configChanged (5)
    }
    ACCESS read-only
    STATUS mandatory
    DESCRIPTION
      "The overall condition (status) of the system represented by
       this MIB. 
       (2) OK
       (3) a minor problem, warning condition (yellow LED on CMC-TC)
       (4) a major problem (red LED on CMC-TC)
       (5) configuration of sensor units changed or
           unit detected (red/yellow/green LED on CMC-TC)"
    ::= { cmcTcMasterTc3MibRev 3 }
          
--cmcTcMasterTc3Status-group

  cmcTcMasterTc3StatusDeviceCMC OBJECT-TYPE
    SYNTAX INTEGER {
      failed(1),
      ok(2)
    }
    ACCESS read-only
    STATUS mandatory
    DESCRIPTION
      "General Status of CMC-TC unit itself
       (1) failed
       (2) OK"
    ::= { cmcTcMasterTc3Status 1 }

  cmcTcMasterTc3UnitsConnected OBJECT-TYPE
    SYNTAX INTEGER 
    ACCESS read-only
    STATUS mandatory
    DESCRIPTION
      "Number of sensor units connected to the CMC-TC, Port 1 to 4"
    ::= { cmcTcMasterTc3Status 2 }

--unit 1

  cmcTcMasterTc3Unit1TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 1"
    ::= { cmcTcMasterTc3StatusSensorUnit1 1 }

  cmcTcMasterTc3Unit1Text OBJECT-TYPE
    SYNTAX DisplayString (SIZE (0..10))
    ACCESS read-write
    STATUS mandatory
    DESCRIPTION
      "Descriptional text for sensor unit connected to port 1"
    ::= { cmcTcMasterTc3StatusSensorUnit1 2 }

  cmcTcMasterTc3Unit1Serial OBJECT-TYPE
    SYNTAX INTEGER 
    ACCESS read-only
    STATUS mandatory
    DESCRIPTION
      "Serialnumber of sensor unit connected to port 1"
    ::= { cmcTcMasterTc3StatusSensorUnit1 3 }

  cmcTcMasterTc3Unit1Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 1
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc3StatusSensorUnit1 4 }

-- Sensors
              
  cmcTcMasterTc3Unit1NumberOfSensors OBJECT-TYPE
    SYNTAX INTEGER 
    ACCESS read-only
    STATUS mandatory
    DESCRIPTION
      "Number of sensors connected to sensor unit 1"
    ::= { cmcTcMasterTc3StatusUnit1Sensors 1 }

-- table with entry for each sensor available on this unit              

  cmcTcMasterTc3Unit1SensorTable OBJECT-TYPE
    SYNTAX SEQUENCE OF CmcTcMasterTc3Unit1SensorEntry
    ACCESS not-accessible
    STATUS mandatory
    DESCRIPTION
      "Headline of sensor table"
    ::= { cmcTcMasterTc3StatusUnit1Sensors 2 }

  cmcTcMasterTc3Unit1SensorEntry OBJECT-TYPE
    SYNTAX CmcTcMasterTc3Unit1SensorEntry
    ACCESS not-accessible
    STATUS mandatory
    DESCRIPTION
      "Entries of sensor table"
    INDEX { cmcTcMasterTc3Unit1SensorIndex }
    ::= { cmcTcMasterTc3Unit1SensorTable 1 }

    CmcTcMasterTc3Unit1SensorEntry ::=
      SEQUENCE {
        cmcTcMasterTc3Unit1SensorIndex
          INTEGER,
        cmcTcMasterTc3Unit1SensorType
          INTEGER,
        cmcTcMasterTc3Unit1SensorText
          DisplayString (SIZE (0..20)),                
        cmcTcMasterTc3Unit1SensorStatus
          INTEGER,
        cmcTcMasterTc3Unit1SensorValue
          INTEGER,
        cmcTcMasterTc3Unit1SensorSetHigh
          INTEGER,
        cmcTcMasterTc3Unit1SensorSetLow
          INTEGER,
        cmcTcMasterTc3Unit1SensorSetWarn
          INTEGER                
      }

    cmcTcMasterTc3Unit1SensorIndex OBJECT-TYPE
      SYNTAX INTEGER (1..32000)
      ACCESS read-only
      STATUS mandatory
      DESCRIPTION
        "Index for the list of value entries. Its value ranges
         between 1 and the value of cmcTcMasterTc3Unit1NumberOfSensors." 
      ::= { cmcTcMasterTc3Unit1SensorEntry 1 }

    cmcTcMasterTc3Unit1SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 1 to sensor[cmcTcMasterTc3Unit1SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc3Unit1SensorEntry 2 }

    cmcTcMasterTc3Unit1SensorText OBJECT-TYPE
      SYNTAX DisplayString (SIZE (0..20))
      ACCESS read-write
      STATUS mandatory
      DESCRIPTION
        "Descriptional text for each sensor (entry in the table)"
      ::= { cmcTcMasterTc3Unit1SensorEntry 3 }
              
    cmcTcMasterTc3Unit1SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc3Unit1SensorEntry 4 }

    cmcTcMasterTc3Unit1SensorValue OBJECT-TYPE
      SYNTAX INTEGER 
      ACCESS read-only
      STATUS mandatory
      DESCRIPTION
        "Value of sensor"
      ::= { cmcTcMasterTc3Unit1SensorEntry 5 }

    cmcTcMasterTc3Unit1SensorSetHigh OBJECT-TYPE
      SYNTAX INTEGER (0..300) 
      ACCESS read-write
      STATUS mandatory
      DESCRIPTION
        "Value for high setpoint of sensor"
      ::= { cmcTcMasterTc3Unit1SensorEntry 6 }

    cmcTcMasterTc3Unit1SensorSetLow OBJECT-TYPE
      SYNTAX INTEGER (0..300) 
      ACCESS read-write
      STATUS mandatory
      DESCRIPTION
        "Value for low setpoint of sensor,
         also used as alarm delay"
      ::= { cmcTcMasterTc3Unit1SensorEntry 7 }

    cmcTcMasterTc3Unit1SensorSetWarn OBJECT-TYPE
      SYNTAX INTEGER (0..300) 
      ACCESS read-write
      STATUS mandatory
      DESCRIPTION
        "Value for warning setpoint of sensor, 
         also used as fan threshold"
      ::= { cmcTcMasterTc3Unit1SensorEntry 8 }
                
-- Outputs              

  cmcTcMasterTc3Unit1NumberOfOutputs OBJECT-TYPE
    SYNTAX INTEGER 
    ACCESS read-only
    STATUS mandatory
    DESCRIPTION
      "Number of outputs available on sensor unit 1"
    ::= { cmcTcMasterTc3StatusUnit1Outputs 1 }

-- table with entry for each output available on this unit              
                
  cmcTcMasterTc3Unit1OutputTable OBJECT-TYPE
    SYNTAX SEQUENCE OF CmcTcMasterTc3Unit1OutputEntry
    ACCESS not-accessible
    STATUS mandatory
    DESCRIPTION
      "Headline of output table"
    ::= { cmcTcMasterTc3StatusUnit1Outputs 2 }

  cmcTcMasterTc3Unit1OutputEntry OBJECT-TYPE
    SYNTAX CmcTcMasterTc3Unit1OutputEntry
    ACCESS not-accessible
    STATUS mandatory
    DESCRIPTION
      "Entries of output table"
    INDEX { cmcTcMasterTc3Unit1OutputIndex }
    ::= { cmcTcMasterTc3Unit1OutputTable 1 }

    CmcTcMasterTc3Unit1OutputEntry ::=
      SEQUENCE {
        cmcTcMasterTc3Unit1OutputIndex
          INTEGER,
        cmcTcMasterTc3Unit1OutputType
          INTEGER,
        cmcTcMasterTc3Unit1OutputText
          DisplayString (SIZE (0..20)),                
        cmcTcMasterTc3Unit1OutputStatus
          INTEGER,
        cmcTcMasterTc3Unit1OutputValue
          INTEGER,
        cmcTcMasterTc3Unit1OutputSet
          INTEGER,
        cmcTcMasterTc3Unit1OutputConfig
          INTEGER,                
        cmcTcMasterTc3Unit1OutputDelay
          INTEGER,
        cmcTcMasterTc3Unit1OutputTimeoutAction
          INTEGER
      }

    cmcTcMasterTc3Unit1OutputIndex OBJECT-TYPE
      SYNTAX INTEGER (1..32000)
      ACCESS read-only
      STATUS mandatory
      DESCRIPTION
        "Index for the list of output entries. Its value ranges
         between 1 and the value of cmcTcMasterTc3Unit1NumberOfOutputs." 
      ::= { cmcTcMasterTc3Unit1OutputEntry 1 }

    cmcTcMasterTc3Unit1OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 1 to output[cmcTcMasterTc3Unit1OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc3Unit1OutputEntry 2 }

    cmcTcMasterTc3Unit1OutputText OBJECT-TYPE
      SYNTAX DisplayString (SIZE (0..20))
      ACCESS read-write
      STATUS mandatory
      DESCRIPTION
        "Descriptional text for each output (entry in the table)"
      ::= { cmcTcMasterTc3Unit1OutputEntry 3 }
              
    cmcTcMasterTc3Unit1OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc3Unit1OutputEntry 4 }

    cmcTcMasterTc3Unit1OutputValue OBJECT-TYPE
      SYNTAX INTEGER (-32000..32000) 
      ACCESS read-write
      STATUS mandatory
      DESCRIPTION
        "Value for output"
      ::= { cmcTcMasterTc3Unit1OutputEntry 5 }

    cmcTcMasterTc3Unit1OutputSet OBJECT-TYPE
      SYNTAX INTEGER {
        off (1),
        on (2),
        lock (3),
        unlock (4),
        unlockDelay (5)
      }
      ACCESS read-write
      STATUS mandatory
      DESCRIPTION
        "Command for output"
      ::= { cmcTcMasterTc3Unit1OutputEntry 6 }

    cmcTcMasterTc3Unit1OutputConfig OBJECT-TYPE
      SYNTAX INTEGER {
        disRemote (1),
        enRemote (2)
      }
      ACCESS read-write
      STATUS mandatory
      DESCRIPTION
        "Configuration for output
         1: 	disable remote control (e.g. keypad)
         2: 	enable remote control"
      ::= { cmcTcMasterTc3Unit1OutputEntry 7 }

    cmcTcMasterTc3Unit1OutputDelay OBJECT-TYPE
      SYNTAX INTEGER (0..999) 
      ACCESS read-write
      STATUS mandatory
      DESCRIPTION
        "Unsigned Value for delay, 
         after this time the output will fall into the previous state"
      ::= { cmcTcMasterTc3Unit1OutputEntry 8 }

    cmcTcMasterTc3Unit1OutputTimeoutAction OBJECT-TYPE
      SYNTAX INTEGER {
        stay (1),
        off (2),
        on (3)
      }
      ACCESS read-write
      STATUS mandatory
      DESCRIPTION
        "State for output if timeout (RS422) occurs"
      ::= { cmcTcMasterTc3Unit1OutputEntry 9 }
 
-- Messages
              
  cmcTcMasterTc3Unit1NumberOfMsgs OBJECT-TYPE
    SYNTAX INTEGER 
    ACCESS read-only
    STATUS mandatory
    DESCRIPTION
      "Number of messages that can be created with sensor unit 1"
    ::= { cmcTcMasterTc3StatusUnit1Msg 1 }

-- table with entry for each alarm available on this unit               
                
  cmcTcMasterTc3Unit1MsgTable OBJECT-TYPE
    SYNTAX SEQUENCE OF CmcTcMasterTc3Unit1MsgEntry
    ACCESS not-accessible
    STATUS mandatory
    DESCRIPTION
      "Headline of message table"
    ::= { cmcTcMasterTc3StatusUnit1Msg 2 }

  cmcTcMasterTc3Unit1MsgEntry OBJECT-TYPE
    SYNTAX CmcTcMasterTc3Unit1MsgEntry
    ACCESS not-accessible
    STATUS mandatory
    DESCRIPTION
      "Entries of message table"
    INDEX { cmcTcMasterTc3Unit1MsgIndex }
    ::= { cmcTcMasterTc3Unit1MsgTable 1 }

    CmcTcMasterTc3Unit1MsgEntry ::=
      SEQUENCE {
        cmcTcMasterTc3Unit1MsgIndex
          INTEGER, 
        cmcTcMasterTc3Unit1MsgText
          DisplayString (SIZE (0..20)),                
        cmcTcMasterTc3Unit1MsgStatus
          INTEGER,                
        cmcTcMasterTc3Unit1MsgRelay
          INTEGER,
        cmcTcMasterTc3Unit1MsgBeeper
          INTEGER,
        cmcTcMasterTc3Unit1MsgTrap1
          INTEGER,
        cmcTcMasterTc3Unit1MsgTrap2
          INTEGER,
        cmcTcMasterTc3Unit1MsgTrap3
          INTEGER,
        cmcTcMasterTc3Unit1MsgTrap4
          INTEGER,                 
        cmcTcMasterTc3Unit1MsgQuit
          INTEGER              
      }

    cmcTcMasterTc3Unit1MsgIndex OBJECT-TYPE
      SYNTAX INTEGER (1..32000)
      ACCESS read-only
      STATUS mandatory
      DESCRIPTION
        "Index for the list of message entries. Its value ranges
         between 1 and the value of cmcTcMasterTc3Unit1NumberOfMsgs." 
      ::= { cmcTcMasterTc3Unit1MsgEntry 1 }

    cmcTcMasterTc3Unit1MsgText OBJECT-TYPE
      SYNTAX DisplayString (SIZE (0..20))
      ACCESS read-write
      STATUS mandatory
      DESCRIPTION
        "Descriptional text for each message (entry in the table)"
      ::= { cmcTcMasterTc3Unit1MsgEntry 2 }
              
    cmcTcMasterTc3Unit1MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc3Unit1OutputSet)
         17: door is unlocked by WEB
         18: door is unlocked by timer
         19: no access, wrong keycode or cardnumber
         20: orientation of PSM-Unit is circuit 1
         21: orientation of PSM-Unit is circuit 2"
      ::= { cmcTcMasterTc3Unit1MsgEntry 3 }
        
    cmcTcMasterTc3Unit1MsgRelay OBJECT-TYPE
      SYNTAX INTEGER {
        disable (1),
        enable (2)
      }
      ACCESS read-write
      STATUS mandatory
      DESCRIPTION
        "Setup of Alarm relay for this message/alarm
         1:        no switching of alarm relay             
         2:        switching of alarm relay" 
      ::= { cmcTcMasterTc3Unit1MsgEntry 4 }

    cmcTcMasterTc3Unit1MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc3Unit1MsgEntry 5 }

    cmcTcMasterTc3Unit1MsgTrap1 OBJECT-TYPE
      SYNTAX INTEGER {
        disable (1),
        enable (2)
      }
      ACCESS read-write
      STATUS mandatory
      DESCRIPTION
        "Trap receiver 1 activated"
      ::= { cmcTcMasterTc3Unit1MsgEntry 6 }

    cmcTcMasterTc3Unit1MsgTrap2 OBJECT-TYPE
      SYNTAX INTEGER {
        disable (1),
        enable (2)
      }
      ACCESS read-write
      STATUS mandatory
      DESCRIPTION
        "Trap receiver 2 activated"
      ::= { cmcTcMasterTc3Unit1MsgEntry 7 }
 
    cmcTcMasterTc3Unit1MsgTrap3 OBJECT-TYPE
      SYNTAX INTEGER {
        disable (1),
        enable (2)
      }
      ACCESS read-write
      STATUS mandatory
      DESCRIPTION
        "Trap receiver 3 activated"
      ::= { cmcTcMasterTc3Unit1MsgEntry 8 }

    cmcTcMasterTc3Unit1MsgTrap4 OBJECT-TYPE
      SYNTAX INTEGER {
        disable (1),
        enable (2)
      }
      ACCESS read-write
      STATUS mandatory
      DESCRIPTION
        "Trap receiver 4 and Event Logging activated"
      ::= { cmcTcMasterTc3Unit1MsgEntry 9 }

    cmcTcMasterTc3Unit1MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc3Unit1MsgEntry 10 }

-- unit2

  cmcTcMasterTc3Unit2TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 2"
    ::= { cmcTcMasterTc3StatusSensorUnit2 1 }

  cmcTcMasterTc3Unit2Text OBJECT-TYPE
    SYNTAX DisplayString (SIZE (0..10))
    ACCESS read-write
    STATUS mandatory
    DESCRIPTION
      "Descriptional text for sensor unit connected to port 2"
    ::= { cmcTcMasterTc3StatusSensorUnit2 2 }

  cmcTcMasterTc3Unit2Serial OBJECT-TYPE
    SYNTAX INTEGER 
    ACCESS read-only
    STATUS mandatory
    DESCRIPTION
      "Serialnumber of sensor unit connected to port 2"
    ::= { cmcTcMasterTc3StatusSensorUnit2 3 }

  cmcTcMasterTc3Unit2Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 2
       (1) OK
       (2) error
       (3) configuration of sensor unit has changed, confirmation required
       (4) Quit from sensor unit to confirm configuration changes
       (5) timeout of sensor unit, confirmation required
       (6) sensor unit detected, needs to be confirmed
       (8) supply voltage is too low"              
    ::= { cmcTcMasterTc3StatusSensorUnit2 4 }

-- unit 2 table

-- Sensors              

  cmcTcMasterTc3Unit2NumberOfSensors OBJECT-TYPE
    SYNTAX INTEGER 
    ACCESS read-only
    STATUS mandatory
    DESCRIPTION
      "Number of sensors connected to sensor unit 2"
    ::= { cmcTcMasterTc3StatusUnit2Sensors 1 }

-- table with entry for each sensor available on this unit              

  cmcTcMasterTc3Unit2SensorTable OBJECT-TYPE
    SYNTAX SEQUENCE OF CmcTcMasterTc3Unit2SensorEntry
    ACCESS not-accessible
    STATUS mandatory
    DESCRIPTION
      "Headline of sensor table"
    ::= { cmcTcMasterTc3StatusUnit2Sensors 2 }

  cmcTcMasterTc3Unit2SensorEntry OBJECT-TYPE
    SYNTAX CmcTcMasterTc3Unit2SensorEntry
    ACCESS not-accessible
    STATUS mandatory
    DESCRIPTION
      "Entries of sensor table"
    INDEX { cmcTcMasterTc3Unit2SensorIndex }
    ::= { cmcTcMasterTc3Unit2SensorTable 1 }

    CmcTcMasterTc3Unit2SensorEntry ::=
      SEQUENCE {
        cmcTcMasterTc3Unit2SensorIndex
          INTEGER,
        cmcTcMasterTc3Unit2SensorType
          INTEGER,
        cmcTcMasterTc3Unit2SensorText
          DisplayString (SIZE (0..20)),                
        cmcTcMasterTc3Unit2SensorStatus
          INTEGER,
        cmcTcMasterTc3Unit2SensorValue
          INTEGER,
        cmcTcMasterTc3Unit2SensorSetHigh
          INTEGER,
        cmcTcMasterTc3Unit2SensorSetLow
          INTEGER,                 
        cmcTcMasterTc3Unit2SensorSetWarn
          INTEGER  
      }

    cmcTcMasterTc3Unit2SensorIndex OBJECT-TYPE
      SYNTAX INTEGER (1..32000)
      ACCESS read-only
      STATUS mandatory
      DESCRIPTION
        "Index for the list of value entries. Its value ranges
         between 1 and the value of cmcTcMasterTc3Unit2NumberOfSensors." 
      ::= { cmcTcMasterTc3Unit2SensorEntry 1 }

    cmcTcMasterTc3Unit2SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 2 to sensor[cmcTcMasterTc3Unit2SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc3Unit2SensorEntry 2 }
        
    cmcTcMasterTc3Unit2SensorText OBJECT-TYPE
      SYNTAX DisplayString (SIZE (0..20))
      ACCESS read-write
      STATUS mandatory
      DESCRIPTION
        "Descriptional text for each sensor (entry in the table)"
      ::= { cmcTcMasterTc3Unit2SensorEntry 3 }
              
    cmcTcMasterTc3Unit2SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc3Unit2SensorEntry 4 }

    cmcTcMasterTc3Unit2SensorValue OBJECT-TYPE
      SYNTAX INTEGER 
      ACCESS read-only
      STATUS mandatory
      DESCRIPTION
        "Value of sensor"
      ::= { cmcTcMasterTc3Unit2SensorEntry 5 }

    cmcTcMasterTc3Unit2SensorSetHigh OBJECT-TYPE
      SYNTAX INTEGER (0..300) 
      ACCESS read-write
      STATUS mandatory
      DESCRIPTION
        "Value for high setpoint of sensor"
      ::= { cmcTcMasterTc3Unit2SensorEntry 6 }

    cmcTcMasterTc3Unit2SensorSetLow OBJECT-TYPE
      SYNTAX INTEGER (0..300) 
      ACCESS read-write
      STATUS mandatory
      DESCRIPTION
        "Value for low setpoint of sensor,
         also used as alarm delay"
      ::= { cmcTcMasterTc3Unit2SensorEntry 7 }

    cmcTcMasterTc3Unit2SensorSetWarn OBJECT-TYPE
      SYNTAX INTEGER (0..300) 
      ACCESS read-write
      STATUS mandatory
      DESCRIPTION
        "Value for warning setpoint of sensor,
         also used as fan threshold"
      ::= { cmcTcMasterTc3Unit2SensorEntry 8 }

-- Outputs              

  cmcTcMasterTc3Unit2NumberOfOutputs OBJECT-TYPE
    SYNTAX INTEGER 
    ACCESS read-only
    STATUS mandatory
    DESCRIPTION
      "Number of outputs available on sensor unit 2"
    ::= { cmcTcMasterTc3StatusUnit2Outputs 1 }

-- table with entry for each output available on this unit              
                
  cmcTcMasterTc3Unit2OutputTable OBJECT-TYPE
    SYNTAX SEQUENCE OF CmcTcMasterTc3Unit2OutputEntry
    ACCESS not-accessible
    STATUS mandatory
    DESCRIPTION
      "Headline of output table"
    ::= { cmcTcMasterTc3StatusUnit2Outputs 2 }

  cmcTcMasterTc3Unit2OutputEntry OBJECT-TYPE
    SYNTAX CmcTcMasterTc3Unit2OutputEntry
    ACCESS not-accessible
    STATUS mandatory
    DESCRIPTION
      "Entries of output table"
    INDEX { cmcTcMasterTc3Unit2OutputIndex }
    ::= { cmcTcMasterTc3Unit2OutputTable 1 }

    CmcTcMasterTc3Unit2OutputEntry ::=
      SEQUENCE {
        cmcTcMasterTc3Unit2OutputIndex
          INTEGER,
        cmcTcMasterTc3Unit2OutputType
          INTEGER,
        cmcTcMasterTc3Unit2OutputText
          DisplayString (SIZE (0..20)),                
        cmcTcMasterTc3Unit2OutputStatus
          INTEGER,
        cmcTcMasterTc3Unit2OutputValue
          INTEGER,
        cmcTcMasterTc3Unit2OutputSet
          INTEGER,
        cmcTcMasterTc3Unit2OutputConfig
          INTEGER,                
        cmcTcMasterTc3Unit2OutputDelay
          INTEGER,
        cmcTcMasterTc3Unit2OutputTimeoutAction
          INTEGER
      }

    cmcTcMasterTc3Unit2OutputIndex OBJECT-TYPE
      SYNTAX INTEGER (1..32000)
      ACCESS read-only
      STATUS mandatory
      DESCRIPTION
        "Index for the list of output entries. Its value ranges
         between 1 and the value of cmcTcMasterTc3Unit2NumberOfOutputs." 
      ::= { cmcTcMasterTc3Unit2OutputEntry 1 }

    cmcTcMasterTc3Unit2OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 2 to output[cmcTcMasterTc3Unit2OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc3Unit2OutputEntry 2 }

        
    cmcTcMasterTc3Unit2OutputText OBJECT-TYPE
      SYNTAX DisplayString (SIZE (0..20))
      ACCESS read-write
      STATUS mandatory
      DESCRIPTION
        "Descriptional text for each output (entry in the table)"
      ::= { cmcTcMasterTc3Unit2OutputEntry 3 }
              
    cmcTcMasterTc3Unit2OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc3Unit2OutputEntry 4 }

    cmcTcMasterTc3Unit2OutputValue OBJECT-TYPE
      SYNTAX INTEGER (-32000..32000) 
      ACCESS read-write
      STATUS mandatory
      DESCRIPTION
        "Value for output"
      ::= { cmcTcMasterTc3Unit2OutputEntry 5 }

    cmcTcMasterTc3Unit2OutputSet OBJECT-TYPE
      SYNTAX INTEGER {
        off (1),
        on (2),
        lock (3),
        unlock (4),
        unlockDelay (5)
      }
      ACCESS read-write
      STATUS mandatory
      DESCRIPTION
        "Command for output"
      ::= { cmcTcMasterTc3Unit2OutputEntry 6 }

    cmcTcMasterTc3Unit2OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc3Unit2OutputEntry 7 }

    cmcTcMasterTc3Unit2OutputDelay OBJECT-TYPE
      SYNTAX INTEGER (0..999) 
      ACCESS read-write
      STATUS mandatory
      DESCRIPTION
        "Unsigned Value for delay, 
         after this time the output will fall into the previous state"
      ::= { cmcTcMasterTc3Unit2OutputEntry 8 }

    cmcTcMasterTc3Unit2OutputTimeoutAction OBJECT-TYPE
      SYNTAX INTEGER {
        stay (1),
        off (2),
        on (3)
      }
      ACCESS read-write
      STATUS mandatory
      DESCRIPTION
        "State for output if timeout (RS422) occurs"
      ::= { cmcTcMasterTc3Unit2OutputEntry 9 }

-- Messages
              
  cmcTcMasterTc3Unit2NumberOfMsgs OBJECT-TYPE
    SYNTAX INTEGER 
    ACCESS read-only
    STATUS mandatory
    DESCRIPTION
      "Number of messages that can be created with sensor unit 2"
    ::= { cmcTcMasterTc3StatusUnit2Msg 1 }

-- table with entry for each alarm available on this unit               
                
  cmcTcMasterTc3Unit2MsgTable OBJECT-TYPE
    SYNTAX SEQUENCE OF CmcTcMasterTc3Unit2MsgEntry
    ACCESS not-accessible
    STATUS mandatory
    DESCRIPTION
      "Headline of message table"
    ::= { cmcTcMasterTc3StatusUnit2Msg 2 }

  cmcTcMasterTc3Unit2MsgEntry OBJECT-TYPE
    SYNTAX CmcTcMasterTc3Unit2MsgEntry
    ACCESS not-accessible
    STATUS mandatory
    DESCRIPTION
      "Entries of message table"
    INDEX { cmcTcMasterTc3Unit2MsgIndex }
    ::= { cmcTcMasterTc3Unit2MsgTable 1 }

    CmcTcMasterTc3Unit2MsgEntry ::=
      SEQUENCE {
        cmcTcMasterTc3Unit2MsgIndex
          INTEGER,
        cmcTcMasterTc3Unit2MsgText
          DisplayString (SIZE (0..20)),
        cmcTcMasterTc3Unit2MsgStatus
          INTEGER, 
        cmcTcMasterTc3Unit2MsgRelay
          INTEGER,
        cmcTcMasterTc3Unit2MsgBeeper
          INTEGER,
        cmcTcMasterTc3Unit2MsgTrap1
          INTEGER,
        cmcTcMasterTc3Unit2MsgTrap2
          INTEGER,
        cmcTcMasterTc3Unit2MsgTrap3
          INTEGER,
        cmcTcMasterTc3Unit2MsgTrap4
          INTEGER,                 
        cmcTcMasterTc3Unit2MsgQuit
          INTEGER              
      }

    cmcTcMasterTc3Unit2MsgIndex OBJECT-TYPE
      SYNTAX INTEGER (1..32000)
      ACCESS read-only
      STATUS mandatory
      DESCRIPTION
        "Index for the list of message entries. Its value ranges
         between 1 and the value of cmcTcMasterTc3Unit2NumberOfMsgs." 
      ::= { cmcTcMasterTc3Unit2MsgEntry 1 }

    cmcTcMasterTc3Unit2MsgText OBJECT-TYPE
      SYNTAX DisplayString (SIZE (0..20))
      ACCESS read-write
      STATUS mandatory
      DESCRIPTION
        "Descriptional text for each message (entry in the table)"
      ::= { cmcTcMasterTc3Unit2MsgEntry 2 }

    cmcTcMasterTc3Unit2MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc3Unit2OutputSet)
         17: door is unlocked by WEB
         18: door is unlocked by timer
         19: no access, wrong keycode or cardnumber
         20: orientation of PSM-Unit is circuit 1
         21: orientation of PSM-Unit is circuit 2"
      ::= { cmcTcMasterTc3Unit2MsgEntry 3 }

    cmcTcMasterTc3Unit2MsgRelay OBJECT-TYPE
      SYNTAX INTEGER {
        disable (1),
        enable (2)
      }
      ACCESS read-write
      STATUS mandatory
      DESCRIPTION
        "Setup of Alarm relay for this alarm
         2:        no switching of alarm relay             
         1:        switching of alarm relay" 
      ::= { cmcTcMasterTc3Unit2MsgEntry 4 }

    cmcTcMasterTc3Unit2MsgBeeper OBJECT-TYPE
      SYNTAX INTEGER {
        disable (1),
        enable (2)
      }
      ACCESS read-write
      STATUS mandatory
      DESCRIPTION
        "Setup of Alarm beeper for this alarm
         2:        no audible alarm
         1:        audible alarm" 
      ::= { cmcTcMasterTc3Unit2MsgEntry 5 }

    cmcTcMasterTc3Unit2MsgTrap1 OBJECT-TYPE
      SYNTAX INTEGER {
        disable (1),
        enable (2)
      }
      ACCESS read-write
      STATUS mandatory
      DESCRIPTION
        "Trap receiver 1 activated"
      ::= { cmcTcMasterTc3Unit2MsgEntry 6 }

    cmcTcMasterTc3Unit2MsgTrap2 OBJECT-TYPE
      SYNTAX INTEGER {
        disable (1),
        enable (2)
      }
      ACCESS read-write
      STATUS mandatory
      DESCRIPTION
        "Trap receiver 2 activated"
      ::= { cmcTcMasterTc3Unit2MsgEntry 7 }
 
    cmcTcMasterTc3Unit2MsgTrap3 OBJECT-TYPE
      SYNTAX INTEGER {
        disable (1),
        enable (2)
      }
      ACCESS read-write
      STATUS mandatory
      DESCRIPTION
        "Trap receiver 3 activated"
      ::= { cmcTcMasterTc3Unit2MsgEntry 8 }

    cmcTcMasterTc3Unit2MsgTrap4 OBJECT-TYPE
      SYNTAX INTEGER {
        disable (1),
        enable (2)
      }
      ACCESS read-write
      STATUS mandatory
      DESCRIPTION
        "Trap receiver 4 and Event Logging activated"
      ::= { cmcTcMasterTc3Unit2MsgEntry 9 }

    cmcTcMasterTc3Unit2MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc3Unit2MsgEntry 10 }

-- unit 3
  cmcTcMasterTc3Unit3TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 3"
    ::= { cmcTcMasterTc3StatusSensorUnit3 1 }

  cmcTcMasterTc3Unit3Text OBJECT-TYPE
    SYNTAX DisplayString (SIZE (0..10))
    ACCESS read-write
    STATUS mandatory
    DESCRIPTION
      "Descriptional text for sensor unit connected to port 3"
    ::= { cmcTcMasterTc3StatusSensorUnit3 2 }

  cmcTcMasterTc3Unit3Serial OBJECT-TYPE
    SYNTAX INTEGER 
    ACCESS  read-only
    STATUS  mandatory
    DESCRIPTION
      "Serialnumber of sensor unit connected to port 3"
    ::= { cmcTcMasterTc3StatusSensorUnit3 3 }

  cmcTcMasterTc3Unit3Status OBJECT-TYPE
    SYNTAX INTEGER {
      ok(1),
      error(2),
      changed(3),
      quit(4),
      timeout(5),
      detected(6),
      notAvail(7),
      lowPower(8)
    }
    ACCESS  read-only
    STATUS  mandatory
    DESCRIPTION
      "General Status sensor unit connected to port 3
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc3StatusSensorUnit3 4 }

-- Sensors              

  cmcTcMasterTc3Unit3NumberOfSensors OBJECT-TYPE
    SYNTAX INTEGER 
    ACCESS read-only
    STATUS mandatory
    DESCRIPTION
      "Number of sensors connected to sensor unit 3"
    ::= { cmcTcMasterTc3StatusUnit3Sensors 1 }

-- table with entry for each sensor available on this unit              
        
  cmcTcMasterTc3Unit3SensorTable OBJECT-TYPE
    SYNTAX SEQUENCE OF CmcTcMasterTc3Unit3SensorEntry
    ACCESS not-accessible
    STATUS mandatory
    DESCRIPTION
      "Headline of sensor table"
    ::= { cmcTcMasterTc3StatusUnit3Sensors 2 }

  cmcTcMasterTc3Unit3SensorEntry OBJECT-TYPE
    SYNTAX CmcTcMasterTc3Unit3SensorEntry
    ACCESS not-accessible
    STATUS mandatory
    DESCRIPTION
      "Entries of sensor table"
    INDEX { cmcTcMasterTc3Unit3SensorIndex }
    ::= { cmcTcMasterTc3Unit3SensorTable 1 }

    CmcTcMasterTc3Unit3SensorEntry ::=
      SEQUENCE {
        cmcTcMasterTc3Unit3SensorIndex
          INTEGER,
        cmcTcMasterTc3Unit3SensorType
          INTEGER,
        cmcTcMasterTc3Unit3SensorText
          DisplayString (SIZE (0..20)),                
        cmcTcMasterTc3Unit3SensorStatus
          INTEGER,
        cmcTcMasterTc3Unit3SensorValue
          INTEGER,
        cmcTcMasterTc3Unit3SensorSetHigh
          INTEGER,
        cmcTcMasterTc3Unit3SensorSetLow
          INTEGER,                 
        cmcTcMasterTc3Unit3SensorSetWarn
          INTEGER  
      }

    cmcTcMasterTc3Unit3SensorIndex OBJECT-TYPE
      SYNTAX INTEGER (1..32000)
      ACCESS read-only
      STATUS mandatory
      DESCRIPTION
        "Index for the list of value entries. Its value ranges
         between 1 and the value of cmcTcMasterTc3Unit3NumberOfSensors." 
      ::= { cmcTcMasterTc3Unit3SensorEntry 1 }

    cmcTcMasterTc3Unit3SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 3 to sensor[cmcTcMasterTc3Unit3SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc3Unit3SensorEntry 2 }

    cmcTcMasterTc3Unit3SensorText OBJECT-TYPE
      SYNTAX DisplayString (SIZE (0..20))
      ACCESS read-write
      STATUS mandatory
      DESCRIPTION
        "Descriptional text for each sensor (entry in the table)"
      ::= { cmcTcMasterTc3Unit3SensorEntry 3 }
              
    cmcTcMasterTc3Unit3SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc3Unit3SensorEntry 4 }

    cmcTcMasterTc3Unit3SensorValue OBJECT-TYPE
      SYNTAX INTEGER 
      ACCESS read-only
      STATUS mandatory
      DESCRIPTION
        "Value of sensor"
      ::= { cmcTcMasterTc3Unit3SensorEntry 5 }

    cmcTcMasterTc3Unit3SensorSetHigh OBJECT-TYPE
      SYNTAX INTEGER (0..300) 
      ACCESS read-write
      STATUS mandatory
      DESCRIPTION
        "Value for high setpoint of sensor"
      ::= { cmcTcMasterTc3Unit3SensorEntry 6 }

    cmcTcMasterTc3Unit3SensorSetLow OBJECT-TYPE
      SYNTAX INTEGER (0..300) 
      ACCESS read-write
      STATUS mandatory
      DESCRIPTION
        "Value for low setpoint of sensor,
         also used as alarm delay"
      ::= { cmcTcMasterTc3Unit3SensorEntry 7 }

    cmcTcMasterTc3Unit3SensorSetWarn OBJECT-TYPE
      SYNTAX INTEGER (0..300) 
      ACCESS read-write
      STATUS mandatory
      DESCRIPTION
        "Value for warning setpoint of sensor,
         also used as fan threshold"
      ::= { cmcTcMasterTc3Unit3SensorEntry 8 }
                
-- Outputs              

  cmcTcMasterTc3Unit3NumberOfOutputs OBJECT-TYPE
    SYNTAX INTEGER 
    ACCESS read-only
    STATUS mandatory
    DESCRIPTION
      "Number of outputs available on sensor unit 3"
    ::= { cmcTcMasterTc3StatusUnit3Outputs 1 }

-- table with entry for each output available on this unit              
                
  cmcTcMasterTc3Unit3OutputTable OBJECT-TYPE
    SYNTAX SEQUENCE OF CmcTcMasterTc3Unit3OutputEntry
    ACCESS not-accessible
    STATUS mandatory
    DESCRIPTION
      "Headline of output table"
    ::= { cmcTcMasterTc3StatusUnit3Outputs 2 }

  cmcTcMasterTc3Unit3OutputEntry OBJECT-TYPE
    SYNTAX CmcTcMasterTc3Unit3OutputEntry
    ACCESS not-accessible
    STATUS mandatory
    DESCRIPTION
      "Entries of output table"
    INDEX { cmcTcMasterTc3Unit3OutputIndex }
    ::= { cmcTcMasterTc3Unit3OutputTable 1 }

    CmcTcMasterTc3Unit3OutputEntry ::=
      SEQUENCE {
        cmcTcMasterTc3Unit3OutputIndex
          INTEGER,
        cmcTcMasterTc3Unit3OutputType
          INTEGER,
        cmcTcMasterTc3Unit3OutputText
          DisplayString (SIZE (0..20)),                
        cmcTcMasterTc3Unit3OutputStatus
          INTEGER,
        cmcTcMasterTc3Unit3OutputValue
          INTEGER,
        cmcTcMasterTc3Unit3OutputSet
          INTEGER,
        cmcTcMasterTc3Unit3OutputConfig
          INTEGER,
        cmcTcMasterTc3Unit3OutputDelay
          INTEGER,
        cmcTcMasterTc3Unit3OutputTimeoutAction
          INTEGER
      }

    cmcTcMasterTc3Unit3OutputIndex OBJECT-TYPE
      SYNTAX INTEGER (1..32000)
      ACCESS read-only
      STATUS mandatory
      DESCRIPTION
        "Index for the list of output entries. Its value ranges
         between 1 and the value of cmcTcMasterTc3Unit3NumberOfOutputs." 
      ::= { cmcTcMasterTc3Unit3OutputEntry 1 }

    cmcTcMasterTc3Unit3OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 3 to output[cmcTcMasterTc3Unit3OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc3Unit3OutputEntry 2 }

        
    cmcTcMasterTc3Unit3OutputText OBJECT-TYPE
      SYNTAX DisplayString (SIZE (0..20))
      ACCESS read-write
      STATUS mandatory
      DESCRIPTION
        "Descriptional text for each output (entry in the table)"
      ::= { cmcTcMasterTc3Unit3OutputEntry 3 }
              
    cmcTcMasterTc3Unit3OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc3Unit3OutputEntry 4 }

    cmcTcMasterTc3Unit3OutputValue OBJECT-TYPE
      SYNTAX INTEGER (-32000..32000) 
      ACCESS read-write
      STATUS mandatory
      DESCRIPTION
        "Value for output"
      ::= { cmcTcMasterTc3Unit3OutputEntry 5 }

    cmcTcMasterTc3Unit3OutputSet OBJECT-TYPE
      SYNTAX INTEGER {
        off (1),
        on (2),
        lock (3),
        unlock (4),
        unlockDelay (5)
      }
      ACCESS read-write
      STATUS mandatory
      DESCRIPTION
        "Command for output"
      ::= { cmcTcMasterTc3Unit3OutputEntry 6 }

    cmcTcMasterTc3Unit3OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc3Unit3OutputEntry 7 }

    cmcTcMasterTc3Unit3OutputDelay OBJECT-TYPE
      SYNTAX INTEGER (0..999) 
      ACCESS read-write
      STATUS mandatory
      DESCRIPTION
        "Unsigned Value for delay, 
         after this time the output will fall into the previous state"
      ::= { cmcTcMasterTc3Unit3OutputEntry 8 }

    cmcTcMasterTc3Unit3OutputTimeoutAction OBJECT-TYPE
      SYNTAX INTEGER {
        stay (1),
        off (2),
        on (3)
      }
      ACCESS read-write
      STATUS mandatory
      DESCRIPTION
        "State for output if timeout (RS422) occurs"
      ::= { cmcTcMasterTc3Unit3OutputEntry 9 }

-- Messages
              
  cmcTcMasterTc3Unit3NumberOfMsgs OBJECT-TYPE
    SYNTAX INTEGER 
    ACCESS read-only
    STATUS mandatory
    DESCRIPTION
      "Number of messages that can be created with sensor unit 3"
    ::= { cmcTcMasterTc3StatusUnit3Msg 1 }

-- table with entry for each alarm available on this unit               
                
  cmcTcMasterTc3Unit3MsgTable OBJECT-TYPE
    SYNTAX SEQUENCE OF CmcTcMasterTc3Unit3MsgEntry
    ACCESS not-accessible
    STATUS mandatory
    DESCRIPTION
      "Headline of message table"
    ::= { cmcTcMasterTc3StatusUnit3Msg 2 }

  cmcTcMasterTc3Unit3MsgEntry OBJECT-TYPE
    SYNTAX CmcTcMasterTc3Unit3MsgEntry
    ACCESS not-accessible
    STATUS mandatory
    DESCRIPTION
      "Entries of message table"
    INDEX { cmcTcMasterTc3Unit3MsgIndex }
    ::= { cmcTcMasterTc3Unit3MsgTable 1 }

    CmcTcMasterTc3Unit3MsgEntry ::=
      SEQUENCE {
        cmcTcMasterTc3Unit3MsgIndex
          INTEGER,
        cmcTcMasterTc3Unit3MsgText
          DisplayString (SIZE (0..20)),
        cmcTcMasterTc3Unit3MsgStatus
          INTEGER, 
        cmcTcMasterTc3Unit3MsgRelay
          INTEGER,
        cmcTcMasterTc3Unit3MsgBeeper
          INTEGER,
        cmcTcMasterTc3Unit3MsgTrap1
          INTEGER,
        cmcTcMasterTc3Unit3MsgTrap2
          INTEGER,
        cmcTcMasterTc3Unit3MsgTrap3
          INTEGER,
        cmcTcMasterTc3Unit3MsgTrap4
          INTEGER,                 
        cmcTcMasterTc3Unit3MsgQuit
          INTEGER              
      }

    cmcTcMasterTc3Unit3MsgIndex OBJECT-TYPE
      SYNTAX INTEGER (1..32000)
      ACCESS read-only
      STATUS mandatory
      DESCRIPTION
        "Index for the list of message entries. Its value ranges
         between 1 and the value of cmcTcMasterTc3Unit3NumberOfMsgs." 
      ::= { cmcTcMasterTc3Unit3MsgEntry 1 }

    cmcTcMasterTc3Unit3MsgText OBJECT-TYPE
      SYNTAX DisplayString (SIZE (0..20))
      ACCESS read-write
      STATUS mandatory
      DESCRIPTION
        "Descriptional text for each message (entry in the table)"
      ::= { cmcTcMasterTc3Unit3MsgEntry 2 }

    cmcTcMasterTc3Unit3MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc3Unit3OutputSet)
         17: door is unlocked by WEB
         18: door is unlocked by timer
         19: no access, wrong keycode or cardnumber
         20: orientation of PSM-Unit is circuit 1
         21: orientation of PSM-Unit is circuit 2"
      ::= { cmcTcMasterTc3Unit3MsgEntry 3 }

    cmcTcMasterTc3Unit3MsgRelay OBJECT-TYPE
      SYNTAX INTEGER {
        disable (1),
        enable (2)
      }
      ACCESS read-write
      STATUS mandatory
      DESCRIPTION
        "Setup of Alarm relay for this alarm
         1:        no switching of alarm relay             
         2:        switching of alarm relay" 
      ::= { cmcTcMasterTc3Unit3MsgEntry 4 }

    cmcTcMasterTc3Unit3MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc3Unit3MsgEntry 5 }

    cmcTcMasterTc3Unit3MsgTrap1 OBJECT-TYPE
      SYNTAX INTEGER {
        disable (1),
        enable (2)
      }
      ACCESS read-write
      STATUS mandatory
      DESCRIPTION
        "Trap receiver 1 activated"
      ::= { cmcTcMasterTc3Unit3MsgEntry 6 }

    cmcTcMasterTc3Unit3MsgTrap2 OBJECT-TYPE
      SYNTAX INTEGER {
        disable (1),
        enable (2)
      }
      ACCESS read-write
      STATUS mandatory
      DESCRIPTION
        "Trap receiver 2 activated"
      ::= { cmcTcMasterTc3Unit3MsgEntry 7 }
 
    cmcTcMasterTc3Unit3MsgTrap3 OBJECT-TYPE
      SYNTAX INTEGER {
        disable (1),
        enable (2)
      }
      ACCESS read-write
      STATUS mandatory
      DESCRIPTION
        "Trap receiver 3 activated"
      ::= { cmcTcMasterTc3Unit3MsgEntry 8 }

    cmcTcMasterTc3Unit3MsgTrap4 OBJECT-TYPE
      SYNTAX INTEGER {
        disable (1),
        enable (2)
      }
      ACCESS read-write
      STATUS mandatory
      DESCRIPTION
        "Trap receiver 4 and Event Logging activated"
      ::= { cmcTcMasterTc3Unit3MsgEntry 9 }

    cmcTcMasterTc3Unit3MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc3Unit3MsgEntry 10 }

-- unit4

  cmcTcMasterTc3Unit4TypeOfDevice OBJECT-TYPE
    SYNTAX INTEGER {
      notAvail (1),
      unitIO (2),
      unitAccess (3),
      unitClimate (4),
      unitFCS (5),
      unitRTT (6),
      unitRLCP (7),
      unitPSM (8)
    }
    ACCESS  read-only
    STATUS  mandatory
    DESCRIPTION
      "Type of sensor unit connected to port 4"
    ::= { cmcTcMasterTc3StatusSensorUnit4 1 }

  cmcTcMasterTc3Unit4Text OBJECT-TYPE
    SYNTAX DisplayString (SIZE (0..10))
    ACCESS read-write
    STATUS mandatory
    DESCRIPTION
      "Descriptional text for sensor unit connected to port 4"
    ::= { cmcTcMasterTc3StatusSensorUnit4 2 }

  cmcTcMasterTc3Unit4Serial OBJECT-TYPE
    SYNTAX INTEGER 
    ACCESS read-only
    STATUS mandatory
    DESCRIPTION
      "Serialnumber of sensor unit connected to port 4"
    ::= { cmcTcMasterTc3StatusSensorUnit4 3 }

  cmcTcMasterTc3Unit4Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 4
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc3StatusSensorUnit4 4 }

-- Sensors
              
  cmcTcMasterTc3Unit4NumberOfSensors OBJECT-TYPE
    SYNTAX INTEGER 
    ACCESS read-only
    STATUS mandatory
    DESCRIPTION
      "Number of sensors connected to sensor unit 4"
    ::= { cmcTcMasterTc3StatusUnit4Sensors 1 }

-- table with entry for each sensor available on this unit              
                
  cmcTcMasterTc3Unit4SensorTable OBJECT-TYPE
    SYNTAX SEQUENCE OF CmcTcMasterTc3Unit4SensorEntry
    ACCESS not-accessible
    STATUS mandatory
    DESCRIPTION
      "Headline of sensor table"
    ::= { cmcTcMasterTc3StatusUnit4Sensors 2 }

  cmcTcMasterTc3Unit4SensorEntry OBJECT-TYPE
    SYNTAX CmcTcMasterTc3Unit4SensorEntry
    ACCESS not-accessible
    STATUS mandatory
    DESCRIPTION
      "Entries of sensor table"
    INDEX { cmcTcMasterTc3Unit4SensorIndex }
    ::= { cmcTcMasterTc3Unit4SensorTable 1 }

    CmcTcMasterTc3Unit4SensorEntry ::=
      SEQUENCE {
        cmcTcMasterTc3Unit4SensorIndex
          INTEGER,
        cmcTcMasterTc3Unit4SensorType
          INTEGER,
        cmcTcMasterTc3Unit4SensorText
          DisplayString (SIZE (0..20)),                
        cmcTcMasterTc3Unit4SensorStatus
          INTEGER,
        cmcTcMasterTc3Unit4SensorValue
          INTEGER,
        cmcTcMasterTc3Unit4SensorSetHigh
          INTEGER,
        cmcTcMasterTc3Unit4SensorSetLow
          INTEGER,                 
        cmcTcMasterTc3Unit4SensorSetWarn
          INTEGER  
      }

    cmcTcMasterTc3Unit4SensorIndex OBJECT-TYPE
      SYNTAX INTEGER (1..32000)
      ACCESS read-only
      STATUS mandatory
      DESCRIPTION
        "Index for the list of value entries. Its value ranges
         between 1 and the value of cmcTcMasterTc3Unit4NumberOfSensors." 
      ::= { cmcTcMasterTc3Unit4SensorEntry 1 }

    cmcTcMasterTc3Unit4SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 4 to sensor[cmcTcMasterTc3Unit4SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc3Unit4SensorEntry 2 }

    cmcTcMasterTc3Unit4SensorText OBJECT-TYPE
      SYNTAX DisplayString (SIZE (0..20))
      ACCESS read-write
      STATUS mandatory
      DESCRIPTION
        "Descriptional text for each sensor (entry in the table)"
      ::= { cmcTcMasterTc3Unit4SensorEntry 3 }
              
    cmcTcMasterTc3Unit4SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc3Unit4SensorEntry 4 }

    cmcTcMasterTc3Unit4SensorValue OBJECT-TYPE
      SYNTAX INTEGER 
      ACCESS read-only
      STATUS mandatory
      DESCRIPTION
        "Value of sensor"
      ::= { cmcTcMasterTc3Unit4SensorEntry 5 }

    cmcTcMasterTc3Unit4SensorSetHigh OBJECT-TYPE
      SYNTAX INTEGER (0..300) 
      ACCESS read-write
      STATUS mandatory
      DESCRIPTION
        "Value for high setpoint of sensor"
      ::= { cmcTcMasterTc3Unit4SensorEntry 6 }

    cmcTcMasterTc3Unit4SensorSetLow OBJECT-TYPE
      SYNTAX INTEGER (0..300) 
      ACCESS read-write
      STATUS mandatory
      DESCRIPTION
        "Value for low setpoint of sensor,
         also used as alarm delay"
      ::= { cmcTcMasterTc3Unit4SensorEntry 7 }

    cmcTcMasterTc3Unit4SensorSetWarn OBJECT-TYPE
      SYNTAX INTEGER (0..300) 
      ACCESS read-write
      STATUS mandatory
      DESCRIPTION
        "Value for warning setpoint of sensor,
         also used as fan threshold"
      ::= { cmcTcMasterTc3Unit4SensorEntry 8 }

-- Outputs              

  cmcTcMasterTc3Unit4NumberOfOutputs OBJECT-TYPE
    SYNTAX INTEGER 
    ACCESS read-only
    STATUS mandatory
    DESCRIPTION
      "Number of outputs available on sensor unit 4"
    ::= { cmcTcMasterTc3StatusUnit4Outputs 1 }

-- table with entry for each output available on this unit              
                
  cmcTcMasterTc3Unit4OutputTable OBJECT-TYPE
    SYNTAX SEQUENCE OF CmcTcMasterTc3Unit4OutputEntry
    ACCESS not-accessible
    STATUS mandatory
    DESCRIPTION
      "Headline of output table"
    ::= { cmcTcMasterTc3StatusUnit4Outputs 2 }

  cmcTcMasterTc3Unit4OutputEntry OBJECT-TYPE
    SYNTAX CmcTcMasterTc3Unit4OutputEntry
    ACCESS not-accessible
    STATUS mandatory
    DESCRIPTION
      "Entries of output table"
    INDEX { cmcTcMasterTc3Unit4OutputIndex }
    ::= { cmcTcMasterTc3Unit4OutputTable 1 }

    CmcTcMasterTc3Unit4OutputEntry ::=
      SEQUENCE {
        cmcTcMasterTc3Unit4OutputIndex
          INTEGER,
        cmcTcMasterTc3Unit4OutputType
          INTEGER,
        cmcTcMasterTc3Unit4OutputText
          DisplayString (SIZE (0..20)),                
        cmcTcMasterTc3Unit4OutputStatus
          INTEGER,
        cmcTcMasterTc3Unit4OutputValue
          INTEGER,
        cmcTcMasterTc3Unit4OutputSet
          INTEGER,
        cmcTcMasterTc3Unit4OutputConfig
          INTEGER,
        cmcTcMasterTc3Unit4OutputDelay
          INTEGER,
        cmcTcMasterTc3Unit4OutputTimeoutAction
          INTEGER
      }

    cmcTcMasterTc3Unit4OutputIndex OBJECT-TYPE
      SYNTAX INTEGER (1..32000)
      ACCESS read-only
      STATUS mandatory
      DESCRIPTION
        "Index for the list of output entries. Its value ranges
         between 1 and the value of cmcTcMasterTc3Unit4NumberOfOutputs." 
      ::= { cmcTcMasterTc3Unit4OutputEntry 1 }

    cmcTcMasterTc3Unit4OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 4 to output[cmcTcMasterTc3Unit4OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc3Unit4OutputEntry 2 }

    cmcTcMasterTc3Unit4OutputText OBJECT-TYPE
      SYNTAX DisplayString (SIZE (0..20))
      ACCESS read-write
      STATUS mandatory
      DESCRIPTION
        "Descriptional text for each output (entry in the table)"
      ::= { cmcTcMasterTc3Unit4OutputEntry 3 }
              
    cmcTcMasterTc3Unit4OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc3Unit4OutputEntry 4 }

    cmcTcMasterTc3Unit4OutputValue OBJECT-TYPE
      SYNTAX INTEGER (-32000..32000) 
      ACCESS read-write
      STATUS mandatory
      DESCRIPTION
        "Value for output"
      ::= { cmcTcMasterTc3Unit4OutputEntry 5 }

    cmcTcMasterTc3Unit4OutputSet OBJECT-TYPE
      SYNTAX INTEGER {
        off (1),
        on (2),
        lock (3),
        unlock (4),
        unlockDelay (5)
      }
      ACCESS read-write
      STATUS mandatory
      DESCRIPTION
        "Command for output"
      ::= { cmcTcMasterTc3Unit4OutputEntry 6 }

    cmcTcMasterTc3Unit4OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc3Unit4OutputEntry 7 }

    cmcTcMasterTc3Unit4OutputDelay OBJECT-TYPE
      SYNTAX INTEGER (0..999) 
      ACCESS read-write
      STATUS mandatory
      DESCRIPTION
        "Unsigned Value for delay, 
         after this time the output will fall into the previous state"
      ::= { cmcTcMasterTc3Unit4OutputEntry 8 }

    cmcTcMasterTc3Unit4OutputTimeoutAction OBJECT-TYPE
      SYNTAX INTEGER {
        stay (1),
        off (2),
        on (3)
      }
      ACCESS read-write
      STATUS mandatory
      DESCRIPTION
        "State for output if timeout (RS422) occurs"
      ::= { cmcTcMasterTc3Unit4OutputEntry 9 }

-- Messages
              
  cmcTcMasterTc3Unit4NumberOfMsgs OBJECT-TYPE
    SYNTAX INTEGER 
    ACCESS read-only
    STATUS mandatory
    DESCRIPTION
      "Number of messages that can be created with sensor unit 4"
    ::= { cmcTcMasterTc3StatusUnit4Msg 1 }

-- table with entry for each alarm available on this unit               
                
  cmcTcMasterTc3Unit4MsgTable OBJECT-TYPE
    SYNTAX SEQUENCE OF CmcTcMasterTc3Unit4MsgEntry
    ACCESS not-accessible
    STATUS mandatory
    DESCRIPTION
      "Headline of message table"
    ::= { cmcTcMasterTc3StatusUnit4Msg 2 }

  cmcTcMasterTc3Unit4MsgEntry OBJECT-TYPE
    SYNTAX CmcTcMasterTc3Unit4MsgEntry
    ACCESS not-accessible
    STATUS mandatory
    DESCRIPTION
      "Entries of message table"
    INDEX { cmcTcMasterTc3Unit4MsgIndex }
    ::= { cmcTcMasterTc3Unit4MsgTable 1 }

    CmcTcMasterTc3Unit4MsgEntry ::=
      SEQUENCE {
        cmcTcMasterTc3Unit4MsgIndex
          INTEGER,
        cmcTcMasterTc3Unit4MsgText
          DisplayString (SIZE (0..20)),                
        cmcTcMasterTc3Unit4MsgStatus
          INTEGER, 
        cmcTcMasterTc3Unit4MsgRelay
          INTEGER,
        cmcTcMasterTc3Unit4MsgBeeper
          INTEGER,
        cmcTcMasterTc3Unit4MsgTrap1
          INTEGER,
        cmcTcMasterTc3Unit4MsgTrap2
          INTEGER,
        cmcTcMasterTc3Unit4MsgTrap3
          INTEGER,
        cmcTcMasterTc3Unit4MsgTrap4
          INTEGER,                 
        cmcTcMasterTc3Unit4MsgQuit
          INTEGER              
      }

    cmcTcMasterTc3Unit4MsgIndex OBJECT-TYPE
      SYNTAX INTEGER (1..32000)
      ACCESS read-only
      STATUS mandatory
      DESCRIPTION
        "Index for the list of message entries. Its value ranges
         between 1 and the value of cmcTcMasterTc3Unit4NumberOfMsgs." 
      ::= { cmcTcMasterTc3Unit4MsgEntry 1 }

    cmcTcMasterTc3Unit4MsgText OBJECT-TYPE
      SYNTAX DisplayString (SIZE (0..20))
      ACCESS read-write
      STATUS mandatory
      DESCRIPTION
        "Descriptional text for each message (entry in the table)"
      ::= { cmcTcMasterTc3Unit4MsgEntry 2 }

    cmcTcMasterTc3Unit4MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc3Unit4OutputSet)
         17: door is unlocked by WEB
         18: door is unlocked by timer
         19: no access, wrong keycode or cardnumber
         20: orientation of PSM-Unit is circuit 1
         21: orientation of PSM-Unit is circuit 2"
      ::= { cmcTcMasterTc3Unit4MsgEntry 3 }

    cmcTcMasterTc3Unit4MsgRelay OBJECT-TYPE
      SYNTAX INTEGER {
        disable (1),
        enable (2)
      }
      ACCESS read-write
      STATUS mandatory
      DESCRIPTION
        "Setup of Alarm relay for this alarm
         1:        no switching of alarm relay             
         2:        switching of alarm relay" 
      ::= { cmcTcMasterTc3Unit4MsgEntry 4 }

    cmcTcMasterTc3Unit4MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc3Unit4MsgEntry 5 }

    cmcTcMasterTc3Unit4MsgTrap1 OBJECT-TYPE
      SYNTAX INTEGER {
        disable (1),
        enable (2)
      }
      ACCESS read-write
      STATUS mandatory
      DESCRIPTION
        "Trap receiver 1 activated"
      ::= { cmcTcMasterTc3Unit4MsgEntry 6 }

    cmcTcMasterTc3Unit4MsgTrap2 OBJECT-TYPE
      SYNTAX INTEGER {
        disable (1),
        enable (2)
      }
      ACCESS read-write
      STATUS mandatory
      DESCRIPTION
        "Trap receiver 2 activated"
      ::= { cmcTcMasterTc3Unit4MsgEntry 7 }
 
    cmcTcMasterTc3Unit4MsgTrap3 OBJECT-TYPE
      SYNTAX INTEGER {
        disable (1),
        enable (2)
      }
      ACCESS read-write
      STATUS mandatory
      DESCRIPTION
        "Trap receiver 3 activated"
      ::= { cmcTcMasterTc3Unit4MsgEntry 8 }

    cmcTcMasterTc3Unit4MsgTrap4 OBJECT-TYPE
      SYNTAX INTEGER {
        disable (1),
        enable (2)
      }
      ACCESS read-write
      STATUS mandatory
      DESCRIPTION
        "Trap receiver 4 and Event Logging activated"
      ::= { cmcTcMasterTc3Unit4MsgEntry 9 }

    cmcTcMasterTc3Unit4MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc3Unit4MsgEntry 10 }

--Status extension unit

  cmcTcMasterTc3ValuesRelay OBJECT-TYPE
    SYNTAX INTEGER {
      disable (1),
      enable (2)
    }
    ACCESS read-write
    STATUS mandatory
    DESCRIPTION
      "Setup of Alarm relay for alarm ext. unit(s)
       1:        no switching of alarm relay             
       2:        switching of alarm relay" 
    ::= { cmcTcMasterTc3StatusExtUnit 1 }

  cmcTcMasterTc3ValuesBeeper OBJECT-TYPE
    SYNTAX INTEGER {
      disable (1),
      enable (2)
    }
    ACCESS read-write
    STATUS mandatory
    DESCRIPTION
      "Setup of Alarm beeper for alarm ext. unit(s)
       1:        no audible alarm
       2:        audible alarm" 
    ::= { cmcTcMasterTc3StatusExtUnit 2 }

  cmcTcMasterTc3ValuesTrap1 OBJECT-TYPE
    SYNTAX INTEGER {
      disable (1),
      enable (2)
    }
    ACCESS read-write
    STATUS mandatory
    DESCRIPTION
      "Trap receiver 1 activated"
    ::= { cmcTcMasterTc3StatusExtUnit 3 }

  cmcTcMasterTc3ValuesTrap2 OBJECT-TYPE
    SYNTAX INTEGER {
      disable (1),
      enable (2)
    }
    ACCESS read-write
    STATUS mandatory
    DESCRIPTION
      "Trap receiver 2 activated"
    ::= { cmcTcMasterTc3StatusExtUnit 4 }
 
  cmcTcMasterTc3ValuesTrap3 OBJECT-TYPE
    SYNTAX INTEGER {
      disable (1),
      enable (2)
    }
    ACCESS read-write
    STATUS mandatory
    DESCRIPTION
      "Trap receiver 3 activated"
    ::= { cmcTcMasterTc3StatusExtUnit 5 }

  cmcTcMasterTc3ValuesTrap4 OBJECT-TYPE
    SYNTAX INTEGER {
      disable (1),
      enable (2)
    }
    ACCESS read-write
    STATUS mandatory
    DESCRIPTION
      "Trap receiver 4 and Event Logging activated"
    ::= { cmcTcMasterTc3StatusExtUnit 6 }
 
  cmcTcMasterTc3NumberOfValues OBJECT-TYPE
    SYNTAX INTEGER 
    ACCESS  read-only
    STATUS  mandatory
    DESCRIPTION
      "Number of values availabel on extension units connected to the CMC-TC"
    ::= { cmcTcMasterTc3StatusExtUnit 7 }

-- table with entry for each value available on extension units              

  cmcTcMasterTc3ValuesTable OBJECT-TYPE
    SYNTAX SEQUENCE OF CmcTcMasterTc3ValuesEntry
    ACCESS not-accessible
    STATUS mandatory
    DESCRIPTION
      "Headline of values-table"
    ::= { cmcTcMasterTc3StatusExtUnit 8 }

  cmcTcMasterTc3ValuesEntry OBJECT-TYPE
    SYNTAX CmcTcMasterTc3ValuesEntry
    ACCESS not-accessible
    STATUS mandatory
    DESCRIPTION
      "Entries of values-table"
    INDEX { cmcTcMasterTc3ValuesIndex }
    ::= { cmcTcMasterTc3ValuesTable 1 }

    CmcTcMasterTc3ValuesEntry ::=
      SEQUENCE {
        cmcTcMasterTc3ValuesIndex
          INTEGER,
        cmcTcMasterTc3ValuesText
          DisplayString (SIZE (0..20)),                
        cmcTcMasterTc3ValuesStatus
          INTEGER,
        cmcTcMasterTc3ValuesValue
          INTEGER,
        cmcTcMasterTc3ValuesSetHigh
          INTEGER,
        cmcTcMasterTc3ValuesSetLow
          INTEGER
      }

    cmcTcMasterTc3ValuesIndex OBJECT-TYPE
      SYNTAX INTEGER (1..32000)
      ACCESS read-only
      STATUS mandatory
      DESCRIPTION
        "Index for the list of value entries. Its value ranges
         between 1 and the value of cmcTcMasterTc3NumberOfValues." 
      ::= { cmcTcMasterTc3ValuesEntry 1 }

        
    cmcTcMasterTc3ValuesText OBJECT-TYPE
      SYNTAX DisplayString (SIZE (0..20))
      ACCESS read-write
      STATUS mandatory
      DESCRIPTION
        "Descriptional text for each value (entry in the table)
         of the extension card"
      ::= { cmcTcMasterTc3ValuesEntry 2 }
              
    cmcTcMasterTc3ValuesStatus OBJECT-TYPE
      SYNTAX INTEGER {
        notAvail(1),
        lost(2),
        changed(3),
        ok(4),
        tooLow(5),
        tooHigh(6),
        error(7)
      }
      ACCESS read-only
      STATUS mandatory
      DESCRIPTION
        "Actual status of the value of the extension card"
      ::= { cmcTcMasterTc3ValuesEntry 3 }

    cmcTcMasterTc3ValuesValue OBJECT-TYPE
      SYNTAX INTEGER 
      ACCESS read-only
      STATUS mandatory
      DESCRIPTION
        "Value of sensor"
      ::= { cmcTcMasterTc3ValuesEntry 4 }

    cmcTcMasterTc3ValuesSetHigh OBJECT-TYPE
      SYNTAX INTEGER (0..255) 
      ACCESS read-write
      STATUS mandatory
      DESCRIPTION
        "Value for high setpoint of sensor"
      ::= { cmcTcMasterTc3ValuesEntry 5 }

    cmcTcMasterTc3ValuesSetLow OBJECT-TYPE
      SYNTAX INTEGER (0..255) 
      ACCESS read-write
      STATUS mandatory
      DESCRIPTION
        "Value for low setpoint of sensor"
      ::= { cmcTcMasterTc3ValuesEntry 6 }

--cmcTcMasterTc3SetupGeneral-group

  cmcTcMasterTc3SetTempUnit OBJECT-TYPE
    SYNTAX INTEGER {
      celsius(1),
      fahrenheit(2)
    }
    ACCESS read-write
    STATUS mandatory
    DESCRIPTION
      "Unit of all temperature values and setpoints, Celsius or Fahrenheit"
   ::= { cmcTcMasterTc3SetupGeneral 1 }

  cmcTcMasterTc3SetBeeper OBJECT-TYPE
    SYNTAX INTEGER {
      off(1),
      on(2)
    }
    ACCESS read-write
    STATUS mandatory
    DESCRIPTION
      "Audible alarm in CMC-TC unit:
       (2): beeper is on
       (1): beeper is off (general)"
    ::= { cmcTcMasterTc3SetupGeneral 2 }


  cmcTcMasterTc3QuitRelay OBJECT-TYPE
    SYNTAX INTEGER {
      disabled(1),
      enabled(2)
    }
    ACCESS read-write
    STATUS mandatory
    DESCRIPTION
      "Enable or disable acknowledging currently active alarm relay 
       (with 'C' on CMC-TC)."
    ::= { cmcTcMasterTc3SetupGeneral 3 }

  cmcTcMasterTc3LogicRelay OBJECT-TYPE
    SYNTAX INTEGER {
      closeAtAlarm(1),
      openAtAlarm(2),
      off(3)
    }
    ACCESS read-write
    STATUS mandatory
    DESCRIPTION
      "Logic of alarm relay: 
       (1) Relay will pick up in case of an alarm
       (2) Relay will release in case of an alarm
       (3) Relay off (general)"
    ::= { cmcTcMasterTc3SetupGeneral 4 }

  cmcTcMasterTc3WebAccess OBJECT-TYPE
    SYNTAX INTEGER {
      viewOnly(1),
      fullAccess(2),
      off(3)
    }
    ACCESS read-write
    STATUS mandatory
    DESCRIPTION
      "Web access via HTTP: 
       (1) view only
       (2) full Access, read and set
       (3) Web disabled (general)"
    ::= { cmcTcMasterTc3SetupGeneral 5 }
 
  cmcTcMasterTc3SetupDate OBJECT-TYPE
    SYNTAX DisplayString (SIZE (0..10))
    ACCESS read-write
    STATUS mandatory
    DESCRIPTION
      "actual Date in format DD.MM.YYYY"
    ::= { cmcTcMasterTc3SetupGeneral 6 }

  cmcTcMasterTc3SetupTime OBJECT-TYPE
    SYNTAX DisplayString (SIZE (0..8))
    ACCESS read-write
    STATUS mandatory
    DESCRIPTION
      "actual Time in format HH:MM:SS, HH (0-23), MM (0-59), SS (0-59)"
    ::= { cmcTcMasterTc3SetupGeneral 7 }
 
-- table for timer function
 
  cmcTcMasterTc3TimerNumber OBJECT-TYPE
    SYNTAX INTEGER 
    ACCESS read-only
    STATUS mandatory
    DESCRIPTION
      "Number of timers available on this unit"
    ::= { cmcTcMasterTc3TimerTable1 1 }

  cmcTcMasterTc3TimerTable OBJECT-TYPE
    SYNTAX SEQUENCE OF CmcTcMasterTc3TimerEntry
    ACCESS not-accessible
    STATUS mandatory
    DESCRIPTION
      "Headline of timer-table"
    ::= { cmcTcMasterTc3TimerTable1 2 }

  cmcTcMasterTc3TimerEntry OBJECT-TYPE
    SYNTAX CmcTcMasterTc3TimerEntry
    ACCESS not-accessible
    STATUS mandatory
    DESCRIPTION
      "Entries of timer-table"
    INDEX { cmcTcMasterTc3TimerIndex }
    ::= { cmcTcMasterTc3TimerTable 1 }

    CmcTcMasterTc3TimerEntry ::=
      SEQUENCE {
        cmcTcMasterTc3TimerIndex
          INTEGER,
        cmcTcMasterTc3TimerStatus
          INTEGER,
        cmcTcMasterTc3TimerDayOfWeek
          INTEGER,  
        cmcTcMasterTc3TimeOn 
          DisplayString (SIZE (0..5)),                              
        cmcTcMasterTc3TimeOff 
          DisplayString (SIZE (0..5)),                              
        cmcTcMasterTc3TimeControl
          INTEGER,
        cmcTcMasterTc3TimerFunction
           INTEGER
      }

    cmcTcMasterTc3TimerIndex OBJECT-TYPE
      SYNTAX INTEGER (1..32000)
      ACCESS read-only
      STATUS mandatory
      DESCRIPTION
        "Index for the list of timer entries. Its value ranges
         between 1 and the value of cmcTcMasterTc3TimerNumber." 
      ::= { cmcTcMasterTc3TimerEntry 1 }

    cmcTcMasterTc3TimerStatus OBJECT-TYPE
      SYNTAX INTEGER {
        switchedOff(1),
        switchedOn(2),
        noTime(3) 
      }
      ACCESS read-only
      STATUS mandatory
      DESCRIPTION
        "Actual status of the timer"
      ::= { cmcTcMasterTc3TimerEntry 2 }

    cmcTcMasterTc3TimerDayOfWeek OBJECT-TYPE
      SYNTAX INTEGER {
        sun(1),
        mon(2),
        tue(3) ,
        wed(4),
        thu(5),
        fri(6),
        sat(7),
        sat-sun(8),
        mon-fri(9),
        mon-sun(10)
      }
      ACCESS read-write
      STATUS mandatory
      DESCRIPTION
        "Selection of day of week for timer to switch"
      ::= { cmcTcMasterTc3TimerEntry 3 }
             
    cmcTcMasterTc3TimeOn OBJECT-TYPE
      SYNTAX DisplayString (SIZE (0..5))
      ACCESS read-write
      STATUS mandatory
      DESCRIPTION
        "Time to switch on current function, 
         Format: HH:MM"
      ::= { cmcTcMasterTc3TimerEntry 4 }

    cmcTcMasterTc3TimeOff OBJECT-TYPE
      SYNTAX DisplayString (SIZE (0..5))
      ACCESS read-write
      STATUS mandatory
      DESCRIPTION
        "Time to switch off current function,
         Format: HH:MM"
      ::= { cmcTcMasterTc3TimerEntry 5 }

    cmcTcMasterTc3TimeControl OBJECT-TYPE
      SYNTAX INTEGER  {
        disabled(1),
        enabled(2)
      }
      ACCESS read-write
      STATUS mandatory
      DESCRIPTION
        "Control via RTC"
      ::= { cmcTcMasterTc3TimerEntry 6 }

    cmcTcMasterTc3TimerFunction OBJECT-TYPE
      SYNTAX INTEGER {
        disKeypad1-1 (1),
        disKeypad2-1 (2),
        disKeypad1-2 (3),
        disKeypad2-2 (4),
        disKeypad1-3 (5),
        disKeypad2-3 (6),
        disKeypad1-4 (7),
        disKeypad2-4 (8),
        unlDoor1-1 (9),
        unlDoor2-1 (10),
        unlDoor1-2 (11),
        unlDoor2-2 (12),
        unlDoor1-3 (13),
        unlDoor2-3 (14),
        unlDoor1-4 (15),
        unlDoor2-5 (16),
        disTrapRec1 (17),
        disTrapRec2 (18),
        disTrapRec3 (19),
        disTrapRec4 (20),
        disSMS (21),
        schedule1 (22),
        schedule2 (23),
        schedule3 (24),
        schedule4 (25)
      }
      ACCESS read-write
      STATUS mandatory
      DESCRIPTION
        "Function which is controlled via timer
         1:     unlock via keypad 1 on unit 1 or remote input lock 1 is disabled
         2:     unlock via keypad 2 on unit 1 or remote input lock 2 is disabled
         3      unlock via keypad 1 on unit 2 or remote input lock 1 is disabled
         4:     unlock via keypad 2 on unit 2 or remote input lock 2 is disabled
         5:     unlock via keypad 1 on unit 3 or remote input lock 1 is disabled
         6:     unlock via keypad 2 on unit 3 or remote input lock 2 is disabled
         7:     unlock via keypad 1 on unit 4 or remote input lock 1 is disabled
         8:     unlock via keypad 2 on unit 4 or remote input lock 2 is disabled
         9:     Lock of door 1 on unit 1 will be unlocked
         10:    Lock of door 2 on unit 1 will be unlocked
         11:    Lock of door 1 on unit 2 will be unlocked
         12:    Lock of door 2 on unit 2 will be unlocked
         13:    Lock of door 1 on unit 3 will be unlocked
         14:    Lock of door 2 on unit 3 will be unlocked
         15:    Lock of door 1 on unit 4 will be unlocked
         16:    Lock of door 2 on unit 4 will be unlocked
         17-20: sending Traps to this Trap receiver will be disabled
         21:    sending SMS will be disabled
         22-25: Scheduled alarm off"
      ::= { cmcTcMasterTc3TimerEntry 7 }

--cmcTcMasterTc3TrapTable-group

  cmcTcMasterTc3TraptableNumber OBJECT-TYPE
    SYNTAX INTEGER 
    ACCESS read-only
    STATUS mandatory
    DESCRIPTION
      "Number of trapTable entries. The number of trap-receiver"
    ::= { cmcTcMasterTc3Traps 1 }

  cmcTcMasterTc3TrapTableTable OBJECT-TYPE    
    SYNTAX SEQUENCE OF CmcTcMasterTc3TrapTableEntry
    ACCESS not-accessible
    STATUS mandatory
    DESCRIPTION
     "A list of trap-receiver entries"
    ::= { cmcTcMasterTc3Traps 2 }

  cmcTcMasterTc3TrapTableEntry OBJECT-TYPE
    SYNTAX CmcTcMasterTc3TrapTableEntry
    ACCESS not-accessible
    STATUS mandatory
    DESCRIPTION
      "Entries of cmcTcMasterTc3TrapTable"
    INDEX   { cmcTcMasterTc3TrapIndex }
    ::= { cmcTcMasterTc3TrapTableTable 1 }      
              
    CmcTcMasterTc3TrapTableEntry ::=
      SEQUENCE {
        cmcTcMasterTc3TrapIndex
          INTEGER,
        cmcTcMasterTc3TrapStatus
          INTEGER,
        cmcTcMasterTc3TrapIPaddress
          DisplayString
      }

    cmcTcMasterTc3TrapIndex OBJECT-TYPE
      SYNTAX INTEGER (1..32000)
      ACCESS read-only
      STATUS mandatory
      DESCRIPTION
        "Index for the trap-receiver-table. Its value ranges between
         1 and the value of cmcTcMasterTc3TraptableNumber "
      ::= { cmcTcMasterTc3TrapTableEntry 1 }

    cmcTcMasterTc3TrapStatus OBJECT-TYPE
      SYNTAX INTEGER {
        disabled(1),
        enabled(2)
      }
      ACCESS read-write
      STATUS mandatory
      DESCRIPTION
        "Enable or disable trap receiver"
      ::= { cmcTcMasterTc3TrapTableEntry 2 }

    cmcTcMasterTc3TrapIPaddress OBJECT-TYPE
      SYNTAX DisplayString (SIZE (0..15))
      ACCESS read-write
      STATUS mandatory
      DESCRIPTION
        "IP-address of trap-receiver"
      ::= { cmcTcMasterTc3TrapTableEntry 3 }

--cmcTcMasterTc3Control-group (Added in Version 1.1)

  cmcTcMasterTc1QuitUnit OBJECT-TYPE
    SYNTAX INTEGER {
      noQuit(1),
      quit(2),
    }
    ACCESS read-write
    STATUS mandatory
    DESCRIPTION
      "Command to quit (acknowledge) alarms of CMC-TC unit.
       Setting to 'quit' (2) will have same result as pressing 'C' on Units.
       Variable is automatically set back to 'noQuit' (1)."
    ::= { cmcTcMasterTc3Control 1 }

--cmcTcMasterDevice4-group

  cmcTcMasterDev4Type OBJECT-TYPE
    SYNTAX INTEGER {
      other (0),
      cmc (1),
      pcu (3),
      tc (4)
    }
    ACCESS read-only
    STATUS mandatory
    DESCRIPTION
      "Type of device4"
    ::= { cmcTcMasterDevice4 1 }

  cmcTcMasterDev4Status OBJECT-TYPE
    SYNTAX INTEGER {
      other (1),
      notConnected (2),
      normal (3),
      minor (4),
      major (5),
      configChanged (6),
      connectionLost (10)
    }
    ACCESS read-only
    STATUS mandatory
    DESCRIPTION
      "Status of device4"
    ::= { cmcTcMasterDevice4 2 }

  cmcTcMasterDev4Descr OBJECT-TYPE
    SYNTAX DisplayString (SIZE (0..255))
    ACCESS read-only
    STATUS mandatory
    DESCRIPTION
      "A textual description of the entity.  This value
       should include the full name and version
       identification of the system's hardware type,
       software operating-system, and networking
       software.  It is mandatory that this only contain
       printable ASCII characters."
    ::= { cmcTcMasterDevice4 3 }

  cmcTcMasterDev4UpTime OBJECT-TYPE
    SYNTAX TimeTicks
    ACCESS read-only
    STATUS mandatory
    DESCRIPTION
      "The time (in hundredths of a second) since the
       network management portion of the system was last
       re-initialized."
    ::= { cmcTcMasterDevice4 4 }

  cmcTcMasterDev4Contact OBJECT-TYPE
    SYNTAX DisplayString (SIZE (0..255))
    ACCESS read-write
    STATUS mandatory
    DESCRIPTION
      "The textual identification of the contact person
       for this managed node, together with information
       on how to contact this person."
    ::= { cmcTcMasterDevice4 5 }

  cmcTcMasterDev4Name OBJECT-TYPE
    SYNTAX DisplayString (SIZE (0..255))
    ACCESS read-write
    STATUS mandatory
    DESCRIPTION
      "An administratively-assigned name for this
       managed node.  By convention, this is the node's
       fully-qualified domain name."
    ::= { cmcTcMasterDevice4 6 }

  cmcTcMasterDev4Location OBJECT-TYPE
    SYNTAX DisplayString (SIZE (0..255))
    ACCESS read-write
    STATUS mandatory
    DESCRIPTION
      "The physical location of this node (e.g.,
       `telephone closet, 3rd floor')."
    ::= { cmcTcMasterDevice4 7 }

--cmcTcMasterCmc4Values-group

  cmcTcMasterCmc4ValueTemperature1 OBJECT-TYPE
    SYNTAX INTEGER
    ACCESS read-only
    STATUS mandatory
    DESCRIPTION
      "Actual value of temperature 1 in deg C"
    ::= { cmcTcMasterCmc4Values 1 }

  cmcTcMasterCmc4ValueTemperature2 OBJECT-TYPE
    SYNTAX INTEGER
    ACCESS read-only
    STATUS mandatory
    DESCRIPTION
      "Actual value of temperature 2 in deg C"
    ::= { cmcTcMasterCmc4Values 2 }

  cmcTcMasterCmc4ValuePowerSupply OBJECT-TYPE
    SYNTAX INTEGER
    ACCESS read-only
    STATUS mandatory
    DESCRIPTION
      "Actual value of power supply in V"
    ::= { cmcTcMasterCmc4Values 3 }

  cmcTcMasterCmc4ValueAnalogAux1 OBJECT-TYPE
    SYNTAX INTEGER
    ACCESS read-only
    STATUS mandatory
    DESCRIPTION
      "Actual value of aux. analog input 1
      (4-20mA = 0-100%)"
    ::= { cmcTcMasterCmc4Values 4 }

  cmcTcMasterCmc4ValueAnalogAux2 OBJECT-TYPE
    SYNTAX INTEGER
    ACCESS read-only
    STATUS mandatory
    DESCRIPTION
      "Actual value of aux. analog input 2
      (4-20mA = 0-100%)"
    ::= { cmcTcMasterCmc4Values 5 }

--cmcTcMasterCmc4Values-table-group

  cmcTcMasterCmc4ValuesNumber OBJECT-TYPE
    SYNTAX INTEGER
    ACCESS read-only
    STATUS mandatory
    DESCRIPTION
      "Number of value-table entries"
    ::= { cmcTcMasterCmc4Table1 1 }

  cmcTcMasterCmc4ValuesTable OBJECT-TYPE
    SYNTAX SEQUENCE OF CmcTcMasterCmc4ValuesEntry
    ACCESS not-accessible
    STATUS mandatory
    DESCRIPTION
      "Headline of value-table"
    ::= { cmcTcMasterCmc4Table1 2 }

  cmcTcMasterCmc4ValuesEntry OBJECT-TYPE
    SYNTAX CmcTcMasterCmc4ValuesEntry
    ACCESS not-accessible
    STATUS mandatory
    DESCRIPTION
      "Entries of value-table"
    INDEX { cmcTcMasterCmc4ValuesIndex }
    ::= { cmcTcMasterCmc4ValuesTable 1 }

  CmcTcMasterCmc4ValuesEntry ::=
    SEQUENCE {
      cmcTcMasterCmc4ValuesIndex
        INTEGER,
      cmcTcMasterCmc4ValuesText
        DisplayString (SIZE (0..31)),
      cmcTcMasterCmc4ValuesValue
        INTEGER,
      cmcTcMasterCmc4ValuesStatus
        INTEGER,
      cmcTcMasterCmc4ValuesMaxValue
        INTEGER,
      cmcTcMasterCmc4ValuesMinValue
        INTEGER
    }

    cmcTcMasterCmc4ValuesIndex OBJECT-TYPE
      SYNTAX INTEGER (1..32000)
      ACCESS read-only
      STATUS mandatory
      DESCRIPTION
        "Index for the list of value entries. Its value ranges
        between 1 and the value of valuesNumber."
      ::= { cmcTcMasterCmc4ValuesEntry 1 }

    cmcTcMasterCmc4ValuesText OBJECT-TYPE
      SYNTAX DisplayString (SIZE (0..31))
      ACCESS read-write
      STATUS mandatory
      DESCRIPTION
        "Text of the entry in the value-table"
      ::= { cmcTcMasterCmc4ValuesEntry 2 }

    cmcTcMasterCmc4ValuesValue OBJECT-TYPE
      SYNTAX INTEGER
      ACCESS read-only
      STATUS mandatory
      DESCRIPTION
        "Actual value of the value-table"
      ::= { cmcTcMasterCmc4ValuesEntry 3 }

    cmcTcMasterCmc4ValuesStatus OBJECT-TYPE
      SYNTAX INTEGER {
        valueOK(1),
        valueTooLow(2),
        valueTooHigh(3),
        valueERROR(4),
        notAvail(5)
      }
      ACCESS read-only
      STATUS mandatory
      DESCRIPTION
        "Status of the value"
      ::= { cmcTcMasterCmc4ValuesEntry 4 }

    cmcTcMasterCmc4ValuesMaxValue OBJECT-TYPE
      SYNTAX INTEGER
      ACCESS read-write
      STATUS mandatory
      DESCRIPTION
        "Value for max. alarm"
      ::= { cmcTcMasterCmc4ValuesEntry 5 }

    cmcTcMasterCmc4ValuesMinValue OBJECT-TYPE
      SYNTAX INTEGER
      ACCESS read-write
      STATUS mandatory
      DESCRIPTION
        "Value for min. alarm"
      ::= { cmcTcMasterCmc4ValuesEntry 6 }

--cmcTcMasterCmc4status-group

  cmcTcMasterCmc4StatusTemperature1 OBJECT-TYPE
    SYNTAX DisplayString (SIZE (0..31))
    ACCESS read-only
    STATUS mandatory
    DESCRIPTION
      "Status temperature 1, OK/ too low/ too high
       (see setpoints of temperature 1)"
    ::= { cmcTcMasterCmc4Status 1 }

  cmcTcMasterCmc4StatusTemperature2 OBJECT-TYPE
    SYNTAX DisplayString (SIZE (0..31))
    ACCESS read-only
    STATUS mandatory
    DESCRIPTION
      "Status temperature 2, OK/ too low/ too high
       (see setpoints of temperature 2)"
    ::= { cmcTcMasterCmc4Status 2 }

  cmcTcMasterCmc4StatusFan1 OBJECT-TYPE
    SYNTAX DisplayString (SIZE (0..31))
    ACCESS read-only
    STATUS mandatory
    DESCRIPTION
      "Status fan 1, Stop/ running/ fault"
    ::= { cmcTcMasterCmc4Status 3 }

  cmcTcMasterCmc4StatusFan2 OBJECT-TYPE
    SYNTAX DisplayString (SIZE (0..31))
    ACCESS read-only
    STATUS mandatory
    DESCRIPTION
      "Status fan 2, Stop/ running/ fault"
    ::= { cmcTcMasterCmc4Status 4 }

  cmcTcMasterCmc4StatusHeating OBJECT-TYPE
    SYNTAX DisplayString (SIZE (0..31))
    ACCESS read-only
    STATUS mandatory
    DESCRIPTION
      "Status heating, On/Off"
    ::= { cmcTcMasterCmc4Status 5 }

  cmcTcMasterCmc4StatusPowerSupply OBJECT-TYPE
    SYNTAX DisplayString (SIZE (0..31))
    ACCESS read-only
    STATUS mandatory
    DESCRIPTION
      "Status power supply, OK/ too low/ too high
       (see setpoints of power supply)"
    ::= { cmcTcMasterCmc4Status 6 }

  cmcTcMasterCmc4StatusAnalogAux1 OBJECT-TYPE
    SYNTAX DisplayString (SIZE (0..31))
    ACCESS read-only
    STATUS mandatory
    DESCRIPTION
      "Status aux analog input 1, OK/ too low/ too high"
    ::= { cmcTcMasterCmc4Status 7 }

  cmcTcMasterCmc4StatusAnalogAux2 OBJECT-TYPE
    SYNTAX DisplayString (SIZE (0..31))
    ACCESS read-only
    STATUS mandatory
    DESCRIPTION
      "Status aux analog input 2, OK/ too low/ too high"
    ::= { cmcTcMasterCmc4Status 8 }

  cmcTcMasterCmc4StatusDoor OBJECT-TYPE
    SYNTAX DisplayString (SIZE (0..31))
    ACCESS read-only
    STATUS mandatory
    DESCRIPTION
      "Status door, open/closed/locked"
    ::= { cmcTcMasterCmc4Status 9 }

  cmcTcMasterCmc4StatusUps1 OBJECT-TYPE
    SYNTAX DisplayString (SIZE (0..31))
    ACCESS read-only
    STATUS mandatory
    DESCRIPTION
      "Status UPS 1, OK/ fault"
    ::= { cmcTcMasterCmc4Status 10 }

  cmcTcMasterCmc4StatusUps2 OBJECT-TYPE
    SYNTAX DisplayString (SIZE (0..31))
    ACCESS read-only
    STATUS mandatory
    DESCRIPTION
      "Status UPS 2, OK/ fault"
    ::= { cmcTcMasterCmc4Status 11 }

  cmcTcMasterCmc4StatusSmokeSensor OBJECT-TYPE
    SYNTAX DisplayString (SIZE (0..31))
    ACCESS read-only
    STATUS mandatory
    DESCRIPTION
      "Status smoke-sensor, OK/ smoke"
    ::= { cmcTcMasterCmc4Status 12 }

  cmcTcMasterCmc4StatusVibrationSensor OBJECT-TYPE
    SYNTAX DisplayString (SIZE (0..31))
    ACCESS read-only
    STATUS mandatory
    DESCRIPTION
      "Status vibration sensor, OK/ vibration"
    ::= { cmcTcMasterCmc4Status 13 }

  cmcTcMasterCmc4StatusMessage OBJECT-TYPE
    SYNTAX DisplayString (SIZE (0..31))
    ACCESS read-only
    STATUS mandatory
    DESCRIPTION
      "Message from CMC"
    ::= { cmcTcMasterCmc4Status 14 }

  cmcTcMasterCmc4ValueOperatingTime OBJECT-TYPE
    SYNTAX DisplayString (SIZE (0..31))
    ACCESS read-only
    STATUS mandatory
    DESCRIPTION
      "Operating time CMC-unit"
    ::= { cmcTcMasterCmc4Status 15 }

  cmcTcMasterCmc4StatusUnit OBJECT-TYPE
    SYNTAX INTEGER {
      unitCelsius(1),
      unitFahrenheit(2)
    }
    ACCESS read-only
    STATUS mandatory
    DESCRIPTION
      "Unit of temperature-values, Celsius or Fahrenheit"
   ::= { cmcTcMasterCmc4Status 16 }


--cmcTcMasterCmc4Status-table-group

  cmcTcMasterCmc4StatusNumber OBJECT-TYPE
    SYNTAX INTEGER 
    ACCESS read-only
    STATUS mandatory
    DESCRIPTION
      "Number of status-table entries"
    ::= { cmcTcMasterCmc4Table 1 }

  cmcTcMasterCmc4StatusTable OBJECT-TYPE
    SYNTAX SEQUENCE OF CmcTcMasterCmc4StatusEntry
    ACCESS not-accessible
    STATUS mandatory
    DESCRIPTION
      "Headline of table"
    ::= { cmcTcMasterCmc4Table 2 }

  cmcTcMasterCmc4StatusEntry OBJECT-TYPE
    SYNTAX CmcTcMasterCmc4StatusEntry
    ACCESS not-accessible
    STATUS mandatory
    DESCRIPTION
      "A list of status entries.  The number of
       entries is given by the value of cmcTcMasterCmc4StatusNumber." 
    INDEX { cmcTcMasterCmc4StatusIndex }
    ::= { cmcTcMasterCmc4StatusTable 1 }

  CmcTcMasterCmc4StatusEntry ::=
    SEQUENCE {
      cmcTcMasterCmc4StatusIndex
        INTEGER,
      cmcTcMasterCmc4StatusText
        DisplayString (SIZE (0..31)),
      cmcTcMasterCmc4StatusStatus
        INTEGER              
    }

    cmcTcMasterCmc4StatusIndex OBJECT-TYPE
      SYNTAX INTEGER (1..32000)
      ACCESS read-only
      STATUS mandatory
      DESCRIPTION
        "Index fo the list of status entries. Its value ranges
         between 1 and the value of cmcTcMasterCmc4StatusNumber." 
      ::= { cmcTcMasterCmc4StatusEntry 1 }

    cmcTcMasterCmc4StatusText OBJECT-TYPE
      SYNTAX DisplayString (SIZE (0..31))
      ACCESS read-write
      STATUS mandatory
      DESCRIPTION
        "Text of the entry in the status-table"
      ::= { cmcTcMasterCmc4StatusEntry 2 }

    cmcTcMasterCmc4StatusStatus OBJECT-TYPE
      SYNTAX INTEGER  {
        statusOK(1),
        alarm(2),
        security(3),
        notAvail(4)
      }
      ACCESS read-only
      STATUS mandatory
      DESCRIPTION
        "Status of the table entry"
      ::= { cmcTcMasterCmc4StatusEntry 3 }

--******************************************************************************

--cmcTCMasterCmc4Set-group

  cmcTcMasterCmc4StatusAccess OBJECT-TYPE
    SYNTAX DisplayString (SIZE (0..31))
    ACCESS read-write
    STATUS mandatory
    DESCRIPTION
      "Status access"
    ::= { cmcTcMasterCmc4Set 1 }

  cmcTcMasterCmc4SetDoor OBJECT-TYPE
    SYNTAX INTEGER {
      lockDoor(1),
      openDoorTime(2),
      openDoorAccess(3),
      openDoor(4)
    }
    ACCESS read-write
    STATUS mandatory
    DESCRIPTION
      "Set door, see table"
    ::= { cmcTcMasterCmc4Set 2 }

  cmcTcMasterCmc4SetMessage OBJECT-TYPE
    SYNTAX DisplayString (SIZE (0..31))
    ACCESS read-write
    STATUS mandatory
    DESCRIPTION
      "Set message"
    ::= { cmcTcMasterCmc4Set 3 }

  cmcTcMasterCmc4SetFault        OBJECT-TYPE
    SYNTAX INTEGER {
      clearFault(1),
      setFault(2)
    }
    ACCESS read-write
    STATUS mandatory
    DESCRIPTION
      "Set fault, see table"
    ::= { cmcTcMasterCmc4Set 4 }

--cmcTcMasterCmc4RelayControl-group

  cmcTcMasterCmc4RelaytableMaxNum OBJECT-TYPE
    SYNTAX INTEGER 
    ACCESS read-only
    STATUS mandatory
    DESCRIPTION
      "Number of table entries"
    ::= { cmcTcMasterCmc4RelayControl 1 }

  cmcTcMasterCmc4RelayTable OBJECT-TYPE
    SYNTAX SEQUENCE OF CmcTcMasterCmc4RelayEntry
    ACCESS not-accessible
    STATUS mandatory
    DESCRIPTION
      "Headline of table for relay control"
    ::= { cmcTcMasterCmc4RelayControl 2 }

  cmcTcMasterCmc4RelayEntry OBJECT-TYPE
    SYNTAX CmcTcMasterCmc4RelayEntry
    ACCESS not-accessible
    STATUS mandatory
    DESCRIPTION
      "Entries"
    INDEX { cmcTcMasterCmc4RelaytableIndex }
    ::= { cmcTcMasterCmc4RelayTable 1 }

  CmcTcMasterCmc4RelayEntry ::=
    SEQUENCE {
      cmcTcMasterCmc4RelaytableIndex
        INTEGER,
      cmcTcMasterCmc4RelaytableText
	DisplayString (SIZE (0..31)),
      cmcTcMasterCmc4RelaytableStatus
        INTEGER              
    }

    cmcTcMasterCmc4RelaytableIndex OBJECT-TYPE
      SYNTAX INTEGER (1..32000)
      ACCESS read-only
      STATUS mandatory
      DESCRIPTION
        "Index for the relay-table. Its value ranges
         between 1 and cmcTcMasterCmc4RelaytableMaxNum"
      ::= { cmcTcMasterCmc4RelayEntry 1 }

    cmcTcMasterCmc4RelaytableText OBJECT-TYPE
      SYNTAX DisplayString (SIZE (0..31))
      ACCESS read-write
      STATUS mandatory
      DESCRIPTION
        "Description-Text for each relay in the table"
      ::= { cmcTcMasterCmc4RelayEntry 2 }

    cmcTcMasterCmc4RelaytableStatus OBJECT-TYPE
      SYNTAX INTEGER  {
        relayOFF(1),
        relayON(2),
        notAvail(3)
      }
      ACCESS read-write
      STATUS mandatory
      DESCRIPTION
        "Status of relays in the table"
      ::= { cmcTcMasterCmc4RelayEntry 3 }

--cmcTcMasterCmc4Setpoints-group

  cmcTcMasterCmc4SetpointFan1 OBJECT-TYPE
    SYNTAX INTEGER 
    ACCESS read-write
    STATUS mandatory
    DESCRIPTION
      "Setpoint Fan 1 in C, Fan 1 will start
       if temperature 1 exceeds this value"
    ::= { cmcTcMasterCmc4Setpoints 1 }

  cmcTcMasterCmc4SetpointFan2 OBJECT-TYPE
    SYNTAX INTEGER 
    ACCESS read-write
    STATUS mandatory
    DESCRIPTION
      "Setpoint Fan 2 in C, Fan 2 will start
       if temperature 2 exceeds this value"
    ::= { cmcTcMasterCmc4Setpoints 2 }

  cmcTcMasterCmc4SetpointHeating OBJECT-TYPE
    SYNTAX INTEGER 
    ACCESS read-write
    STATUS mandatory
    DESCRIPTION
      "Setpoint heating in C, heating will start
       if lowest value of temperature 1 and 2 falls below this value"
    ::= { cmcTcMasterCmc4Setpoints 3 }

  cmcTcMasterCmc4SetpointHighTemperature1 OBJECT-TYPE
    SYNTAX INTEGER 
    ACCESS read-write
    STATUS mandatory
    DESCRIPTION
      "Setpoint high value alarm temperature 1"
    ::= { cmcTcMasterCmc4Setpoints 4 }

  cmcTcMasterCmc4SetpointLowTemperature1 OBJECT-TYPE
    SYNTAX INTEGER 
    ACCESS read-write
    STATUS mandatory
    DESCRIPTION
      "Setpoint low value alarm temperature 1"
    ::= { cmcTcMasterCmc4Setpoints 5 }

  cmcTcMasterCmc4SetpointHighTemperature2 OBJECT-TYPE
    SYNTAX INTEGER 
    ACCESS read-write
    STATUS mandatory
    DESCRIPTION
      "Setpoint high value alarm temperature 2"
    ::= { cmcTcMasterCmc4Setpoints 6 }

  cmcTcMasterCmc4SetpointLowTemperature2 OBJECT-TYPE
    SYNTAX INTEGER 
    ACCESS read-write
    STATUS mandatory
    DESCRIPTION
      "Setpoint low value alarm temperature 2"
    ::= { cmcTcMasterCmc4Setpoints 7 }

  cmcTcMasterCmc4SetpointHighVoltage OBJECT-TYPE
    SYNTAX INTEGER 
    ACCESS read-write
    STATUS mandatory
    DESCRIPTION
      "Setpoint high value supply voltage alarm"
    ::= { cmcTcMasterCmc4Setpoints 8 }

  cmcTcMasterCmc4SetpointLowVoltage OBJECT-TYPE
    SYNTAX INTEGER
    ACCESS read-write
    STATUS mandatory
    DESCRIPTION
      "Setpoint low value supply voltage alarm"
    ::= { cmcTcMasterCmc4Setpoints 9 }

  cmcTcMasterCmc4SetpointLowAux1 OBJECT-TYPE
    SYNTAX INTEGER 
    ACCESS read-write
    STATUS mandatory
    DESCRIPTION
      "Setpoint low value Aux input 1 alarm"
    ::= { cmcTcMasterCmc4Setpoints 10 }

  cmcTcMasterCmc4SetpointHighAux1 OBJECT-TYPE
    SYNTAX INTEGER 
    ACCESS read-write
    STATUS mandatory
    DESCRIPTION
      "Setpoint high value Aux input 1 alarm"
    ::= { cmcTcMasterCmc4Setpoints 11 }

  cmcTcMasterCmc4SetpointLowAux2 OBJECT-TYPE
    SYNTAX INTEGER 
    ACCESS read-write
    STATUS mandatory
    DESCRIPTION
      "Setpoint low value Aux input 2 alarm"
    ::= { cmcTcMasterCmc4Setpoints 12 }

  cmcTcMasterCmc4SetpointHighAux2 OBJECT-TYPE
    SYNTAX INTEGER 
    ACCESS read-write
    STATUS mandatory
    DESCRIPTION
      "Setpoint high value Aux input alarm"
    ::= { cmcTcMasterCmc4Setpoints 13 }

--cmcTcMasterCmc4TrapControl-group

  cmcTcMasterCmc4SetTrapRepeat OBJECT-TYPE
    SYNTAX INTEGER {
      disableTrapRepeat(1),
      enableTrapRepeat(2)
    }
    ACCESS read-write
    STATUS mandatory
    DESCRIPTION
      "Enable/disable repeating of traps. If enabled, traps will
       be repeated after a repeat time, set in setTrapRepeatTime.
       Repeating can be stopped by setting setTrapQuit to quitTrap"
    ::= { cmcTcMasterCmc4TrapControl 1 }

  cmcTcMasterCmc4SetTrapRepeatTime OBJECT-TYPE
    SYNTAX INTEGER 
    ACCESS read-write
    STATUS mandatory
    DESCRIPTION
      "Time value (sec) for trap-repeating, if setTrapRepeat is enabled"
    ::= { cmcTcMasterCmc4TrapControl 2 }

  cmcTcMasterCmc4SetTrapQuit OBJECT-TYPE
    SYNTAX INTEGER {
      quitTrap(1),
      quitTrapOK(2),
      noTrapToQuit(3),
      trapToQuit(4)
    }
    ACCESS read-write
    STATUS mandatory
    DESCRIPTION
      "Quit trap to stop repeating."
    ::= { cmcTcMasterCmc4TrapControl 3 }

--cmcTcMasterCmc4TrapTable-group

  cmcTcMasterCmc4TraptableNumber OBJECT-TYPE
    SYNTAX INTEGER 
    ACCESS read-only
    STATUS mandatory
    DESCRIPTION
      "Number of trapTable entries. The number of trap-receiver"
    ::= { cmcTcMasterCmc4Traps 1 }

  cmcTcMasterCmc4TrapTable OBJECT-TYPE
    SYNTAX SEQUENCE OF CmcTcMasterCmc4TrapEntry
    ACCESS not-accessible
    STATUS mandatory
    DESCRIPTION
      "A list of trap-receiver entries"
    ::= { cmcTcMasterCmc4Traps 2 }

  cmcTcMasterCmc4TrapEntry OBJECT-TYPE
    SYNTAX CmcTcMasterCmc4TrapEntry
    ACCESS not-accessible
    STATUS mandatory
    DESCRIPTION
      "Entries of trapTable"
    INDEX { cmcTcMasterCmc4TrapIndex }
    ::= { cmcTcMasterCmc4TrapTable 1 }

  CmcTcMasterCmc4TrapEntry ::=
    SEQUENCE {
      cmcTcMasterCmc4TrapIndex
        INTEGER,
      cmcTcMasterCmc4TrapStatus
        INTEGER,
      cmcTcMasterCmc4TrapIPaddress
        DisplayString
    }

    cmcTcMasterCmc4TrapIndex OBJECT-TYPE
      SYNTAX INTEGER (1..32000)
      ACCESS read-only
      STATUS mandatory
      DESCRIPTION
        "Index for the trap-receiver-table. Its value ranges between
         1 and the value of cmcTcMasterCmc4TraptableNumber "
      ::= { cmcTcMasterCmc4TrapEntry 1 }

    cmcTcMasterCmc4TrapStatus OBJECT-TYPE
      SYNTAX INTEGER  {
        enabled(1),
        disabled(2)
      }
      ACCESS read-write
      STATUS mandatory
      DESCRIPTION
        "Enable or disable trap receiver"
      ::= { cmcTcMasterCmc4TrapEntry 2 }

    cmcTcMasterCmc4TrapIPaddress OBJECT-TYPE
      SYNTAX DisplayString (SIZE (0..31))
      ACCESS read-write
      STATUS mandatory
      DESCRIPTION
        "IP-address of trap-receiver"
      ::= { cmcTcMasterCmc4TrapEntry 3 }

--cmcTcMasterPcu4MibRev-group
          
  cmcTcMasterPcu4MibMajRev OBJECT-TYPE
    SYNTAX INTEGER (1..32000)
    ACCESS read-only
    STATUS mandatory
    DESCRIPTION
      "The Major Revision level.
       A change in the major revision level represents a major change
       in the architecture of the MIB. A change in the major revision 
       level may indicate a significant change in the information,
       correct interpretation of data may require a MIB document
       with the same major revision level."
    ::= { cmcTcMasterPcu4MibRev 1 }

  cmcTcMasterPcu4MibMinRev OBJECT-TYPE
    SYNTAX INTEGER (0..32000)
    ACCESS read-only
    STATUS mandatory
    DESCRIPTION
      "The Minor Revision level.
       A change in the minor revision level may represent some minor
       additional support, no changes to any pre-existing information
       has occurred."
    ::= { cmcTcMasterPcu4MibRev 2 }

  cmcTcMasterPcu4MibCondition OBJECT-TYPE
    SYNTAX INTEGER {
      other (1),
      ok (2),
      degraded (3),
      failed (4)
    }
    ACCESS read-only
    STATUS mandatory
    DESCRIPTION
      "The overall condition (status) of the system represented by
       this MIB. 
       (2) OK
       (3) a minor problem, warning condition (yellow LED on PCU)
       (4) a major problem (red LED on PCU)"
    ::= { cmcTcMasterPcu4MibRev 3 }

--cmcTcMasterPcu4Values-group

  cmcTcMasterPcu4ValueEnergy1 OBJECT-TYPE
    SYNTAX INTEGER 
    ACCESS read-only
    STATUS mandatory
    DESCRIPTION
      "Total value of the Energy (Wh), measured on IEC input 1"
    ::= { cmcTcMasterPcu4Values 1 }

  cmcTcMasterPcu4ValueEnergy2 OBJECT-TYPE
    SYNTAX INTEGER 
    ACCESS read-only
    STATUS mandatory
    DESCRIPTION
      "Actual value of the Energy (Wh), measured on IEC input 2"
    ::= { cmcTcMasterPcu4Values 2 }

  cmcTcMasterPcu4ValueEnergy1Time OBJECT-TYPE
    SYNTAX INTEGER 
    ACCESS read-only
    STATUS mandatory
    DESCRIPTION
      "Actual value of the Energy (Wh), measured on IEC input 1, can be set to 0
       Value can be used to calculate the energy over a fixed time"
    ::= { cmcTcMasterPcu4Values 3 }

  cmcTcMasterPcu4ValueEnergy2Time OBJECT-TYPE
    SYNTAX INTEGER 
    ACCESS read-only
    STATUS mandatory
    DESCRIPTION
      "Actual value of the Energy (Wh), measured on IEC input 2, can be set to 0.
       Value can be used to calculate the energy over a fixed time"
    ::= { cmcTcMasterPcu4Values 4 }

  cmcTcMasterPcu4ValuePower1 OBJECT-TYPE
    SYNTAX INTEGER 
    ACCESS read-only
    STATUS mandatory
    DESCRIPTION
      "Calculated actual power 1 (W). Calculated from cmcTcMasterPcu4ValueEnergy1/time"
    ::= { cmcTcMasterPcu4Values 5 }
          
  cmcTcMasterPcu4ValuePower2 OBJECT-TYPE
    SYNTAX INTEGER 
    ACCESS read-only
    STATUS mandatory
    DESCRIPTION
      "Calculated actual power 2 (W). Calculated from cmcTcMasterPcu4ValueEnergy2/time"
    ::= { cmcTcMasterPcu4Values 6 }
          
  cmcTcMasterPcu4ValueTemperature OBJECT-TYPE
    SYNTAX INTEGER 
    ACCESS read-only
    STATUS mandatory
    DESCRIPTION
      "Actual value of temperature 1 in deg C or deg F"
    ::= { cmcTcMasterPcu4Values 7 }
          
--cmcTcMasterPcu4Status-group

  cmcTcMasterPcu4StatusInput1 OBJECT-TYPE
    SYNTAX INTEGER {
      false(1),
      true(2),
      pending(3),
      notAvail(4)
    }
    ACCESS read-only
    STATUS mandatory
    DESCRIPTION
      "Status of digital Input 1
       (1) digital signal is true (contact closed if setup is NO)
       (2) digital signal is false(contact opened if setup is NO),
       note setup of input (NO/NC)
       (3) digital input is pending, note setup of delay"
    ::= { cmcTcMasterPcu4Status 1 }

  cmcTcMasterPcu4StatusInput2 OBJECT-TYPE
    SYNTAX INTEGER {
      false(1),
      true(2),
      pending(3),
      notAvail(4)
    }
    ACCESS read-only
    STATUS mandatory
    DESCRIPTION
      "Status of digital Input 2
       (1) digital signal is true (contact closed if setup is NO)
       (2) digital signal is false(contact opened if setup is NO),
       note setup of input (NO/NC)
       (3) digital input is pending, note setup of delay"
    ::= { cmcTcMasterPcu4Status 2 }

  cmcTcMasterPcu4StatusPower1 OBJECT-TYPE
    SYNTAX INTEGER {
      ok(1),
      tooHigh(2),
      tooLow(3),
      warning(4),
      error(5),
      notAvail(6)
    }
    ACCESS read-only
    STATUS mandatory
    DESCRIPTION
      "Status Power 1, see setpoints"
    ::= { cmcTcMasterPcu4Status 3 }

  cmcTcMasterPcu4StatusPower2 OBJECT-TYPE
    SYNTAX INTEGER {
      ok(1),
      tooHigh(2),
      tooLow(3),
      warning(4),
      error(5),
      notAvail(6)
    }
    ACCESS read-only
    STATUS mandatory
    DESCRIPTION
      "Status Power 2, see setpoints"
    ::= { cmcTcMasterPcu4Status 4 }

  cmcTcMasterPcu4StatusTemperature OBJECT-TYPE
    SYNTAX INTEGER {
      ok(1),
      tooHigh(2),
      tooLow(3),
      warning(4),
      error(5)
    }
    ACCESS read-only
    STATUS mandatory
    DESCRIPTION
      "Status temperature 1, OK/ too high/ too low
       (see setpoints of temperature 1)"
    ::= { cmcTcMasterPcu4Status 5 }

--cmcTcMasterPcu4Status-table-group

  cmcTcMasterPcu4OutletsNumber OBJECT-TYPE
    SYNTAX INTEGER 
    ACCESS read-only
    STATUS mandatory
    DESCRIPTION
      "Number of value-table entries=number of outlets available on this unit"
    ::= { cmcTcMasterPcu4StatusTable1 1 }

  cmcTcMasterPcu4StatusTable OBJECT-TYPE
    SYNTAX SEQUENCE OF CmcTcMasterPcu4StatusEntry
    ACCESS not-accessible
    STATUS mandatory
    DESCRIPTION
      "Headline of status-table"
    ::= { cmcTcMasterPcu4StatusTable1 2 }

  cmcTcMasterPcu4StatusEntry OBJECT-TYPE
    SYNTAX CmcTcMasterPcu4StatusEntry
    ACCESS not-accessible
    STATUS mandatory
    DESCRIPTION
      "Entries of status-table"
    INDEX { cmcTcMasterPcu4StatusIndex }
    ::= { cmcTcMasterPcu4StatusTable 1 }

    CmcTcMasterPcu4StatusEntry ::=
      SEQUENCE {
        cmcTcMasterPcu4StatusIndex
          INTEGER,
        cmcTcMasterPcu4StatusText
          DisplayString (SIZE (0..31)),                
        cmcTcMasterPcu4StatusStatus
          INTEGER,
        cmcTcMasterPcu4ControlSNMP
          INTEGER,
        cmcTcMasterPcu4FrontSwitch
          INTEGER,
        cmcTcMasterPcu4Delay
          INTEGER,
        cmcTcMasterPcu4Input1
          INTEGER,
        cmcTcMasterPcu4Input2
          INTEGER,
        cmcTcMasterPcu4Temperature
          INTEGER,          
        cmcTcMasterPcu4Power
          INTEGER,          
        cmcTcMasterPcu4RestoreOutputStatus
          INTEGER           
      }

    cmcTcMasterPcu4StatusIndex OBJECT-TYPE
      SYNTAX INTEGER (1..32000)
      ACCESS read-only
      STATUS mandatory
      DESCRIPTION
        "Index for the list of value entries. Its value ranges
         between 1 and the value of cmcTcMasterPcu4OutletsNumber."
      ::= { cmcTcMasterPcu4StatusEntry 1 }

    cmcTcMasterPcu4StatusText OBJECT-TYPE
      SYNTAX DisplayString (SIZE (0..31))
      ACCESS read-write
      STATUS mandatory
      DESCRIPTION
        "Descriptional text for each outlet (entry in the table)"
      ::= { cmcTcMasterPcu4StatusEntry 2 }
              
    cmcTcMasterPcu4StatusStatus OBJECT-TYPE
      SYNTAX INTEGER {
        ok(1),
        onFrontKey(2),
        offFrontKey(3),
        onWEB(4),
        offWEB(5),
        onInput1(6),
        offInput1(7),
        onInput2(8),
        offInput2(9),
        onTemp(10),
        offTemp(11),
        onSNMP(12),
        offSNMP(13),
        onTimer(14),
        offTimer(15),
        onDelay(16),
        onConsole(17),
        offConsole(18),
        onReboot(19), 
        offReboot(20),
        onPower(21),
        offPower(22)
      }
      ACCESS read-only
      STATUS mandatory
      DESCRIPTION
        "Actual status of the outlet"
      ::= { cmcTcMasterPcu4StatusEntry 3 }

    cmcTcMasterPcu4ControlSNMP OBJECT-TYPE
      SYNTAX INTEGER  {
        on(1),
        off(2)
      }
      ACCESS read-write
      STATUS mandatory
      DESCRIPTION
        "Control via SNMP"
      ::= { cmcTcMasterPcu4StatusEntry 4 }

    cmcTcMasterPcu4FrontSwitch OBJECT-TYPE
      SYNTAX INTEGER {
        disabled(1),
        enabled(2)
      }
      ACCESS read-write
      STATUS mandatory
      DESCRIPTION
        "Control via front switch"
      ::= { cmcTcMasterPcu4StatusEntry 5 }
 
    cmcTcMasterPcu4Delay OBJECT-TYPE
      SYNTAX INTEGER (0..300)
      ACCESS read-write
      STATUS mandatory
      DESCRIPTION
        "Value for delay time in seconds.
         Value>0: Output is switched off for this time (in sec)"
      ::= { cmcTcMasterPcu4StatusEntry 6 }

    cmcTcMasterPcu4Input1 OBJECT-TYPE
      SYNTAX INTEGER {
        disabled(1),
        switchOn(2),
        switchOff(3),
        switchOnOff(4)
      }
      ACCESS read-write
      STATUS mandatory
      DESCRIPTION
        "Control via digital input 1
         (1): disabled
         (2): output is switched on in case of input 1 alarm
         (3): output is switched off in case of input 1 alarm
         (4): output has same status as input 1"
      ::= { cmcTcMasterPcu4StatusEntry 7 }

    cmcTcMasterPcu4Input2 OBJECT-TYPE
      SYNTAX INTEGER {
        disabled(1),
        switchOn(2),
        switchOff(3),
        switchOnOff(4)
      }
      ACCESS read-write
      STATUS mandatory
      DESCRIPTION
        "Control via digital input 2
         (1): disabled
         (2): output is switched on in case of input 2 alarm
         (3): output is switched off in case of input 2 alarm
         (4): output has same status as input 2"             
      ::= { cmcTcMasterPcu4StatusEntry 8 }

    cmcTcMasterPcu4Temperature OBJECT-TYPE
      SYNTAX INTEGER {
        disabled(1),
        switchOffAlarm(2),
        switchOnAlarm(3),
        switchOffSetpoint(4),
        switchOnSetpoint(5)
      }
      ACCESS read-write
      STATUS mandatory
      DESCRIPTION
        "Control via temperature alarm or setpoint
         (1): disabled
         (2): output is switched off in case of temperature alarm
         (3): output is switched on in case of temperature alarm
         (4): output is switched off if temperature setpoint (cmcTcMasterPcu4SetpointTemperature)
              is reached
         (5): output is switched on if temperature setpoint (cmcTcMasterPcu4SetpointTemperature)
              is reached"
      ::= { cmcTcMasterPcu4StatusEntry 9 }   
    
    cmcTcMasterPcu4Power OBJECT-TYPE
      SYNTAX INTEGER {
        disabled(1),
        switchOffAlarm(2),
        switchOffWarning(3),
        switchOnAlarm(4),
        switchOnWarning(5)
      }
      ACCESS read-write
      STATUS mandatory
      DESCRIPTION
        "Control via power setpoint
         (1): disabled
         (2): output is switched off upon power high alarm (cmcTcMasterPcu4SetpointHighPower1)
         (3): output is switched off upon power warning (cmcTcMasterPcu4SetpointWarningPower1)
         (4): output is switched on upon power alarm (cmcTcMasterPcu4SetpointHigh(Low)Power1)
         (5): output is switched on upon power warning (cmcTcMasterPcu4SetpointWarningPower1)             "
      ::= { cmcTcMasterPcu4StatusEntry 10 }                

    cmcTcMasterPcu4RestoreOutputStatus OBJECT-TYPE
      SYNTAX INTEGER {
        disabled(1),
        enabled(2)
      }
      ACCESS read-write
      STATUS mandatory
      DESCRIPTION
        "Save last output status and switch output to this status after reboot"
      ::= { cmcTcMasterPcu4StatusEntry 11 }
                
--cmcTcMasterPcu4SetupGeneral-group

  cmcTcMasterPcu4SetTempUnit OBJECT-TYPE
    SYNTAX INTEGER {
      celsius(1),
      fahrenheit(2)
    }
    ACCESS read-write
    STATUS mandatory
    DESCRIPTION
      "Unit of all temperature values and setpoints, Celsius or Fahrenheit"
    ::= { cmcTcMasterPcu4SetupGeneral 1 }

  cmcTcMasterPcu4SetBeeper OBJECT-TYPE
    SYNTAX INTEGER {
      off(1),
      on(2),
      enableClear(3)
    }
    ACCESS read-write
    STATUS mandatory
    DESCRIPTION
      "Audible alarm in PCU unit:
       (1): beeper is off (general)
       (2): beeper is on (Alarm)
       (3): enable Clear (cmcTcMasterPcu4ClearAlarm)"
    ::= { cmcTcMasterPcu4SetupGeneral 2 }

  cmcTcMasterPcu4LogicRelay OBJECT-TYPE
    SYNTAX INTEGER {
      closeAtAlarm(1),
      openAtAlarm(2),
      off(3),
      enableRemote(4)
    }
    ACCESS read-write
    STATUS mandatory
    DESCRIPTION
      "Logic of alarm relay: 
       (1): Relay will pick up in case of an alarm
       (2): Relay will release in case of an alarm
       (3): Relay off (general)
       (4): enable remote relay control (SNMP set)"
    ::= { cmcTcMasterPcu4SetupGeneral 3 }
 
  cmcTcMasterPcu4ClearRelay OBJECT-TYPE
    SYNTAX INTEGER {
      disabled(1),
      enabled(2)
    }
    ACCESS read-write
    STATUS mandatory
    DESCRIPTION
      "Enable clear of alarm relay: 
       (1): Relay cannot be cleared by cmcTcMasterPcu4ClearAlarm
       (2): Relay can be cleared by cmcTcMasterPcu4ClearAlarm"
    ::= { cmcTcMasterPcu4SetupGeneral 4 }                  

  cmcTcMasterPcu4WebAccess OBJECT-TYPE
    SYNTAX INTEGER {
      viewOnly(1),
      fullAccess(2),
      off(3)
    }
    ACCESS read-write
    STATUS mandatory
    DESCRIPTION
      "Web access via HTTP: 
       (1): view only
       (2): full Access, read and set
       (3): Web disabled (general)"
    ::= { cmcTcMasterPcu4SetupGeneral 5 }
 
  cmcTcMasterPcu4SetupDate OBJECT-TYPE
    SYNTAX DisplayString (SIZE (0..10))
    ACCESS read-write
    STATUS mandatory
    DESCRIPTION
      "actual Date in format DD.MM.YYYY"
    ::= { cmcTcMasterPcu4SetupGeneral 6 }

  cmcTcMasterPcu4SetupTime OBJECT-TYPE
    SYNTAX DisplayString (SIZE (0..8))
    ACCESS read-write
    STATUS mandatory
    DESCRIPTION
      "actual Time in format HH:MM:SS, HH (0-23), MM (0-59), SS (0-59)"
    ::= { cmcTcMasterPcu4SetupGeneral 7 }

--cmcTcMasterPcu4TimerTable1-group
 
  cmcTcMasterPcu4TimerNumber OBJECT-TYPE
    SYNTAX INTEGER 
    ACCESS read-only
    STATUS mandatory
    DESCRIPTION
      "Number of timers available on this unit"
    ::= { cmcTcMasterPcu4TimerTable1 1 }

  cmcTcMasterPcu4TimerTable OBJECT-TYPE
    SYNTAX SEQUENCE OF CmcTcMasterPcu4TimerEntry
    ACCESS not-accessible
    STATUS mandatory
    DESCRIPTION
      "Headline of timer-table"
    ::= { cmcTcMasterPcu4TimerTable1 2 }

  cmcTcMasterPcu4TimerEntry OBJECT-TYPE
    SYNTAX CmcTcMasterPcu4TimerEntry
    ACCESS not-accessible
    STATUS mandatory
    DESCRIPTION
      "Entries of timer-table"
    INDEX { cmcTcMasterPcu4TimerIndex }
    ::= { cmcTcMasterPcu4TimerTable 1 }

    CmcTcMasterPcu4TimerEntry ::=
      SEQUENCE {
        cmcTcMasterPcu4TimerIndex
          INTEGER,
        cmcTcMasterPcu4TimerStatus
          INTEGER,
        cmcTcMasterPcu4TimerDayOfWeek
          INTEGER,  
        cmcTcMasterPcu4TimeOn 
          DisplayString (SIZE (0..5)),                              
        cmcTcMasterPcu4TimeOff 
          DisplayString (SIZE (0..5)),                              
        cmcTcMasterPcu4TimeControl
          INTEGER,
        cmcTcMasterPcu4TimerOutput1
          INTEGER,
        cmcTcMasterPcu4TimerOutput2
          INTEGER         
      }

    cmcTcMasterPcu4TimerIndex OBJECT-TYPE
      SYNTAX INTEGER (1..32000)
      ACCESS read-only
      STATUS mandatory
      DESCRIPTION
        "Index for the list of timer entries. Its value ranges
         between 1 and the value of cmcTcMasterPcu4TimerNumber." 
      ::= { cmcTcMasterPcu4TimerEntry 1 }

    cmcTcMasterPcu4TimerStatus OBJECT-TYPE
      SYNTAX INTEGER {
        switchedOff(1),
        switchedOn(2),
        noTime(3) 
      }
      ACCESS read-only
      STATUS mandatory
      DESCRIPTION
        "Actual status of the timer"
      ::= { cmcTcMasterPcu4TimerEntry 2 }

    cmcTcMasterPcu4TimerDayOfWeek OBJECT-TYPE
      SYNTAX INTEGER {
        sun(1),
        mon(2),
        tue(3) ,
        wed(4),
        thu(5),
        fre(6),
        sat(7),
        sat-sun(8),
        mo-fr(9),
        mo-su(10)
      }
      ACCESS read-write
      STATUS mandatory
      DESCRIPTION
        "Day when the timer is active"
      ::= { cmcTcMasterPcu4TimerEntry 3 }
             
    cmcTcMasterPcu4TimeOn OBJECT-TYPE
      SYNTAX DisplayString (SIZE (0..5))
      ACCESS read-write
      STATUS mandatory
      DESCRIPTION
        "Time to switch on current outlet, 
         Format: HH:MM"
      ::= { cmcTcMasterPcu4TimerEntry 4 }

    cmcTcMasterPcu4TimeOff OBJECT-TYPE
      SYNTAX DisplayString (SIZE (0..5))
      ACCESS read-write
      STATUS mandatory
      DESCRIPTION
        "Time to switch off current outlet,
         Format: HH:MM"
      ::= { cmcTcMasterPcu4TimerEntry 5 }

    cmcTcMasterPcu4TimeControl OBJECT-TYPE
      SYNTAX INTEGER {
        disabled(1),
        enabled(2)
      }
      ACCESS read-write
      STATUS mandatory
      DESCRIPTION
        "Control via RTC"
      ::= { cmcTcMasterPcu4TimerEntry 6 }

    cmcTcMasterPcu4TimerOutput1 OBJECT-TYPE
      SYNTAX INTEGER 
      ACCESS read-write
      STATUS mandatory
      DESCRIPTION
        "Output which is controlled via timer"
      ::= { cmcTcMasterPcu4TimerEntry 7 }

    cmcTcMasterPcu4TimerOutput2 OBJECT-TYPE
      SYNTAX INTEGER 
      ACCESS read-write
      STATUS mandatory
      DESCRIPTION
        "Output which is controlled via timer"
      ::= { cmcTcMasterPcu4TimerEntry 8 }

--cmcTcMasterPcu4SetupPower1-group                     

  cmcTcMasterPcu4SetupPower1Avail OBJECT-TYPE
    SYNTAX INTEGER {
      notAvailable(1),
      available(2)
    }
    ACCESS read-write
    STATUS mandatory
    DESCRIPTION
      "Energy sensor 1 sensor:   
       (1) not available
       (2) available"
    ::= { cmcTcMasterPcu4SetupPower1 1 }

  cmcTcMasterPcu4SetupPower1Relay OBJECT-TYPE
    SYNTAX INTEGER {
      disabled(1),
      enabled(2)
    }
    ACCESS read-write
    STATUS mandatory
    DESCRIPTION
      "Alert handling of Alarm Relay in case of an alarm condition
       of Power 1:  
       (1) no switching of Relays
       (2) Relay will switch"
    ::= { cmcTcMasterPcu4SetupPower1 2 }

  cmcTcMasterPcu4SetupPower1Beeper OBJECT-TYPE
    SYNTAX INTEGER {
      disabled(1),
      enabled(2)
    }
    ACCESS read-write
    STATUS mandatory
    DESCRIPTION
      "Alert handling of beeper of in case of an alarm condition
       of Power 1: 
       (1) No Audible Alarm
       (2) Start Audible Alarm"
    ::= { cmcTcMasterPcu4SetupPower1 3 }

--cmcTcMasterPcu4SetupPower2-group                     

  cmcTcMasterPcu4SetupPower2Avail OBJECT-TYPE
    SYNTAX INTEGER {
      notAvailable(1),
      available(2)
    }
    ACCESS read-write
    STATUS mandatory
    DESCRIPTION
      "Energy sensor 2:   
       (1) not available
       (2) available"
    ::= { cmcTcMasterPcu4SetupPower2 1 }

  cmcTcMasterPcu4SetupPower2Relay OBJECT-TYPE
    SYNTAX INTEGER {
      disabled(1),
      enabled(2)
    }
    ACCESS read-write
    STATUS mandatory
    DESCRIPTION
      "Alert handling of Alarm Relay in case of an alarm condition
       of Power 2:  
       (1) no switching of Relay
       (2) Relay will switch"
    ::= { cmcTcMasterPcu4SetupPower2 2 }

  cmcTcMasterPcu4SetupPower2Beeper OBJECT-TYPE
    SYNTAX INTEGER {
      disabled(1),
      enabled(2)
    }
    ACCESS read-write
    STATUS mandatory
    DESCRIPTION
      "Alert handling of beeper of in case of an alarm condition
       of Power 2: 
       (1) No Audible Alarm
       (2) Start Audible Alarm"
    ::= { cmcTcMasterPcu4SetupPower2 3 }

--cmcTcMasterPcu4SetupInput1-group

  cmcTcMasterPcu4SetupInput1Avail OBJECT-TYPE
    SYNTAX INTEGER {
      notAvailable(1),
      available(2)
    }
    ACCESS read-write
    STATUS mandatory
    DESCRIPTION
      "Input 1 sensor:   
       (1) not available
       (2) available"
    ::= { cmcTcMasterPcu4SetupInput1 1 }

  cmcTcMasterPcu4SetupInput1Relay OBJECT-TYPE
    SYNTAX INTEGER {
      disabled(1),
      enabled(2)
    }
    ACCESS read-write
    STATUS mandatory
    DESCRIPTION
      "Alert handling of Alarm Relay in case of an alarm condition
       of Input 1:  
       (1) no switching of Relay
       (2) Relay will switch"
    ::= { cmcTcMasterPcu4SetupInput1 2 }

  cmcTcMasterPcu4SetupInput1Beeper OBJECT-TYPE
    SYNTAX INTEGER {
      disabled(1),
      enabled(2)
    }
    ACCESS read-write
    STATUS mandatory
    DESCRIPTION
      "Alert handling of beeper of in case of an alarm condition
       of Input 1: 
       (1) No Audible Alarm
       (2) Start Audible Alarm"
    ::= { cmcTcMasterPcu4SetupInput1 3 }

  cmcTcMasterPcu4SetupInput1Contact OBJECT-TYPE
    SYNTAX INTEGER {
      contactNO(1),
      contactNC(2),
      notAvail(3)
    }
    ACCESS read-write
    STATUS mandatory
    DESCRIPTION
      "Setup of digital input 1"
    ::= { cmcTcMasterPcu4SetupInput1 4 }

  cmcTcMasterPcu4SetupInput1Delay OBJECT-TYPE
    SYNTAX INTEGER (0..60)
    ACCESS read-write
    STATUS mandatory
    DESCRIPTION
      "Delay for changing of input state"
    ::= { cmcTcMasterPcu4SetupInput1 5 }

--cmcTcMasterPcu4SetupInput2-group

  cmcTcMasterPcu4SetupInput2Avail OBJECT-TYPE
    SYNTAX INTEGER {
      notAvailable(1),
      available(2)
    }
    ACCESS read-write
    STATUS mandatory
    DESCRIPTION
      "Input 2 sensor:   
       (2) available
       (1) not available"
    ::= { cmcTcMasterPcu4SetupInput2 1 }

  cmcTcMasterPcu4SetupInput2Relay OBJECT-TYPE
    SYNTAX INTEGER {
      disabled(1),
      enabled(2)
    }
    ACCESS read-write
    STATUS mandatory
    DESCRIPTION
      "Alert handling of Alarm Relay in case of an alarm condition
       of Input 1:  
       (1) no switching of Relays
       (2) Relay will switch"
    ::= { cmcTcMasterPcu4SetupInput2 2 }

  cmcTcMasterPcu4SetupInput2Beeper OBJECT-TYPE
    SYNTAX INTEGER {
      disabled(1),
      enabled(2)
    }
    ACCESS read-write
    STATUS mandatory
    DESCRIPTION
      "Alert handling of beeper of in case of an alarm condition
       of Input 2: 
       (1) No Audible Alarm
       (2) Start Audible Alarm"
    ::= { cmcTcMasterPcu4SetupInput2 3 }

  cmcTcMasterPcu4SetupInput2Contact OBJECT-TYPE
    SYNTAX INTEGER {
      contactNO(1),
      contactNC(2),
      notAvail(3)
    }
    ACCESS read-write
    STATUS mandatory
    DESCRIPTION
      "Setup of digital input 2"
    ::= { cmcTcMasterPcu4SetupInput2 4 }

  cmcTcMasterPcu4SetupInput2Delay OBJECT-TYPE
    SYNTAX INTEGER (0..60)
    ACCESS read-write
    STATUS mandatory
    DESCRIPTION
      "Delay for changing of input state"
    ::= { cmcTcMasterPcu4SetupInput2 5 }

--cmcTcMasterPcu4SetupTemperature-group                     

  cmcTcMasterPcu4SetupTemperatureAvail OBJECT-TYPE
    SYNTAX INTEGER {
      notAvailable(1),
      available(2)
    }
    ACCESS read-write
    STATUS mandatory
    DESCRIPTION
      "Temp sensor 1:   
       (1) not available
       (2) available"
    ::= { cmcTcMasterPcu4SetupTemperature 1 }

  cmcTcMasterPcu4SetupTemperatureRelay OBJECT-TYPE
    SYNTAX INTEGER {
      disabled(1),
      enabled(2)
    }
    ACCESS read-write
    STATUS mandatory
    DESCRIPTION
      "Alert handling of Alarm Relay in case of an alarm condition
       of Temperature:  
       (1) no switching of Relays
       (2) Relay will switch"
    ::= { cmcTcMasterPcu4SetupTemperature 2 }

  cmcTcMasterPcu4SetupTemperatureBeeper OBJECT-TYPE
    SYNTAX INTEGER {
      disabled(1),
      enabled(2)
    }
    ACCESS read-write
    STATUS mandatory
    DESCRIPTION
      "Alert handling of beeper of in case of an alarm condition
       of Temperature: 
       (1) No Audible Alarm
       (2) Start Audible Alarm"
    ::= { cmcTcMasterPcu4SetupTemperature 3 }

--cmcTcMasterPcu4SetupGeneral-group

  cmcTcMasterPcu4SetMessage OBJECT-TYPE
    SYNTAX DisplayString (SIZE (0..31))
    ACCESS read-write
    STATUS mandatory
    DESCRIPTION
      "Set message"
    ::= { cmcTcMasterPcu4SetupDevice 1 }

--cmcTcMasterPcu4Setpoints-group

  cmcTcMasterPcu4SetpointHighPower1 OBJECT-TYPE
    SYNTAX INTEGER 
    ACCESS read-write
    STATUS mandatory
    DESCRIPTION
      "Setpoint high value power consumption 1 alarm"
    ::= { cmcTcMasterPcu4Setpoints 1 }

  cmcTcMasterPcu4SetpointWarningPower1 OBJECT-TYPE
    SYNTAX INTEGER 
    ACCESS read-write
    STATUS mandatory
    DESCRIPTION
      "Setpoint warning value power consumption 1 alarm"
    ::= { cmcTcMasterPcu4Setpoints 2 }

  cmcTcMasterPcu4SetpointLowPower1 OBJECT-TYPE
    SYNTAX INTEGER
    ACCESS read-write
    STATUS mandatory
    DESCRIPTION
      "Setpoint low value power consumption 1 alarm"
    ::= { cmcTcMasterPcu4Setpoints 3 }

  cmcTcMasterPcu4SetpointHighPower2 OBJECT-TYPE
    SYNTAX INTEGER 
    ACCESS read-write
    STATUS mandatory
    DESCRIPTION
      "Setpoint high value power consumption 2 alarm"
    ::= { cmcTcMasterPcu4Setpoints 4 }

  cmcTcMasterPcu4SetpointWarningPower2 OBJECT-TYPE
    SYNTAX INTEGER 
    ACCESS read-write
    STATUS mandatory
    DESCRIPTION
      "Setpoint warning value power consumption 2 alarm"
    ::= { cmcTcMasterPcu4Setpoints 5 }

  cmcTcMasterPcu4SetpointLowPower2 OBJECT-TYPE
    SYNTAX INTEGER
    ACCESS read-write
    STATUS mandatory
    DESCRIPTION
      "Setpoint low value power consumption 2 alarm"
    ::= { cmcTcMasterPcu4Setpoints 6 }

  cmcTcMasterPcu4SetpointHighTemperature OBJECT-TYPE
    SYNTAX INTEGER (0..200)
    ACCESS read-write
    STATUS mandatory
    DESCRIPTION
      "Setpoint high value alarm temperature "
    ::= { cmcTcMasterPcu4Setpoints 7 }

  cmcTcMasterPcu4SetpointLowTemperature OBJECT-TYPE
    SYNTAX INTEGER (0..50)
    ACCESS read-write
    STATUS mandatory
    DESCRIPTION
      "Setpoint low value alarm temperature "
    ::= { cmcTcMasterPcu4Setpoints 8 }
 
  cmcTcMasterPcu4SetpointTemperature OBJECT-TYPE
    SYNTAX INTEGER (0..200)
    ACCESS read-write
    STATUS mandatory
    DESCRIPTION
      "Setpoint temperature for outlet control 
       and temperature warning"
    ::= { cmcTcMasterPcu4Setpoints 9 }

  cmcTcMasterPcu4SetpointTemperatureHyst OBJECT-TYPE
    SYNTAX INTEGER (0..15)
    ACCESS read-write
    STATUS mandatory
    DESCRIPTION
      "Hysteresis for cmcTcMasterPcu4SetpointTemperature"
    ::= { cmcTcMasterPcu4Setpoints 10 }
 
--cmcTcMasterPcu4Control-group

  cmcTcMasterPcu4ResetEnergy1 OBJECT-TYPE
    SYNTAX INTEGER {
      noReset(1),
      reset(2)
    }
    ACCESS read-write
    STATUS mandatory
    DESCRIPTION
      "Reset value of cmcTcMasterPcu4ValueEnergy1Time"
    ::= { cmcTcMasterPcu4Control 1 }

  cmcTcMasterPcu4ResetEnergy2 OBJECT-TYPE
    SYNTAX INTEGER {
      noReset(1),
      reset(2)
    }
    ACCESS read-write
    STATUS mandatory
    DESCRIPTION
      "Reset value of cmcTcMasterPcu4ValueEnergy2Time"
    ::= { cmcTcMasterPcu4Control 2 }

  cmcTcMasterPcu4ControlAlarmRelay OBJECT-TYPE
    SYNTAX INTEGER {
      relayOff(1),
      relayOn(2)
    }
    ACCESS read-write
    STATUS mandatory
    DESCRIPTION
      "Control of Alarm relay"
    ::= { cmcTcMasterPcu4Control 3 }

  cmcTcMasterPcu4ClearAlarm OBJECT-TYPE
    SYNTAX INTEGER {
      noClear(1),
      clear(2)
    }
    ACCESS read-write
    STATUS mandatory
    DESCRIPTION
      "Clear alarm, beeper and relay"
    ::= { cmcTcMasterPcu4Control 4 }

--cmcTcMasterPcu4TrapTable-group

  cmcTcMasterPcu4TrapTableNumber OBJECT-TYPE
    SYNTAX INTEGER 
    ACCESS read-only
    STATUS mandatory
    DESCRIPTION
      "Number of cmcTcMasterPcu4TrapTable entries. The number of trap-receivers avail."
    ::= { cmcTcMasterPcu4Traps 1 }

  cmcTcMasterPcu4TrapTable OBJECT-TYPE
    SYNTAX SEQUENCE OF CmcTcMasterPcu4TrapEntry
    ACCESS not-accessible
    STATUS mandatory
    DESCRIPTION
      "A list of trap-receiver entries"
    ::= { cmcTcMasterPcu4Traps 2 }

  cmcTcMasterPcu4TrapEntry OBJECT-TYPE
    SYNTAX CmcTcMasterPcu4TrapEntry
    ACCESS not-accessible
    STATUS mandatory
    DESCRIPTION
      "Entries of cmcTcMasterPcu4TrapTable"
    INDEX { cmcTcMasterPcu4TrapIndex }
    ::= { cmcTcMasterPcu4TrapTable 1 }

    CmcTcMasterPcu4TrapEntry ::=
      SEQUENCE {
        cmcTcMasterPcu4TrapIndex
          INTEGER,
        cmcTcMasterPcu4TrapStatus
          INTEGER,
        cmcTcMasterPcu4TrapIPaddress
          DisplayString
      }

    cmcTcMasterPcu4TrapIndex OBJECT-TYPE
      SYNTAX INTEGER (1..32000)
      ACCESS read-only
      STATUS mandatory
      DESCRIPTION
        "Index for the trap-receiver-table. Its value ranges between
         1 and the value of cmcTcMasterPcu4TrapTableNumber "
      ::= { cmcTcMasterPcu4TrapEntry 1 }

    cmcTcMasterPcu4TrapStatus OBJECT-TYPE
      SYNTAX INTEGER {
        disabled(1),
        enabled(2)
      }
      ACCESS read-write
      STATUS mandatory
      DESCRIPTION
        "Enable or disable trap receiver"
      ::= { cmcTcMasterPcu4TrapEntry 2 }

    cmcTcMasterPcu4TrapIPaddress OBJECT-TYPE
      SYNTAX DisplayString (SIZE (0..15))
      ACCESS read-write
      STATUS mandatory
      DESCRIPTION
        "IP-address of trap-receiver"
      ::= { cmcTcMasterPcu4TrapEntry 3 }

--cmcTcMasterTc4MibRev-group
          
  cmcTcMasterTc4MibMajRev OBJECT-TYPE
    SYNTAX INTEGER (1..32000)
    ACCESS read-only
    STATUS mandatory
    DESCRIPTION
      "The Major Revision level.
       A change in the major revision level represents a major change
       in the architecture of the MIB. A change in the major revision 
       level may indicate a significant change in the information,
       correct interpretation of data may require a MIB document
       with the same major revision level."
    ::= { cmcTcMasterTc4MibRev 1 }

  cmcTcMasterTc4MibMinRev OBJECT-TYPE
    SYNTAX INTEGER (0..32000)
    ACCESS read-only
    STATUS mandatory
    DESCRIPTION
      "The Minor Revision level.
       A change in the minor revision level may represent some minor
       additional support, no changes to any pre-existing information
       has occurred."
    ::= { cmcTcMasterTc4MibRev 2 }

  cmcTcMasterTc4MibCondition OBJECT-TYPE
    SYNTAX INTEGER {
      other (1),
      ok (2),
      degraded (3),
      failed (4),
      configChanged (5)
    }
    ACCESS read-only
    STATUS mandatory
    DESCRIPTION
      "The overall condition (status) of the system represented by
       this MIB. 
       (2) OK
       (3) a minor problem, warning condition (yellow LED on CMC-TC)
       (4) a major problem (red LED on CMC-TC)
       (5) configuration of sensor units changed or
           unit detected (red/yellow/green LED on CMC-TC)"
    ::= { cmcTcMasterTc4MibRev 3 }
          
--cmcTcMasterTc4Status-group

  cmcTcMasterTc4StatusDeviceCMC OBJECT-TYPE
    SYNTAX INTEGER {
      failed(1),
      ok(2)
    }
    ACCESS read-only
    STATUS mandatory
    DESCRIPTION
      "General Status of CMC-TC unit itself
       (1) failed
       (2) OK"
    ::= { cmcTcMasterTc4Status 1 }

  cmcTcMasterTc4UnitsConnected OBJECT-TYPE
    SYNTAX INTEGER 
    ACCESS read-only
    STATUS mandatory
    DESCRIPTION
      "Number of sensor units connected to the CMC-TC, Port 1 to 4"
    ::= { cmcTcMasterTc4Status 2 }

--unit 1

  cmcTcMasterTc4Unit1TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 1"
    ::= { cmcTcMasterTc4StatusSensorUnit1 1 }

  cmcTcMasterTc4Unit1Text OBJECT-TYPE
    SYNTAX DisplayString (SIZE (0..10))
    ACCESS read-write
    STATUS mandatory
    DESCRIPTION
      "Descriptional text for sensor unit connected to port 1"
    ::= { cmcTcMasterTc4StatusSensorUnit1 2 }

  cmcTcMasterTc4Unit1Serial OBJECT-TYPE
    SYNTAX INTEGER 
    ACCESS read-only
    STATUS mandatory
    DESCRIPTION
      "Serialnumber of sensor unit connected to port 1"
    ::= { cmcTcMasterTc4StatusSensorUnit1 3 }

  cmcTcMasterTc4Unit1Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 1
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc4StatusSensorUnit1 4 }

-- Sensors
              
  cmcTcMasterTc4Unit1NumberOfSensors OBJECT-TYPE
    SYNTAX INTEGER 
    ACCESS read-only
    STATUS mandatory
    DESCRIPTION
      "Number of sensors connected to sensor unit 1"
    ::= { cmcTcMasterTc4StatusUnit1Sensors 1 }

-- table with entry for each sensor available on this unit              

  cmcTcMasterTc4Unit1SensorTable OBJECT-TYPE
    SYNTAX SEQUENCE OF CmcTcMasterTc4Unit1SensorEntry
    ACCESS not-accessible
    STATUS mandatory
    DESCRIPTION
      "Headline of sensor table"
    ::= { cmcTcMasterTc4StatusUnit1Sensors 2 }

  cmcTcMasterTc4Unit1SensorEntry OBJECT-TYPE
    SYNTAX CmcTcMasterTc4Unit1SensorEntry
    ACCESS not-accessible
    STATUS mandatory
    DESCRIPTION
      "Entries of sensor table"
    INDEX { cmcTcMasterTc4Unit1SensorIndex }
    ::= { cmcTcMasterTc4Unit1SensorTable 1 }

    CmcTcMasterTc4Unit1SensorEntry ::=
      SEQUENCE {
        cmcTcMasterTc4Unit1SensorIndex
          INTEGER,
        cmcTcMasterTc4Unit1SensorType
          INTEGER,
        cmcTcMasterTc4Unit1SensorText
          DisplayString (SIZE (0..20)),                
        cmcTcMasterTc4Unit1SensorStatus
          INTEGER,
        cmcTcMasterTc4Unit1SensorValue
          INTEGER,
        cmcTcMasterTc4Unit1SensorSetHigh
          INTEGER,
        cmcTcMasterTc4Unit1SensorSetLow
          INTEGER,
        cmcTcMasterTc4Unit1SensorSetWarn
          INTEGER                
      }

    cmcTcMasterTc4Unit1SensorIndex OBJECT-TYPE
      SYNTAX INTEGER (1..32000)
      ACCESS read-only
      STATUS mandatory
      DESCRIPTION
        "Index for the list of value entries. Its value ranges
         between 1 and the value of cmcTcMasterTc4Unit1NumberOfSensors." 
      ::= { cmcTcMasterTc4Unit1SensorEntry 1 }

    cmcTcMasterTc4Unit1SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 1 to sensor[cmcTcMasterTc4Unit1SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc4Unit1SensorEntry 2 }

    cmcTcMasterTc4Unit1SensorText OBJECT-TYPE
      SYNTAX DisplayString (SIZE (0..20))
      ACCESS read-write
      STATUS mandatory
      DESCRIPTION
        "Descriptional text for each sensor (entry in the table)"
      ::= { cmcTcMasterTc4Unit1SensorEntry 3 }
              
    cmcTcMasterTc4Unit1SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc4Unit1SensorEntry 4 }

    cmcTcMasterTc4Unit1SensorValue OBJECT-TYPE
      SYNTAX INTEGER 
      ACCESS read-only
      STATUS mandatory
      DESCRIPTION
        "Value of sensor"
      ::= { cmcTcMasterTc4Unit1SensorEntry 5 }

    cmcTcMasterTc4Unit1SensorSetHigh OBJECT-TYPE
      SYNTAX INTEGER (0..300) 
      ACCESS read-write
      STATUS mandatory
      DESCRIPTION
        "Value for high setpoint of sensor"
      ::= { cmcTcMasterTc4Unit1SensorEntry 6 }

    cmcTcMasterTc4Unit1SensorSetLow OBJECT-TYPE
      SYNTAX INTEGER (0..300) 
      ACCESS read-write
      STATUS mandatory
      DESCRIPTION
        "Value for low setpoint of sensor,
         also used as alarm delay"
      ::= { cmcTcMasterTc4Unit1SensorEntry 7 }

    cmcTcMasterTc4Unit1SensorSetWarn OBJECT-TYPE
      SYNTAX INTEGER (0..300) 
      ACCESS read-write
      STATUS mandatory
      DESCRIPTION
        "Value for warning setpoint of sensor, 
         also used as fan threshold"
      ::= { cmcTcMasterTc4Unit1SensorEntry 8 }
                
-- Outputs              

  cmcTcMasterTc4Unit1NumberOfOutputs OBJECT-TYPE
    SYNTAX INTEGER 
    ACCESS read-only
    STATUS mandatory
    DESCRIPTION
      "Number of outputs available on sensor unit 1"
    ::= { cmcTcMasterTc4StatusUnit1Outputs 1 }

-- table with entry for each output available on this unit              
                
  cmcTcMasterTc4Unit1OutputTable OBJECT-TYPE
    SYNTAX SEQUENCE OF CmcTcMasterTc4Unit1OutputEntry
    ACCESS not-accessible
    STATUS mandatory
    DESCRIPTION
      "Headline of output table"
    ::= { cmcTcMasterTc4StatusUnit1Outputs 2 }

  cmcTcMasterTc4Unit1OutputEntry OBJECT-TYPE
    SYNTAX CmcTcMasterTc4Unit1OutputEntry
    ACCESS not-accessible
    STATUS mandatory
    DESCRIPTION
      "Entries of output table"
    INDEX { cmcTcMasterTc4Unit1OutputIndex }
    ::= { cmcTcMasterTc4Unit1OutputTable 1 }

    CmcTcMasterTc4Unit1OutputEntry ::=
      SEQUENCE {
        cmcTcMasterTc4Unit1OutputIndex
          INTEGER,
        cmcTcMasterTc4Unit1OutputType
          INTEGER,
        cmcTcMasterTc4Unit1OutputText
          DisplayString (SIZE (0..20)),                
        cmcTcMasterTc4Unit1OutputStatus
          INTEGER,
        cmcTcMasterTc4Unit1OutputValue
          INTEGER,
        cmcTcMasterTc4Unit1OutputSet
          INTEGER,
        cmcTcMasterTc4Unit1OutputConfig
          INTEGER,                
        cmcTcMasterTc4Unit1OutputDelay
          INTEGER,
        cmcTcMasterTc4Unit1OutputTimeoutAction
          INTEGER
      }

    cmcTcMasterTc4Unit1OutputIndex OBJECT-TYPE
      SYNTAX INTEGER (1..32000)
      ACCESS read-only
      STATUS mandatory
      DESCRIPTION
        "Index for the list of output entries. Its value ranges
         between 1 and the value of cmcTcMasterTc4Unit1NumberOfOutputs." 
      ::= { cmcTcMasterTc4Unit1OutputEntry 1 }

    cmcTcMasterTc4Unit1OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 1 to output[cmcTcMasterTc4Unit1OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc4Unit1OutputEntry 2 }

    cmcTcMasterTc4Unit1OutputText OBJECT-TYPE
      SYNTAX DisplayString (SIZE (0..20))
      ACCESS read-write
      STATUS mandatory
      DESCRIPTION
        "Descriptional text for each output (entry in the table)"
      ::= { cmcTcMasterTc4Unit1OutputEntry 3 }
              
    cmcTcMasterTc4Unit1OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc4Unit1OutputEntry 4 }

    cmcTcMasterTc4Unit1OutputValue OBJECT-TYPE
      SYNTAX INTEGER (-32000..32000) 
      ACCESS read-write
      STATUS mandatory
      DESCRIPTION
        "Value for output"
      ::= { cmcTcMasterTc4Unit1OutputEntry 5 }

    cmcTcMasterTc4Unit1OutputSet OBJECT-TYPE
      SYNTAX INTEGER {
        off (1),
        on (2),
        lock (3),
        unlock (4),
        unlockDelay (5)
      }
      ACCESS read-write
      STATUS mandatory
      DESCRIPTION
        "Command for output"
      ::= { cmcTcMasterTc4Unit1OutputEntry 6 }

    cmcTcMasterTc4Unit1OutputConfig OBJECT-TYPE
      SYNTAX INTEGER {
        disRemote (1),
        enRemote (2)
      }
      ACCESS read-write
      STATUS mandatory
      DESCRIPTION
        "Configuration for output
         1: 	disable remote control (e.g. keypad)
         2: 	enable remote control"
      ::= { cmcTcMasterTc4Unit1OutputEntry 7 }

    cmcTcMasterTc4Unit1OutputDelay OBJECT-TYPE
      SYNTAX INTEGER (0..999) 
      ACCESS read-write
      STATUS mandatory
      DESCRIPTION
        "Unsigned Value for delay, 
         after this time the output will fall into the previous state"
      ::= { cmcTcMasterTc4Unit1OutputEntry 8 }

    cmcTcMasterTc4Unit1OutputTimeoutAction OBJECT-TYPE
      SYNTAX INTEGER {
        stay (1),
        off (2),
        on (3)
      }
      ACCESS read-write
      STATUS mandatory
      DESCRIPTION
        "State for output if timeout (RS422) occurs"
      ::= { cmcTcMasterTc4Unit1OutputEntry 9 }
 
-- Messages
              
  cmcTcMasterTc4Unit1NumberOfMsgs OBJECT-TYPE
    SYNTAX INTEGER 
    ACCESS read-only
    STATUS mandatory
    DESCRIPTION
      "Number of messages that can be created with sensor unit 1"
    ::= { cmcTcMasterTc4StatusUnit1Msg 1 }

-- table with entry for each alarm available on this unit               
                
  cmcTcMasterTc4Unit1MsgTable OBJECT-TYPE
    SYNTAX SEQUENCE OF CmcTcMasterTc4Unit1MsgEntry
    ACCESS not-accessible
    STATUS mandatory
    DESCRIPTION
      "Headline of message table"
    ::= { cmcTcMasterTc4StatusUnit1Msg 2 }

  cmcTcMasterTc4Unit1MsgEntry OBJECT-TYPE
    SYNTAX CmcTcMasterTc4Unit1MsgEntry
    ACCESS not-accessible
    STATUS mandatory
    DESCRIPTION
      "Entries of message table"
    INDEX { cmcTcMasterTc4Unit1MsgIndex }
    ::= { cmcTcMasterTc4Unit1MsgTable 1 }

    CmcTcMasterTc4Unit1MsgEntry ::=
      SEQUENCE {
        cmcTcMasterTc4Unit1MsgIndex
          INTEGER, 
        cmcTcMasterTc4Unit1MsgText
          DisplayString (SIZE (0..20)),                
        cmcTcMasterTc4Unit1MsgStatus
          INTEGER,                
        cmcTcMasterTc4Unit1MsgRelay
          INTEGER,
        cmcTcMasterTc4Unit1MsgBeeper
          INTEGER,
        cmcTcMasterTc4Unit1MsgTrap1
          INTEGER,
        cmcTcMasterTc4Unit1MsgTrap2
          INTEGER,
        cmcTcMasterTc4Unit1MsgTrap3
          INTEGER,
        cmcTcMasterTc4Unit1MsgTrap4
          INTEGER,                 
        cmcTcMasterTc4Unit1MsgQuit
          INTEGER              
      }

    cmcTcMasterTc4Unit1MsgIndex OBJECT-TYPE
      SYNTAX INTEGER (1..32000)
      ACCESS read-only
      STATUS mandatory
      DESCRIPTION
        "Index for the list of message entries. Its value ranges
         between 1 and the value of cmcTcMasterTc4Unit1NumberOfMsgs." 
      ::= { cmcTcMasterTc4Unit1MsgEntry 1 }

    cmcTcMasterTc4Unit1MsgText OBJECT-TYPE
      SYNTAX DisplayString (SIZE (0..20))
      ACCESS read-write
      STATUS mandatory
      DESCRIPTION
        "Descriptional text for each message (entry in the table)"
      ::= { cmcTcMasterTc4Unit1MsgEntry 2 }
              
    cmcTcMasterTc4Unit1MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc4Unit1OutputSet)
         17: door is unlocked by WEB
         18: door is unlocked by timer
         19: no access, wrong keycode or cardnumber
         20: orientation of PSM-Unit is circuit 1
         21: orientation of PSM-Unit is circuit 2"
      ::= { cmcTcMasterTc4Unit1MsgEntry 3 }
        
    cmcTcMasterTc4Unit1MsgRelay OBJECT-TYPE
      SYNTAX INTEGER {
        disable (1),
        enable (2)
      }
      ACCESS read-write
      STATUS mandatory
      DESCRIPTION
        "Setup of Alarm relay for this message/alarm
         1:        no switching of alarm relay             
         2:        switching of alarm relay" 
      ::= { cmcTcMasterTc4Unit1MsgEntry 4 }

    cmcTcMasterTc4Unit1MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc4Unit1MsgEntry 5 }

    cmcTcMasterTc4Unit1MsgTrap1 OBJECT-TYPE
      SYNTAX INTEGER {
        disable (1),
        enable (2)
      }
      ACCESS read-write
      STATUS mandatory
      DESCRIPTION
        "Trap receiver 1 activated"
      ::= { cmcTcMasterTc4Unit1MsgEntry 6 }

    cmcTcMasterTc4Unit1MsgTrap2 OBJECT-TYPE
      SYNTAX INTEGER {
        disable (1),
        enable (2)
      }
      ACCESS read-write
      STATUS mandatory
      DESCRIPTION
        "Trap receiver 2 activated"
      ::= { cmcTcMasterTc4Unit1MsgEntry 7 }
 
    cmcTcMasterTc4Unit1MsgTrap3 OBJECT-TYPE
      SYNTAX INTEGER {
        disable (1),
        enable (2)
      }
      ACCESS read-write
      STATUS mandatory
      DESCRIPTION
        "Trap receiver 3 activated"
      ::= { cmcTcMasterTc4Unit1MsgEntry 8 }

    cmcTcMasterTc4Unit1MsgTrap4 OBJECT-TYPE
      SYNTAX INTEGER {
        disable (1),
        enable (2)
      }
      ACCESS read-write
      STATUS mandatory
      DESCRIPTION
        "Trap receiver 4 and Event Logging activated"
      ::= { cmcTcMasterTc4Unit1MsgEntry 9 }

    cmcTcMasterTc4Unit1MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc4Unit1MsgEntry 10 }

-- unit2

  cmcTcMasterTc4Unit2TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 2"
    ::= { cmcTcMasterTc4StatusSensorUnit2 1 }

  cmcTcMasterTc4Unit2Text OBJECT-TYPE
    SYNTAX DisplayString (SIZE (0..10))
    ACCESS read-write
    STATUS mandatory
    DESCRIPTION
      "Descriptional text for sensor unit connected to port 2"
    ::= { cmcTcMasterTc4StatusSensorUnit2 2 }

  cmcTcMasterTc4Unit2Serial OBJECT-TYPE
    SYNTAX INTEGER 
    ACCESS read-only
    STATUS mandatory
    DESCRIPTION
      "Serialnumber of sensor unit connected to port 2"
    ::= { cmcTcMasterTc4StatusSensorUnit2 3 }

  cmcTcMasterTc4Unit2Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 2
       (1) OK
       (2) error
       (3) configuration of sensor unit has changed, confirmation required
       (4) Quit from sensor unit to confirm configuration changes
       (5) timeout of sensor unit, confirmation required
       (6) sensor unit detected, needs to be confirmed
       (8) supply voltage is too low"              
    ::= { cmcTcMasterTc4StatusSensorUnit2 4 }

-- unit 2 table

-- Sensors              

  cmcTcMasterTc4Unit2NumberOfSensors OBJECT-TYPE
    SYNTAX INTEGER 
    ACCESS read-only
    STATUS mandatory
    DESCRIPTION
      "Number of sensors connected to sensor unit 2"
    ::= { cmcTcMasterTc4StatusUnit2Sensors 1 }

-- table with entry for each sensor available on this unit              

  cmcTcMasterTc4Unit2SensorTable OBJECT-TYPE
    SYNTAX SEQUENCE OF CmcTcMasterTc4Unit2SensorEntry
    ACCESS not-accessible
    STATUS mandatory
    DESCRIPTION
      "Headline of sensor table"
    ::= { cmcTcMasterTc4StatusUnit2Sensors 2 }

  cmcTcMasterTc4Unit2SensorEntry OBJECT-TYPE
    SYNTAX CmcTcMasterTc4Unit2SensorEntry
    ACCESS not-accessible
    STATUS mandatory
    DESCRIPTION
      "Entries of sensor table"
    INDEX { cmcTcMasterTc4Unit2SensorIndex }
    ::= { cmcTcMasterTc4Unit2SensorTable 1 }

    CmcTcMasterTc4Unit2SensorEntry ::=
      SEQUENCE {
        cmcTcMasterTc4Unit2SensorIndex
          INTEGER,
        cmcTcMasterTc4Unit2SensorType
          INTEGER,
        cmcTcMasterTc4Unit2SensorText
          DisplayString (SIZE (0..20)),                
        cmcTcMasterTc4Unit2SensorStatus
          INTEGER,
        cmcTcMasterTc4Unit2SensorValue
          INTEGER,
        cmcTcMasterTc4Unit2SensorSetHigh
          INTEGER,
        cmcTcMasterTc4Unit2SensorSetLow
          INTEGER,                 
        cmcTcMasterTc4Unit2SensorSetWarn
          INTEGER  
      }

    cmcTcMasterTc4Unit2SensorIndex OBJECT-TYPE
      SYNTAX INTEGER (1..32000)
      ACCESS read-only
      STATUS mandatory
      DESCRIPTION
        "Index for the list of value entries. Its value ranges
         between 1 and the value of cmcTcMasterTc4Unit2NumberOfSensors." 
      ::= { cmcTcMasterTc4Unit2SensorEntry 1 }

    cmcTcMasterTc4Unit2SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 2 to sensor[cmcTcMasterTc4Unit2SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc4Unit2SensorEntry 2 }
        
    cmcTcMasterTc4Unit2SensorText OBJECT-TYPE
      SYNTAX DisplayString (SIZE (0..20))
      ACCESS read-write
      STATUS mandatory
      DESCRIPTION
        "Descriptional text for each sensor (entry in the table)"
      ::= { cmcTcMasterTc4Unit2SensorEntry 3 }
              
    cmcTcMasterTc4Unit2SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc4Unit2SensorEntry 4 }

    cmcTcMasterTc4Unit2SensorValue OBJECT-TYPE
      SYNTAX INTEGER 
      ACCESS read-only
      STATUS mandatory
      DESCRIPTION
        "Value of sensor"
      ::= { cmcTcMasterTc4Unit2SensorEntry 5 }

    cmcTcMasterTc4Unit2SensorSetHigh OBJECT-TYPE
      SYNTAX INTEGER (0..300) 
      ACCESS read-write
      STATUS mandatory
      DESCRIPTION
        "Value for high setpoint of sensor"
      ::= { cmcTcMasterTc4Unit2SensorEntry 6 }

    cmcTcMasterTc4Unit2SensorSetLow OBJECT-TYPE
      SYNTAX INTEGER (0..300) 
      ACCESS read-write
      STATUS mandatory
      DESCRIPTION
        "Value for low setpoint of sensor,
         also used as alarm delay"
      ::= { cmcTcMasterTc4Unit2SensorEntry 7 }

    cmcTcMasterTc4Unit2SensorSetWarn OBJECT-TYPE
      SYNTAX INTEGER (0..300) 
      ACCESS read-write
      STATUS mandatory
      DESCRIPTION
        "Value for warning setpoint of sensor,
         also used as fan threshold"
      ::= { cmcTcMasterTc4Unit2SensorEntry 8 }

-- Outputs              

  cmcTcMasterTc4Unit2NumberOfOutputs OBJECT-TYPE
    SYNTAX INTEGER 
    ACCESS read-only
    STATUS mandatory
    DESCRIPTION
      "Number of outputs available on sensor unit 2"
    ::= { cmcTcMasterTc4StatusUnit2Outputs 1 }

-- table with entry for each output available on this unit              
                
  cmcTcMasterTc4Unit2OutputTable OBJECT-TYPE
    SYNTAX SEQUENCE OF CmcTcMasterTc4Unit2OutputEntry
    ACCESS not-accessible
    STATUS mandatory
    DESCRIPTION
      "Headline of output table"
    ::= { cmcTcMasterTc4StatusUnit2Outputs 2 }

  cmcTcMasterTc4Unit2OutputEntry OBJECT-TYPE
    SYNTAX CmcTcMasterTc4Unit2OutputEntry
    ACCESS not-accessible
    STATUS mandatory
    DESCRIPTION
      "Entries of output table"
    INDEX { cmcTcMasterTc4Unit2OutputIndex }
    ::= { cmcTcMasterTc4Unit2OutputTable 1 }

    CmcTcMasterTc4Unit2OutputEntry ::=
      SEQUENCE {
        cmcTcMasterTc4Unit2OutputIndex
          INTEGER,
        cmcTcMasterTc4Unit2OutputType
          INTEGER,
        cmcTcMasterTc4Unit2OutputText
          DisplayString (SIZE (0..20)),                
        cmcTcMasterTc4Unit2OutputStatus
          INTEGER,
        cmcTcMasterTc4Unit2OutputValue
          INTEGER,
        cmcTcMasterTc4Unit2OutputSet
          INTEGER,
        cmcTcMasterTc4Unit2OutputConfig
          INTEGER,                
        cmcTcMasterTc4Unit2OutputDelay
          INTEGER,
        cmcTcMasterTc4Unit2OutputTimeoutAction
          INTEGER
      }

    cmcTcMasterTc4Unit2OutputIndex OBJECT-TYPE
      SYNTAX INTEGER (1..32000)
      ACCESS read-only
      STATUS mandatory
      DESCRIPTION
        "Index for the list of output entries. Its value ranges
         between 1 and the value of cmcTcMasterTc4Unit2NumberOfOutputs." 
      ::= { cmcTcMasterTc4Unit2OutputEntry 1 }

    cmcTcMasterTc4Unit2OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 2 to output[cmcTcMasterTc4Unit2OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc4Unit2OutputEntry 2 }

        
    cmcTcMasterTc4Unit2OutputText OBJECT-TYPE
      SYNTAX DisplayString (SIZE (0..20))
      ACCESS read-write
      STATUS mandatory
      DESCRIPTION
        "Descriptional text for each output (entry in the table)"
      ::= { cmcTcMasterTc4Unit2OutputEntry 3 }
              
    cmcTcMasterTc4Unit2OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc4Unit2OutputEntry 4 }

    cmcTcMasterTc4Unit2OutputValue OBJECT-TYPE
      SYNTAX INTEGER (-32000..32000) 
      ACCESS read-write
      STATUS mandatory
      DESCRIPTION
        "Value for output"
      ::= { cmcTcMasterTc4Unit2OutputEntry 5 }

    cmcTcMasterTc4Unit2OutputSet OBJECT-TYPE
      SYNTAX INTEGER {
        off (1),
        on (2),
        lock (3),
        unlock (4),
        unlockDelay (5)
      }
      ACCESS read-write
      STATUS mandatory
      DESCRIPTION
        "Command for output"
      ::= { cmcTcMasterTc4Unit2OutputEntry 6 }

    cmcTcMasterTc4Unit2OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc4Unit2OutputEntry 7 }

    cmcTcMasterTc4Unit2OutputDelay OBJECT-TYPE
      SYNTAX INTEGER (0..999) 
      ACCESS read-write
      STATUS mandatory
      DESCRIPTION
        "Unsigned Value for delay, 
         after this time the output will fall into the previous state"
      ::= { cmcTcMasterTc4Unit2OutputEntry 8 }

    cmcTcMasterTc4Unit2OutputTimeoutAction OBJECT-TYPE
      SYNTAX INTEGER {
        stay (1),
        off (2),
        on (3)
      }
      ACCESS read-write
      STATUS mandatory
      DESCRIPTION
        "State for output if timeout (RS422) occurs"
      ::= { cmcTcMasterTc4Unit2OutputEntry 9 }

-- Messages
              
  cmcTcMasterTc4Unit2NumberOfMsgs OBJECT-TYPE
    SYNTAX INTEGER 
    ACCESS read-only
    STATUS mandatory
    DESCRIPTION
      "Number of messages that can be created with sensor unit 2"
    ::= { cmcTcMasterTc4StatusUnit2Msg 1 }

-- table with entry for each alarm available on this unit               
                
  cmcTcMasterTc4Unit2MsgTable OBJECT-TYPE
    SYNTAX SEQUENCE OF CmcTcMasterTc4Unit2MsgEntry
    ACCESS not-accessible
    STATUS mandatory
    DESCRIPTION
      "Headline of message table"
    ::= { cmcTcMasterTc4StatusUnit2Msg 2 }

  cmcTcMasterTc4Unit2MsgEntry OBJECT-TYPE
    SYNTAX CmcTcMasterTc4Unit2MsgEntry
    ACCESS not-accessible
    STATUS mandatory
    DESCRIPTION
      "Entries of message table"
    INDEX { cmcTcMasterTc4Unit2MsgIndex }
    ::= { cmcTcMasterTc4Unit2MsgTable 1 }

    CmcTcMasterTc4Unit2MsgEntry ::=
      SEQUENCE {
        cmcTcMasterTc4Unit2MsgIndex
          INTEGER,
        cmcTcMasterTc4Unit2MsgText
          DisplayString (SIZE (0..20)),
        cmcTcMasterTc4Unit2MsgStatus
          INTEGER, 
        cmcTcMasterTc4Unit2MsgRelay
          INTEGER,
        cmcTcMasterTc4Unit2MsgBeeper
          INTEGER,
        cmcTcMasterTc4Unit2MsgTrap1
          INTEGER,
        cmcTcMasterTc4Unit2MsgTrap2
          INTEGER,
        cmcTcMasterTc4Unit2MsgTrap3
          INTEGER,
        cmcTcMasterTc4Unit2MsgTrap4
          INTEGER,                 
        cmcTcMasterTc4Unit2MsgQuit
          INTEGER              
      }

    cmcTcMasterTc4Unit2MsgIndex OBJECT-TYPE
      SYNTAX INTEGER (1..32000)
      ACCESS read-only
      STATUS mandatory
      DESCRIPTION
        "Index for the list of message entries. Its value ranges
         between 1 and the value of cmcTcMasterTc4Unit2NumberOfMsgs." 
      ::= { cmcTcMasterTc4Unit2MsgEntry 1 }

    cmcTcMasterTc4Unit2MsgText OBJECT-TYPE
      SYNTAX DisplayString (SIZE (0..20))
      ACCESS read-write
      STATUS mandatory
      DESCRIPTION
        "Descriptional text for each message (entry in the table)"
      ::= { cmcTcMasterTc4Unit2MsgEntry 2 }

    cmcTcMasterTc4Unit2MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc4Unit2OutputSet)
         17: door is unlocked by WEB
         18: door is unlocked by timer
         19: no access, wrong keycode or cardnumber
         20: orientation of PSM-Unit is circuit 1
         21: orientation of PSM-Unit is circuit 2"
      ::= { cmcTcMasterTc4Unit2MsgEntry 3 }

    cmcTcMasterTc4Unit2MsgRelay OBJECT-TYPE
      SYNTAX INTEGER {
        disable (1),
        enable (2)
      }
      ACCESS read-write
      STATUS mandatory
      DESCRIPTION
        "Setup of Alarm relay for this alarm
         2:        no switching of alarm relay             
         1:        switching of alarm relay" 
      ::= { cmcTcMasterTc4Unit2MsgEntry 4 }

    cmcTcMasterTc4Unit2MsgBeeper OBJECT-TYPE
      SYNTAX INTEGER {
        disable (1),
        enable (2)
      }
      ACCESS read-write
      STATUS mandatory
      DESCRIPTION
        "Setup of Alarm beeper for this alarm
         2:        no audible alarm
         1:        audible alarm" 
      ::= { cmcTcMasterTc4Unit2MsgEntry 5 }

    cmcTcMasterTc4Unit2MsgTrap1 OBJECT-TYPE
      SYNTAX INTEGER {
        disable (1),
        enable (2)
      }
      ACCESS read-write
      STATUS mandatory
      DESCRIPTION
        "Trap receiver 1 activated"
      ::= { cmcTcMasterTc4Unit2MsgEntry 6 }

    cmcTcMasterTc4Unit2MsgTrap2 OBJECT-TYPE
      SYNTAX INTEGER {
        disable (1),
        enable (2)
      }
      ACCESS read-write
      STATUS mandatory
      DESCRIPTION
        "Trap receiver 2 activated"
      ::= { cmcTcMasterTc4Unit2MsgEntry 7 }
 
    cmcTcMasterTc4Unit2MsgTrap3 OBJECT-TYPE
      SYNTAX INTEGER {
        disable (1),
        enable (2)
      }
      ACCESS read-write
      STATUS mandatory
      DESCRIPTION
        "Trap receiver 3 activated"
      ::= { cmcTcMasterTc4Unit2MsgEntry 8 }

    cmcTcMasterTc4Unit2MsgTrap4 OBJECT-TYPE
      SYNTAX INTEGER {
        disable (1),
        enable (2)
      }
      ACCESS read-write
      STATUS mandatory
      DESCRIPTION
        "Trap receiver 4 and Event Logging activated"
      ::= { cmcTcMasterTc4Unit2MsgEntry 9 }

    cmcTcMasterTc4Unit2MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc4Unit2MsgEntry 10 }

-- unit 3
  cmcTcMasterTc4Unit3TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 3"
    ::= { cmcTcMasterTc4StatusSensorUnit3 1 }

  cmcTcMasterTc4Unit3Text OBJECT-TYPE
    SYNTAX DisplayString (SIZE (0..10))
    ACCESS read-write
    STATUS mandatory
    DESCRIPTION
      "Descriptional text for sensor unit connected to port 3"
    ::= { cmcTcMasterTc4StatusSensorUnit3 2 }

  cmcTcMasterTc4Unit3Serial OBJECT-TYPE
    SYNTAX INTEGER 
    ACCESS  read-only
    STATUS  mandatory
    DESCRIPTION
      "Serialnumber of sensor unit connected to port 3"
    ::= { cmcTcMasterTc4StatusSensorUnit3 3 }

  cmcTcMasterTc4Unit3Status OBJECT-TYPE
    SYNTAX INTEGER {
      ok(1),
      error(2),
      changed(3),
      quit(4),
      timeout(5),
      detected(6),
      notAvail(7),
      lowPower(8)
    }
    ACCESS  read-only
    STATUS  mandatory
    DESCRIPTION
      "General Status sensor unit connected to port 3
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc4StatusSensorUnit3 4 }

-- Sensors              

  cmcTcMasterTc4Unit3NumberOfSensors OBJECT-TYPE
    SYNTAX INTEGER 
    ACCESS read-only
    STATUS mandatory
    DESCRIPTION
      "Number of sensors connected to sensor unit 3"
    ::= { cmcTcMasterTc4StatusUnit3Sensors 1 }

-- table with entry for each sensor available on this unit              
        
  cmcTcMasterTc4Unit3SensorTable OBJECT-TYPE
    SYNTAX SEQUENCE OF CmcTcMasterTc4Unit3SensorEntry
    ACCESS not-accessible
    STATUS mandatory
    DESCRIPTION
      "Headline of sensor table"
    ::= { cmcTcMasterTc4StatusUnit3Sensors 2 }

  cmcTcMasterTc4Unit3SensorEntry OBJECT-TYPE
    SYNTAX CmcTcMasterTc4Unit3SensorEntry
    ACCESS not-accessible
    STATUS mandatory
    DESCRIPTION
      "Entries of sensor table"
    INDEX { cmcTcMasterTc4Unit3SensorIndex }
    ::= { cmcTcMasterTc4Unit3SensorTable 1 }

    CmcTcMasterTc4Unit3SensorEntry ::=
      SEQUENCE {
        cmcTcMasterTc4Unit3SensorIndex
          INTEGER,
        cmcTcMasterTc4Unit3SensorType
          INTEGER,
        cmcTcMasterTc4Unit3SensorText
          DisplayString (SIZE (0..20)),                
        cmcTcMasterTc4Unit3SensorStatus
          INTEGER,
        cmcTcMasterTc4Unit3SensorValue
          INTEGER,
        cmcTcMasterTc4Unit3SensorSetHigh
          INTEGER,
        cmcTcMasterTc4Unit3SensorSetLow
          INTEGER,                 
        cmcTcMasterTc4Unit3SensorSetWarn
          INTEGER  
      }

    cmcTcMasterTc4Unit3SensorIndex OBJECT-TYPE
      SYNTAX INTEGER (1..32000)
      ACCESS read-only
      STATUS mandatory
      DESCRIPTION
        "Index for the list of value entries. Its value ranges
         between 1 and the value of cmcTcMasterTc4Unit3NumberOfSensors." 
      ::= { cmcTcMasterTc4Unit3SensorEntry 1 }

    cmcTcMasterTc4Unit3SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 3 to sensor[cmcTcMasterTc4Unit3SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc4Unit3SensorEntry 2 }

    cmcTcMasterTc4Unit3SensorText OBJECT-TYPE
      SYNTAX DisplayString (SIZE (0..20))
      ACCESS read-write
      STATUS mandatory
      DESCRIPTION
        "Descriptional text for each sensor (entry in the table)"
      ::= { cmcTcMasterTc4Unit3SensorEntry 3 }
              
    cmcTcMasterTc4Unit3SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc4Unit3SensorEntry 4 }

    cmcTcMasterTc4Unit3SensorValue OBJECT-TYPE
      SYNTAX INTEGER 
      ACCESS read-only
      STATUS mandatory
      DESCRIPTION
        "Value of sensor"
      ::= { cmcTcMasterTc4Unit3SensorEntry 5 }

    cmcTcMasterTc4Unit3SensorSetHigh OBJECT-TYPE
      SYNTAX INTEGER (0..300) 
      ACCESS read-write
      STATUS mandatory
      DESCRIPTION
        "Value for high setpoint of sensor"
      ::= { cmcTcMasterTc4Unit3SensorEntry 6 }

    cmcTcMasterTc4Unit3SensorSetLow OBJECT-TYPE
      SYNTAX INTEGER (0..300) 
      ACCESS read-write
      STATUS mandatory
      DESCRIPTION
        "Value for low setpoint of sensor,
         also used as alarm delay"
      ::= { cmcTcMasterTc4Unit3SensorEntry 7 }

    cmcTcMasterTc4Unit3SensorSetWarn OBJECT-TYPE
      SYNTAX INTEGER (0..300) 
      ACCESS read-write
      STATUS mandatory
      DESCRIPTION
        "Value for warning setpoint of sensor,
         also used as fan threshold"
      ::= { cmcTcMasterTc4Unit3SensorEntry 8 }
                
-- Outputs              

  cmcTcMasterTc4Unit3NumberOfOutputs OBJECT-TYPE
    SYNTAX INTEGER 
    ACCESS read-only
    STATUS mandatory
    DESCRIPTION
      "Number of outputs available on sensor unit 3"
    ::= { cmcTcMasterTc4StatusUnit3Outputs 1 }

-- table with entry for each output available on this unit              
                
  cmcTcMasterTc4Unit3OutputTable OBJECT-TYPE
    SYNTAX SEQUENCE OF CmcTcMasterTc4Unit3OutputEntry
    ACCESS not-accessible
    STATUS mandatory
    DESCRIPTION
      "Headline of output table"
    ::= { cmcTcMasterTc4StatusUnit3Outputs 2 }

  cmcTcMasterTc4Unit3OutputEntry OBJECT-TYPE
    SYNTAX CmcTcMasterTc4Unit3OutputEntry
    ACCESS not-accessible
    STATUS mandatory
    DESCRIPTION
      "Entries of output table"
    INDEX { cmcTcMasterTc4Unit3OutputIndex }
    ::= { cmcTcMasterTc4Unit3OutputTable 1 }

    CmcTcMasterTc4Unit3OutputEntry ::=
      SEQUENCE {
        cmcTcMasterTc4Unit3OutputIndex
          INTEGER,
        cmcTcMasterTc4Unit3OutputType
          INTEGER,
        cmcTcMasterTc4Unit3OutputText
          DisplayString (SIZE (0..20)),                
        cmcTcMasterTc4Unit3OutputStatus
          INTEGER,
        cmcTcMasterTc4Unit3OutputValue
          INTEGER,
        cmcTcMasterTc4Unit3OutputSet
          INTEGER,
        cmcTcMasterTc4Unit3OutputConfig
          INTEGER,
        cmcTcMasterTc4Unit3OutputDelay
          INTEGER,
        cmcTcMasterTc4Unit3OutputTimeoutAction
          INTEGER
      }

    cmcTcMasterTc4Unit3OutputIndex OBJECT-TYPE
      SYNTAX INTEGER (1..32000)
      ACCESS read-only
      STATUS mandatory
      DESCRIPTION
        "Index for the list of output entries. Its value ranges
         between 1 and the value of cmcTcMasterTc4Unit3NumberOfOutputs." 
      ::= { cmcTcMasterTc4Unit3OutputEntry 1 }

    cmcTcMasterTc4Unit3OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 3 to output[cmcTcMasterTc4Unit3OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc4Unit3OutputEntry 2 }

        
    cmcTcMasterTc4Unit3OutputText OBJECT-TYPE
      SYNTAX DisplayString (SIZE (0..20))
      ACCESS read-write
      STATUS mandatory
      DESCRIPTION
        "Descriptional text for each output (entry in the table)"
      ::= { cmcTcMasterTc4Unit3OutputEntry 3 }
              
    cmcTcMasterTc4Unit3OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc4Unit3OutputEntry 4 }

    cmcTcMasterTc4Unit3OutputValue OBJECT-TYPE
      SYNTAX INTEGER (-32000..32000) 
      ACCESS read-write
      STATUS mandatory
      DESCRIPTION
        "Value for output"
      ::= { cmcTcMasterTc4Unit3OutputEntry 5 }

    cmcTcMasterTc4Unit3OutputSet OBJECT-TYPE
      SYNTAX INTEGER {
        off (1),
        on (2),
        lock (3),
        unlock (4),
        unlockDelay (5)
      }
      ACCESS read-write
      STATUS mandatory
      DESCRIPTION
        "Command for output"
      ::= { cmcTcMasterTc4Unit3OutputEntry 6 }

    cmcTcMasterTc4Unit3OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc4Unit3OutputEntry 7 }

    cmcTcMasterTc4Unit3OutputDelay OBJECT-TYPE
      SYNTAX INTEGER (0..999) 
      ACCESS read-write
      STATUS mandatory
      DESCRIPTION
        "Unsigned Value for delay, 
         after this time the output will fall into the previous state"
      ::= { cmcTcMasterTc4Unit3OutputEntry 8 }

    cmcTcMasterTc4Unit3OutputTimeoutAction OBJECT-TYPE
      SYNTAX INTEGER {
        stay (1),
        off (2),
        on (3)
      }
      ACCESS read-write
      STATUS mandatory
      DESCRIPTION
        "State for output if timeout (RS422) occurs"
      ::= { cmcTcMasterTc4Unit3OutputEntry 9 }

-- Messages
              
  cmcTcMasterTc4Unit3NumberOfMsgs OBJECT-TYPE
    SYNTAX INTEGER 
    ACCESS read-only
    STATUS mandatory
    DESCRIPTION
      "Number of messages that can be created with sensor unit 3"
    ::= { cmcTcMasterTc4StatusUnit3Msg 1 }

-- table with entry for each alarm available on this unit               
                
  cmcTcMasterTc4Unit3MsgTable OBJECT-TYPE
    SYNTAX SEQUENCE OF CmcTcMasterTc4Unit3MsgEntry
    ACCESS not-accessible
    STATUS mandatory
    DESCRIPTION
      "Headline of message table"
    ::= { cmcTcMasterTc4StatusUnit3Msg 2 }

  cmcTcMasterTc4Unit3MsgEntry OBJECT-TYPE
    SYNTAX CmcTcMasterTc4Unit3MsgEntry
    ACCESS not-accessible
    STATUS mandatory
    DESCRIPTION
      "Entries of message table"
    INDEX { cmcTcMasterTc4Unit3MsgIndex }
    ::= { cmcTcMasterTc4Unit3MsgTable 1 }

    CmcTcMasterTc4Unit3MsgEntry ::=
      SEQUENCE {
        cmcTcMasterTc4Unit3MsgIndex
          INTEGER,
        cmcTcMasterTc4Unit3MsgText
          DisplayString (SIZE (0..20)),
        cmcTcMasterTc4Unit3MsgStatus
          INTEGER, 
        cmcTcMasterTc4Unit3MsgRelay
          INTEGER,
        cmcTcMasterTc4Unit3MsgBeeper
          INTEGER,
        cmcTcMasterTc4Unit3MsgTrap1
          INTEGER,
        cmcTcMasterTc4Unit3MsgTrap2
          INTEGER,
        cmcTcMasterTc4Unit3MsgTrap3
          INTEGER,
        cmcTcMasterTc4Unit3MsgTrap4
          INTEGER,                 
        cmcTcMasterTc4Unit3MsgQuit
          INTEGER              
      }

    cmcTcMasterTc4Unit3MsgIndex OBJECT-TYPE
      SYNTAX INTEGER (1..32000)
      ACCESS read-only
      STATUS mandatory
      DESCRIPTION
        "Index for the list of message entries. Its value ranges
         between 1 and the value of cmcTcMasterTc4Unit3NumberOfMsgs." 
      ::= { cmcTcMasterTc4Unit3MsgEntry 1 }

    cmcTcMasterTc4Unit3MsgText OBJECT-TYPE
      SYNTAX DisplayString (SIZE (0..20))
      ACCESS read-write
      STATUS mandatory
      DESCRIPTION
        "Descriptional text for each message (entry in the table)"
      ::= { cmcTcMasterTc4Unit3MsgEntry 2 }

    cmcTcMasterTc4Unit3MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc4Unit3OutputSet)
         17: door is unlocked by WEB
         18: door is unlocked by timer
         19: no access, wrong keycode or cardnumber
         20: orientation of PSM-Unit is circuit 1
         21: orientation of PSM-Unit is circuit 2"
      ::= { cmcTcMasterTc4Unit3MsgEntry 3 }

    cmcTcMasterTc4Unit3MsgRelay OBJECT-TYPE
      SYNTAX INTEGER {
        disable (1),
        enable (2)
      }
      ACCESS read-write
      STATUS mandatory
      DESCRIPTION
        "Setup of Alarm relay for this alarm
         1:        no switching of alarm relay             
         2:        switching of alarm relay" 
      ::= { cmcTcMasterTc4Unit3MsgEntry 4 }

    cmcTcMasterTc4Unit3MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc4Unit3MsgEntry 5 }

    cmcTcMasterTc4Unit3MsgTrap1 OBJECT-TYPE
      SYNTAX INTEGER {
        disable (1),
        enable (2)
      }
      ACCESS read-write
      STATUS mandatory
      DESCRIPTION
        "Trap receiver 1 activated"
      ::= { cmcTcMasterTc4Unit3MsgEntry 6 }

    cmcTcMasterTc4Unit3MsgTrap2 OBJECT-TYPE
      SYNTAX INTEGER {
        disable (1),
        enable (2)
      }
      ACCESS read-write
      STATUS mandatory
      DESCRIPTION
        "Trap receiver 2 activated"
      ::= { cmcTcMasterTc4Unit3MsgEntry 7 }
 
    cmcTcMasterTc4Unit3MsgTrap3 OBJECT-TYPE
      SYNTAX INTEGER {
        disable (1),
        enable (2)
      }
      ACCESS read-write
      STATUS mandatory
      DESCRIPTION
        "Trap receiver 3 activated"
      ::= { cmcTcMasterTc4Unit3MsgEntry 8 }

    cmcTcMasterTc4Unit3MsgTrap4 OBJECT-TYPE
      SYNTAX INTEGER {
        disable (1),
        enable (2)
      }
      ACCESS read-write
      STATUS mandatory
      DESCRIPTION
        "Trap receiver 4 and Event Logging activated"
      ::= { cmcTcMasterTc4Unit3MsgEntry 9 }

    cmcTcMasterTc4Unit3MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc4Unit3MsgEntry 10 }

-- unit4

  cmcTcMasterTc4Unit4TypeOfDevice OBJECT-TYPE
    SYNTAX INTEGER {
      notAvail (1),
      unitIO (2),
      unitAccess (3),
      unitClimate (4),
      unitFCS (5),
      unitRTT (6),
      unitRLCP (7),
      unitPSM (8)
    }
    ACCESS  read-only
    STATUS  mandatory
    DESCRIPTION
      "Type of sensor unit connected to port 4"
    ::= { cmcTcMasterTc4StatusSensorUnit4 1 }

  cmcTcMasterTc4Unit4Text OBJECT-TYPE
    SYNTAX DisplayString (SIZE (0..10))
    ACCESS read-write
    STATUS mandatory
    DESCRIPTION
      "Descriptional text for sensor unit connected to port 4"
    ::= { cmcTcMasterTc4StatusSensorUnit4 2 }

  cmcTcMasterTc4Unit4Serial OBJECT-TYPE
    SYNTAX INTEGER 
    ACCESS read-only
    STATUS mandatory
    DESCRIPTION
      "Serialnumber of sensor unit connected to port 4"
    ::= { cmcTcMasterTc4StatusSensorUnit4 3 }

  cmcTcMasterTc4Unit4Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 4
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc4StatusSensorUnit4 4 }

-- Sensors
              
  cmcTcMasterTc4Unit4NumberOfSensors OBJECT-TYPE
    SYNTAX INTEGER 
    ACCESS read-only
    STATUS mandatory
    DESCRIPTION
      "Number of sensors connected to sensor unit 4"
    ::= { cmcTcMasterTc4StatusUnit4Sensors 1 }

-- table with entry for each sensor available on this unit              
                
  cmcTcMasterTc4Unit4SensorTable OBJECT-TYPE
    SYNTAX SEQUENCE OF CmcTcMasterTc4Unit4SensorEntry
    ACCESS not-accessible
    STATUS mandatory
    DESCRIPTION
      "Headline of sensor table"
    ::= { cmcTcMasterTc4StatusUnit4Sensors 2 }

  cmcTcMasterTc4Unit4SensorEntry OBJECT-TYPE
    SYNTAX CmcTcMasterTc4Unit4SensorEntry
    ACCESS not-accessible
    STATUS mandatory
    DESCRIPTION
      "Entries of sensor table"
    INDEX { cmcTcMasterTc4Unit4SensorIndex }
    ::= { cmcTcMasterTc4Unit4SensorTable 1 }

    CmcTcMasterTc4Unit4SensorEntry ::=
      SEQUENCE {
        cmcTcMasterTc4Unit4SensorIndex
          INTEGER,
        cmcTcMasterTc4Unit4SensorType
          INTEGER,
        cmcTcMasterTc4Unit4SensorText
          DisplayString (SIZE (0..20)),                
        cmcTcMasterTc4Unit4SensorStatus
          INTEGER,
        cmcTcMasterTc4Unit4SensorValue
          INTEGER,
        cmcTcMasterTc4Unit4SensorSetHigh
          INTEGER,
        cmcTcMasterTc4Unit4SensorSetLow
          INTEGER,                 
        cmcTcMasterTc4Unit4SensorSetWarn
          INTEGER  
      }

    cmcTcMasterTc4Unit4SensorIndex OBJECT-TYPE
      SYNTAX INTEGER (1..32000)
      ACCESS read-only
      STATUS mandatory
      DESCRIPTION
        "Index for the list of value entries. Its value ranges
         between 1 and the value of cmcTcMasterTc4Unit4NumberOfSensors." 
      ::= { cmcTcMasterTc4Unit4SensorEntry 1 }

    cmcTcMasterTc4Unit4SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 4 to sensor[cmcTcMasterTc4Unit4SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc4Unit4SensorEntry 2 }

    cmcTcMasterTc4Unit4SensorText OBJECT-TYPE
      SYNTAX DisplayString (SIZE (0..20))
      ACCESS read-write
      STATUS mandatory
      DESCRIPTION
        "Descriptional text for each sensor (entry in the table)"
      ::= { cmcTcMasterTc4Unit4SensorEntry 3 }
              
    cmcTcMasterTc4Unit4SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc4Unit4SensorEntry 4 }

    cmcTcMasterTc4Unit4SensorValue OBJECT-TYPE
      SYNTAX INTEGER 
      ACCESS read-only
      STATUS mandatory
      DESCRIPTION
        "Value of sensor"
      ::= { cmcTcMasterTc4Unit4SensorEntry 5 }

    cmcTcMasterTc4Unit4SensorSetHigh OBJECT-TYPE
      SYNTAX INTEGER (0..300) 
      ACCESS read-write
      STATUS mandatory
      DESCRIPTION
        "Value for high setpoint of sensor"
      ::= { cmcTcMasterTc4Unit4SensorEntry 6 }

    cmcTcMasterTc4Unit4SensorSetLow OBJECT-TYPE
      SYNTAX INTEGER (0..300) 
      ACCESS read-write
      STATUS mandatory
      DESCRIPTION
        "Value for low setpoint of sensor,
         also used as alarm delay"
      ::= { cmcTcMasterTc4Unit4SensorEntry 7 }

    cmcTcMasterTc4Unit4SensorSetWarn OBJECT-TYPE
      SYNTAX INTEGER (0..300) 
      ACCESS read-write
      STATUS mandatory
      DESCRIPTION
        "Value for warning setpoint of sensor,
         also used as fan threshold"
      ::= { cmcTcMasterTc4Unit4SensorEntry 8 }

-- Outputs              

  cmcTcMasterTc4Unit4NumberOfOutputs OBJECT-TYPE
    SYNTAX INTEGER 
    ACCESS read-only
    STATUS mandatory
    DESCRIPTION
      "Number of outputs available on sensor unit 4"
    ::= { cmcTcMasterTc4StatusUnit4Outputs 1 }

-- table with entry for each output available on this unit              
                
  cmcTcMasterTc4Unit4OutputTable OBJECT-TYPE
    SYNTAX SEQUENCE OF CmcTcMasterTc4Unit4OutputEntry
    ACCESS not-accessible
    STATUS mandatory
    DESCRIPTION
      "Headline of output table"
    ::= { cmcTcMasterTc4StatusUnit4Outputs 2 }

  cmcTcMasterTc4Unit4OutputEntry OBJECT-TYPE
    SYNTAX CmcTcMasterTc4Unit4OutputEntry
    ACCESS not-accessible
    STATUS mandatory
    DESCRIPTION
      "Entries of output table"
    INDEX { cmcTcMasterTc4Unit4OutputIndex }
    ::= { cmcTcMasterTc4Unit4OutputTable 1 }

    CmcTcMasterTc4Unit4OutputEntry ::=
      SEQUENCE {
        cmcTcMasterTc4Unit4OutputIndex
          INTEGER,
        cmcTcMasterTc4Unit4OutputType
          INTEGER,
        cmcTcMasterTc4Unit4OutputText
          DisplayString (SIZE (0..20)),                
        cmcTcMasterTc4Unit4OutputStatus
          INTEGER,
        cmcTcMasterTc4Unit4OutputValue
          INTEGER,
        cmcTcMasterTc4Unit4OutputSet
          INTEGER,
        cmcTcMasterTc4Unit4OutputConfig
          INTEGER,
        cmcTcMasterTc4Unit4OutputDelay
          INTEGER,
        cmcTcMasterTc4Unit4OutputTimeoutAction
          INTEGER
      }

    cmcTcMasterTc4Unit4OutputIndex OBJECT-TYPE
      SYNTAX INTEGER (1..32000)
      ACCESS read-only
      STATUS mandatory
      DESCRIPTION
        "Index for the list of output entries. Its value ranges
         between 1 and the value of cmcTcMasterTc4Unit4NumberOfOutputs." 
      ::= { cmcTcMasterTc4Unit4OutputEntry 1 }

    cmcTcMasterTc4Unit4OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 4 to output[cmcTcMasterTc4Unit4OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc4Unit4OutputEntry 2 }

    cmcTcMasterTc4Unit4OutputText OBJECT-TYPE
      SYNTAX DisplayString (SIZE (0..20))
      ACCESS read-write
      STATUS mandatory
      DESCRIPTION
        "Descriptional text for each output (entry in the table)"
      ::= { cmcTcMasterTc4Unit4OutputEntry 3 }
              
    cmcTcMasterTc4Unit4OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc4Unit4OutputEntry 4 }

    cmcTcMasterTc4Unit4OutputValue OBJECT-TYPE
      SYNTAX INTEGER (-32000..32000) 
      ACCESS read-write
      STATUS mandatory
      DESCRIPTION
        "Value for output"
      ::= { cmcTcMasterTc4Unit4OutputEntry 5 }

    cmcTcMasterTc4Unit4OutputSet OBJECT-TYPE
      SYNTAX INTEGER {
        off (1),
        on (2),
        lock (3),
        unlock (4),
        unlockDelay (5)
      }
      ACCESS read-write
      STATUS mandatory
      DESCRIPTION
        "Command for output"
      ::= { cmcTcMasterTc4Unit4OutputEntry 6 }

    cmcTcMasterTc4Unit4OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc4Unit4OutputEntry 7 }

    cmcTcMasterTc4Unit4OutputDelay OBJECT-TYPE
      SYNTAX INTEGER (0..999) 
      ACCESS read-write
      STATUS mandatory
      DESCRIPTION
        "Unsigned Value for delay, 
         after this time the output will fall into the previous state"
      ::= { cmcTcMasterTc4Unit4OutputEntry 8 }

    cmcTcMasterTc4Unit4OutputTimeoutAction OBJECT-TYPE
      SYNTAX INTEGER {
        stay (1),
        off (2),
        on (3)
      }
      ACCESS read-write
      STATUS mandatory
      DESCRIPTION
        "State for output if timeout (RS422) occurs"
      ::= { cmcTcMasterTc4Unit4OutputEntry 9 }

-- Messages
              
  cmcTcMasterTc4Unit4NumberOfMsgs OBJECT-TYPE
    SYNTAX INTEGER 
    ACCESS read-only
    STATUS mandatory
    DESCRIPTION
      "Number of messages that can be created with sensor unit 4"
    ::= { cmcTcMasterTc4StatusUnit4Msg 1 }

-- table with entry for each alarm available on this unit               
                
  cmcTcMasterTc4Unit4MsgTable OBJECT-TYPE
    SYNTAX SEQUENCE OF CmcTcMasterTc4Unit4MsgEntry
    ACCESS not-accessible
    STATUS mandatory
    DESCRIPTION
      "Headline of message table"
    ::= { cmcTcMasterTc4StatusUnit4Msg 2 }

  cmcTcMasterTc4Unit4MsgEntry OBJECT-TYPE
    SYNTAX CmcTcMasterTc4Unit4MsgEntry
    ACCESS not-accessible
    STATUS mandatory
    DESCRIPTION
      "Entries of message table"
    INDEX { cmcTcMasterTc4Unit4MsgIndex }
    ::= { cmcTcMasterTc4Unit4MsgTable 1 }

    CmcTcMasterTc4Unit4MsgEntry ::=
      SEQUENCE {
        cmcTcMasterTc4Unit4MsgIndex
          INTEGER,
        cmcTcMasterTc4Unit4MsgText
          DisplayString (SIZE (0..20)),                
        cmcTcMasterTc4Unit4MsgStatus
          INTEGER, 
        cmcTcMasterTc4Unit4MsgRelay
          INTEGER,
        cmcTcMasterTc4Unit4MsgBeeper
          INTEGER,
        cmcTcMasterTc4Unit4MsgTrap1
          INTEGER,
        cmcTcMasterTc4Unit4MsgTrap2
          INTEGER,
        cmcTcMasterTc4Unit4MsgTrap3
          INTEGER,
        cmcTcMasterTc4Unit4MsgTrap4
          INTEGER,                 
        cmcTcMasterTc4Unit4MsgQuit
          INTEGER              
      }

    cmcTcMasterTc4Unit4MsgIndex OBJECT-TYPE
      SYNTAX INTEGER (1..32000)
      ACCESS read-only
      STATUS mandatory
      DESCRIPTION
        "Index for the list of message entries. Its value ranges
         between 1 and the value of cmcTcMasterTc4Unit4NumberOfMsgs." 
      ::= { cmcTcMasterTc4Unit4MsgEntry 1 }

    cmcTcMasterTc4Unit4MsgText OBJECT-TYPE
      SYNTAX DisplayString (SIZE (0..20))
      ACCESS read-write
      STATUS mandatory
      DESCRIPTION
        "Descriptional text for each message (entry in the table)"
      ::= { cmcTcMasterTc4Unit4MsgEntry 2 }

    cmcTcMasterTc4Unit4MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc4Unit4OutputSet)
         17: door is unlocked by WEB
         18: door is unlocked by timer
         19: no access, wrong keycode or cardnumber
         20: orientation of PSM-Unit is circuit 1
         21: orientation of PSM-Unit is circuit 2"
      ::= { cmcTcMasterTc4Unit4MsgEntry 3 }

    cmcTcMasterTc4Unit4MsgRelay OBJECT-TYPE
      SYNTAX INTEGER {
        disable (1),
        enable (2)
      }
      ACCESS read-write
      STATUS mandatory
      DESCRIPTION
        "Setup of Alarm relay for this alarm
         1:        no switching of alarm relay             
         2:        switching of alarm relay" 
      ::= { cmcTcMasterTc4Unit4MsgEntry 4 }

    cmcTcMasterTc4Unit4MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc4Unit4MsgEntry 5 }

    cmcTcMasterTc4Unit4MsgTrap1 OBJECT-TYPE
      SYNTAX INTEGER {
        disable (1),
        enable (2)
      }
      ACCESS read-write
      STATUS mandatory
      DESCRIPTION
        "Trap receiver 1 activated"
      ::= { cmcTcMasterTc4Unit4MsgEntry 6 }

    cmcTcMasterTc4Unit4MsgTrap2 OBJECT-TYPE
      SYNTAX INTEGER {
        disable (1),
        enable (2)
      }
      ACCESS read-write
      STATUS mandatory
      DESCRIPTION
        "Trap receiver 2 activated"
      ::= { cmcTcMasterTc4Unit4MsgEntry 7 }
 
    cmcTcMasterTc4Unit4MsgTrap3 OBJECT-TYPE
      SYNTAX INTEGER {
        disable (1),
        enable (2)
      }
      ACCESS read-write
      STATUS mandatory
      DESCRIPTION
        "Trap receiver 3 activated"
      ::= { cmcTcMasterTc4Unit4MsgEntry 8 }

    cmcTcMasterTc4Unit4MsgTrap4 OBJECT-TYPE
      SYNTAX INTEGER {
        disable (1),
        enable (2)
      }
      ACCESS read-write
      STATUS mandatory
      DESCRIPTION
        "Trap receiver 4 and Event Logging activated"
      ::= { cmcTcMasterTc4Unit4MsgEntry 9 }

    cmcTcMasterTc4Unit4MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc4Unit4MsgEntry 10 }

--Status extension unit

  cmcTcMasterTc4ValuesRelay OBJECT-TYPE
    SYNTAX INTEGER {
      disable (1),
      enable (2)
    }
    ACCESS read-write
    STATUS mandatory
    DESCRIPTION
      "Setup of Alarm relay for alarm ext. unit(s)
       1:        no switching of alarm relay             
       2:        switching of alarm relay" 
    ::= { cmcTcMasterTc4StatusExtUnit 1 }

  cmcTcMasterTc4ValuesBeeper OBJECT-TYPE
    SYNTAX INTEGER {
      disable (1),
      enable (2)
    }
    ACCESS read-write
    STATUS mandatory
    DESCRIPTION
      "Setup of Alarm beeper for alarm ext. unit(s)
       1:        no audible alarm
       2:        audible alarm" 
    ::= { cmcTcMasterTc4StatusExtUnit 2 }

  cmcTcMasterTc4ValuesTrap1 OBJECT-TYPE
    SYNTAX INTEGER {
      disable (1),
      enable (2)
    }
    ACCESS read-write
    STATUS mandatory
    DESCRIPTION
      "Trap receiver 1 activated"
    ::= { cmcTcMasterTc4StatusExtUnit 3 }

  cmcTcMasterTc4ValuesTrap2 OBJECT-TYPE
    SYNTAX INTEGER {
      disable (1),
      enable (2)
    }
    ACCESS read-write
    STATUS mandatory
    DESCRIPTION
      "Trap receiver 2 activated"
    ::= { cmcTcMasterTc4StatusExtUnit 4 }
 
  cmcTcMasterTc4ValuesTrap3 OBJECT-TYPE
    SYNTAX INTEGER {
      disable (1),
      enable (2)
    }
    ACCESS read-write
    STATUS mandatory
    DESCRIPTION
      "Trap receiver 3 activated"
    ::= { cmcTcMasterTc4StatusExtUnit 5 }

  cmcTcMasterTc4ValuesTrap4 OBJECT-TYPE
    SYNTAX INTEGER {
      disable (1),
      enable (2)
    }
    ACCESS read-write
    STATUS mandatory
    DESCRIPTION
      "Trap receiver 4 and Event Logging activated"
    ::= { cmcTcMasterTc4StatusExtUnit 6 }
 
  cmcTcMasterTc4NumberOfValues OBJECT-TYPE
    SYNTAX INTEGER 
    ACCESS  read-only
    STATUS  mandatory
    DESCRIPTION
      "Number of values availabel on extension units connected to the CMC-TC"
    ::= { cmcTcMasterTc4StatusExtUnit 7 }

-- table with entry for each value available on extension units              

  cmcTcMasterTc4ValuesTable OBJECT-TYPE
    SYNTAX SEQUENCE OF CmcTcMasterTc4ValuesEntry
    ACCESS not-accessible
    STATUS mandatory
    DESCRIPTION
      "Headline of values-table"
    ::= { cmcTcMasterTc4StatusExtUnit 8 }

  cmcTcMasterTc4ValuesEntry OBJECT-TYPE
    SYNTAX CmcTcMasterTc4ValuesEntry
    ACCESS not-accessible
    STATUS mandatory
    DESCRIPTION
      "Entries of values-table"
    INDEX { cmcTcMasterTc4ValuesIndex }
    ::= { cmcTcMasterTc4ValuesTable 1 }

    CmcTcMasterTc4ValuesEntry ::=
      SEQUENCE {
        cmcTcMasterTc4ValuesIndex
          INTEGER,
        cmcTcMasterTc4ValuesText
          DisplayString (SIZE (0..20)),                
        cmcTcMasterTc4ValuesStatus
          INTEGER,
        cmcTcMasterTc4ValuesValue
          INTEGER,
        cmcTcMasterTc4ValuesSetHigh
          INTEGER,
        cmcTcMasterTc4ValuesSetLow
          INTEGER
      }

    cmcTcMasterTc4ValuesIndex OBJECT-TYPE
      SYNTAX INTEGER (1..32000)
      ACCESS read-only
      STATUS mandatory
      DESCRIPTION
        "Index for the list of value entries. Its value ranges
         between 1 and the value of cmcTcMasterTc4NumberOfValues." 
      ::= { cmcTcMasterTc4ValuesEntry 1 }

        
    cmcTcMasterTc4ValuesText OBJECT-TYPE
      SYNTAX DisplayString (SIZE (0..20))
      ACCESS read-write
      STATUS mandatory
      DESCRIPTION
        "Descriptional text for each value (entry in the table)
         of the extension card"
      ::= { cmcTcMasterTc4ValuesEntry 2 }
              
    cmcTcMasterTc4ValuesStatus OBJECT-TYPE
      SYNTAX INTEGER {
        notAvail(1),
        lost(2),
        changed(3),
        ok(4),
        tooLow(5),
        tooHigh(6),
        error(7)
      }
      ACCESS read-only
      STATUS mandatory
      DESCRIPTION
        "Actual status of the value of the extension card"
      ::= { cmcTcMasterTc4ValuesEntry 3 }

    cmcTcMasterTc4ValuesValue OBJECT-TYPE
      SYNTAX INTEGER 
      ACCESS read-only
      STATUS mandatory
      DESCRIPTION
        "Value of sensor"
      ::= { cmcTcMasterTc4ValuesEntry 4 }

    cmcTcMasterTc4ValuesSetHigh OBJECT-TYPE
      SYNTAX INTEGER (0..255) 
      ACCESS read-write
      STATUS mandatory
      DESCRIPTION
        "Value for high setpoint of sensor"
      ::= { cmcTcMasterTc4ValuesEntry 5 }

    cmcTcMasterTc4ValuesSetLow OBJECT-TYPE
      SYNTAX INTEGER (0..255) 
      ACCESS read-write
      STATUS mandatory
      DESCRIPTION
        "Value for low setpoint of sensor"
      ::= { cmcTcMasterTc4ValuesEntry 6 }

--cmcTcMasterTc4SetupGeneral-group

  cmcTcMasterTc4SetTempUnit OBJECT-TYPE
    SYNTAX INTEGER {
      celsius(1),
      fahrenheit(2)
    }
    ACCESS read-write
    STATUS mandatory
    DESCRIPTION
      "Unit of all temperature values and setpoints, Celsius or Fahrenheit"
   ::= { cmcTcMasterTc4SetupGeneral 1 }

  cmcTcMasterTc4SetBeeper OBJECT-TYPE
    SYNTAX INTEGER {
      off(1),
      on(2)
    }
    ACCESS read-write
    STATUS mandatory
    DESCRIPTION
      "Audible alarm in CMC-TC unit:
       (2): beeper is on
       (1): beeper is off (general)"
    ::= { cmcTcMasterTc4SetupGeneral 2 }


  cmcTcMasterTc4QuitRelay OBJECT-TYPE
    SYNTAX INTEGER {
      disabled(1),
      enabled(2)
    }
    ACCESS read-write
    STATUS mandatory
    DESCRIPTION
      "Enable or disable acknowledging currently active alarm relay 
       (with 'C' on CMC-TC)."
    ::= { cmcTcMasterTc4SetupGeneral 3 }

  cmcTcMasterTc4LogicRelay OBJECT-TYPE
    SYNTAX INTEGER {
      closeAtAlarm(1),
      openAtAlarm(2),
      off(3)
    }
    ACCESS read-write
    STATUS mandatory
    DESCRIPTION
      "Logic of alarm relay: 
       (1) Relay will pick up in case of an alarm
       (2) Relay will release in case of an alarm
       (3) Relay off (general)"
    ::= { cmcTcMasterTc4SetupGeneral 4 }

  cmcTcMasterTc4WebAccess OBJECT-TYPE
    SYNTAX INTEGER {
      viewOnly(1),
      fullAccess(2),
      off(3)
    }
    ACCESS read-write
    STATUS mandatory
    DESCRIPTION
      "Web access via HTTP: 
       (1) view only
       (2) full Access, read and set
       (3) Web disabled (general)"
    ::= { cmcTcMasterTc4SetupGeneral 5 }
 
  cmcTcMasterTc4SetupDate OBJECT-TYPE
    SYNTAX DisplayString (SIZE (0..10))
    ACCESS read-write
    STATUS mandatory
    DESCRIPTION
      "actual Date in format DD.MM.YYYY"
    ::= { cmcTcMasterTc4SetupGeneral 6 }

  cmcTcMasterTc4SetupTime OBJECT-TYPE
    SYNTAX DisplayString (SIZE (0..8))
    ACCESS read-write
    STATUS mandatory
    DESCRIPTION
      "actual Time in format HH:MM:SS, HH (0-23), MM (0-59), SS (0-59)"
    ::= { cmcTcMasterTc4SetupGeneral 7 }
 
-- table for timer function
 
  cmcTcMasterTc4TimerNumber OBJECT-TYPE
    SYNTAX INTEGER 
    ACCESS read-only
    STATUS mandatory
    DESCRIPTION
      "Number of timers available on this unit"
    ::= { cmcTcMasterTc4TimerTable1 1 }

  cmcTcMasterTc4TimerTable OBJECT-TYPE
    SYNTAX SEQUENCE OF CmcTcMasterTc4TimerEntry
    ACCESS not-accessible
    STATUS mandatory
    DESCRIPTION
      "Headline of timer-table"
    ::= { cmcTcMasterTc4TimerTable1 2 }

  cmcTcMasterTc4TimerEntry OBJECT-TYPE
    SYNTAX CmcTcMasterTc4TimerEntry
    ACCESS not-accessible
    STATUS mandatory
    DESCRIPTION
      "Entries of timer-table"
    INDEX { cmcTcMasterTc4TimerIndex }
    ::= { cmcTcMasterTc4TimerTable 1 }

    CmcTcMasterTc4TimerEntry ::=
      SEQUENCE {
        cmcTcMasterTc4TimerIndex
          INTEGER,
        cmcTcMasterTc4TimerStatus
          INTEGER,
        cmcTcMasterTc4TimerDayOfWeek
          INTEGER,  
        cmcTcMasterTc4TimeOn 
          DisplayString (SIZE (0..5)),                              
        cmcTcMasterTc4TimeOff 
          DisplayString (SIZE (0..5)),                              
        cmcTcMasterTc4TimeControl
          INTEGER,
        cmcTcMasterTc4TimerFunction
           INTEGER
      }

    cmcTcMasterTc4TimerIndex OBJECT-TYPE
      SYNTAX INTEGER (1..32000)
      ACCESS read-only
      STATUS mandatory
      DESCRIPTION
        "Index for the list of timer entries. Its value ranges
         between 1 and the value of cmcTcMasterTc4TimerNumber." 
      ::= { cmcTcMasterTc4TimerEntry 1 }

    cmcTcMasterTc4TimerStatus OBJECT-TYPE
      SYNTAX INTEGER {
        switchedOff(1),
        switchedOn(2),
        noTime(3) 
      }
      ACCESS read-only
      STATUS mandatory
      DESCRIPTION
        "Actual status of the timer"
      ::= { cmcTcMasterTc4TimerEntry 2 }

    cmcTcMasterTc4TimerDayOfWeek OBJECT-TYPE
      SYNTAX INTEGER {
        sun(1),
        mon(2),
        tue(3) ,
        wed(4),
        thu(5),
        fri(6),
        sat(7),
        sat-sun(8),
        mon-fri(9),
        mon-sun(10)
      }
      ACCESS read-write
      STATUS mandatory
      DESCRIPTION
        "Selection of day of week for timer to switch"
      ::= { cmcTcMasterTc4TimerEntry 3 }
             
    cmcTcMasterTc4TimeOn OBJECT-TYPE
      SYNTAX DisplayString (SIZE (0..5))
      ACCESS read-write
      STATUS mandatory
      DESCRIPTION
        "Time to switch on current function, 
         Format: HH:MM"
      ::= { cmcTcMasterTc4TimerEntry 4 }

    cmcTcMasterTc4TimeOff OBJECT-TYPE
      SYNTAX DisplayString (SIZE (0..5))
      ACCESS read-write
      STATUS mandatory
      DESCRIPTION
        "Time to switch off current function,
         Format: HH:MM"
      ::= { cmcTcMasterTc4TimerEntry 5 }

    cmcTcMasterTc4TimeControl OBJECT-TYPE
      SYNTAX INTEGER  {
        disabled(1),
        enabled(2)
      }
      ACCESS read-write
      STATUS mandatory
      DESCRIPTION
        "Control via RTC"
      ::= { cmcTcMasterTc4TimerEntry 6 }

    cmcTcMasterTc4TimerFunction OBJECT-TYPE
      SYNTAX INTEGER {
        disKeypad1-1 (1),
        disKeypad2-1 (2),
        disKeypad1-2 (3),
        disKeypad2-2 (4),
        disKeypad1-3 (5),
        disKeypad2-3 (6),
        disKeypad1-4 (7),
        disKeypad2-4 (8),
        unlDoor1-1 (9),
        unlDoor2-1 (10),
        unlDoor1-2 (11),
        unlDoor2-2 (12),
        unlDoor1-3 (13),
        unlDoor2-3 (14),
        unlDoor1-4 (15),
        unlDoor2-5 (16),
        disTrapRec1 (17),
        disTrapRec2 (18),
        disTrapRec3 (19),
        disTrapRec4 (20),
        disSMS (21),
        schedule1 (22),
        schedule2 (23),
        schedule3 (24),
        schedule4 (25)
      }
      ACCESS read-write
      STATUS mandatory
      DESCRIPTION
        "Function which is controlled via timer
         1:     unlock via keypad 1 on unit 1 or remote input lock 1 is disabled
         2:     unlock via keypad 2 on unit 1 or remote input lock 2 is disabled
         3      unlock via keypad 1 on unit 2 or remote input lock 1 is disabled
         4:     unlock via keypad 2 on unit 2 or remote input lock 2 is disabled
         5:     unlock via keypad 1 on unit 3 or remote input lock 1 is disabled
         6:     unlock via keypad 2 on unit 3 or remote input lock 2 is disabled
         7:     unlock via keypad 1 on unit 4 or remote input lock 1 is disabled
         8:     unlock via keypad 2 on unit 4 or remote input lock 2 is disabled
         9:     Lock of door 1 on unit 1 will be unlocked
         10:    Lock of door 2 on unit 1 will be unlocked
         11:    Lock of door 1 on unit 2 will be unlocked
         12:    Lock of door 2 on unit 2 will be unlocked
         13:    Lock of door 1 on unit 3 will be unlocked
         14:    Lock of door 2 on unit 3 will be unlocked
         15:    Lock of door 1 on unit 4 will be unlocked
         16:    Lock of door 2 on unit 4 will be unlocked
         17-20: sending Traps to this Trap receiver will be disabled
         21:    sending SMS will be disabled
         22-25: Scheduled alarm off"
      ::= { cmcTcMasterTc4TimerEntry 7 }

--cmcTcMasterTc4TrapTable-group

  cmcTcMasterTc4TraptableNumber OBJECT-TYPE
    SYNTAX INTEGER 
    ACCESS read-only
    STATUS mandatory
    DESCRIPTION
      "Number of trapTable entries. The number of trap-receiver"
    ::= { cmcTcMasterTc4Traps 1 }

  cmcTcMasterTc4TrapTableTable OBJECT-TYPE    
    SYNTAX SEQUENCE OF CmcTcMasterTc4TrapTableEntry
    ACCESS not-accessible
    STATUS mandatory
    DESCRIPTION
     "A list of trap-receiver entries"
    ::= { cmcTcMasterTc4Traps 2 }

  cmcTcMasterTc4TrapTableEntry OBJECT-TYPE
    SYNTAX CmcTcMasterTc4TrapTableEntry
    ACCESS not-accessible
    STATUS mandatory
    DESCRIPTION
      "Entries of cmcTcMasterTc4TrapTable"
    INDEX   { cmcTcMasterTc4TrapIndex }
    ::= { cmcTcMasterTc4TrapTableTable 1 }      
              
    CmcTcMasterTc4TrapTableEntry ::=
      SEQUENCE {
        cmcTcMasterTc4TrapIndex
          INTEGER,
        cmcTcMasterTc4TrapStatus
          INTEGER,
        cmcTcMasterTc4TrapIPaddress
          DisplayString
      }

    cmcTcMasterTc4TrapIndex OBJECT-TYPE
      SYNTAX INTEGER (1..32000)
      ACCESS read-only
      STATUS mandatory
      DESCRIPTION
        "Index for the trap-receiver-table. Its value ranges between
         1 and the value of cmcTcMasterTc4TraptableNumber "
      ::= { cmcTcMasterTc4TrapTableEntry 1 }

    cmcTcMasterTc4TrapStatus OBJECT-TYPE
      SYNTAX INTEGER {
        disabled(1),
        enabled(2)
      }
      ACCESS read-write
      STATUS mandatory
      DESCRIPTION
        "Enable or disable trap receiver"
      ::= { cmcTcMasterTc4TrapTableEntry 2 }

    cmcTcMasterTc4TrapIPaddress OBJECT-TYPE
      SYNTAX DisplayString (SIZE (0..15))
      ACCESS read-write
      STATUS mandatory
      DESCRIPTION
        "IP-address of trap-receiver"
      ::= { cmcTcMasterTc4TrapTableEntry 3 }

--cmcTcMasterTc4Control-group (Added in Version 1.1)

  cmcTcMasterTc1QuitUnit OBJECT-TYPE
    SYNTAX INTEGER {
      noQuit(1),
      quit(2),
    }
    ACCESS read-write
    STATUS mandatory
    DESCRIPTION
      "Command to quit (acknowledge) alarms of CMC-TC unit.
       Setting to 'quit' (2) will have same result as pressing 'C' on Units.
       Variable is automatically set back to 'noQuit' (1)."
    ::= { cmcTcMasterTc4Control 1 }

--cmcTcMasterDevice5-group

  cmcTcMasterDev5Type OBJECT-TYPE
    SYNTAX INTEGER {
      other (0),
      cmc (1),
      pcu (3),
      tc (4)
    }
    ACCESS read-only
    STATUS mandatory
    DESCRIPTION
      "Type of device5"
    ::= { cmcTcMasterDevice5 1 }

  cmcTcMasterDev5Status OBJECT-TYPE
    SYNTAX INTEGER {
      other (1),
      notConnected (2),
      normal (3),
      minor (4),
      major (5),
      configChanged (6),
      connectionLost (10)
    }
    ACCESS read-only
    STATUS mandatory
    DESCRIPTION
      "Status of device5"
    ::= { cmcTcMasterDevice5 2 }

  cmcTcMasterDev5Descr OBJECT-TYPE
    SYNTAX DisplayString (SIZE (0..255))
    ACCESS read-only
    STATUS mandatory
    DESCRIPTION
      "A textual description of the entity.  This value
       should include the full name and version
       identification of the system's hardware type,
       software operating-system, and networking
       software.  It is mandatory that this only contain
       printable ASCII characters."
    ::= { cmcTcMasterDevice5 3 }

  cmcTcMasterDev5UpTime OBJECT-TYPE
    SYNTAX TimeTicks
    ACCESS read-only
    STATUS mandatory
    DESCRIPTION
      "The time (in hundredths of a second) since the
       network management portion of the system was last
       re-initialized."
    ::= { cmcTcMasterDevice5 4 }

  cmcTcMasterDev5Contact OBJECT-TYPE
    SYNTAX DisplayString (SIZE (0..255))
    ACCESS read-write
    STATUS mandatory
    DESCRIPTION
      "The textual identification of the contact person
       for this managed node, together with information
       on how to contact this person."
    ::= { cmcTcMasterDevice5 5 }

  cmcTcMasterDev5Name OBJECT-TYPE
    SYNTAX DisplayString (SIZE (0..255))
    ACCESS read-write
    STATUS mandatory
    DESCRIPTION
      "An administratively-assigned name for this
       managed node.  By convention, this is the node's
       fully-qualified domain name."
    ::= { cmcTcMasterDevice5 6 }

  cmcTcMasterDev5Location OBJECT-TYPE
    SYNTAX DisplayString (SIZE (0..255))
    ACCESS read-write
    STATUS mandatory
    DESCRIPTION
      "The physical location of this node (e.g.,
       `telephone closet, 3rd floor')."
    ::= { cmcTcMasterDevice5 7 }

--cmcTcMasterCmc5Values-group

  cmcTcMasterCmc5ValueTemperature1 OBJECT-TYPE
    SYNTAX INTEGER
    ACCESS read-only
    STATUS mandatory
    DESCRIPTION
      "Actual value of temperature 1 in deg C"
    ::= { cmcTcMasterCmc5Values 1 }

  cmcTcMasterCmc5ValueTemperature2 OBJECT-TYPE
    SYNTAX INTEGER
    ACCESS read-only
    STATUS mandatory
    DESCRIPTION
      "Actual value of temperature 2 in deg C"
    ::= { cmcTcMasterCmc5Values 2 }

  cmcTcMasterCmc5ValuePowerSupply OBJECT-TYPE
    SYNTAX INTEGER
    ACCESS read-only
    STATUS mandatory
    DESCRIPTION
      "Actual value of power supply in V"
    ::= { cmcTcMasterCmc5Values 3 }

  cmcTcMasterCmc5ValueAnalogAux1 OBJECT-TYPE
    SYNTAX INTEGER
    ACCESS read-only
    STATUS mandatory
    DESCRIPTION
      "Actual value of aux. analog input 1
      (4-20mA = 0-100%)"
    ::= { cmcTcMasterCmc5Values 4 }

  cmcTcMasterCmc5ValueAnalogAux2 OBJECT-TYPE
    SYNTAX INTEGER
    ACCESS read-only
    STATUS mandatory
    DESCRIPTION
      "Actual value of aux. analog input 2
      (4-20mA = 0-100%)"
    ::= { cmcTcMasterCmc5Values 5 }

--cmcTcMasterCmc5Values-table-group

  cmcTcMasterCmc5ValuesNumber OBJECT-TYPE
    SYNTAX INTEGER
    ACCESS read-only
    STATUS mandatory
    DESCRIPTION
      "Number of value-table entries"
    ::= { cmcTcMasterCmc5Table1 1 }

  cmcTcMasterCmc5ValuesTable OBJECT-TYPE
    SYNTAX SEQUENCE OF CmcTcMasterCmc5ValuesEntry
    ACCESS not-accessible
    STATUS mandatory
    DESCRIPTION
      "Headline of value-table"
    ::= { cmcTcMasterCmc5Table1 2 }

  cmcTcMasterCmc5ValuesEntry OBJECT-TYPE
    SYNTAX CmcTcMasterCmc5ValuesEntry
    ACCESS not-accessible
    STATUS mandatory
    DESCRIPTION
      "Entries of value-table"
    INDEX { cmcTcMasterCmc5ValuesIndex }
    ::= { cmcTcMasterCmc5ValuesTable 1 }

  CmcTcMasterCmc5ValuesEntry ::=
    SEQUENCE {
      cmcTcMasterCmc5ValuesIndex
        INTEGER,
      cmcTcMasterCmc5ValuesText
        DisplayString (SIZE (0..31)),
      cmcTcMasterCmc5ValuesValue
        INTEGER,
      cmcTcMasterCmc5ValuesStatus
        INTEGER,
      cmcTcMasterCmc5ValuesMaxValue
        INTEGER,
      cmcTcMasterCmc5ValuesMinValue
        INTEGER
    }

    cmcTcMasterCmc5ValuesIndex OBJECT-TYPE
      SYNTAX INTEGER (1..32000)
      ACCESS read-only
      STATUS mandatory
      DESCRIPTION
        "Index for the list of value entries. Its value ranges
        between 1 and the value of valuesNumber."
      ::= { cmcTcMasterCmc5ValuesEntry 1 }

    cmcTcMasterCmc5ValuesText OBJECT-TYPE
      SYNTAX DisplayString (SIZE (0..31))
      ACCESS read-write
      STATUS mandatory
      DESCRIPTION
        "Text of the entry in the value-table"
      ::= { cmcTcMasterCmc5ValuesEntry 2 }

    cmcTcMasterCmc5ValuesValue OBJECT-TYPE
      SYNTAX INTEGER
      ACCESS read-only
      STATUS mandatory
      DESCRIPTION
        "Actual value of the value-table"
      ::= { cmcTcMasterCmc5ValuesEntry 3 }

    cmcTcMasterCmc5ValuesStatus OBJECT-TYPE
      SYNTAX INTEGER {
        valueOK(1),
        valueTooLow(2),
        valueTooHigh(3),
        valueERROR(4),
        notAvail(5)
      }
      ACCESS read-only
      STATUS mandatory
      DESCRIPTION
        "Status of the value"
      ::= { cmcTcMasterCmc5ValuesEntry 4 }

    cmcTcMasterCmc5ValuesMaxValue OBJECT-TYPE
      SYNTAX INTEGER
      ACCESS read-write
      STATUS mandatory
      DESCRIPTION
        "Value for max. alarm"
      ::= { cmcTcMasterCmc5ValuesEntry 5 }

    cmcTcMasterCmc5ValuesMinValue OBJECT-TYPE
      SYNTAX INTEGER
      ACCESS read-write
      STATUS mandatory
      DESCRIPTION
        "Value for min. alarm"
      ::= { cmcTcMasterCmc5ValuesEntry 6 }

--cmcTcMasterCmc5status-group

  cmcTcMasterCmc5StatusTemperature1 OBJECT-TYPE
    SYNTAX DisplayString (SIZE (0..31))
    ACCESS read-only
    STATUS mandatory
    DESCRIPTION
      "Status temperature 1, OK/ too low/ too high
       (see setpoints of temperature 1)"
    ::= { cmcTcMasterCmc5Status 1 }

  cmcTcMasterCmc5StatusTemperature2 OBJECT-TYPE
    SYNTAX DisplayString (SIZE (0..31))
    ACCESS read-only
    STATUS mandatory
    DESCRIPTION
      "Status temperature 2, OK/ too low/ too high
       (see setpoints of temperature 2)"
    ::= { cmcTcMasterCmc5Status 2 }

  cmcTcMasterCmc5StatusFan1 OBJECT-TYPE
    SYNTAX DisplayString (SIZE (0..31))
    ACCESS read-only
    STATUS mandatory
    DESCRIPTION
      "Status fan 1, Stop/ running/ fault"
    ::= { cmcTcMasterCmc5Status 3 }

  cmcTcMasterCmc5StatusFan2 OBJECT-TYPE
    SYNTAX DisplayString (SIZE (0..31))
    ACCESS read-only
    STATUS mandatory
    DESCRIPTION
      "Status fan 2, Stop/ running/ fault"
    ::= { cmcTcMasterCmc5Status 4 }

  cmcTcMasterCmc5StatusHeating OBJECT-TYPE
    SYNTAX DisplayString (SIZE (0..31))
    ACCESS read-only
    STATUS mandatory
    DESCRIPTION
      "Status heating, On/Off"
    ::= { cmcTcMasterCmc5Status 5 }

  cmcTcMasterCmc5StatusPowerSupply OBJECT-TYPE
    SYNTAX DisplayString (SIZE (0..31))
    ACCESS read-only
    STATUS mandatory
    DESCRIPTION
      "Status power supply, OK/ too low/ too high
       (see setpoints of power supply)"
    ::= { cmcTcMasterCmc5Status 6 }

  cmcTcMasterCmc5StatusAnalogAux1 OBJECT-TYPE
    SYNTAX DisplayString (SIZE (0..31))
    ACCESS read-only
    STATUS mandatory
    DESCRIPTION
      "Status aux analog input 1, OK/ too low/ too high"
    ::= { cmcTcMasterCmc5Status 7 }

  cmcTcMasterCmc5StatusAnalogAux2 OBJECT-TYPE
    SYNTAX DisplayString (SIZE (0..31))
    ACCESS read-only
    STATUS mandatory
    DESCRIPTION
      "Status aux analog input 2, OK/ too low/ too high"
    ::= { cmcTcMasterCmc5Status 8 }

  cmcTcMasterCmc5StatusDoor OBJECT-TYPE
    SYNTAX DisplayString (SIZE (0..31))
    ACCESS read-only
    STATUS mandatory
    DESCRIPTION
      "Status door, open/closed/locked"
    ::= { cmcTcMasterCmc5Status 9 }

  cmcTcMasterCmc5StatusUps1 OBJECT-TYPE
    SYNTAX DisplayString (SIZE (0..31))
    ACCESS read-only
    STATUS mandatory
    DESCRIPTION
      "Status UPS 1, OK/ fault"
    ::= { cmcTcMasterCmc5Status 10 }

  cmcTcMasterCmc5StatusUps2 OBJECT-TYPE
    SYNTAX DisplayString (SIZE (0..31))
    ACCESS read-only
    STATUS mandatory
    DESCRIPTION
      "Status UPS 2, OK/ fault"
    ::= { cmcTcMasterCmc5Status 11 }

  cmcTcMasterCmc5StatusSmokeSensor OBJECT-TYPE
    SYNTAX DisplayString (SIZE (0..31))
    ACCESS read-only
    STATUS mandatory
    DESCRIPTION
      "Status smoke-sensor, OK/ smoke"
    ::= { cmcTcMasterCmc5Status 12 }

  cmcTcMasterCmc5StatusVibrationSensor OBJECT-TYPE
    SYNTAX DisplayString (SIZE (0..31))
    ACCESS read-only
    STATUS mandatory
    DESCRIPTION
      "Status vibration sensor, OK/ vibration"
    ::= { cmcTcMasterCmc5Status 13 }

  cmcTcMasterCmc5StatusMessage OBJECT-TYPE
    SYNTAX DisplayString (SIZE (0..31))
    ACCESS read-only
    STATUS mandatory
    DESCRIPTION
      "Message from CMC"
    ::= { cmcTcMasterCmc5Status 14 }

  cmcTcMasterCmc5ValueOperatingTime OBJECT-TYPE
    SYNTAX DisplayString (SIZE (0..31))
    ACCESS read-only
    STATUS mandatory
    DESCRIPTION
      "Operating time CMC-unit"
    ::= { cmcTcMasterCmc5Status 15 }

  cmcTcMasterCmc5StatusUnit OBJECT-TYPE
    SYNTAX INTEGER {
      unitCelsius(1),
      unitFahrenheit(2)
    }
    ACCESS read-only
    STATUS mandatory
    DESCRIPTION
      "Unit of temperature-values, Celsius or Fahrenheit"
   ::= { cmcTcMasterCmc5Status 16 }


--cmcTcMasterCmc5Status-table-group

  cmcTcMasterCmc5StatusNumber OBJECT-TYPE
    SYNTAX INTEGER 
    ACCESS read-only
    STATUS mandatory
    DESCRIPTION
      "Number of status-table entries"
    ::= { cmcTcMasterCmc5Table 1 }

  cmcTcMasterCmc5StatusTable OBJECT-TYPE
    SYNTAX SEQUENCE OF CmcTcMasterCmc5StatusEntry
    ACCESS not-accessible
    STATUS mandatory
    DESCRIPTION
      "Headline of table"
    ::= { cmcTcMasterCmc5Table 2 }

  cmcTcMasterCmc5StatusEntry OBJECT-TYPE
    SYNTAX CmcTcMasterCmc5StatusEntry
    ACCESS not-accessible
    STATUS mandatory
    DESCRIPTION
      "A list of status entries.  The number of
       entries is given by the value of cmcTcMasterCmc5StatusNumber." 
    INDEX { cmcTcMasterCmc5StatusIndex }
    ::= { cmcTcMasterCmc5StatusTable 1 }

  CmcTcMasterCmc5StatusEntry ::=
    SEQUENCE {
      cmcTcMasterCmc5StatusIndex
        INTEGER,
      cmcTcMasterCmc5StatusText
        DisplayString (SIZE (0..31)),
      cmcTcMasterCmc5StatusStatus
        INTEGER              
    }

    cmcTcMasterCmc5StatusIndex OBJECT-TYPE
      SYNTAX INTEGER (1..32000)
      ACCESS read-only
      STATUS mandatory
      DESCRIPTION
        "Index fo the list of status entries. Its value ranges
         between 1 and the value of cmcTcMasterCmc5StatusNumber." 
      ::= { cmcTcMasterCmc5StatusEntry 1 }

    cmcTcMasterCmc5StatusText OBJECT-TYPE
      SYNTAX DisplayString (SIZE (0..31))
      ACCESS read-write
      STATUS mandatory
      DESCRIPTION
        "Text of the entry in the status-table"
      ::= { cmcTcMasterCmc5StatusEntry 2 }

    cmcTcMasterCmc5StatusStatus OBJECT-TYPE
      SYNTAX INTEGER  {
        statusOK(1),
        alarm(2),
        security(3),
        notAvail(4)
      }
      ACCESS read-only
      STATUS mandatory
      DESCRIPTION
        "Status of the table entry"
      ::= { cmcTcMasterCmc5StatusEntry 3 }

--******************************************************************************

--cmcTCMasterCmc5Set-group

  cmcTcMasterCmc5StatusAccess OBJECT-TYPE
    SYNTAX DisplayString (SIZE (0..31))
    ACCESS read-write
    STATUS mandatory
    DESCRIPTION
      "Status access"
    ::= { cmcTcMasterCmc5Set 1 }

  cmcTcMasterCmc5SetDoor OBJECT-TYPE
    SYNTAX INTEGER {
      lockDoor(1),
      openDoorTime(2),
      openDoorAccess(3),
      openDoor(4)
    }
    ACCESS read-write
    STATUS mandatory
    DESCRIPTION
      "Set door, see table"
    ::= { cmcTcMasterCmc5Set 2 }

  cmcTcMasterCmc5SetMessage OBJECT-TYPE
    SYNTAX DisplayString (SIZE (0..31))
    ACCESS read-write
    STATUS mandatory
    DESCRIPTION
      "Set message"
    ::= { cmcTcMasterCmc5Set 3 }

  cmcTcMasterCmc5SetFault        OBJECT-TYPE
    SYNTAX INTEGER {
      clearFault(1),
      setFault(2)
    }
    ACCESS read-write
    STATUS mandatory
    DESCRIPTION
      "Set fault, see table"
    ::= { cmcTcMasterCmc5Set 4 }

--cmcTcMasterCmc5RelayControl-group

  cmcTcMasterCmc5RelaytableMaxNum OBJECT-TYPE
    SYNTAX INTEGER 
    ACCESS read-only
    STATUS mandatory
    DESCRIPTION
      "Number of table entries"
    ::= { cmcTcMasterCmc5RelayControl 1 }

  cmcTcMasterCmc5RelayTable OBJECT-TYPE
    SYNTAX SEQUENCE OF CmcTcMasterCmc5RelayEntry
    ACCESS not-accessible
    STATUS mandatory
    DESCRIPTION
      "Headline of table for relay control"
    ::= { cmcTcMasterCmc5RelayControl 2 }

  cmcTcMasterCmc5RelayEntry OBJECT-TYPE
    SYNTAX CmcTcMasterCmc5RelayEntry
    ACCESS not-accessible
    STATUS mandatory
    DESCRIPTION
      "Entries"
    INDEX { cmcTcMasterCmc5RelaytableIndex }
    ::= { cmcTcMasterCmc5RelayTable 1 }

  CmcTcMasterCmc5RelayEntry ::=
    SEQUENCE {
      cmcTcMasterCmc5RelaytableIndex
        INTEGER,
      cmcTcMasterCmc5RelaytableText
	DisplayString (SIZE (0..31)),
      cmcTcMasterCmc5RelaytableStatus
        INTEGER              
    }

    cmcTcMasterCmc5RelaytableIndex OBJECT-TYPE
      SYNTAX INTEGER (1..32000)
      ACCESS read-only
      STATUS mandatory
      DESCRIPTION
        "Index for the relay-table. Its value ranges
         between 1 and cmcTcMasterCmc5RelaytableMaxNum"
      ::= { cmcTcMasterCmc5RelayEntry 1 }

    cmcTcMasterCmc5RelaytableText OBJECT-TYPE
      SYNTAX DisplayString (SIZE (0..31))
      ACCESS read-write
      STATUS mandatory
      DESCRIPTION
        "Description-Text for each relay in the table"
      ::= { cmcTcMasterCmc5RelayEntry 2 }

    cmcTcMasterCmc5RelaytableStatus OBJECT-TYPE
      SYNTAX INTEGER  {
        relayOFF(1),
        relayON(2),
        notAvail(3)
      }
      ACCESS read-write
      STATUS mandatory
      DESCRIPTION
        "Status of relays in the table"
      ::= { cmcTcMasterCmc5RelayEntry 3 }

--cmcTcMasterCmc5Setpoints-group

  cmcTcMasterCmc5SetpointFan1 OBJECT-TYPE
    SYNTAX INTEGER 
    ACCESS read-write
    STATUS mandatory
    DESCRIPTION
      "Setpoint Fan 1 in C, Fan 1 will start
       if temperature 1 exceeds this value"
    ::= { cmcTcMasterCmc5Setpoints 1 }

  cmcTcMasterCmc5SetpointFan2 OBJECT-TYPE
    SYNTAX INTEGER 
    ACCESS read-write
    STATUS mandatory
    DESCRIPTION
      "Setpoint Fan 2 in C, Fan 2 will start
       if temperature 2 exceeds this value"
    ::= { cmcTcMasterCmc5Setpoints 2 }

  cmcTcMasterCmc5SetpointHeating OBJECT-TYPE
    SYNTAX INTEGER 
    ACCESS read-write
    STATUS mandatory
    DESCRIPTION
      "Setpoint heating in C, heating will start
       if lowest value of temperature 1 and 2 falls below this value"
    ::= { cmcTcMasterCmc5Setpoints 3 }

  cmcTcMasterCmc5SetpointHighTemperature1 OBJECT-TYPE
    SYNTAX INTEGER 
    ACCESS read-write
    STATUS mandatory
    DESCRIPTION
      "Setpoint high value alarm temperature 1"
    ::= { cmcTcMasterCmc5Setpoints 4 }

  cmcTcMasterCmc5SetpointLowTemperature1 OBJECT-TYPE
    SYNTAX INTEGER 
    ACCESS read-write
    STATUS mandatory
    DESCRIPTION
      "Setpoint low value alarm temperature 1"
    ::= { cmcTcMasterCmc5Setpoints 5 }

  cmcTcMasterCmc5SetpointHighTemperature2 OBJECT-TYPE
    SYNTAX INTEGER 
    ACCESS read-write
    STATUS mandatory
    DESCRIPTION
      "Setpoint high value alarm temperature 2"
    ::= { cmcTcMasterCmc5Setpoints 6 }

  cmcTcMasterCmc5SetpointLowTemperature2 OBJECT-TYPE
    SYNTAX INTEGER 
    ACCESS read-write
    STATUS mandatory
    DESCRIPTION
      "Setpoint low value alarm temperature 2"
    ::= { cmcTcMasterCmc5Setpoints 7 }

  cmcTcMasterCmc5SetpointHighVoltage OBJECT-TYPE
    SYNTAX INTEGER 
    ACCESS read-write
    STATUS mandatory
    DESCRIPTION
      "Setpoint high value supply voltage alarm"
    ::= { cmcTcMasterCmc5Setpoints 8 }

  cmcTcMasterCmc5SetpointLowVoltage OBJECT-TYPE
    SYNTAX INTEGER
    ACCESS read-write
    STATUS mandatory
    DESCRIPTION
      "Setpoint low value supply voltage alarm"
    ::= { cmcTcMasterCmc5Setpoints 9 }

  cmcTcMasterCmc5SetpointLowAux1 OBJECT-TYPE
    SYNTAX INTEGER 
    ACCESS read-write
    STATUS mandatory
    DESCRIPTION
      "Setpoint low value Aux input 1 alarm"
    ::= { cmcTcMasterCmc5Setpoints 10 }

  cmcTcMasterCmc5SetpointHighAux1 OBJECT-TYPE
    SYNTAX INTEGER 
    ACCESS read-write
    STATUS mandatory
    DESCRIPTION
      "Setpoint high value Aux input 1 alarm"
    ::= { cmcTcMasterCmc5Setpoints 11 }

  cmcTcMasterCmc5SetpointLowAux2 OBJECT-TYPE
    SYNTAX INTEGER 
    ACCESS read-write
    STATUS mandatory
    DESCRIPTION
      "Setpoint low value Aux input 2 alarm"
    ::= { cmcTcMasterCmc5Setpoints 12 }

  cmcTcMasterCmc5SetpointHighAux2 OBJECT-TYPE
    SYNTAX INTEGER 
    ACCESS read-write
    STATUS mandatory
    DESCRIPTION
      "Setpoint high value Aux input alarm"
    ::= { cmcTcMasterCmc5Setpoints 13 }

--cmcTcMasterCmc5TrapControl-group

  cmcTcMasterCmc5SetTrapRepeat OBJECT-TYPE
    SYNTAX INTEGER {
      disableTrapRepeat(1),
      enableTrapRepeat(2)
    }
    ACCESS read-write
    STATUS mandatory
    DESCRIPTION
      "Enable/disable repeating of traps. If enabled, traps will
       be repeated after a repeat time, set in setTrapRepeatTime.
       Repeating can be stopped by setting setTrapQuit to quitTrap"
    ::= { cmcTcMasterCmc5TrapControl 1 }

  cmcTcMasterCmc5SetTrapRepeatTime OBJECT-TYPE
    SYNTAX INTEGER 
    ACCESS read-write
    STATUS mandatory
    DESCRIPTION
      "Time value (sec) for trap-repeating, if setTrapRepeat is enabled"
    ::= { cmcTcMasterCmc5TrapControl 2 }

  cmcTcMasterCmc5SetTrapQuit OBJECT-TYPE
    SYNTAX INTEGER {
      quitTrap(1),
      quitTrapOK(2),
      noTrapToQuit(3),
      trapToQuit(4)
    }
    ACCESS read-write
    STATUS mandatory
    DESCRIPTION
      "Quit trap to stop repeating."
    ::= { cmcTcMasterCmc5TrapControl 3 }

--cmcTcMasterCmc5TrapTable-group

  cmcTcMasterCmc5TraptableNumber OBJECT-TYPE
    SYNTAX INTEGER 
    ACCESS read-only
    STATUS mandatory
    DESCRIPTION
      "Number of trapTable entries. The number of trap-receiver"
    ::= { cmcTcMasterCmc5Traps 1 }

  cmcTcMasterCmc5TrapTable OBJECT-TYPE
    SYNTAX SEQUENCE OF CmcTcMasterCmc5TrapEntry
    ACCESS not-accessible
    STATUS mandatory
    DESCRIPTION
      "A list of trap-receiver entries"
    ::= { cmcTcMasterCmc5Traps 2 }

  cmcTcMasterCmc5TrapEntry OBJECT-TYPE
    SYNTAX CmcTcMasterCmc5TrapEntry
    ACCESS not-accessible
    STATUS mandatory
    DESCRIPTION
      "Entries of trapTable"
    INDEX { cmcTcMasterCmc5TrapIndex }
    ::= { cmcTcMasterCmc5TrapTable 1 }

  CmcTcMasterCmc5TrapEntry ::=
    SEQUENCE {
      cmcTcMasterCmc5TrapIndex
        INTEGER,
      cmcTcMasterCmc5TrapStatus
        INTEGER,
      cmcTcMasterCmc5TrapIPaddress
        DisplayString
    }

    cmcTcMasterCmc5TrapIndex OBJECT-TYPE
      SYNTAX INTEGER (1..32000)
      ACCESS read-only
      STATUS mandatory
      DESCRIPTION
        "Index for the trap-receiver-table. Its value ranges between
         1 and the value of cmcTcMasterCmc5TraptableNumber "
      ::= { cmcTcMasterCmc5TrapEntry 1 }

    cmcTcMasterCmc5TrapStatus OBJECT-TYPE
      SYNTAX INTEGER  {
        enabled(1),
        disabled(2)
      }
      ACCESS read-write
      STATUS mandatory
      DESCRIPTION
        "Enable or disable trap receiver"
      ::= { cmcTcMasterCmc5TrapEntry 2 }

    cmcTcMasterCmc5TrapIPaddress OBJECT-TYPE
      SYNTAX DisplayString (SIZE (0..31))
      ACCESS read-write
      STATUS mandatory
      DESCRIPTION
        "IP-address of trap-receiver"
      ::= { cmcTcMasterCmc5TrapEntry 3 }

--cmcTcMasterPcu5MibRev-group
          
  cmcTcMasterPcu5MibMajRev OBJECT-TYPE
    SYNTAX INTEGER (1..32000)
    ACCESS read-only
    STATUS mandatory
    DESCRIPTION
      "The Major Revision level.
       A change in the major revision level represents a major change
       in the architecture of the MIB. A change in the major revision 
       level may indicate a significant change in the information,
       correct interpretation of data may require a MIB document
       with the same major revision level."
    ::= { cmcTcMasterPcu5MibRev 1 }

  cmcTcMasterPcu5MibMinRev OBJECT-TYPE
    SYNTAX INTEGER (0..32000)
    ACCESS read-only
    STATUS mandatory
    DESCRIPTION
      "The Minor Revision level.
       A change in the minor revision level may represent some minor
       additional support, no changes to any pre-existing information
       has occurred."
    ::= { cmcTcMasterPcu5MibRev 2 }

  cmcTcMasterPcu5MibCondition OBJECT-TYPE
    SYNTAX INTEGER {
      other (1),
      ok (2),
      degraded (3),
      failed (4)
    }
    ACCESS read-only
    STATUS mandatory
    DESCRIPTION
      "The overall condition (status) of the system represented by
       this MIB. 
       (2) OK
       (3) a minor problem, warning condition (yellow LED on PCU)
       (4) a major problem (red LED on PCU)"
    ::= { cmcTcMasterPcu5MibRev 3 }

--cmcTcMasterPcu5Values-group

  cmcTcMasterPcu5ValueEnergy1 OBJECT-TYPE
    SYNTAX INTEGER 
    ACCESS read-only
    STATUS mandatory
    DESCRIPTION
      "Total value of the Energy (Wh), measured on IEC input 1"
    ::= { cmcTcMasterPcu5Values 1 }

  cmcTcMasterPcu5ValueEnergy2 OBJECT-TYPE
    SYNTAX INTEGER 
    ACCESS read-only
    STATUS mandatory
    DESCRIPTION
      "Actual value of the Energy (Wh), measured on IEC input 2"
    ::= { cmcTcMasterPcu5Values 2 }

  cmcTcMasterPcu5ValueEnergy1Time OBJECT-TYPE
    SYNTAX INTEGER 
    ACCESS read-only
    STATUS mandatory
    DESCRIPTION
      "Actual value of the Energy (Wh), measured on IEC input 1, can be set to 0
       Value can be used to calculate the energy over a fixed time"
    ::= { cmcTcMasterPcu5Values 3 }

  cmcTcMasterPcu5ValueEnergy2Time OBJECT-TYPE
    SYNTAX INTEGER 
    ACCESS read-only
    STATUS mandatory
    DESCRIPTION
      "Actual value of the Energy (Wh), measured on IEC input 2, can be set to 0.
       Value can be used to calculate the energy over a fixed time"
    ::= { cmcTcMasterPcu5Values 4 }

  cmcTcMasterPcu5ValuePower1 OBJECT-TYPE
    SYNTAX INTEGER 
    ACCESS read-only
    STATUS mandatory
    DESCRIPTION
      "Calculated actual power 1 (W). Calculated from cmcTcMasterPcu5ValueEnergy1/time"
    ::= { cmcTcMasterPcu5Values 5 }
          
  cmcTcMasterPcu5ValuePower2 OBJECT-TYPE
    SYNTAX INTEGER 
    ACCESS read-only
    STATUS mandatory
    DESCRIPTION
      "Calculated actual power 2 (W). Calculated from cmcTcMasterPcu5ValueEnergy2/time"
    ::= { cmcTcMasterPcu5Values 6 }
          
  cmcTcMasterPcu5ValueTemperature OBJECT-TYPE
    SYNTAX INTEGER 
    ACCESS read-only
    STATUS mandatory
    DESCRIPTION
      "Actual value of temperature 1 in deg C or deg F"
    ::= { cmcTcMasterPcu5Values 7 }
          
--cmcTcMasterPcu5Status-group

  cmcTcMasterPcu5StatusInput1 OBJECT-TYPE
    SYNTAX INTEGER {
      false(1),
      true(2),
      pending(3),
      notAvail(4)
    }
    ACCESS read-only
    STATUS mandatory
    DESCRIPTION
      "Status of digital Input 1
       (1) digital signal is true (contact closed if setup is NO)
       (2) digital signal is false(contact opened if setup is NO),
       note setup of input (NO/NC)
       (3) digital input is pending, note setup of delay"
    ::= { cmcTcMasterPcu5Status 1 }

  cmcTcMasterPcu5StatusInput2 OBJECT-TYPE
    SYNTAX INTEGER {
      false(1),
      true(2),
      pending(3),
      notAvail(4)
    }
    ACCESS read-only
    STATUS mandatory
    DESCRIPTION
      "Status of digital Input 2
       (1) digital signal is true (contact closed if setup is NO)
       (2) digital signal is false(contact opened if setup is NO),
       note setup of input (NO/NC)
       (3) digital input is pending, note setup of delay"
    ::= { cmcTcMasterPcu5Status 2 }

  cmcTcMasterPcu5StatusPower1 OBJECT-TYPE
    SYNTAX INTEGER {
      ok(1),
      tooHigh(2),
      tooLow(3),
      warning(4),
      error(5),
      notAvail(6)
    }
    ACCESS read-only
    STATUS mandatory
    DESCRIPTION
      "Status Power 1, see setpoints"
    ::= { cmcTcMasterPcu5Status 3 }

  cmcTcMasterPcu5StatusPower2 OBJECT-TYPE
    SYNTAX INTEGER {
      ok(1),
      tooHigh(2),
      tooLow(3),
      warning(4),
      error(5),
      notAvail(6)
    }
    ACCESS read-only
    STATUS mandatory
    DESCRIPTION
      "Status Power 2, see setpoints"
    ::= { cmcTcMasterPcu5Status 4 }

  cmcTcMasterPcu5StatusTemperature OBJECT-TYPE
    SYNTAX INTEGER {
      ok(1),
      tooHigh(2),
      tooLow(3),
      warning(4),
      error(5)
    }
    ACCESS read-only
    STATUS mandatory
    DESCRIPTION
      "Status temperature 1, OK/ too high/ too low
       (see setpoints of temperature 1)"
    ::= { cmcTcMasterPcu5Status 5 }

--cmcTcMasterPcu5Status-table-group

  cmcTcMasterPcu5OutletsNumber OBJECT-TYPE
    SYNTAX INTEGER 
    ACCESS read-only
    STATUS mandatory
    DESCRIPTION
      "Number of value-table entries=number of outlets available on this unit"
    ::= { cmcTcMasterPcu5StatusTable1 1 }

  cmcTcMasterPcu5StatusTable OBJECT-TYPE
    SYNTAX SEQUENCE OF CmcTcMasterPcu5StatusEntry
    ACCESS not-accessible
    STATUS mandatory
    DESCRIPTION
      "Headline of status-table"
    ::= { cmcTcMasterPcu5StatusTable1 2 }

  cmcTcMasterPcu5StatusEntry OBJECT-TYPE
    SYNTAX CmcTcMasterPcu5StatusEntry
    ACCESS not-accessible
    STATUS mandatory
    DESCRIPTION
      "Entries of status-table"
    INDEX { cmcTcMasterPcu5StatusIndex }
    ::= { cmcTcMasterPcu5StatusTable 1 }

    CmcTcMasterPcu5StatusEntry ::=
      SEQUENCE {
        cmcTcMasterPcu5StatusIndex
          INTEGER,
        cmcTcMasterPcu5StatusText
          DisplayString (SIZE (0..31)),                
        cmcTcMasterPcu5StatusStatus
          INTEGER,
        cmcTcMasterPcu5ControlSNMP
          INTEGER,
        cmcTcMasterPcu5FrontSwitch
          INTEGER,
        cmcTcMasterPcu5Delay
          INTEGER,
        cmcTcMasterPcu5Input1
          INTEGER,
        cmcTcMasterPcu5Input2
          INTEGER,
        cmcTcMasterPcu5Temperature
          INTEGER,          
        cmcTcMasterPcu5Power
          INTEGER,          
        cmcTcMasterPcu5RestoreOutputStatus
          INTEGER           
      }

    cmcTcMasterPcu5StatusIndex OBJECT-TYPE
      SYNTAX INTEGER (1..32000)
      ACCESS read-only
      STATUS mandatory
      DESCRIPTION
        "Index for the list of value entries. Its value ranges
         between 1 and the value of cmcTcMasterPcu5OutletsNumber."
      ::= { cmcTcMasterPcu5StatusEntry 1 }

    cmcTcMasterPcu5StatusText OBJECT-TYPE
      SYNTAX DisplayString (SIZE (0..31))
      ACCESS read-write
      STATUS mandatory
      DESCRIPTION
        "Descriptional text for each outlet (entry in the table)"
      ::= { cmcTcMasterPcu5StatusEntry 2 }
              
    cmcTcMasterPcu5StatusStatus OBJECT-TYPE
      SYNTAX INTEGER {
        ok(1),
        onFrontKey(2),
        offFrontKey(3),
        onWEB(4),
        offWEB(5),
        onInput1(6),
        offInput1(7),
        onInput2(8),
        offInput2(9),
        onTemp(10),
        offTemp(11),
        onSNMP(12),
        offSNMP(13),
        onTimer(14),
        offTimer(15),
        onDelay(16),
        onConsole(17),
        offConsole(18),
        onReboot(19), 
        offReboot(20),
        onPower(21),
        offPower(22)
      }
      ACCESS read-only
      STATUS mandatory
      DESCRIPTION
        "Actual status of the outlet"
      ::= { cmcTcMasterPcu5StatusEntry 3 }

    cmcTcMasterPcu5ControlSNMP OBJECT-TYPE
      SYNTAX INTEGER  {
        on(1),
        off(2)
      }
      ACCESS read-write
      STATUS mandatory
      DESCRIPTION
        "Control via SNMP"
      ::= { cmcTcMasterPcu5StatusEntry 4 }

    cmcTcMasterPcu5FrontSwitch OBJECT-TYPE
      SYNTAX INTEGER {
        disabled(1),
        enabled(2)
      }
      ACCESS read-write
      STATUS mandatory
      DESCRIPTION
        "Control via front switch"
      ::= { cmcTcMasterPcu5StatusEntry 5 }
 
    cmcTcMasterPcu5Delay OBJECT-TYPE
      SYNTAX INTEGER (0..300)
      ACCESS read-write
      STATUS mandatory
      DESCRIPTION
        "Value for delay time in seconds.
         Value>0: Output is switched off for this time (in sec)"
      ::= { cmcTcMasterPcu5StatusEntry 6 }

    cmcTcMasterPcu5Input1 OBJECT-TYPE
      SYNTAX INTEGER {
        disabled(1),
        switchOn(2),
        switchOff(3),
        switchOnOff(4)
      }
      ACCESS read-write
      STATUS mandatory
      DESCRIPTION
        "Control via digital input 1
         (1): disabled
         (2): output is switched on in case of input 1 alarm
         (3): output is switched off in case of input 1 alarm
         (4): output has same status as input 1"
      ::= { cmcTcMasterPcu5StatusEntry 7 }

    cmcTcMasterPcu5Input2 OBJECT-TYPE
      SYNTAX INTEGER {
        disabled(1),
        switchOn(2),
        switchOff(3),
        switchOnOff(4)
      }
      ACCESS read-write
      STATUS mandatory
      DESCRIPTION
        "Control via digital input 2
         (1): disabled
         (2): output is switched on in case of input 2 alarm
         (3): output is switched off in case of input 2 alarm
         (4): output has same status as input 2"             
      ::= { cmcTcMasterPcu5StatusEntry 8 }

    cmcTcMasterPcu5Temperature OBJECT-TYPE
      SYNTAX INTEGER {
        disabled(1),
        switchOffAlarm(2),
        switchOnAlarm(3),
        switchOffSetpoint(4),
        switchOnSetpoint(5)
      }
      ACCESS read-write
      STATUS mandatory
      DESCRIPTION
        "Control via temperature alarm or setpoint
         (1): disabled
         (2): output is switched off in case of temperature alarm
         (3): output is switched on in case of temperature alarm
         (4): output is switched off if temperature setpoint (cmcTcMasterPcu5SetpointTemperature)
              is reached
         (5): output is switched on if temperature setpoint (cmcTcMasterPcu5SetpointTemperature)
              is reached"
      ::= { cmcTcMasterPcu5StatusEntry 9 }   
    
    cmcTcMasterPcu5Power OBJECT-TYPE
      SYNTAX INTEGER {
        disabled(1),
        switchOffAlarm(2),
        switchOffWarning(3),
        switchOnAlarm(4),
        switchOnWarning(5)
      }
      ACCESS read-write
      STATUS mandatory
      DESCRIPTION
        "Control via power setpoint
         (1): disabled
         (2): output is switched off upon power high alarm (cmcTcMasterPcu5SetpointHighPower1)
         (3): output is switched off upon power warning (cmcTcMasterPcu5SetpointWarningPower1)
         (4): output is switched on upon power alarm (cmcTcMasterPcu5SetpointHigh(Low)Power1)
         (5): output is switched on upon power warning (cmcTcMasterPcu5SetpointWarningPower1)             "
      ::= { cmcTcMasterPcu5StatusEntry 10 }                

    cmcTcMasterPcu5RestoreOutputStatus OBJECT-TYPE
      SYNTAX INTEGER {
        disabled(1),
        enabled(2)
      }
      ACCESS read-write
      STATUS mandatory
      DESCRIPTION
        "Save last output status and switch output to this status after reboot"
      ::= { cmcTcMasterPcu5StatusEntry 11 }
                
--cmcTcMasterPcu5SetupGeneral-group

  cmcTcMasterPcu5SetTempUnit OBJECT-TYPE
    SYNTAX INTEGER {
      celsius(1),
      fahrenheit(2)
    }
    ACCESS read-write
    STATUS mandatory
    DESCRIPTION
      "Unit of all temperature values and setpoints, Celsius or Fahrenheit"
    ::= { cmcTcMasterPcu5SetupGeneral 1 }

  cmcTcMasterPcu5SetBeeper OBJECT-TYPE
    SYNTAX INTEGER {
      off(1),
      on(2),
      enableClear(3)
    }
    ACCESS read-write
    STATUS mandatory
    DESCRIPTION
      "Audible alarm in PCU unit:
       (1): beeper is off (general)
       (2): beeper is on (Alarm)
       (3): enable Clear (cmcTcMasterPcu5ClearAlarm)"
    ::= { cmcTcMasterPcu5SetupGeneral 2 }

  cmcTcMasterPcu5LogicRelay OBJECT-TYPE
    SYNTAX INTEGER {
      closeAtAlarm(1),
      openAtAlarm(2),
      off(3),
      enableRemote(4)
    }
    ACCESS read-write
    STATUS mandatory
    DESCRIPTION
      "Logic of alarm relay: 
       (1): Relay will pick up in case of an alarm
       (2): Relay will release in case of an alarm
       (3): Relay off (general)
       (4): enable remote relay control (SNMP set)"
    ::= { cmcTcMasterPcu5SetupGeneral 3 }
 
  cmcTcMasterPcu5ClearRelay OBJECT-TYPE
    SYNTAX INTEGER {
      disabled(1),
      enabled(2)
    }
    ACCESS read-write
    STATUS mandatory
    DESCRIPTION
      "Enable clear of alarm relay: 
       (1): Relay cannot be cleared by cmcTcMasterPcu5ClearAlarm
       (2): Relay can be cleared by cmcTcMasterPcu5ClearAlarm"
    ::= { cmcTcMasterPcu5SetupGeneral 4 }                  

  cmcTcMasterPcu5WebAccess OBJECT-TYPE
    SYNTAX INTEGER {
      viewOnly(1),
      fullAccess(2),
      off(3)
    }
    ACCESS read-write
    STATUS mandatory
    DESCRIPTION
      "Web access via HTTP: 
       (1): view only
       (2): full Access, read and set
       (3): Web disabled (general)"
    ::= { cmcTcMasterPcu5SetupGeneral 5 }
 
  cmcTcMasterPcu5SetupDate OBJECT-TYPE
    SYNTAX DisplayString (SIZE (0..10))
    ACCESS read-write
    STATUS mandatory
    DESCRIPTION
      "actual Date in format DD.MM.YYYY"
    ::= { cmcTcMasterPcu5SetupGeneral 6 }

  cmcTcMasterPcu5SetupTime OBJECT-TYPE
    SYNTAX DisplayString (SIZE (0..8))
    ACCESS read-write
    STATUS mandatory
    DESCRIPTION
      "actual Time in format HH:MM:SS, HH (0-23), MM (0-59), SS (0-59)"
    ::= { cmcTcMasterPcu5SetupGeneral 7 }

--cmcTcMasterPcu5TimerTable1-group
 
  cmcTcMasterPcu5TimerNumber OBJECT-TYPE
    SYNTAX INTEGER 
    ACCESS read-only
    STATUS mandatory
    DESCRIPTION
      "Number of timers available on this unit"
    ::= { cmcTcMasterPcu5TimerTable1 1 }

  cmcTcMasterPcu5TimerTable OBJECT-TYPE
    SYNTAX SEQUENCE OF CmcTcMasterPcu5TimerEntry
    ACCESS not-accessible
    STATUS mandatory
    DESCRIPTION
      "Headline of timer-table"
    ::= { cmcTcMasterPcu5TimerTable1 2 }

  cmcTcMasterPcu5TimerEntry OBJECT-TYPE
    SYNTAX CmcTcMasterPcu5TimerEntry
    ACCESS not-accessible
    STATUS mandatory
    DESCRIPTION
      "Entries of timer-table"
    INDEX { cmcTcMasterPcu5TimerIndex }
    ::= { cmcTcMasterPcu5TimerTable 1 }

    CmcTcMasterPcu5TimerEntry ::=
      SEQUENCE {
        cmcTcMasterPcu5TimerIndex
          INTEGER,
        cmcTcMasterPcu5TimerStatus
          INTEGER,
        cmcTcMasterPcu5TimerDayOfWeek
          INTEGER,  
        cmcTcMasterPcu5TimeOn 
          DisplayString (SIZE (0..5)),                              
        cmcTcMasterPcu5TimeOff 
          DisplayString (SIZE (0..5)),                              
        cmcTcMasterPcu5TimeControl
          INTEGER,
        cmcTcMasterPcu5TimerOutput1
          INTEGER,
        cmcTcMasterPcu5TimerOutput2
          INTEGER         
      }

    cmcTcMasterPcu5TimerIndex OBJECT-TYPE
      SYNTAX INTEGER (1..32000)
      ACCESS read-only
      STATUS mandatory
      DESCRIPTION
        "Index for the list of timer entries. Its value ranges
         between 1 and the value of cmcTcMasterPcu5TimerNumber." 
      ::= { cmcTcMasterPcu5TimerEntry 1 }

    cmcTcMasterPcu5TimerStatus OBJECT-TYPE
      SYNTAX INTEGER {
        switchedOff(1),
        switchedOn(2),
        noTime(3) 
      }
      ACCESS read-only
      STATUS mandatory
      DESCRIPTION
        "Actual status of the timer"
      ::= { cmcTcMasterPcu5TimerEntry 2 }

    cmcTcMasterPcu5TimerDayOfWeek OBJECT-TYPE
      SYNTAX INTEGER {
        sun(1),
        mon(2),
        tue(3) ,
        wed(4),
        thu(5),
        fre(6),
        sat(7),
        sat-sun(8),
        mo-fr(9),
        mo-su(10)
      }
      ACCESS read-write
      STATUS mandatory
      DESCRIPTION
        "Day when the timer is active"
      ::= { cmcTcMasterPcu5TimerEntry 3 }
             
    cmcTcMasterPcu5TimeOn OBJECT-TYPE
      SYNTAX DisplayString (SIZE (0..5))
      ACCESS read-write
      STATUS mandatory
      DESCRIPTION
        "Time to switch on current outlet, 
         Format: HH:MM"
      ::= { cmcTcMasterPcu5TimerEntry 4 }

    cmcTcMasterPcu5TimeOff OBJECT-TYPE
      SYNTAX DisplayString (SIZE (0..5))
      ACCESS read-write
      STATUS mandatory
      DESCRIPTION
        "Time to switch off current outlet,
         Format: HH:MM"
      ::= { cmcTcMasterPcu5TimerEntry 5 }

    cmcTcMasterPcu5TimeControl OBJECT-TYPE
      SYNTAX INTEGER {
        disabled(1),
        enabled(2)
      }
      ACCESS read-write
      STATUS mandatory
      DESCRIPTION
        "Control via RTC"
      ::= { cmcTcMasterPcu5TimerEntry 6 }

    cmcTcMasterPcu5TimerOutput1 OBJECT-TYPE
      SYNTAX INTEGER 
      ACCESS read-write
      STATUS mandatory
      DESCRIPTION
        "Output which is controlled via timer"
      ::= { cmcTcMasterPcu5TimerEntry 7 }

    cmcTcMasterPcu5TimerOutput2 OBJECT-TYPE
      SYNTAX INTEGER 
      ACCESS read-write
      STATUS mandatory
      DESCRIPTION
        "Output which is controlled via timer"
      ::= { cmcTcMasterPcu5TimerEntry 8 }

--cmcTcMasterPcu5SetupPower1-group                     

  cmcTcMasterPcu5SetupPower1Avail OBJECT-TYPE
    SYNTAX INTEGER {
      notAvailable(1),
      available(2)
    }
    ACCESS read-write
    STATUS mandatory
    DESCRIPTION
      "Energy sensor 1 sensor:   
       (1) not available
       (2) available"
    ::= { cmcTcMasterPcu5SetupPower1 1 }

  cmcTcMasterPcu5SetupPower1Relay OBJECT-TYPE
    SYNTAX INTEGER {
      disabled(1),
      enabled(2)
    }
    ACCESS read-write
    STATUS mandatory
    DESCRIPTION
      "Alert handling of Alarm Relay in case of an alarm condition
       of Power 1:  
       (1) no switching of Relays
       (2) Relay will switch"
    ::= { cmcTcMasterPcu5SetupPower1 2 }

  cmcTcMasterPcu5SetupPower1Beeper OBJECT-TYPE
    SYNTAX INTEGER {
      disabled(1),
      enabled(2)
    }
    ACCESS read-write
    STATUS mandatory
    DESCRIPTION
      "Alert handling of beeper of in case of an alarm condition
       of Power 1: 
       (1) No Audible Alarm
       (2) Start Audible Alarm"
    ::= { cmcTcMasterPcu5SetupPower1 3 }

--cmcTcMasterPcu5SetupPower2-group                     

  cmcTcMasterPcu5SetupPower2Avail OBJECT-TYPE
    SYNTAX INTEGER {
      notAvailable(1),
      available(2)
    }
    ACCESS read-write
    STATUS mandatory
    DESCRIPTION
      "Energy sensor 2:   
       (1) not available
       (2) available"
    ::= { cmcTcMasterPcu5SetupPower2 1 }

  cmcTcMasterPcu5SetupPower2Relay OBJECT-TYPE
    SYNTAX INTEGER {
      disabled(1),
      enabled(2)
    }
    ACCESS read-write
    STATUS mandatory
    DESCRIPTION
      "Alert handling of Alarm Relay in case of an alarm condition
       of Power 2:  
       (1) no switching of Relay
       (2) Relay will switch"
    ::= { cmcTcMasterPcu5SetupPower2 2 }

  cmcTcMasterPcu5SetupPower2Beeper OBJECT-TYPE
    SYNTAX INTEGER {
      disabled(1),
      enabled(2)
    }
    ACCESS read-write
    STATUS mandatory
    DESCRIPTION
      "Alert handling of beeper of in case of an alarm condition
       of Power 2: 
       (1) No Audible Alarm
       (2) Start Audible Alarm"
    ::= { cmcTcMasterPcu5SetupPower2 3 }

--cmcTcMasterPcu5SetupInput1-group

  cmcTcMasterPcu5SetupInput1Avail OBJECT-TYPE
    SYNTAX INTEGER {
      notAvailable(1),
      available(2)
    }
    ACCESS read-write
    STATUS mandatory
    DESCRIPTION
      "Input 1 sensor:   
       (1) not available
       (2) available"
    ::= { cmcTcMasterPcu5SetupInput1 1 }

  cmcTcMasterPcu5SetupInput1Relay OBJECT-TYPE
    SYNTAX INTEGER {
      disabled(1),
      enabled(2)
    }
    ACCESS read-write
    STATUS mandatory
    DESCRIPTION
      "Alert handling of Alarm Relay in case of an alarm condition
       of Input 1:  
       (1) no switching of Relay
       (2) Relay will switch"
    ::= { cmcTcMasterPcu5SetupInput1 2 }

  cmcTcMasterPcu5SetupInput1Beeper OBJECT-TYPE
    SYNTAX INTEGER {
      disabled(1),
      enabled(2)
    }
    ACCESS read-write
    STATUS mandatory
    DESCRIPTION
      "Alert handling of beeper of in case of an alarm condition
       of Input 1: 
       (1) No Audible Alarm
       (2) Start Audible Alarm"
    ::= { cmcTcMasterPcu5SetupInput1 3 }

  cmcTcMasterPcu5SetupInput1Contact OBJECT-TYPE
    SYNTAX INTEGER {
      contactNO(1),
      contactNC(2),
      notAvail(3)
    }
    ACCESS read-write
    STATUS mandatory
    DESCRIPTION
      "Setup of digital input 1"
    ::= { cmcTcMasterPcu5SetupInput1 4 }

  cmcTcMasterPcu5SetupInput1Delay OBJECT-TYPE
    SYNTAX INTEGER (0..60)
    ACCESS read-write
    STATUS mandatory
    DESCRIPTION
      "Delay for changing of input state"
    ::= { cmcTcMasterPcu5SetupInput1 5 }

--cmcTcMasterPcu5SetupInput2-group

  cmcTcMasterPcu5SetupInput2Avail OBJECT-TYPE
    SYNTAX INTEGER {
      notAvailable(1),
      available(2)
    }
    ACCESS read-write
    STATUS mandatory
    DESCRIPTION
      "Input 2 sensor:   
       (2) available
       (1) not available"
    ::= { cmcTcMasterPcu5SetupInput2 1 }

  cmcTcMasterPcu5SetupInput2Relay OBJECT-TYPE
    SYNTAX INTEGER {
      disabled(1),
      enabled(2)
    }
    ACCESS read-write
    STATUS mandatory
    DESCRIPTION
      "Alert handling of Alarm Relay in case of an alarm condition
       of Input 1:  
       (1) no switching of Relays
       (2) Relay will switch"
    ::= { cmcTcMasterPcu5SetupInput2 2 }

  cmcTcMasterPcu5SetupInput2Beeper OBJECT-TYPE
    SYNTAX INTEGER {
      disabled(1),
      enabled(2)
    }
    ACCESS read-write
    STATUS mandatory
    DESCRIPTION
      "Alert handling of beeper of in case of an alarm condition
       of Input 2: 
       (1) No Audible Alarm
       (2) Start Audible Alarm"
    ::= { cmcTcMasterPcu5SetupInput2 3 }

  cmcTcMasterPcu5SetupInput2Contact OBJECT-TYPE
    SYNTAX INTEGER {
      contactNO(1),
      contactNC(2),
      notAvail(3)
    }
    ACCESS read-write
    STATUS mandatory
    DESCRIPTION
      "Setup of digital input 2"
    ::= { cmcTcMasterPcu5SetupInput2 4 }

  cmcTcMasterPcu5SetupInput2Delay OBJECT-TYPE
    SYNTAX INTEGER (0..60)
    ACCESS read-write
    STATUS mandatory
    DESCRIPTION
      "Delay for changing of input state"
    ::= { cmcTcMasterPcu5SetupInput2 5 }

--cmcTcMasterPcu5SetupTemperature-group                     

  cmcTcMasterPcu5SetupTemperatureAvail OBJECT-TYPE
    SYNTAX INTEGER {
      notAvailable(1),
      available(2)
    }
    ACCESS read-write
    STATUS mandatory
    DESCRIPTION
      "Temp sensor 1:   
       (1) not available
       (2) available"
    ::= { cmcTcMasterPcu5SetupTemperature 1 }

  cmcTcMasterPcu5SetupTemperatureRelay OBJECT-TYPE
    SYNTAX INTEGER {
      disabled(1),
      enabled(2)
    }
    ACCESS read-write
    STATUS mandatory
    DESCRIPTION
      "Alert handling of Alarm Relay in case of an alarm condition
       of Temperature:  
       (1) no switching of Relays
       (2) Relay will switch"
    ::= { cmcTcMasterPcu5SetupTemperature 2 }

  cmcTcMasterPcu5SetupTemperatureBeeper OBJECT-TYPE
    SYNTAX INTEGER {
      disabled(1),
      enabled(2)
    }
    ACCESS read-write
    STATUS mandatory
    DESCRIPTION
      "Alert handling of beeper of in case of an alarm condition
       of Temperature: 
       (1) No Audible Alarm
       (2) Start Audible Alarm"
    ::= { cmcTcMasterPcu5SetupTemperature 3 }

--cmcTcMasterPcu5SetupGeneral-group

  cmcTcMasterPcu5SetMessage OBJECT-TYPE
    SYNTAX DisplayString (SIZE (0..31))
    ACCESS read-write
    STATUS mandatory
    DESCRIPTION
      "Set message"
    ::= { cmcTcMasterPcu5SetupDevice 1 }

--cmcTcMasterPcu5Setpoints-group

  cmcTcMasterPcu5SetpointHighPower1 OBJECT-TYPE
    SYNTAX INTEGER 
    ACCESS read-write
    STATUS mandatory
    DESCRIPTION
      "Setpoint high value power consumption 1 alarm"
    ::= { cmcTcMasterPcu5Setpoints 1 }

  cmcTcMasterPcu5SetpointWarningPower1 OBJECT-TYPE
    SYNTAX INTEGER 
    ACCESS read-write
    STATUS mandatory
    DESCRIPTION
      "Setpoint warning value power consumption 1 alarm"
    ::= { cmcTcMasterPcu5Setpoints 2 }

  cmcTcMasterPcu5SetpointLowPower1 OBJECT-TYPE
    SYNTAX INTEGER
    ACCESS read-write
    STATUS mandatory
    DESCRIPTION
      "Setpoint low value power consumption 1 alarm"
    ::= { cmcTcMasterPcu5Setpoints 3 }

  cmcTcMasterPcu5SetpointHighPower2 OBJECT-TYPE
    SYNTAX INTEGER 
    ACCESS read-write
    STATUS mandatory
    DESCRIPTION
      "Setpoint high value power consumption 2 alarm"
    ::= { cmcTcMasterPcu5Setpoints 4 }

  cmcTcMasterPcu5SetpointWarningPower2 OBJECT-TYPE
    SYNTAX INTEGER 
    ACCESS read-write
    STATUS mandatory
    DESCRIPTION
      "Setpoint warning value power consumption 2 alarm"
    ::= { cmcTcMasterPcu5Setpoints 5 }

  cmcTcMasterPcu5SetpointLowPower2 OBJECT-TYPE
    SYNTAX INTEGER
    ACCESS read-write
    STATUS mandatory
    DESCRIPTION
      "Setpoint low value power consumption 2 alarm"
    ::= { cmcTcMasterPcu5Setpoints 6 }

  cmcTcMasterPcu5SetpointHighTemperature OBJECT-TYPE
    SYNTAX INTEGER (0..200)
    ACCESS read-write
    STATUS mandatory
    DESCRIPTION
      "Setpoint high value alarm temperature "
    ::= { cmcTcMasterPcu5Setpoints 7 }

  cmcTcMasterPcu5SetpointLowTemperature OBJECT-TYPE
    SYNTAX INTEGER (0..50)
    ACCESS read-write
    STATUS mandatory
    DESCRIPTION
      "Setpoint low value alarm temperature "
    ::= { cmcTcMasterPcu5Setpoints 8 }
 
  cmcTcMasterPcu5SetpointTemperature OBJECT-TYPE
    SYNTAX INTEGER (0..200)
    ACCESS read-write
    STATUS mandatory
    DESCRIPTION
      "Setpoint temperature for outlet control 
       and temperature warning"
    ::= { cmcTcMasterPcu5Setpoints 9 }

  cmcTcMasterPcu5SetpointTemperatureHyst OBJECT-TYPE
    SYNTAX INTEGER (0..15)
    ACCESS read-write
    STATUS mandatory
    DESCRIPTION
      "Hysteresis for cmcTcMasterPcu5SetpointTemperature"
    ::= { cmcTcMasterPcu5Setpoints 10 }
 
--cmcTcMasterPcu5Control-group

  cmcTcMasterPcu5ResetEnergy1 OBJECT-TYPE
    SYNTAX INTEGER {
      noReset(1),
      reset(2)
    }
    ACCESS read-write
    STATUS mandatory
    DESCRIPTION
      "Reset value of cmcTcMasterPcu5ValueEnergy1Time"
    ::= { cmcTcMasterPcu5Control 1 }

  cmcTcMasterPcu5ResetEnergy2 OBJECT-TYPE
    SYNTAX INTEGER {
      noReset(1),
      reset(2)
    }
    ACCESS read-write
    STATUS mandatory
    DESCRIPTION
      "Reset value of cmcTcMasterPcu5ValueEnergy2Time"
    ::= { cmcTcMasterPcu5Control 2 }

  cmcTcMasterPcu5ControlAlarmRelay OBJECT-TYPE
    SYNTAX INTEGER {
      relayOff(1),
      relayOn(2)
    }
    ACCESS read-write
    STATUS mandatory
    DESCRIPTION
      "Control of Alarm relay"
    ::= { cmcTcMasterPcu5Control 3 }

  cmcTcMasterPcu5ClearAlarm OBJECT-TYPE
    SYNTAX INTEGER {
      noClear(1),
      clear(2)
    }
    ACCESS read-write
    STATUS mandatory
    DESCRIPTION
      "Clear alarm, beeper and relay"
    ::= { cmcTcMasterPcu5Control 4 }

--cmcTcMasterPcu5TrapTable-group

  cmcTcMasterPcu5TrapTableNumber OBJECT-TYPE
    SYNTAX INTEGER 
    ACCESS read-only
    STATUS mandatory
    DESCRIPTION
      "Number of cmcTcMasterPcu5TrapTable entries. The number of trap-receivers avail."
    ::= { cmcTcMasterPcu5Traps 1 }

  cmcTcMasterPcu5TrapTable OBJECT-TYPE
    SYNTAX SEQUENCE OF CmcTcMasterPcu5TrapEntry
    ACCESS not-accessible
    STATUS mandatory
    DESCRIPTION
      "A list of trap-receiver entries"
    ::= { cmcTcMasterPcu5Traps 2 }

  cmcTcMasterPcu5TrapEntry OBJECT-TYPE
    SYNTAX CmcTcMasterPcu5TrapEntry
    ACCESS not-accessible
    STATUS mandatory
    DESCRIPTION
      "Entries of cmcTcMasterPcu5TrapTable"
    INDEX { cmcTcMasterPcu5TrapIndex }
    ::= { cmcTcMasterPcu5TrapTable 1 }

    CmcTcMasterPcu5TrapEntry ::=
      SEQUENCE {
        cmcTcMasterPcu5TrapIndex
          INTEGER,
        cmcTcMasterPcu5TrapStatus
          INTEGER,
        cmcTcMasterPcu5TrapIPaddress
          DisplayString
      }

    cmcTcMasterPcu5TrapIndex OBJECT-TYPE
      SYNTAX INTEGER (1..32000)
      ACCESS read-only
      STATUS mandatory
      DESCRIPTION
        "Index for the trap-receiver-table. Its value ranges between
         1 and the value of cmcTcMasterPcu5TrapTableNumber "
      ::= { cmcTcMasterPcu5TrapEntry 1 }

    cmcTcMasterPcu5TrapStatus OBJECT-TYPE
      SYNTAX INTEGER {
        disabled(1),
        enabled(2)
      }
      ACCESS read-write
      STATUS mandatory
      DESCRIPTION
        "Enable or disable trap receiver"
      ::= { cmcTcMasterPcu5TrapEntry 2 }

    cmcTcMasterPcu5TrapIPaddress OBJECT-TYPE
      SYNTAX DisplayString (SIZE (0..15))
      ACCESS read-write
      STATUS mandatory
      DESCRIPTION
        "IP-address of trap-receiver"
      ::= { cmcTcMasterPcu5TrapEntry 3 }

--cmcTcMasterTc5MibRev-group
          
  cmcTcMasterTc5MibMajRev OBJECT-TYPE
    SYNTAX INTEGER (1..32000)
    ACCESS read-only
    STATUS mandatory
    DESCRIPTION
      "The Major Revision level.
       A change in the major revision level represents a major change
       in the architecture of the MIB. A change in the major revision 
       level may indicate a significant change in the information,
       correct interpretation of data may require a MIB document
       with the same major revision level."
    ::= { cmcTcMasterTc5MibRev 1 }

  cmcTcMasterTc5MibMinRev OBJECT-TYPE
    SYNTAX INTEGER (0..32000)
    ACCESS read-only
    STATUS mandatory
    DESCRIPTION
      "The Minor Revision level.
       A change in the minor revision level may represent some minor
       additional support, no changes to any pre-existing information
       has occurred."
    ::= { cmcTcMasterTc5MibRev 2 }

  cmcTcMasterTc5MibCondition OBJECT-TYPE
    SYNTAX INTEGER {
      other (1),
      ok (2),
      degraded (3),
      failed (4),
      configChanged (5)
    }
    ACCESS read-only
    STATUS mandatory
    DESCRIPTION
      "The overall condition (status) of the system represented by
       this MIB. 
       (2) OK
       (3) a minor problem, warning condition (yellow LED on CMC-TC)
       (4) a major problem (red LED on CMC-TC)
       (5) configuration of sensor units changed or
           unit detected (red/yellow/green LED on CMC-TC)"
    ::= { cmcTcMasterTc5MibRev 3 }
          
--cmcTcMasterTc5Status-group

  cmcTcMasterTc5StatusDeviceCMC OBJECT-TYPE
    SYNTAX INTEGER {
      failed(1),
      ok(2)
    }
    ACCESS read-only
    STATUS mandatory
    DESCRIPTION
      "General Status of CMC-TC unit itself
       (1) failed
       (2) OK"
    ::= { cmcTcMasterTc5Status 1 }

  cmcTcMasterTc5UnitsConnected OBJECT-TYPE
    SYNTAX INTEGER 
    ACCESS read-only
    STATUS mandatory
    DESCRIPTION
      "Number of sensor units connected to the CMC-TC, Port 1 to 4"
    ::= { cmcTcMasterTc5Status 2 }

--unit 1

  cmcTcMasterTc5Unit1TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 1"
    ::= { cmcTcMasterTc5StatusSensorUnit1 1 }

  cmcTcMasterTc5Unit1Text OBJECT-TYPE
    SYNTAX DisplayString (SIZE (0..10))
    ACCESS read-write
    STATUS mandatory
    DESCRIPTION
      "Descriptional text for sensor unit connected to port 1"
    ::= { cmcTcMasterTc5StatusSensorUnit1 2 }

  cmcTcMasterTc5Unit1Serial OBJECT-TYPE
    SYNTAX INTEGER 
    ACCESS read-only
    STATUS mandatory
    DESCRIPTION
      "Serialnumber of sensor unit connected to port 1"
    ::= { cmcTcMasterTc5StatusSensorUnit1 3 }

  cmcTcMasterTc5Unit1Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 1
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc5StatusSensorUnit1 4 }

-- Sensors
              
  cmcTcMasterTc5Unit1NumberOfSensors OBJECT-TYPE
    SYNTAX INTEGER 
    ACCESS read-only
    STATUS mandatory
    DESCRIPTION
      "Number of sensors connected to sensor unit 1"
    ::= { cmcTcMasterTc5StatusUnit1Sensors 1 }

-- table with entry for each sensor available on this unit              

  cmcTcMasterTc5Unit1SensorTable OBJECT-TYPE
    SYNTAX SEQUENCE OF CmcTcMasterTc5Unit1SensorEntry
    ACCESS not-accessible
    STATUS mandatory
    DESCRIPTION
      "Headline of sensor table"
    ::= { cmcTcMasterTc5StatusUnit1Sensors 2 }

  cmcTcMasterTc5Unit1SensorEntry OBJECT-TYPE
    SYNTAX CmcTcMasterTc5Unit1SensorEntry
    ACCESS not-accessible
    STATUS mandatory
    DESCRIPTION
      "Entries of sensor table"
    INDEX { cmcTcMasterTc5Unit1SensorIndex }
    ::= { cmcTcMasterTc5Unit1SensorTable 1 }

    CmcTcMasterTc5Unit1SensorEntry ::=
      SEQUENCE {
        cmcTcMasterTc5Unit1SensorIndex
          INTEGER,
        cmcTcMasterTc5Unit1SensorType
          INTEGER,
        cmcTcMasterTc5Unit1SensorText
          DisplayString (SIZE (0..20)),                
        cmcTcMasterTc5Unit1SensorStatus
          INTEGER,
        cmcTcMasterTc5Unit1SensorValue
          INTEGER,
        cmcTcMasterTc5Unit1SensorSetHigh
          INTEGER,
        cmcTcMasterTc5Unit1SensorSetLow
          INTEGER,
        cmcTcMasterTc5Unit1SensorSetWarn
          INTEGER                
      }

    cmcTcMasterTc5Unit1SensorIndex OBJECT-TYPE
      SYNTAX INTEGER (1..32000)
      ACCESS read-only
      STATUS mandatory
      DESCRIPTION
        "Index for the list of value entries. Its value ranges
         between 1 and the value of cmcTcMasterTc5Unit1NumberOfSensors." 
      ::= { cmcTcMasterTc5Unit1SensorEntry 1 }

    cmcTcMasterTc5Unit1SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 1 to sensor[cmcTcMasterTc5Unit1SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc5Unit1SensorEntry 2 }

    cmcTcMasterTc5Unit1SensorText OBJECT-TYPE
      SYNTAX DisplayString (SIZE (0..20))
      ACCESS read-write
      STATUS mandatory
      DESCRIPTION
        "Descriptional text for each sensor (entry in the table)"
      ::= { cmcTcMasterTc5Unit1SensorEntry 3 }
              
    cmcTcMasterTc5Unit1SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc5Unit1SensorEntry 4 }

    cmcTcMasterTc5Unit1SensorValue OBJECT-TYPE
      SYNTAX INTEGER 
      ACCESS read-only
      STATUS mandatory
      DESCRIPTION
        "Value of sensor"
      ::= { cmcTcMasterTc5Unit1SensorEntry 5 }

    cmcTcMasterTc5Unit1SensorSetHigh OBJECT-TYPE
      SYNTAX INTEGER (0..300) 
      ACCESS read-write
      STATUS mandatory
      DESCRIPTION
        "Value for high setpoint of sensor"
      ::= { cmcTcMasterTc5Unit1SensorEntry 6 }

    cmcTcMasterTc5Unit1SensorSetLow OBJECT-TYPE
      SYNTAX INTEGER (0..300) 
      ACCESS read-write
      STATUS mandatory
      DESCRIPTION
        "Value for low setpoint of sensor,
         also used as alarm delay"
      ::= { cmcTcMasterTc5Unit1SensorEntry 7 }

    cmcTcMasterTc5Unit1SensorSetWarn OBJECT-TYPE
      SYNTAX INTEGER (0..300) 
      ACCESS read-write
      STATUS mandatory
      DESCRIPTION
        "Value for warning setpoint of sensor, 
         also used as fan threshold"
      ::= { cmcTcMasterTc5Unit1SensorEntry 8 }
                
-- Outputs              

  cmcTcMasterTc5Unit1NumberOfOutputs OBJECT-TYPE
    SYNTAX INTEGER 
    ACCESS read-only
    STATUS mandatory
    DESCRIPTION
      "Number of outputs available on sensor unit 1"
    ::= { cmcTcMasterTc5StatusUnit1Outputs 1 }

-- table with entry for each output available on this unit              
                
  cmcTcMasterTc5Unit1OutputTable OBJECT-TYPE
    SYNTAX SEQUENCE OF CmcTcMasterTc5Unit1OutputEntry
    ACCESS not-accessible
    STATUS mandatory
    DESCRIPTION
      "Headline of output table"
    ::= { cmcTcMasterTc5StatusUnit1Outputs 2 }

  cmcTcMasterTc5Unit1OutputEntry OBJECT-TYPE
    SYNTAX CmcTcMasterTc5Unit1OutputEntry
    ACCESS not-accessible
    STATUS mandatory
    DESCRIPTION
      "Entries of output table"
    INDEX { cmcTcMasterTc5Unit1OutputIndex }
    ::= { cmcTcMasterTc5Unit1OutputTable 1 }

    CmcTcMasterTc5Unit1OutputEntry ::=
      SEQUENCE {
        cmcTcMasterTc5Unit1OutputIndex
          INTEGER,
        cmcTcMasterTc5Unit1OutputType
          INTEGER,
        cmcTcMasterTc5Unit1OutputText
          DisplayString (SIZE (0..20)),                
        cmcTcMasterTc5Unit1OutputStatus
          INTEGER,
        cmcTcMasterTc5Unit1OutputValue
          INTEGER,
        cmcTcMasterTc5Unit1OutputSet
          INTEGER,
        cmcTcMasterTc5Unit1OutputConfig
          INTEGER,                
        cmcTcMasterTc5Unit1OutputDelay
          INTEGER,
        cmcTcMasterTc5Unit1OutputTimeoutAction
          INTEGER
      }

    cmcTcMasterTc5Unit1OutputIndex OBJECT-TYPE
      SYNTAX INTEGER (1..32000)
      ACCESS read-only
      STATUS mandatory
      DESCRIPTION
        "Index for the list of output entries. Its value ranges
         between 1 and the value of cmcTcMasterTc5Unit1NumberOfOutputs." 
      ::= { cmcTcMasterTc5Unit1OutputEntry 1 }

    cmcTcMasterTc5Unit1OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 1 to output[cmcTcMasterTc5Unit1OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc5Unit1OutputEntry 2 }

    cmcTcMasterTc5Unit1OutputText OBJECT-TYPE
      SYNTAX DisplayString (SIZE (0..20))
      ACCESS read-write
      STATUS mandatory
      DESCRIPTION
        "Descriptional text for each output (entry in the table)"
      ::= { cmcTcMasterTc5Unit1OutputEntry 3 }
              
    cmcTcMasterTc5Unit1OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc5Unit1OutputEntry 4 }

    cmcTcMasterTc5Unit1OutputValue OBJECT-TYPE
      SYNTAX INTEGER (-32000..32000) 
      ACCESS read-write
      STATUS mandatory
      DESCRIPTION
        "Value for output"
      ::= { cmcTcMasterTc5Unit1OutputEntry 5 }

    cmcTcMasterTc5Unit1OutputSet OBJECT-TYPE
      SYNTAX INTEGER {
        off (1),
        on (2),
        lock (3),
        unlock (4),
        unlockDelay (5)
      }
      ACCESS read-write
      STATUS mandatory
      DESCRIPTION
        "Command for output"
      ::= { cmcTcMasterTc5Unit1OutputEntry 6 }

    cmcTcMasterTc5Unit1OutputConfig OBJECT-TYPE
      SYNTAX INTEGER {
        disRemote (1),
        enRemote (2)
      }
      ACCESS read-write
      STATUS mandatory
      DESCRIPTION
        "Configuration for output
         1: 	disable remote control (e.g. keypad)
         2: 	enable remote control"
      ::= { cmcTcMasterTc5Unit1OutputEntry 7 }

    cmcTcMasterTc5Unit1OutputDelay OBJECT-TYPE
      SYNTAX INTEGER (0..999) 
      ACCESS read-write
      STATUS mandatory
      DESCRIPTION
        "Unsigned Value for delay, 
         after this time the output will fall into the previous state"
      ::= { cmcTcMasterTc5Unit1OutputEntry 8 }

    cmcTcMasterTc5Unit1OutputTimeoutAction OBJECT-TYPE
      SYNTAX INTEGER {
        stay (1),
        off (2),
        on (3)
      }
      ACCESS read-write
      STATUS mandatory
      DESCRIPTION
        "State for output if timeout (RS422) occurs"
      ::= { cmcTcMasterTc5Unit1OutputEntry 9 }
 
-- Messages
              
  cmcTcMasterTc5Unit1NumberOfMsgs OBJECT-TYPE
    SYNTAX INTEGER 
    ACCESS read-only
    STATUS mandatory
    DESCRIPTION
      "Number of messages that can be created with sensor unit 1"
    ::= { cmcTcMasterTc5StatusUnit1Msg 1 }

-- table with entry for each alarm available on this unit               
                
  cmcTcMasterTc5Unit1MsgTable OBJECT-TYPE
    SYNTAX SEQUENCE OF CmcTcMasterTc5Unit1MsgEntry
    ACCESS not-accessible
    STATUS mandatory
    DESCRIPTION
      "Headline of message table"
    ::= { cmcTcMasterTc5StatusUnit1Msg 2 }

  cmcTcMasterTc5Unit1MsgEntry OBJECT-TYPE
    SYNTAX CmcTcMasterTc5Unit1MsgEntry
    ACCESS not-accessible
    STATUS mandatory
    DESCRIPTION
      "Entries of message table"
    INDEX { cmcTcMasterTc5Unit1MsgIndex }
    ::= { cmcTcMasterTc5Unit1MsgTable 1 }

    CmcTcMasterTc5Unit1MsgEntry ::=
      SEQUENCE {
        cmcTcMasterTc5Unit1MsgIndex
          INTEGER, 
        cmcTcMasterTc5Unit1MsgText
          DisplayString (SIZE (0..20)),                
        cmcTcMasterTc5Unit1MsgStatus
          INTEGER,                
        cmcTcMasterTc5Unit1MsgRelay
          INTEGER,
        cmcTcMasterTc5Unit1MsgBeeper
          INTEGER,
        cmcTcMasterTc5Unit1MsgTrap1
          INTEGER,
        cmcTcMasterTc5Unit1MsgTrap2
          INTEGER,
        cmcTcMasterTc5Unit1MsgTrap3
          INTEGER,
        cmcTcMasterTc5Unit1MsgTrap4
          INTEGER,                 
        cmcTcMasterTc5Unit1MsgQuit
          INTEGER              
      }

    cmcTcMasterTc5Unit1MsgIndex OBJECT-TYPE
      SYNTAX INTEGER (1..32000)
      ACCESS read-only
      STATUS mandatory
      DESCRIPTION
        "Index for the list of message entries. Its value ranges
         between 1 and the value of cmcTcMasterTc5Unit1NumberOfMsgs." 
      ::= { cmcTcMasterTc5Unit1MsgEntry 1 }

    cmcTcMasterTc5Unit1MsgText OBJECT-TYPE
      SYNTAX DisplayString (SIZE (0..20))
      ACCESS read-write
      STATUS mandatory
      DESCRIPTION
        "Descriptional text for each message (entry in the table)"
      ::= { cmcTcMasterTc5Unit1MsgEntry 2 }
              
    cmcTcMasterTc5Unit1MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc5Unit1OutputSet)
         17: door is unlocked by WEB
         18: door is unlocked by timer
         19: no access, wrong keycode or cardnumber
         20: orientation of PSM-Unit is circuit 1
         21: orientation of PSM-Unit is circuit 2"
      ::= { cmcTcMasterTc5Unit1MsgEntry 3 }
        
    cmcTcMasterTc5Unit1MsgRelay OBJECT-TYPE
      SYNTAX INTEGER {
        disable (1),
        enable (2)
      }
      ACCESS read-write
      STATUS mandatory
      DESCRIPTION
        "Setup of Alarm relay for this message/alarm
         1:        no switching of alarm relay             
         2:        switching of alarm relay" 
      ::= { cmcTcMasterTc5Unit1MsgEntry 4 }

    cmcTcMasterTc5Unit1MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc5Unit1MsgEntry 5 }

    cmcTcMasterTc5Unit1MsgTrap1 OBJECT-TYPE
      SYNTAX INTEGER {
        disable (1),
        enable (2)
      }
      ACCESS read-write
      STATUS mandatory
      DESCRIPTION
        "Trap receiver 1 activated"
      ::= { cmcTcMasterTc5Unit1MsgEntry 6 }

    cmcTcMasterTc5Unit1MsgTrap2 OBJECT-TYPE
      SYNTAX INTEGER {
        disable (1),
        enable (2)
      }
      ACCESS read-write
      STATUS mandatory
      DESCRIPTION
        "Trap receiver 2 activated"
      ::= { cmcTcMasterTc5Unit1MsgEntry 7 }
 
    cmcTcMasterTc5Unit1MsgTrap3 OBJECT-TYPE
      SYNTAX INTEGER {
        disable (1),
        enable (2)
      }
      ACCESS read-write
      STATUS mandatory
      DESCRIPTION
        "Trap receiver 3 activated"
      ::= { cmcTcMasterTc5Unit1MsgEntry 8 }

    cmcTcMasterTc5Unit1MsgTrap4 OBJECT-TYPE
      SYNTAX INTEGER {
        disable (1),
        enable (2)
      }
      ACCESS read-write
      STATUS mandatory
      DESCRIPTION
        "Trap receiver 4 and Event Logging activated"
      ::= { cmcTcMasterTc5Unit1MsgEntry 9 }

    cmcTcMasterTc5Unit1MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc5Unit1MsgEntry 10 }

-- unit2

  cmcTcMasterTc5Unit2TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 2"
    ::= { cmcTcMasterTc5StatusSensorUnit2 1 }

  cmcTcMasterTc5Unit2Text OBJECT-TYPE
    SYNTAX DisplayString (SIZE (0..10))
    ACCESS read-write
    STATUS mandatory
    DESCRIPTION
      "Descriptional text for sensor unit connected to port 2"
    ::= { cmcTcMasterTc5StatusSensorUnit2 2 }

  cmcTcMasterTc5Unit2Serial OBJECT-TYPE
    SYNTAX INTEGER 
    ACCESS read-only
    STATUS mandatory
    DESCRIPTION
      "Serialnumber of sensor unit connected to port 2"
    ::= { cmcTcMasterTc5StatusSensorUnit2 3 }

  cmcTcMasterTc5Unit2Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 2
       (1) OK
       (2) error
       (3) configuration of sensor unit has changed, confirmation required
       (4) Quit from sensor unit to confirm configuration changes
       (5) timeout of sensor unit, confirmation required
       (6) sensor unit detected, needs to be confirmed
       (8) supply voltage is too low"              
    ::= { cmcTcMasterTc5StatusSensorUnit2 4 }

-- unit 2 table

-- Sensors              

  cmcTcMasterTc5Unit2NumberOfSensors OBJECT-TYPE
    SYNTAX INTEGER 
    ACCESS read-only
    STATUS mandatory
    DESCRIPTION
      "Number of sensors connected to sensor unit 2"
    ::= { cmcTcMasterTc5StatusUnit2Sensors 1 }

-- table with entry for each sensor available on this unit              

  cmcTcMasterTc5Unit2SensorTable OBJECT-TYPE
    SYNTAX SEQUENCE OF CmcTcMasterTc5Unit2SensorEntry
    ACCESS not-accessible
    STATUS mandatory
    DESCRIPTION
      "Headline of sensor table"
    ::= { cmcTcMasterTc5StatusUnit2Sensors 2 }

  cmcTcMasterTc5Unit2SensorEntry OBJECT-TYPE
    SYNTAX CmcTcMasterTc5Unit2SensorEntry
    ACCESS not-accessible
    STATUS mandatory
    DESCRIPTION
      "Entries of sensor table"
    INDEX { cmcTcMasterTc5Unit2SensorIndex }
    ::= { cmcTcMasterTc5Unit2SensorTable 1 }

    CmcTcMasterTc5Unit2SensorEntry ::=
      SEQUENCE {
        cmcTcMasterTc5Unit2SensorIndex
          INTEGER,
        cmcTcMasterTc5Unit2SensorType
          INTEGER,
        cmcTcMasterTc5Unit2SensorText
          DisplayString (SIZE (0..20)),                
        cmcTcMasterTc5Unit2SensorStatus
          INTEGER,
        cmcTcMasterTc5Unit2SensorValue
          INTEGER,
        cmcTcMasterTc5Unit2SensorSetHigh
          INTEGER,
        cmcTcMasterTc5Unit2SensorSetLow
          INTEGER,                 
        cmcTcMasterTc5Unit2SensorSetWarn
          INTEGER  
      }

    cmcTcMasterTc5Unit2SensorIndex OBJECT-TYPE
      SYNTAX INTEGER (1..32000)
      ACCESS read-only
      STATUS mandatory
      DESCRIPTION
        "Index for the list of value entries. Its value ranges
         between 1 and the value of cmcTcMasterTc5Unit2NumberOfSensors." 
      ::= { cmcTcMasterTc5Unit2SensorEntry 1 }

    cmcTcMasterTc5Unit2SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 2 to sensor[cmcTcMasterTc5Unit2SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc5Unit2SensorEntry 2 }
        
    cmcTcMasterTc5Unit2SensorText OBJECT-TYPE
      SYNTAX DisplayString (SIZE (0..20))
      ACCESS read-write
      STATUS mandatory
      DESCRIPTION
        "Descriptional text for each sensor (entry in the table)"
      ::= { cmcTcMasterTc5Unit2SensorEntry 3 }
              
    cmcTcMasterTc5Unit2SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc5Unit2SensorEntry 4 }

    cmcTcMasterTc5Unit2SensorValue OBJECT-TYPE
      SYNTAX INTEGER 
      ACCESS read-only
      STATUS mandatory
      DESCRIPTION
        "Value of sensor"
      ::= { cmcTcMasterTc5Unit2SensorEntry 5 }

    cmcTcMasterTc5Unit2SensorSetHigh OBJECT-TYPE
      SYNTAX INTEGER (0..300) 
      ACCESS read-write
      STATUS mandatory
      DESCRIPTION
        "Value for high setpoint of sensor"
      ::= { cmcTcMasterTc5Unit2SensorEntry 6 }

    cmcTcMasterTc5Unit2SensorSetLow OBJECT-TYPE
      SYNTAX INTEGER (0..300) 
      ACCESS read-write
      STATUS mandatory
      DESCRIPTION
        "Value for low setpoint of sensor,
         also used as alarm delay"
      ::= { cmcTcMasterTc5Unit2SensorEntry 7 }

    cmcTcMasterTc5Unit2SensorSetWarn OBJECT-TYPE
      SYNTAX INTEGER (0..300) 
      ACCESS read-write
      STATUS mandatory
      DESCRIPTION
        "Value for warning setpoint of sensor,
         also used as fan threshold"
      ::= { cmcTcMasterTc5Unit2SensorEntry 8 }

-- Outputs              

  cmcTcMasterTc5Unit2NumberOfOutputs OBJECT-TYPE
    SYNTAX INTEGER 
    ACCESS read-only
    STATUS mandatory
    DESCRIPTION
      "Number of outputs available on sensor unit 2"
    ::= { cmcTcMasterTc5StatusUnit2Outputs 1 }

-- table with entry for each output available on this unit              
                
  cmcTcMasterTc5Unit2OutputTable OBJECT-TYPE
    SYNTAX SEQUENCE OF CmcTcMasterTc5Unit2OutputEntry
    ACCESS not-accessible
    STATUS mandatory
    DESCRIPTION
      "Headline of output table"
    ::= { cmcTcMasterTc5StatusUnit2Outputs 2 }

  cmcTcMasterTc5Unit2OutputEntry OBJECT-TYPE
    SYNTAX CmcTcMasterTc5Unit2OutputEntry
    ACCESS not-accessible
    STATUS mandatory
    DESCRIPTION
      "Entries of output table"
    INDEX { cmcTcMasterTc5Unit2OutputIndex }
    ::= { cmcTcMasterTc5Unit2OutputTable 1 }

    CmcTcMasterTc5Unit2OutputEntry ::=
      SEQUENCE {
        cmcTcMasterTc5Unit2OutputIndex
          INTEGER,
        cmcTcMasterTc5Unit2OutputType
          INTEGER,
        cmcTcMasterTc5Unit2OutputText
          DisplayString (SIZE (0..20)),                
        cmcTcMasterTc5Unit2OutputStatus
          INTEGER,
        cmcTcMasterTc5Unit2OutputValue
          INTEGER,
        cmcTcMasterTc5Unit2OutputSet
          INTEGER,
        cmcTcMasterTc5Unit2OutputConfig
          INTEGER,                
        cmcTcMasterTc5Unit2OutputDelay
          INTEGER,
        cmcTcMasterTc5Unit2OutputTimeoutAction
          INTEGER
      }

    cmcTcMasterTc5Unit2OutputIndex OBJECT-TYPE
      SYNTAX INTEGER (1..32000)
      ACCESS read-only
      STATUS mandatory
      DESCRIPTION
        "Index for the list of output entries. Its value ranges
         between 1 and the value of cmcTcMasterTc5Unit2NumberOfOutputs." 
      ::= { cmcTcMasterTc5Unit2OutputEntry 1 }

    cmcTcMasterTc5Unit2OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 2 to output[cmcTcMasterTc5Unit2OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc5Unit2OutputEntry 2 }

        
    cmcTcMasterTc5Unit2OutputText OBJECT-TYPE
      SYNTAX DisplayString (SIZE (0..20))
      ACCESS read-write
      STATUS mandatory
      DESCRIPTION
        "Descriptional text for each output (entry in the table)"
      ::= { cmcTcMasterTc5Unit2OutputEntry 3 }
              
    cmcTcMasterTc5Unit2OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc5Unit2OutputEntry 4 }

    cmcTcMasterTc5Unit2OutputValue OBJECT-TYPE
      SYNTAX INTEGER (-32000..32000) 
      ACCESS read-write
      STATUS mandatory
      DESCRIPTION
        "Value for output"
      ::= { cmcTcMasterTc5Unit2OutputEntry 5 }

    cmcTcMasterTc5Unit2OutputSet OBJECT-TYPE
      SYNTAX INTEGER {
        off (1),
        on (2),
        lock (3),
        unlock (4),
        unlockDelay (5)
      }
      ACCESS read-write
      STATUS mandatory
      DESCRIPTION
        "Command for output"
      ::= { cmcTcMasterTc5Unit2OutputEntry 6 }

    cmcTcMasterTc5Unit2OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc5Unit2OutputEntry 7 }

    cmcTcMasterTc5Unit2OutputDelay OBJECT-TYPE
      SYNTAX INTEGER (0..999) 
      ACCESS read-write
      STATUS mandatory
      DESCRIPTION
        "Unsigned Value for delay, 
         after this time the output will fall into the previous state"
      ::= { cmcTcMasterTc5Unit2OutputEntry 8 }

    cmcTcMasterTc5Unit2OutputTimeoutAction OBJECT-TYPE
      SYNTAX INTEGER {
        stay (1),
        off (2),
        on (3)
      }
      ACCESS read-write
      STATUS mandatory
      DESCRIPTION
        "State for output if timeout (RS422) occurs"
      ::= { cmcTcMasterTc5Unit2OutputEntry 9 }

-- Messages
              
  cmcTcMasterTc5Unit2NumberOfMsgs OBJECT-TYPE
    SYNTAX INTEGER 
    ACCESS read-only
    STATUS mandatory
    DESCRIPTION
      "Number of messages that can be created with sensor unit 2"
    ::= { cmcTcMasterTc5StatusUnit2Msg 1 }

-- table with entry for each alarm available on this unit               
                
  cmcTcMasterTc5Unit2MsgTable OBJECT-TYPE
    SYNTAX SEQUENCE OF CmcTcMasterTc5Unit2MsgEntry
    ACCESS not-accessible
    STATUS mandatory
    DESCRIPTION
      "Headline of message table"
    ::= { cmcTcMasterTc5StatusUnit2Msg 2 }

  cmcTcMasterTc5Unit2MsgEntry OBJECT-TYPE
    SYNTAX CmcTcMasterTc5Unit2MsgEntry
    ACCESS not-accessible
    STATUS mandatory
    DESCRIPTION
      "Entries of message table"
    INDEX { cmcTcMasterTc5Unit2MsgIndex }
    ::= { cmcTcMasterTc5Unit2MsgTable 1 }

    CmcTcMasterTc5Unit2MsgEntry ::=
      SEQUENCE {
        cmcTcMasterTc5Unit2MsgIndex
          INTEGER,
        cmcTcMasterTc5Unit2MsgText
          DisplayString (SIZE (0..20)),
        cmcTcMasterTc5Unit2MsgStatus
          INTEGER, 
        cmcTcMasterTc5Unit2MsgRelay
          INTEGER,
        cmcTcMasterTc5Unit2MsgBeeper
          INTEGER,
        cmcTcMasterTc5Unit2MsgTrap1
          INTEGER,
        cmcTcMasterTc5Unit2MsgTrap2
          INTEGER,
        cmcTcMasterTc5Unit2MsgTrap3
          INTEGER,
        cmcTcMasterTc5Unit2MsgTrap4
          INTEGER,                 
        cmcTcMasterTc5Unit2MsgQuit
          INTEGER              
      }

    cmcTcMasterTc5Unit2MsgIndex OBJECT-TYPE
      SYNTAX INTEGER (1..32000)
      ACCESS read-only
      STATUS mandatory
      DESCRIPTION
        "Index for the list of message entries. Its value ranges
         between 1 and the value of cmcTcMasterTc5Unit2NumberOfMsgs." 
      ::= { cmcTcMasterTc5Unit2MsgEntry 1 }

    cmcTcMasterTc5Unit2MsgText OBJECT-TYPE
      SYNTAX DisplayString (SIZE (0..20))
      ACCESS read-write
      STATUS mandatory
      DESCRIPTION
        "Descriptional text for each message (entry in the table)"
      ::= { cmcTcMasterTc5Unit2MsgEntry 2 }

    cmcTcMasterTc5Unit2MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc5Unit2OutputSet)
         17: door is unlocked by WEB
         18: door is unlocked by timer
         19: no access, wrong keycode or cardnumber
         20: orientation of PSM-Unit is circuit 1
         21: orientation of PSM-Unit is circuit 2"
      ::= { cmcTcMasterTc5Unit2MsgEntry 3 }

    cmcTcMasterTc5Unit2MsgRelay OBJECT-TYPE
      SYNTAX INTEGER {
        disable (1),
        enable (2)
      }
      ACCESS read-write
      STATUS mandatory
      DESCRIPTION
        "Setup of Alarm relay for this alarm
         2:        no switching of alarm relay             
         1:        switching of alarm relay" 
      ::= { cmcTcMasterTc5Unit2MsgEntry 4 }

    cmcTcMasterTc5Unit2MsgBeeper OBJECT-TYPE
      SYNTAX INTEGER {
        disable (1),
        enable (2)
      }
      ACCESS read-write
      STATUS mandatory
      DESCRIPTION
        "Setup of Alarm beeper for this alarm
         2:        no audible alarm
         1:        audible alarm" 
      ::= { cmcTcMasterTc5Unit2MsgEntry 5 }

    cmcTcMasterTc5Unit2MsgTrap1 OBJECT-TYPE
      SYNTAX INTEGER {
        disable (1),
        enable (2)
      }
      ACCESS read-write
      STATUS mandatory
      DESCRIPTION
        "Trap receiver 1 activated"
      ::= { cmcTcMasterTc5Unit2MsgEntry 6 }

    cmcTcMasterTc5Unit2MsgTrap2 OBJECT-TYPE
      SYNTAX INTEGER {
        disable (1),
        enable (2)
      }
      ACCESS read-write
      STATUS mandatory
      DESCRIPTION
        "Trap receiver 2 activated"
      ::= { cmcTcMasterTc5Unit2MsgEntry 7 }
 
    cmcTcMasterTc5Unit2MsgTrap3 OBJECT-TYPE
      SYNTAX INTEGER {
        disable (1),
        enable (2)
      }
      ACCESS read-write
      STATUS mandatory
      DESCRIPTION
        "Trap receiver 3 activated"
      ::= { cmcTcMasterTc5Unit2MsgEntry 8 }

    cmcTcMasterTc5Unit2MsgTrap4 OBJECT-TYPE
      SYNTAX INTEGER {
        disable (1),
        enable (2)
      }
      ACCESS read-write
      STATUS mandatory
      DESCRIPTION
        "Trap receiver 4 and Event Logging activated"
      ::= { cmcTcMasterTc5Unit2MsgEntry 9 }

    cmcTcMasterTc5Unit2MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc5Unit2MsgEntry 10 }

-- unit 3
  cmcTcMasterTc5Unit3TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 3"
    ::= { cmcTcMasterTc5StatusSensorUnit3 1 }

  cmcTcMasterTc5Unit3Text OBJECT-TYPE
    SYNTAX DisplayString (SIZE (0..10))
    ACCESS read-write
    STATUS mandatory
    DESCRIPTION
      "Descriptional text for sensor unit connected to port 3"
    ::= { cmcTcMasterTc5StatusSensorUnit3 2 }

  cmcTcMasterTc5Unit3Serial OBJECT-TYPE
    SYNTAX INTEGER 
    ACCESS  read-only
    STATUS  mandatory
    DESCRIPTION
      "Serialnumber of sensor unit connected to port 3"
    ::= { cmcTcMasterTc5StatusSensorUnit3 3 }

  cmcTcMasterTc5Unit3Status OBJECT-TYPE
    SYNTAX INTEGER {
      ok(1),
      error(2),
      changed(3),
      quit(4),
      timeout(5),
      detected(6),
      notAvail(7),
      lowPower(8)
    }
    ACCESS  read-only
    STATUS  mandatory
    DESCRIPTION
      "General Status sensor unit connected to port 3
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc5StatusSensorUnit3 4 }

-- Sensors              

  cmcTcMasterTc5Unit3NumberOfSensors OBJECT-TYPE
    SYNTAX INTEGER 
    ACCESS read-only
    STATUS mandatory
    DESCRIPTION
      "Number of sensors connected to sensor unit 3"
    ::= { cmcTcMasterTc5StatusUnit3Sensors 1 }

-- table with entry for each sensor available on this unit              
        
  cmcTcMasterTc5Unit3SensorTable OBJECT-TYPE
    SYNTAX SEQUENCE OF CmcTcMasterTc5Unit3SensorEntry
    ACCESS not-accessible
    STATUS mandatory
    DESCRIPTION
      "Headline of sensor table"
    ::= { cmcTcMasterTc5StatusUnit3Sensors 2 }

  cmcTcMasterTc5Unit3SensorEntry OBJECT-TYPE
    SYNTAX CmcTcMasterTc5Unit3SensorEntry
    ACCESS not-accessible
    STATUS mandatory
    DESCRIPTION
      "Entries of sensor table"
    INDEX { cmcTcMasterTc5Unit3SensorIndex }
    ::= { cmcTcMasterTc5Unit3SensorTable 1 }

    CmcTcMasterTc5Unit3SensorEntry ::=
      SEQUENCE {
        cmcTcMasterTc5Unit3SensorIndex
          INTEGER,
        cmcTcMasterTc5Unit3SensorType
          INTEGER,
        cmcTcMasterTc5Unit3SensorText
          DisplayString (SIZE (0..20)),                
        cmcTcMasterTc5Unit3SensorStatus
          INTEGER,
        cmcTcMasterTc5Unit3SensorValue
          INTEGER,
        cmcTcMasterTc5Unit3SensorSetHigh
          INTEGER,
        cmcTcMasterTc5Unit3SensorSetLow
          INTEGER,                 
        cmcTcMasterTc5Unit3SensorSetWarn
          INTEGER  
      }

    cmcTcMasterTc5Unit3SensorIndex OBJECT-TYPE
      SYNTAX INTEGER (1..32000)
      ACCESS read-only
      STATUS mandatory
      DESCRIPTION
        "Index for the list of value entries. Its value ranges
         between 1 and the value of cmcTcMasterTc5Unit3NumberOfSensors." 
      ::= { cmcTcMasterTc5Unit3SensorEntry 1 }

    cmcTcMasterTc5Unit3SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 3 to sensor[cmcTcMasterTc5Unit3SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc5Unit3SensorEntry 2 }

    cmcTcMasterTc5Unit3SensorText OBJECT-TYPE
      SYNTAX DisplayString (SIZE (0..20))
      ACCESS read-write
      STATUS mandatory
      DESCRIPTION
        "Descriptional text for each sensor (entry in the table)"
      ::= { cmcTcMasterTc5Unit3SensorEntry 3 }
              
    cmcTcMasterTc5Unit3SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc5Unit3SensorEntry 4 }

    cmcTcMasterTc5Unit3SensorValue OBJECT-TYPE
      SYNTAX INTEGER 
      ACCESS read-only
      STATUS mandatory
      DESCRIPTION
        "Value of sensor"
      ::= { cmcTcMasterTc5Unit3SensorEntry 5 }

    cmcTcMasterTc5Unit3SensorSetHigh OBJECT-TYPE
      SYNTAX INTEGER (0..300) 
      ACCESS read-write
      STATUS mandatory
      DESCRIPTION
        "Value for high setpoint of sensor"
      ::= { cmcTcMasterTc5Unit3SensorEntry 6 }

    cmcTcMasterTc5Unit3SensorSetLow OBJECT-TYPE
      SYNTAX INTEGER (0..300) 
      ACCESS read-write
      STATUS mandatory
      DESCRIPTION
        "Value for low setpoint of sensor,
         also used as alarm delay"
      ::= { cmcTcMasterTc5Unit3SensorEntry 7 }

    cmcTcMasterTc5Unit3SensorSetWarn OBJECT-TYPE
      SYNTAX INTEGER (0..300) 
      ACCESS read-write
      STATUS mandatory
      DESCRIPTION
        "Value for warning setpoint of sensor,
         also used as fan threshold"
      ::= { cmcTcMasterTc5Unit3SensorEntry 8 }
                
-- Outputs              

  cmcTcMasterTc5Unit3NumberOfOutputs OBJECT-TYPE
    SYNTAX INTEGER 
    ACCESS read-only
    STATUS mandatory
    DESCRIPTION
      "Number of outputs available on sensor unit 3"
    ::= { cmcTcMasterTc5StatusUnit3Outputs 1 }

-- table with entry for each output available on this unit              
                
  cmcTcMasterTc5Unit3OutputTable OBJECT-TYPE
    SYNTAX SEQUENCE OF CmcTcMasterTc5Unit3OutputEntry
    ACCESS not-accessible
    STATUS mandatory
    DESCRIPTION
      "Headline of output table"
    ::= { cmcTcMasterTc5StatusUnit3Outputs 2 }

  cmcTcMasterTc5Unit3OutputEntry OBJECT-TYPE
    SYNTAX CmcTcMasterTc5Unit3OutputEntry
    ACCESS not-accessible
    STATUS mandatory
    DESCRIPTION
      "Entries of output table"
    INDEX { cmcTcMasterTc5Unit3OutputIndex }
    ::= { cmcTcMasterTc5Unit3OutputTable 1 }

    CmcTcMasterTc5Unit3OutputEntry ::=
      SEQUENCE {
        cmcTcMasterTc5Unit3OutputIndex
          INTEGER,
        cmcTcMasterTc5Unit3OutputType
          INTEGER,
        cmcTcMasterTc5Unit3OutputText
          DisplayString (SIZE (0..20)),                
        cmcTcMasterTc5Unit3OutputStatus
          INTEGER,
        cmcTcMasterTc5Unit3OutputValue
          INTEGER,
        cmcTcMasterTc5Unit3OutputSet
          INTEGER,
        cmcTcMasterTc5Unit3OutputConfig
          INTEGER,
        cmcTcMasterTc5Unit3OutputDelay
          INTEGER,
        cmcTcMasterTc5Unit3OutputTimeoutAction
          INTEGER
      }

    cmcTcMasterTc5Unit3OutputIndex OBJECT-TYPE
      SYNTAX INTEGER (1..32000)
      ACCESS read-only
      STATUS mandatory
      DESCRIPTION
        "Index for the list of output entries. Its value ranges
         between 1 and the value of cmcTcMasterTc5Unit3NumberOfOutputs." 
      ::= { cmcTcMasterTc5Unit3OutputEntry 1 }

    cmcTcMasterTc5Unit3OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 3 to output[cmcTcMasterTc5Unit3OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc5Unit3OutputEntry 2 }

        
    cmcTcMasterTc5Unit3OutputText OBJECT-TYPE
      SYNTAX DisplayString (SIZE (0..20))
      ACCESS read-write
      STATUS mandatory
      DESCRIPTION
        "Descriptional text for each output (entry in the table)"
      ::= { cmcTcMasterTc5Unit3OutputEntry 3 }
              
    cmcTcMasterTc5Unit3OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc5Unit3OutputEntry 4 }

    cmcTcMasterTc5Unit3OutputValue OBJECT-TYPE
      SYNTAX INTEGER (-32000..32000) 
      ACCESS read-write
      STATUS mandatory
      DESCRIPTION
        "Value for output"
      ::= { cmcTcMasterTc5Unit3OutputEntry 5 }

    cmcTcMasterTc5Unit3OutputSet OBJECT-TYPE
      SYNTAX INTEGER {
        off (1),
        on (2),
        lock (3),
        unlock (4),
        unlockDelay (5)
      }
      ACCESS read-write
      STATUS mandatory
      DESCRIPTION
        "Command for output"
      ::= { cmcTcMasterTc5Unit3OutputEntry 6 }

    cmcTcMasterTc5Unit3OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc5Unit3OutputEntry 7 }

    cmcTcMasterTc5Unit3OutputDelay OBJECT-TYPE
      SYNTAX INTEGER (0..999) 
      ACCESS read-write
      STATUS mandatory
      DESCRIPTION
        "Unsigned Value for delay, 
         after this time the output will fall into the previous state"
      ::= { cmcTcMasterTc5Unit3OutputEntry 8 }

    cmcTcMasterTc5Unit3OutputTimeoutAction OBJECT-TYPE
      SYNTAX INTEGER {
        stay (1),
        off (2),
        on (3)
      }
      ACCESS read-write
      STATUS mandatory
      DESCRIPTION
        "State for output if timeout (RS422) occurs"
      ::= { cmcTcMasterTc5Unit3OutputEntry 9 }

-- Messages
              
  cmcTcMasterTc5Unit3NumberOfMsgs OBJECT-TYPE
    SYNTAX INTEGER 
    ACCESS read-only
    STATUS mandatory
    DESCRIPTION
      "Number of messages that can be created with sensor unit 3"
    ::= { cmcTcMasterTc5StatusUnit3Msg 1 }

-- table with entry for each alarm available on this unit               
                
  cmcTcMasterTc5Unit3MsgTable OBJECT-TYPE
    SYNTAX SEQUENCE OF CmcTcMasterTc5Unit3MsgEntry
    ACCESS not-accessible
    STATUS mandatory
    DESCRIPTION
      "Headline of message table"
    ::= { cmcTcMasterTc5StatusUnit3Msg 2 }

  cmcTcMasterTc5Unit3MsgEntry OBJECT-TYPE
    SYNTAX CmcTcMasterTc5Unit3MsgEntry
    ACCESS not-accessible
    STATUS mandatory
    DESCRIPTION
      "Entries of message table"
    INDEX { cmcTcMasterTc5Unit3MsgIndex }
    ::= { cmcTcMasterTc5Unit3MsgTable 1 }

    CmcTcMasterTc5Unit3MsgEntry ::=
      SEQUENCE {
        cmcTcMasterTc5Unit3MsgIndex
          INTEGER,
        cmcTcMasterTc5Unit3MsgText
          DisplayString (SIZE (0..20)),
        cmcTcMasterTc5Unit3MsgStatus
          INTEGER, 
        cmcTcMasterTc5Unit3MsgRelay
          INTEGER,
        cmcTcMasterTc5Unit3MsgBeeper
          INTEGER,
        cmcTcMasterTc5Unit3MsgTrap1
          INTEGER,
        cmcTcMasterTc5Unit3MsgTrap2
          INTEGER,
        cmcTcMasterTc5Unit3MsgTrap3
          INTEGER,
        cmcTcMasterTc5Unit3MsgTrap4
          INTEGER,                 
        cmcTcMasterTc5Unit3MsgQuit
          INTEGER              
      }

    cmcTcMasterTc5Unit3MsgIndex OBJECT-TYPE
      SYNTAX INTEGER (1..32000)
      ACCESS read-only
      STATUS mandatory
      DESCRIPTION
        "Index for the list of message entries. Its value ranges
         between 1 and the value of cmcTcMasterTc5Unit3NumberOfMsgs." 
      ::= { cmcTcMasterTc5Unit3MsgEntry 1 }

    cmcTcMasterTc5Unit3MsgText OBJECT-TYPE
      SYNTAX DisplayString (SIZE (0..20))
      ACCESS read-write
      STATUS mandatory
      DESCRIPTION
        "Descriptional text for each message (entry in the table)"
      ::= { cmcTcMasterTc5Unit3MsgEntry 2 }

    cmcTcMasterTc5Unit3MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc5Unit3OutputSet)
         17: door is unlocked by WEB
         18: door is unlocked by timer
         19: no access, wrong keycode or cardnumber
         20: orientation of PSM-Unit is circuit 1
         21: orientation of PSM-Unit is circuit 2"
      ::= { cmcTcMasterTc5Unit3MsgEntry 3 }

    cmcTcMasterTc5Unit3MsgRelay OBJECT-TYPE
      SYNTAX INTEGER {
        disable (1),
        enable (2)
      }
      ACCESS read-write
      STATUS mandatory
      DESCRIPTION
        "Setup of Alarm relay for this alarm
         1:        no switching of alarm relay             
         2:        switching of alarm relay" 
      ::= { cmcTcMasterTc5Unit3MsgEntry 4 }

    cmcTcMasterTc5Unit3MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc5Unit3MsgEntry 5 }

    cmcTcMasterTc5Unit3MsgTrap1 OBJECT-TYPE
      SYNTAX INTEGER {
        disable (1),
        enable (2)
      }
      ACCESS read-write
      STATUS mandatory
      DESCRIPTION
        "Trap receiver 1 activated"
      ::= { cmcTcMasterTc5Unit3MsgEntry 6 }

    cmcTcMasterTc5Unit3MsgTrap2 OBJECT-TYPE
      SYNTAX INTEGER {
        disable (1),
        enable (2)
      }
      ACCESS read-write
      STATUS mandatory
      DESCRIPTION
        "Trap receiver 2 activated"
      ::= { cmcTcMasterTc5Unit3MsgEntry 7 }
 
    cmcTcMasterTc5Unit3MsgTrap3 OBJECT-TYPE
      SYNTAX INTEGER {
        disable (1),
        enable (2)
      }
      ACCESS read-write
      STATUS mandatory
      DESCRIPTION
        "Trap receiver 3 activated"
      ::= { cmcTcMasterTc5Unit3MsgEntry 8 }

    cmcTcMasterTc5Unit3MsgTrap4 OBJECT-TYPE
      SYNTAX INTEGER {
        disable (1),
        enable (2)
      }
      ACCESS read-write
      STATUS mandatory
      DESCRIPTION
        "Trap receiver 4 and Event Logging activated"
      ::= { cmcTcMasterTc5Unit3MsgEntry 9 }

    cmcTcMasterTc5Unit3MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc5Unit3MsgEntry 10 }

-- unit4

  cmcTcMasterTc5Unit4TypeOfDevice OBJECT-TYPE
    SYNTAX INTEGER {
      notAvail (1),
      unitIO (2),
      unitAccess (3),
      unitClimate (4),
      unitFCS (5),
      unitRTT (6),
      unitRLCP (7),
      unitPSM (8)
    }
    ACCESS  read-only
    STATUS  mandatory
    DESCRIPTION
      "Type of sensor unit connected to port 4"
    ::= { cmcTcMasterTc5StatusSensorUnit4 1 }

  cmcTcMasterTc5Unit4Text OBJECT-TYPE
    SYNTAX DisplayString (SIZE (0..10))
    ACCESS read-write
    STATUS mandatory
    DESCRIPTION
      "Descriptional text for sensor unit connected to port 4"
    ::= { cmcTcMasterTc5StatusSensorUnit4 2 }

  cmcTcMasterTc5Unit4Serial OBJECT-TYPE
    SYNTAX INTEGER 
    ACCESS read-only
    STATUS mandatory
    DESCRIPTION
      "Serialnumber of sensor unit connected to port 4"
    ::= { cmcTcMasterTc5StatusSensorUnit4 3 }

  cmcTcMasterTc5Unit4Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 4
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc5StatusSensorUnit4 4 }

-- Sensors
              
  cmcTcMasterTc5Unit4NumberOfSensors OBJECT-TYPE
    SYNTAX INTEGER 
    ACCESS read-only
    STATUS mandatory
    DESCRIPTION
      "Number of sensors connected to sensor unit 4"
    ::= { cmcTcMasterTc5StatusUnit4Sensors 1 }

-- table with entry for each sensor available on this unit              
                
  cmcTcMasterTc5Unit4SensorTable OBJECT-TYPE
    SYNTAX SEQUENCE OF CmcTcMasterTc5Unit4SensorEntry
    ACCESS not-accessible
    STATUS mandatory
    DESCRIPTION
      "Headline of sensor table"
    ::= { cmcTcMasterTc5StatusUnit4Sensors 2 }

  cmcTcMasterTc5Unit4SensorEntry OBJECT-TYPE
    SYNTAX CmcTcMasterTc5Unit4SensorEntry
    ACCESS not-accessible
    STATUS mandatory
    DESCRIPTION
      "Entries of sensor table"
    INDEX { cmcTcMasterTc5Unit4SensorIndex }
    ::= { cmcTcMasterTc5Unit4SensorTable 1 }

    CmcTcMasterTc5Unit4SensorEntry ::=
      SEQUENCE {
        cmcTcMasterTc5Unit4SensorIndex
          INTEGER,
        cmcTcMasterTc5Unit4SensorType
          INTEGER,
        cmcTcMasterTc5Unit4SensorText
          DisplayString (SIZE (0..20)),                
        cmcTcMasterTc5Unit4SensorStatus
          INTEGER,
        cmcTcMasterTc5Unit4SensorValue
          INTEGER,
        cmcTcMasterTc5Unit4SensorSetHigh
          INTEGER,
        cmcTcMasterTc5Unit4SensorSetLow
          INTEGER,                 
        cmcTcMasterTc5Unit4SensorSetWarn
          INTEGER  
      }

    cmcTcMasterTc5Unit4SensorIndex OBJECT-TYPE
      SYNTAX INTEGER (1..32000)
      ACCESS read-only
      STATUS mandatory
      DESCRIPTION
        "Index for the list of value entries. Its value ranges
         between 1 and the value of cmcTcMasterTc5Unit4NumberOfSensors." 
      ::= { cmcTcMasterTc5Unit4SensorEntry 1 }

    cmcTcMasterTc5Unit4SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 4 to sensor[cmcTcMasterTc5Unit4SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc5Unit4SensorEntry 2 }

    cmcTcMasterTc5Unit4SensorText OBJECT-TYPE
      SYNTAX DisplayString (SIZE (0..20))
      ACCESS read-write
      STATUS mandatory
      DESCRIPTION
        "Descriptional text for each sensor (entry in the table)"
      ::= { cmcTcMasterTc5Unit4SensorEntry 3 }
              
    cmcTcMasterTc5Unit4SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc5Unit4SensorEntry 4 }

    cmcTcMasterTc5Unit4SensorValue OBJECT-TYPE
      SYNTAX INTEGER 
      ACCESS read-only
      STATUS mandatory
      DESCRIPTION
        "Value of sensor"
      ::= { cmcTcMasterTc5Unit4SensorEntry 5 }

    cmcTcMasterTc5Unit4SensorSetHigh OBJECT-TYPE
      SYNTAX INTEGER (0..300) 
      ACCESS read-write
      STATUS mandatory
      DESCRIPTION
        "Value for high setpoint of sensor"
      ::= { cmcTcMasterTc5Unit4SensorEntry 6 }

    cmcTcMasterTc5Unit4SensorSetLow OBJECT-TYPE
      SYNTAX INTEGER (0..300) 
      ACCESS read-write
      STATUS mandatory
      DESCRIPTION
        "Value for low setpoint of sensor,
         also used as alarm delay"
      ::= { cmcTcMasterTc5Unit4SensorEntry 7 }

    cmcTcMasterTc5Unit4SensorSetWarn OBJECT-TYPE
      SYNTAX INTEGER (0..300) 
      ACCESS read-write
      STATUS mandatory
      DESCRIPTION
        "Value for warning setpoint of sensor,
         also used as fan threshold"
      ::= { cmcTcMasterTc5Unit4SensorEntry 8 }

-- Outputs              

  cmcTcMasterTc5Unit4NumberOfOutputs OBJECT-TYPE
    SYNTAX INTEGER 
    ACCESS read-only
    STATUS mandatory
    DESCRIPTION
      "Number of outputs available on sensor unit 4"
    ::= { cmcTcMasterTc5StatusUnit4Outputs 1 }

-- table with entry for each output available on this unit              
                
  cmcTcMasterTc5Unit4OutputTable OBJECT-TYPE
    SYNTAX SEQUENCE OF CmcTcMasterTc5Unit4OutputEntry
    ACCESS not-accessible
    STATUS mandatory
    DESCRIPTION
      "Headline of output table"
    ::= { cmcTcMasterTc5StatusUnit4Outputs 2 }

  cmcTcMasterTc5Unit4OutputEntry OBJECT-TYPE
    SYNTAX CmcTcMasterTc5Unit4OutputEntry
    ACCESS not-accessible
    STATUS mandatory
    DESCRIPTION
      "Entries of output table"
    INDEX { cmcTcMasterTc5Unit4OutputIndex }
    ::= { cmcTcMasterTc5Unit4OutputTable 1 }

    CmcTcMasterTc5Unit4OutputEntry ::=
      SEQUENCE {
        cmcTcMasterTc5Unit4OutputIndex
          INTEGER,
        cmcTcMasterTc5Unit4OutputType
          INTEGER,
        cmcTcMasterTc5Unit4OutputText
          DisplayString (SIZE (0..20)),                
        cmcTcMasterTc5Unit4OutputStatus
          INTEGER,
        cmcTcMasterTc5Unit4OutputValue
          INTEGER,
        cmcTcMasterTc5Unit4OutputSet
          INTEGER,
        cmcTcMasterTc5Unit4OutputConfig
          INTEGER,
        cmcTcMasterTc5Unit4OutputDelay
          INTEGER,
        cmcTcMasterTc5Unit4OutputTimeoutAction
          INTEGER
      }

    cmcTcMasterTc5Unit4OutputIndex OBJECT-TYPE
      SYNTAX INTEGER (1..32000)
      ACCESS read-only
      STATUS mandatory
      DESCRIPTION
        "Index for the list of output entries. Its value ranges
         between 1 and the value of cmcTcMasterTc5Unit4NumberOfOutputs." 
      ::= { cmcTcMasterTc5Unit4OutputEntry 1 }

    cmcTcMasterTc5Unit4OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 4 to output[cmcTcMasterTc5Unit4OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc5Unit4OutputEntry 2 }

    cmcTcMasterTc5Unit4OutputText OBJECT-TYPE
      SYNTAX DisplayString (SIZE (0..20))
      ACCESS read-write
      STATUS mandatory
      DESCRIPTION
        "Descriptional text for each output (entry in the table)"
      ::= { cmcTcMasterTc5Unit4OutputEntry 3 }
              
    cmcTcMasterTc5Unit4OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc5Unit4OutputEntry 4 }

    cmcTcMasterTc5Unit4OutputValue OBJECT-TYPE
      SYNTAX INTEGER (-32000..32000) 
      ACCESS read-write
      STATUS mandatory
      DESCRIPTION
        "Value for output"
      ::= { cmcTcMasterTc5Unit4OutputEntry 5 }

    cmcTcMasterTc5Unit4OutputSet OBJECT-TYPE
      SYNTAX INTEGER {
        off (1),
        on (2),
        lock (3),
        unlock (4),
        unlockDelay (5)
      }
      ACCESS read-write
      STATUS mandatory
      DESCRIPTION
        "Command for output"
      ::= { cmcTcMasterTc5Unit4OutputEntry 6 }

    cmcTcMasterTc5Unit4OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc5Unit4OutputEntry 7 }

    cmcTcMasterTc5Unit4OutputDelay OBJECT-TYPE
      SYNTAX INTEGER (0..999) 
      ACCESS read-write
      STATUS mandatory
      DESCRIPTION
        "Unsigned Value for delay, 
         after this time the output will fall into the previous state"
      ::= { cmcTcMasterTc5Unit4OutputEntry 8 }

    cmcTcMasterTc5Unit4OutputTimeoutAction OBJECT-TYPE
      SYNTAX INTEGER {
        stay (1),
        off (2),
        on (3)
      }
      ACCESS read-write
      STATUS mandatory
      DESCRIPTION
        "State for output if timeout (RS422) occurs"
      ::= { cmcTcMasterTc5Unit4OutputEntry 9 }

-- Messages
              
  cmcTcMasterTc5Unit4NumberOfMsgs OBJECT-TYPE
    SYNTAX INTEGER 
    ACCESS read-only
    STATUS mandatory
    DESCRIPTION
      "Number of messages that can be created with sensor unit 4"
    ::= { cmcTcMasterTc5StatusUnit4Msg 1 }

-- table with entry for each alarm available on this unit               
                
  cmcTcMasterTc5Unit4MsgTable OBJECT-TYPE
    SYNTAX SEQUENCE OF CmcTcMasterTc5Unit4MsgEntry
    ACCESS not-accessible
    STATUS mandatory
    DESCRIPTION
      "Headline of message table"
    ::= { cmcTcMasterTc5StatusUnit4Msg 2 }

  cmcTcMasterTc5Unit4MsgEntry OBJECT-TYPE
    SYNTAX CmcTcMasterTc5Unit4MsgEntry
    ACCESS not-accessible
    STATUS mandatory
    DESCRIPTION
      "Entries of message table"
    INDEX { cmcTcMasterTc5Unit4MsgIndex }
    ::= { cmcTcMasterTc5Unit4MsgTable 1 }

    CmcTcMasterTc5Unit4MsgEntry ::=
      SEQUENCE {
        cmcTcMasterTc5Unit4MsgIndex
          INTEGER,
        cmcTcMasterTc5Unit4MsgText
          DisplayString (SIZE (0..20)),                
        cmcTcMasterTc5Unit4MsgStatus
          INTEGER, 
        cmcTcMasterTc5Unit4MsgRelay
          INTEGER,
        cmcTcMasterTc5Unit4MsgBeeper
          INTEGER,
        cmcTcMasterTc5Unit4MsgTrap1
          INTEGER,
        cmcTcMasterTc5Unit4MsgTrap2
          INTEGER,
        cmcTcMasterTc5Unit4MsgTrap3
          INTEGER,
        cmcTcMasterTc5Unit4MsgTrap4
          INTEGER,                 
        cmcTcMasterTc5Unit4MsgQuit
          INTEGER              
      }

    cmcTcMasterTc5Unit4MsgIndex OBJECT-TYPE
      SYNTAX INTEGER (1..32000)
      ACCESS read-only
      STATUS mandatory
      DESCRIPTION
        "Index for the list of message entries. Its value ranges
         between 1 and the value of cmcTcMasterTc5Unit4NumberOfMsgs." 
      ::= { cmcTcMasterTc5Unit4MsgEntry 1 }

    cmcTcMasterTc5Unit4MsgText OBJECT-TYPE
      SYNTAX DisplayString (SIZE (0..20))
      ACCESS read-write
      STATUS mandatory
      DESCRIPTION
        "Descriptional text for each message (entry in the table)"
      ::= { cmcTcMasterTc5Unit4MsgEntry 2 }

    cmcTcMasterTc5Unit4MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc5Unit4OutputSet)
         17: door is unlocked by WEB
         18: door is unlocked by timer
         19: no access, wrong keycode or cardnumber
         20: orientation of PSM-Unit is circuit 1
         21: orientation of PSM-Unit is circuit 2"
      ::= { cmcTcMasterTc5Unit4MsgEntry 3 }

    cmcTcMasterTc5Unit4MsgRelay OBJECT-TYPE
      SYNTAX INTEGER {
        disable (1),
        enable (2)
      }
      ACCESS read-write
      STATUS mandatory
      DESCRIPTION
        "Setup of Alarm relay for this alarm
         1:        no switching of alarm relay             
         2:        switching of alarm relay" 
      ::= { cmcTcMasterTc5Unit4MsgEntry 4 }

    cmcTcMasterTc5Unit4MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc5Unit4MsgEntry 5 }

    cmcTcMasterTc5Unit4MsgTrap1 OBJECT-TYPE
      SYNTAX INTEGER {
        disable (1),
        enable (2)
      }
      ACCESS read-write
      STATUS mandatory
      DESCRIPTION
        "Trap receiver 1 activated"
      ::= { cmcTcMasterTc5Unit4MsgEntry 6 }

    cmcTcMasterTc5Unit4MsgTrap2 OBJECT-TYPE
      SYNTAX INTEGER {
        disable (1),
        enable (2)
      }
      ACCESS read-write
      STATUS mandatory
      DESCRIPTION
        "Trap receiver 2 activated"
      ::= { cmcTcMasterTc5Unit4MsgEntry 7 }
 
    cmcTcMasterTc5Unit4MsgTrap3 OBJECT-TYPE
      SYNTAX INTEGER {
        disable (1),
        enable (2)
      }
      ACCESS read-write
      STATUS mandatory
      DESCRIPTION
        "Trap receiver 3 activated"
      ::= { cmcTcMasterTc5Unit4MsgEntry 8 }

    cmcTcMasterTc5Unit4MsgTrap4 OBJECT-TYPE
      SYNTAX INTEGER {
        disable (1),
        enable (2)
      }
      ACCESS read-write
      STATUS mandatory
      DESCRIPTION
        "Trap receiver 4 and Event Logging activated"
      ::= { cmcTcMasterTc5Unit4MsgEntry 9 }

    cmcTcMasterTc5Unit4MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc5Unit4MsgEntry 10 }

--Status extension unit

  cmcTcMasterTc5ValuesRelay OBJECT-TYPE
    SYNTAX INTEGER {
      disable (1),
      enable (2)
    }
    ACCESS read-write
    STATUS mandatory
    DESCRIPTION
      "Setup of Alarm relay for alarm ext. unit(s)
       1:        no switching of alarm relay             
       2:        switching of alarm relay" 
    ::= { cmcTcMasterTc5StatusExtUnit 1 }

  cmcTcMasterTc5ValuesBeeper OBJECT-TYPE
    SYNTAX INTEGER {
      disable (1),
      enable (2)
    }
    ACCESS read-write
    STATUS mandatory
    DESCRIPTION
      "Setup of Alarm beeper for alarm ext. unit(s)
       1:        no audible alarm
       2:        audible alarm" 
    ::= { cmcTcMasterTc5StatusExtUnit 2 }

  cmcTcMasterTc5ValuesTrap1 OBJECT-TYPE
    SYNTAX INTEGER {
      disable (1),
      enable (2)
    }
    ACCESS read-write
    STATUS mandatory
    DESCRIPTION
      "Trap receiver 1 activated"
    ::= { cmcTcMasterTc5StatusExtUnit 3 }

  cmcTcMasterTc5ValuesTrap2 OBJECT-TYPE
    SYNTAX INTEGER {
      disable (1),
      enable (2)
    }
    ACCESS read-write
    STATUS mandatory
    DESCRIPTION
      "Trap receiver 2 activated"
    ::= { cmcTcMasterTc5StatusExtUnit 4 }
 
  cmcTcMasterTc5ValuesTrap3 OBJECT-TYPE
    SYNTAX INTEGER {
      disable (1),
      enable (2)
    }
    ACCESS read-write
    STATUS mandatory
    DESCRIPTION
      "Trap receiver 3 activated"
    ::= { cmcTcMasterTc5StatusExtUnit 5 }

  cmcTcMasterTc5ValuesTrap4 OBJECT-TYPE
    SYNTAX INTEGER {
      disable (1),
      enable (2)
    }
    ACCESS read-write
    STATUS mandatory
    DESCRIPTION
      "Trap receiver 4 and Event Logging activated"
    ::= { cmcTcMasterTc5StatusExtUnit 6 }
 
  cmcTcMasterTc5NumberOfValues OBJECT-TYPE
    SYNTAX INTEGER 
    ACCESS  read-only
    STATUS  mandatory
    DESCRIPTION
      "Number of values availabel on extension units connected to the CMC-TC"
    ::= { cmcTcMasterTc5StatusExtUnit 7 }

-- table with entry for each value available on extension units              

  cmcTcMasterTc5ValuesTable OBJECT-TYPE
    SYNTAX SEQUENCE OF CmcTcMasterTc5ValuesEntry
    ACCESS not-accessible
    STATUS mandatory
    DESCRIPTION
      "Headline of values-table"
    ::= { cmcTcMasterTc5StatusExtUnit 8 }

  cmcTcMasterTc5ValuesEntry OBJECT-TYPE
    SYNTAX CmcTcMasterTc5ValuesEntry
    ACCESS not-accessible
    STATUS mandatory
    DESCRIPTION
      "Entries of values-table"
    INDEX { cmcTcMasterTc5ValuesIndex }
    ::= { cmcTcMasterTc5ValuesTable 1 }

    CmcTcMasterTc5ValuesEntry ::=
      SEQUENCE {
        cmcTcMasterTc5ValuesIndex
          INTEGER,
        cmcTcMasterTc5ValuesText
          DisplayString (SIZE (0..20)),                
        cmcTcMasterTc5ValuesStatus
          INTEGER,
        cmcTcMasterTc5ValuesValue
          INTEGER,
        cmcTcMasterTc5ValuesSetHigh
          INTEGER,
        cmcTcMasterTc5ValuesSetLow
          INTEGER
      }

    cmcTcMasterTc5ValuesIndex OBJECT-TYPE
      SYNTAX INTEGER (1..32000)
      ACCESS read-only
      STATUS mandatory
      DESCRIPTION
        "Index for the list of value entries. Its value ranges
         between 1 and the value of cmcTcMasterTc5NumberOfValues." 
      ::= { cmcTcMasterTc5ValuesEntry 1 }

        
    cmcTcMasterTc5ValuesText OBJECT-TYPE
      SYNTAX DisplayString (SIZE (0..20))
      ACCESS read-write
      STATUS mandatory
      DESCRIPTION
        "Descriptional text for each value (entry in the table)
         of the extension card"
      ::= { cmcTcMasterTc5ValuesEntry 2 }
              
    cmcTcMasterTc5ValuesStatus OBJECT-TYPE
      SYNTAX INTEGER {
        notAvail(1),
        lost(2),
        changed(3),
        ok(4),
        tooLow(5),
        tooHigh(6),
        error(7)
      }
      ACCESS read-only
      STATUS mandatory
      DESCRIPTION
        "Actual status of the value of the extension card"
      ::= { cmcTcMasterTc5ValuesEntry 3 }

    cmcTcMasterTc5ValuesValue OBJECT-TYPE
      SYNTAX INTEGER 
      ACCESS read-only
      STATUS mandatory
      DESCRIPTION
        "Value of sensor"
      ::= { cmcTcMasterTc5ValuesEntry 4 }

    cmcTcMasterTc5ValuesSetHigh OBJECT-TYPE
      SYNTAX INTEGER (0..255) 
      ACCESS read-write
      STATUS mandatory
      DESCRIPTION
        "Value for high setpoint of sensor"
      ::= { cmcTcMasterTc5ValuesEntry 5 }

    cmcTcMasterTc5ValuesSetLow OBJECT-TYPE
      SYNTAX INTEGER (0..255) 
      ACCESS read-write
      STATUS mandatory
      DESCRIPTION
        "Value for low setpoint of sensor"
      ::= { cmcTcMasterTc5ValuesEntry 6 }

--cmcTcMasterTc5SetupGeneral-group

  cmcTcMasterTc5SetTempUnit OBJECT-TYPE
    SYNTAX INTEGER {
      celsius(1),
      fahrenheit(2)
    }
    ACCESS read-write
    STATUS mandatory
    DESCRIPTION
      "Unit of all temperature values and setpoints, Celsius or Fahrenheit"
   ::= { cmcTcMasterTc5SetupGeneral 1 }

  cmcTcMasterTc5SetBeeper OBJECT-TYPE
    SYNTAX INTEGER {
      off(1),
      on(2)
    }
    ACCESS read-write
    STATUS mandatory
    DESCRIPTION
      "Audible alarm in CMC-TC unit:
       (2): beeper is on
       (1): beeper is off (general)"
    ::= { cmcTcMasterTc5SetupGeneral 2 }


  cmcTcMasterTc5QuitRelay OBJECT-TYPE
    SYNTAX INTEGER {
      disabled(1),
      enabled(2)
    }
    ACCESS read-write
    STATUS mandatory
    DESCRIPTION
      "Enable or disable acknowledging currently active alarm relay 
       (with 'C' on CMC-TC)."
    ::= { cmcTcMasterTc5SetupGeneral 3 }

  cmcTcMasterTc5LogicRelay OBJECT-TYPE
    SYNTAX INTEGER {
      closeAtAlarm(1),
      openAtAlarm(2),
      off(3)
    }
    ACCESS read-write
    STATUS mandatory
    DESCRIPTION
      "Logic of alarm relay: 
       (1) Relay will pick up in case of an alarm
       (2) Relay will release in case of an alarm
       (3) Relay off (general)"
    ::= { cmcTcMasterTc5SetupGeneral 4 }

  cmcTcMasterTc5WebAccess OBJECT-TYPE
    SYNTAX INTEGER {
      viewOnly(1),
      fullAccess(2),
      off(3)
    }
    ACCESS read-write
    STATUS mandatory
    DESCRIPTION
      "Web access via HTTP: 
       (1) view only
       (2) full Access, read and set
       (3) Web disabled (general)"
    ::= { cmcTcMasterTc5SetupGeneral 5 }
 
  cmcTcMasterTc5SetupDate OBJECT-TYPE
    SYNTAX DisplayString (SIZE (0..10))
    ACCESS read-write
    STATUS mandatory
    DESCRIPTION
      "actual Date in format DD.MM.YYYY"
    ::= { cmcTcMasterTc5SetupGeneral 6 }

  cmcTcMasterTc5SetupTime OBJECT-TYPE
    SYNTAX DisplayString (SIZE (0..8))
    ACCESS read-write
    STATUS mandatory
    DESCRIPTION
      "actual Time in format HH:MM:SS, HH (0-23), MM (0-59), SS (0-59)"
    ::= { cmcTcMasterTc5SetupGeneral 7 }
 
-- table for timer function
 
  cmcTcMasterTc5TimerNumber OBJECT-TYPE
    SYNTAX INTEGER 
    ACCESS read-only
    STATUS mandatory
    DESCRIPTION
      "Number of timers available on this unit"
    ::= { cmcTcMasterTc5TimerTable1 1 }

  cmcTcMasterTc5TimerTable OBJECT-TYPE
    SYNTAX SEQUENCE OF CmcTcMasterTc5TimerEntry
    ACCESS not-accessible
    STATUS mandatory
    DESCRIPTION
      "Headline of timer-table"
    ::= { cmcTcMasterTc5TimerTable1 2 }

  cmcTcMasterTc5TimerEntry OBJECT-TYPE
    SYNTAX CmcTcMasterTc5TimerEntry
    ACCESS not-accessible
    STATUS mandatory
    DESCRIPTION
      "Entries of timer-table"
    INDEX { cmcTcMasterTc5TimerIndex }
    ::= { cmcTcMasterTc5TimerTable 1 }

    CmcTcMasterTc5TimerEntry ::=
      SEQUENCE {
        cmcTcMasterTc5TimerIndex
          INTEGER,
        cmcTcMasterTc5TimerStatus
          INTEGER,
        cmcTcMasterTc5TimerDayOfWeek
          INTEGER,  
        cmcTcMasterTc5TimeOn 
          DisplayString (SIZE (0..5)),                              
        cmcTcMasterTc5TimeOff 
          DisplayString (SIZE (0..5)),                              
        cmcTcMasterTc5TimeControl
          INTEGER,
        cmcTcMasterTc5TimerFunction
           INTEGER
      }

    cmcTcMasterTc5TimerIndex OBJECT-TYPE
      SYNTAX INTEGER (1..32000)
      ACCESS read-only
      STATUS mandatory
      DESCRIPTION
        "Index for the list of timer entries. Its value ranges
         between 1 and the value of cmcTcMasterTc5TimerNumber." 
      ::= { cmcTcMasterTc5TimerEntry 1 }

    cmcTcMasterTc5TimerStatus OBJECT-TYPE
      SYNTAX INTEGER {
        switchedOff(1),
        switchedOn(2),
        noTime(3) 
      }
      ACCESS read-only
      STATUS mandatory
      DESCRIPTION
        "Actual status of the timer"
      ::= { cmcTcMasterTc5TimerEntry 2 }

    cmcTcMasterTc5TimerDayOfWeek OBJECT-TYPE
      SYNTAX INTEGER {
        sun(1),
        mon(2),
        tue(3) ,
        wed(4),
        thu(5),
        fri(6),
        sat(7),
        sat-sun(8),
        mon-fri(9),
        mon-sun(10)
      }
      ACCESS read-write
      STATUS mandatory
      DESCRIPTION
        "Selection of day of week for timer to switch"
      ::= { cmcTcMasterTc5TimerEntry 3 }
             
    cmcTcMasterTc5TimeOn OBJECT-TYPE
      SYNTAX DisplayString (SIZE (0..5))
      ACCESS read-write
      STATUS mandatory
      DESCRIPTION
        "Time to switch on current function, 
         Format: HH:MM"
      ::= { cmcTcMasterTc5TimerEntry 4 }

    cmcTcMasterTc5TimeOff OBJECT-TYPE
      SYNTAX DisplayString (SIZE (0..5))
      ACCESS read-write
      STATUS mandatory
      DESCRIPTION
        "Time to switch off current function,
         Format: HH:MM"
      ::= { cmcTcMasterTc5TimerEntry 5 }

    cmcTcMasterTc5TimeControl OBJECT-TYPE
      SYNTAX INTEGER  {
        disabled(1),
        enabled(2)
      }
      ACCESS read-write
      STATUS mandatory
      DESCRIPTION
        "Control via RTC"
      ::= { cmcTcMasterTc5TimerEntry 6 }

    cmcTcMasterTc5TimerFunction OBJECT-TYPE
      SYNTAX INTEGER {
        disKeypad1-1 (1),
        disKeypad2-1 (2),
        disKeypad1-2 (3),
        disKeypad2-2 (4),
        disKeypad1-3 (5),
        disKeypad2-3 (6),
        disKeypad1-4 (7),
        disKeypad2-4 (8),
        unlDoor1-1 (9),
        unlDoor2-1 (10),
        unlDoor1-2 (11),
        unlDoor2-2 (12),
        unlDoor1-3 (13),
        unlDoor2-3 (14),
        unlDoor1-4 (15),
        unlDoor2-5 (16),
        disTrapRec1 (17),
        disTrapRec2 (18),
        disTrapRec3 (19),
        disTrapRec4 (20),
        disSMS (21),
        schedule1 (22),
        schedule2 (23),
        schedule3 (24),
        schedule4 (25)
      }
      ACCESS read-write
      STATUS mandatory
      DESCRIPTION
        "Function which is controlled via timer
         1:     unlock via keypad 1 on unit 1 or remote input lock 1 is disabled
         2:     unlock via keypad 2 on unit 1 or remote input lock 2 is disabled
         3      unlock via keypad 1 on unit 2 or remote input lock 1 is disabled
         4:     unlock via keypad 2 on unit 2 or remote input lock 2 is disabled
         5:     unlock via keypad 1 on unit 3 or remote input lock 1 is disabled
         6:     unlock via keypad 2 on unit 3 or remote input lock 2 is disabled
         7:     unlock via keypad 1 on unit 4 or remote input lock 1 is disabled
         8:     unlock via keypad 2 on unit 4 or remote input lock 2 is disabled
         9:     Lock of door 1 on unit 1 will be unlocked
         10:    Lock of door 2 on unit 1 will be unlocked
         11:    Lock of door 1 on unit 2 will be unlocked
         12:    Lock of door 2 on unit 2 will be unlocked
         13:    Lock of door 1 on unit 3 will be unlocked
         14:    Lock of door 2 on unit 3 will be unlocked
         15:    Lock of door 1 on unit 4 will be unlocked
         16:    Lock of door 2 on unit 4 will be unlocked
         17-20: sending Traps to this Trap receiver will be disabled
         21:    sending SMS will be disabled
         22-25: Scheduled alarm off"
      ::= { cmcTcMasterTc5TimerEntry 7 }

--cmcTcMasterTc5TrapTable-group

  cmcTcMasterTc5TraptableNumber OBJECT-TYPE
    SYNTAX INTEGER 
    ACCESS read-only
    STATUS mandatory
    DESCRIPTION
      "Number of trapTable entries. The number of trap-receiver"
    ::= { cmcTcMasterTc5Traps 1 }

  cmcTcMasterTc5TrapTableTable OBJECT-TYPE    
    SYNTAX SEQUENCE OF CmcTcMasterTc5TrapTableEntry
    ACCESS not-accessible
    STATUS mandatory
    DESCRIPTION
     "A list of trap-receiver entries"
    ::= { cmcTcMasterTc5Traps 2 }

  cmcTcMasterTc5TrapTableEntry OBJECT-TYPE
    SYNTAX CmcTcMasterTc5TrapTableEntry
    ACCESS not-accessible
    STATUS mandatory
    DESCRIPTION
      "Entries of cmcTcMasterTc5TrapTable"
    INDEX   { cmcTcMasterTc5TrapIndex }
    ::= { cmcTcMasterTc5TrapTableTable 1 }      
              
    CmcTcMasterTc5TrapTableEntry ::=
      SEQUENCE {
        cmcTcMasterTc5TrapIndex
          INTEGER,
        cmcTcMasterTc5TrapStatus
          INTEGER,
        cmcTcMasterTc5TrapIPaddress
          DisplayString
      }

    cmcTcMasterTc5TrapIndex OBJECT-TYPE
      SYNTAX INTEGER (1..32000)
      ACCESS read-only
      STATUS mandatory
      DESCRIPTION
        "Index for the trap-receiver-table. Its value ranges between
         1 and the value of cmcTcMasterTc5TraptableNumber "
      ::= { cmcTcMasterTc5TrapTableEntry 1 }

    cmcTcMasterTc5TrapStatus OBJECT-TYPE
      SYNTAX INTEGER {
        disabled(1),
        enabled(2)
      }
      ACCESS read-write
      STATUS mandatory
      DESCRIPTION
        "Enable or disable trap receiver"
      ::= { cmcTcMasterTc5TrapTableEntry 2 }

    cmcTcMasterTc5TrapIPaddress OBJECT-TYPE
      SYNTAX DisplayString (SIZE (0..15))
      ACCESS read-write
      STATUS mandatory
      DESCRIPTION
        "IP-address of trap-receiver"
      ::= { cmcTcMasterTc5TrapTableEntry 3 }

--cmcTcMasterTc5Control-group (Added in Version 1.1)

  cmcTcMasterTc1QuitUnit OBJECT-TYPE
    SYNTAX INTEGER {
      noQuit(1),
      quit(2),
    }
    ACCESS read-write
    STATUS mandatory
    DESCRIPTION
      "Command to quit (acknowledge) alarms of CMC-TC unit.
       Setting to 'quit' (2) will have same result as pressing 'C' on Units.
       Variable is automatically set back to 'noQuit' (1)."
    ::= { cmcTcMasterTc5Control 1 }

--cmcTcMasterDevice6-group

  cmcTcMasterDev6Type OBJECT-TYPE
    SYNTAX INTEGER {
      other (0),
      cmc (1),
      pcu (3),
      tc (4)
    }
    ACCESS read-only
    STATUS mandatory
    DESCRIPTION
      "Type of device6"
    ::= { cmcTcMasterDevice6 1 }

  cmcTcMasterDev6Status OBJECT-TYPE
    SYNTAX INTEGER {
      other (1),
      notConnected (2),
      normal (3),
      minor (4),
      major (5),
      configChanged (6),
      connectionLost (10)
    }
    ACCESS read-only
    STATUS mandatory
    DESCRIPTION
      "Status of device6"
    ::= { cmcTcMasterDevice6 2 }

  cmcTcMasterDev6Descr OBJECT-TYPE
    SYNTAX DisplayString (SIZE (0..255))
    ACCESS read-only
    STATUS mandatory
    DESCRIPTION
      "A textual description of the entity.  This value
       should include the full name and version
       identification of the system's hardware type,
       software operating-system, and networking
       software.  It is mandatory that this only contain
       printable ASCII characters."
    ::= { cmcTcMasterDevice6 3 }

  cmcTcMasterDev6UpTime OBJECT-TYPE
    SYNTAX TimeTicks
    ACCESS read-only
    STATUS mandatory
    DESCRIPTION
      "The time (in hundredths of a second) since the
       network management portion of the system was last
       re-initialized."
    ::= { cmcTcMasterDevice6 4 }

  cmcTcMasterDev6Contact OBJECT-TYPE
    SYNTAX DisplayString (SIZE (0..255))
    ACCESS read-write
    STATUS mandatory
    DESCRIPTION
      "The textual identification of the contact person
       for this managed node, together with information
       on how to contact this person."
    ::= { cmcTcMasterDevice6 5 }

  cmcTcMasterDev6Name OBJECT-TYPE
    SYNTAX DisplayString (SIZE (0..255))
    ACCESS read-write
    STATUS mandatory
    DESCRIPTION
      "An administratively-assigned name for this
       managed node.  By convention, this is the node's
       fully-qualified domain name."
    ::= { cmcTcMasterDevice6 6 }

  cmcTcMasterDev6Location OBJECT-TYPE
    SYNTAX DisplayString (SIZE (0..255))
    ACCESS read-write
    STATUS mandatory
    DESCRIPTION
      "The physical location of this node (e.g.,
       `telephone closet, 3rd floor')."
    ::= { cmcTcMasterDevice6 7 }

--cmcTcMasterCmc6Values-group

  cmcTcMasterCmc6ValueTemperature1 OBJECT-TYPE
    SYNTAX INTEGER
    ACCESS read-only
    STATUS mandatory
    DESCRIPTION
      "Actual value of temperature 1 in deg C"
    ::= { cmcTcMasterCmc6Values 1 }

  cmcTcMasterCmc6ValueTemperature2 OBJECT-TYPE
    SYNTAX INTEGER
    ACCESS read-only
    STATUS mandatory
    DESCRIPTION
      "Actual value of temperature 2 in deg C"
    ::= { cmcTcMasterCmc6Values 2 }

  cmcTcMasterCmc6ValuePowerSupply OBJECT-TYPE
    SYNTAX INTEGER
    ACCESS read-only
    STATUS mandatory
    DESCRIPTION
      "Actual value of power supply in V"
    ::= { cmcTcMasterCmc6Values 3 }

  cmcTcMasterCmc6ValueAnalogAux1 OBJECT-TYPE
    SYNTAX INTEGER
    ACCESS read-only
    STATUS mandatory
    DESCRIPTION
      "Actual value of aux. analog input 1
      (4-20mA = 0-100%)"
    ::= { cmcTcMasterCmc6Values 4 }

  cmcTcMasterCmc6ValueAnalogAux2 OBJECT-TYPE
    SYNTAX INTEGER
    ACCESS read-only
    STATUS mandatory
    DESCRIPTION
      "Actual value of aux. analog input 2
      (4-20mA = 0-100%)"
    ::= { cmcTcMasterCmc6Values 5 }

--cmcTcMasterCmc6Values-table-group

  cmcTcMasterCmc6ValuesNumber OBJECT-TYPE
    SYNTAX INTEGER
    ACCESS read-only
    STATUS mandatory
    DESCRIPTION
      "Number of value-table entries"
    ::= { cmcTcMasterCmc6Table1 1 }

  cmcTcMasterCmc6ValuesTable OBJECT-TYPE
    SYNTAX SEQUENCE OF CmcTcMasterCmc6ValuesEntry
    ACCESS not-accessible
    STATUS mandatory
    DESCRIPTION
      "Headline of value-table"
    ::= { cmcTcMasterCmc6Table1 2 }

  cmcTcMasterCmc6ValuesEntry OBJECT-TYPE
    SYNTAX CmcTcMasterCmc6ValuesEntry
    ACCESS not-accessible
    STATUS mandatory
    DESCRIPTION
      "Entries of value-table"
    INDEX { cmcTcMasterCmc6ValuesIndex }
    ::= { cmcTcMasterCmc6ValuesTable 1 }

  CmcTcMasterCmc6ValuesEntry ::=
    SEQUENCE {
      cmcTcMasterCmc6ValuesIndex
        INTEGER,
      cmcTcMasterCmc6ValuesText
        DisplayString (SIZE (0..31)),
      cmcTcMasterCmc6ValuesValue
        INTEGER,
      cmcTcMasterCmc6ValuesStatus
        INTEGER,
      cmcTcMasterCmc6ValuesMaxValue
        INTEGER,
      cmcTcMasterCmc6ValuesMinValue
        INTEGER
    }

    cmcTcMasterCmc6ValuesIndex OBJECT-TYPE
      SYNTAX INTEGER (1..32000)
      ACCESS read-only
      STATUS mandatory
      DESCRIPTION
        "Index for the list of value entries. Its value ranges
        between 1 and the value of valuesNumber."
      ::= { cmcTcMasterCmc6ValuesEntry 1 }

    cmcTcMasterCmc6ValuesText OBJECT-TYPE
      SYNTAX DisplayString (SIZE (0..31))
      ACCESS read-write
      STATUS mandatory
      DESCRIPTION
        "Text of the entry in the value-table"
      ::= { cmcTcMasterCmc6ValuesEntry 2 }

    cmcTcMasterCmc6ValuesValue OBJECT-TYPE
      SYNTAX INTEGER
      ACCESS read-only
      STATUS mandatory
      DESCRIPTION
        "Actual value of the value-table"
      ::= { cmcTcMasterCmc6ValuesEntry 3 }

    cmcTcMasterCmc6ValuesStatus OBJECT-TYPE
      SYNTAX INTEGER {
        valueOK(1),
        valueTooLow(2),
        valueTooHigh(3),
        valueERROR(4),
        notAvail(5)
      }
      ACCESS read-only
      STATUS mandatory
      DESCRIPTION
        "Status of the value"
      ::= { cmcTcMasterCmc6ValuesEntry 4 }

    cmcTcMasterCmc6ValuesMaxValue OBJECT-TYPE
      SYNTAX INTEGER
      ACCESS read-write
      STATUS mandatory
      DESCRIPTION
        "Value for max. alarm"
      ::= { cmcTcMasterCmc6ValuesEntry 5 }

    cmcTcMasterCmc6ValuesMinValue OBJECT-TYPE
      SYNTAX INTEGER
      ACCESS read-write
      STATUS mandatory
      DESCRIPTION
        "Value for min. alarm"
      ::= { cmcTcMasterCmc6ValuesEntry 6 }

--cmcTcMasterCmc6status-group

  cmcTcMasterCmc6StatusTemperature1 OBJECT-TYPE
    SYNTAX DisplayString (SIZE (0..31))
    ACCESS read-only
    STATUS mandatory
    DESCRIPTION
      "Status temperature 1, OK/ too low/ too high
       (see setpoints of temperature 1)"
    ::= { cmcTcMasterCmc6Status 1 }

  cmcTcMasterCmc6StatusTemperature2 OBJECT-TYPE
    SYNTAX DisplayString (SIZE (0..31))
    ACCESS read-only
    STATUS mandatory
    DESCRIPTION
      "Status temperature 2, OK/ too low/ too high
       (see setpoints of temperature 2)"
    ::= { cmcTcMasterCmc6Status 2 }

  cmcTcMasterCmc6StatusFan1 OBJECT-TYPE
    SYNTAX DisplayString (SIZE (0..31))
    ACCESS read-only
    STATUS mandatory
    DESCRIPTION
      "Status fan 1, Stop/ running/ fault"
    ::= { cmcTcMasterCmc6Status 3 }

  cmcTcMasterCmc6StatusFan2 OBJECT-TYPE
    SYNTAX DisplayString (SIZE (0..31))
    ACCESS read-only
    STATUS mandatory
    DESCRIPTION
      "Status fan 2, Stop/ running/ fault"
    ::= { cmcTcMasterCmc6Status 4 }

  cmcTcMasterCmc6StatusHeating OBJECT-TYPE
    SYNTAX DisplayString (SIZE (0..31))
    ACCESS read-only
    STATUS mandatory
    DESCRIPTION
      "Status heating, On/Off"
    ::= { cmcTcMasterCmc6Status 5 }

  cmcTcMasterCmc6StatusPowerSupply OBJECT-TYPE
    SYNTAX DisplayString (SIZE (0..31))
    ACCESS read-only
    STATUS mandatory
    DESCRIPTION
      "Status power supply, OK/ too low/ too high
       (see setpoints of power supply)"
    ::= { cmcTcMasterCmc6Status 6 }

  cmcTcMasterCmc6StatusAnalogAux1 OBJECT-TYPE
    SYNTAX DisplayString (SIZE (0..31))
    ACCESS read-only
    STATUS mandatory
    DESCRIPTION
      "Status aux analog input 1, OK/ too low/ too high"
    ::= { cmcTcMasterCmc6Status 7 }

  cmcTcMasterCmc6StatusAnalogAux2 OBJECT-TYPE
    SYNTAX DisplayString (SIZE (0..31))
    ACCESS read-only
    STATUS mandatory
    DESCRIPTION
      "Status aux analog input 2, OK/ too low/ too high"
    ::= { cmcTcMasterCmc6Status 8 }

  cmcTcMasterCmc6StatusDoor OBJECT-TYPE
    SYNTAX DisplayString (SIZE (0..31))
    ACCESS read-only
    STATUS mandatory
    DESCRIPTION
      "Status door, open/closed/locked"
    ::= { cmcTcMasterCmc6Status 9 }

  cmcTcMasterCmc6StatusUps1 OBJECT-TYPE
    SYNTAX DisplayString (SIZE (0..31))
    ACCESS read-only
    STATUS mandatory
    DESCRIPTION
      "Status UPS 1, OK/ fault"
    ::= { cmcTcMasterCmc6Status 10 }

  cmcTcMasterCmc6StatusUps2 OBJECT-TYPE
    SYNTAX DisplayString (SIZE (0..31))
    ACCESS read-only
    STATUS mandatory
    DESCRIPTION
      "Status UPS 2, OK/ fault"
    ::= { cmcTcMasterCmc6Status 11 }

  cmcTcMasterCmc6StatusSmokeSensor OBJECT-TYPE
    SYNTAX DisplayString (SIZE (0..31))
    ACCESS read-only
    STATUS mandatory
    DESCRIPTION
      "Status smoke-sensor, OK/ smoke"
    ::= { cmcTcMasterCmc6Status 12 }

  cmcTcMasterCmc6StatusVibrationSensor OBJECT-TYPE
    SYNTAX DisplayString (SIZE (0..31))
    ACCESS read-only
    STATUS mandatory
    DESCRIPTION
      "Status vibration sensor, OK/ vibration"
    ::= { cmcTcMasterCmc6Status 13 }

  cmcTcMasterCmc6StatusMessage OBJECT-TYPE
    SYNTAX DisplayString (SIZE (0..31))
    ACCESS read-only
    STATUS mandatory
    DESCRIPTION
      "Message from CMC"
    ::= { cmcTcMasterCmc6Status 14 }

  cmcTcMasterCmc6ValueOperatingTime OBJECT-TYPE
    SYNTAX DisplayString (SIZE (0..31))
    ACCESS read-only
    STATUS mandatory
    DESCRIPTION
      "Operating time CMC-unit"
    ::= { cmcTcMasterCmc6Status 15 }

  cmcTcMasterCmc6StatusUnit OBJECT-TYPE
    SYNTAX INTEGER {
      unitCelsius(1),
      unitFahrenheit(2)
    }
    ACCESS read-only
    STATUS mandatory
    DESCRIPTION
      "Unit of temperature-values, Celsius or Fahrenheit"
   ::= { cmcTcMasterCmc6Status 16 }


--cmcTcMasterCmc6Status-table-group

  cmcTcMasterCmc6StatusNumber OBJECT-TYPE
    SYNTAX INTEGER 
    ACCESS read-only
    STATUS mandatory
    DESCRIPTION
      "Number of status-table entries"
    ::= { cmcTcMasterCmc6Table 1 }

  cmcTcMasterCmc6StatusTable OBJECT-TYPE
    SYNTAX SEQUENCE OF CmcTcMasterCmc6StatusEntry
    ACCESS not-accessible
    STATUS mandatory
    DESCRIPTION
      "Headline of table"
    ::= { cmcTcMasterCmc6Table 2 }

  cmcTcMasterCmc6StatusEntry OBJECT-TYPE
    SYNTAX CmcTcMasterCmc6StatusEntry
    ACCESS not-accessible
    STATUS mandatory
    DESCRIPTION
      "A list of status entries.  The number of
       entries is given by the value of cmcTcMasterCmc6StatusNumber." 
    INDEX { cmcTcMasterCmc6StatusIndex }
    ::= { cmcTcMasterCmc6StatusTable 1 }

  CmcTcMasterCmc6StatusEntry ::=
    SEQUENCE {
      cmcTcMasterCmc6StatusIndex
        INTEGER,
      cmcTcMasterCmc6StatusText
        DisplayString (SIZE (0..31)),
      cmcTcMasterCmc6StatusStatus
        INTEGER              
    }

    cmcTcMasterCmc6StatusIndex OBJECT-TYPE
      SYNTAX INTEGER (1..32000)
      ACCESS read-only
      STATUS mandatory
      DESCRIPTION
        "Index fo the list of status entries. Its value ranges
         between 1 and the value of cmcTcMasterCmc6StatusNumber." 
      ::= { cmcTcMasterCmc6StatusEntry 1 }

    cmcTcMasterCmc6StatusText OBJECT-TYPE
      SYNTAX DisplayString (SIZE (0..31))
      ACCESS read-write
      STATUS mandatory
      DESCRIPTION
        "Text of the entry in the status-table"
      ::= { cmcTcMasterCmc6StatusEntry 2 }

    cmcTcMasterCmc6StatusStatus OBJECT-TYPE
      SYNTAX INTEGER  {
        statusOK(1),
        alarm(2),
        security(3),
        notAvail(4)
      }
      ACCESS read-only
      STATUS mandatory
      DESCRIPTION
        "Status of the table entry"
      ::= { cmcTcMasterCmc6StatusEntry 3 }

--******************************************************************************

--cmcTCMasterCmc6Set-group

  cmcTcMasterCmc6StatusAccess OBJECT-TYPE
    SYNTAX DisplayString (SIZE (0..31))
    ACCESS read-write
    STATUS mandatory
    DESCRIPTION
      "Status access"
    ::= { cmcTcMasterCmc6Set 1 }

  cmcTcMasterCmc6SetDoor OBJECT-TYPE
    SYNTAX INTEGER {
      lockDoor(1),
      openDoorTime(2),
      openDoorAccess(3),
      openDoor(4)
    }
    ACCESS read-write
    STATUS mandatory
    DESCRIPTION
      "Set door, see table"
    ::= { cmcTcMasterCmc6Set 2 }

  cmcTcMasterCmc6SetMessage OBJECT-TYPE
    SYNTAX DisplayString (SIZE (0..31))
    ACCESS read-write
    STATUS mandatory
    DESCRIPTION
      "Set message"
    ::= { cmcTcMasterCmc6Set 3 }

  cmcTcMasterCmc6SetFault        OBJECT-TYPE
    SYNTAX INTEGER {
      clearFault(1),
      setFault(2)
    }
    ACCESS read-write
    STATUS mandatory
    DESCRIPTION
      "Set fault, see table"
    ::= { cmcTcMasterCmc6Set 4 }

--cmcTcMasterCmc6RelayControl-group

  cmcTcMasterCmc6RelaytableMaxNum OBJECT-TYPE
    SYNTAX INTEGER 
    ACCESS read-only
    STATUS mandatory
    DESCRIPTION
      "Number of table entries"
    ::= { cmcTcMasterCmc6RelayControl 1 }

  cmcTcMasterCmc6RelayTable OBJECT-TYPE
    SYNTAX SEQUENCE OF CmcTcMasterCmc6RelayEntry
    ACCESS not-accessible
    STATUS mandatory
    DESCRIPTION
      "Headline of table for relay control"
    ::= { cmcTcMasterCmc6RelayControl 2 }

  cmcTcMasterCmc6RelayEntry OBJECT-TYPE
    SYNTAX CmcTcMasterCmc6RelayEntry
    ACCESS not-accessible
    STATUS mandatory
    DESCRIPTION
      "Entries"
    INDEX { cmcTcMasterCmc6RelaytableIndex }
    ::= { cmcTcMasterCmc6RelayTable 1 }

  CmcTcMasterCmc6RelayEntry ::=
    SEQUENCE {
      cmcTcMasterCmc6RelaytableIndex
        INTEGER,
      cmcTcMasterCmc6RelaytableText
	DisplayString (SIZE (0..31)),
      cmcTcMasterCmc6RelaytableStatus
        INTEGER              
    }

    cmcTcMasterCmc6RelaytableIndex OBJECT-TYPE
      SYNTAX INTEGER (1..32000)
      ACCESS read-only
      STATUS mandatory
      DESCRIPTION
        "Index for the relay-table. Its value ranges
         between 1 and cmcTcMasterCmc6RelaytableMaxNum"
      ::= { cmcTcMasterCmc6RelayEntry 1 }

    cmcTcMasterCmc6RelaytableText OBJECT-TYPE
      SYNTAX DisplayString (SIZE (0..31))
      ACCESS read-write
      STATUS mandatory
      DESCRIPTION
        "Description-Text for each relay in the table"
      ::= { cmcTcMasterCmc6RelayEntry 2 }

    cmcTcMasterCmc6RelaytableStatus OBJECT-TYPE
      SYNTAX INTEGER  {
        relayOFF(1),
        relayON(2),
        notAvail(3)
      }
      ACCESS read-write
      STATUS mandatory
      DESCRIPTION
        "Status of relays in the table"
      ::= { cmcTcMasterCmc6RelayEntry 3 }

--cmcTcMasterCmc6Setpoints-group

  cmcTcMasterCmc6SetpointFan1 OBJECT-TYPE
    SYNTAX INTEGER 
    ACCESS read-write
    STATUS mandatory
    DESCRIPTION
      "Setpoint Fan 1 in C, Fan 1 will start
       if temperature 1 exceeds this value"
    ::= { cmcTcMasterCmc6Setpoints 1 }

  cmcTcMasterCmc6SetpointFan2 OBJECT-TYPE
    SYNTAX INTEGER 
    ACCESS read-write
    STATUS mandatory
    DESCRIPTION
      "Setpoint Fan 2 in C, Fan 2 will start
       if temperature 2 exceeds this value"
    ::= { cmcTcMasterCmc6Setpoints 2 }

  cmcTcMasterCmc6SetpointHeating OBJECT-TYPE
    SYNTAX INTEGER 
    ACCESS read-write
    STATUS mandatory
    DESCRIPTION
      "Setpoint heating in C, heating will start
       if lowest value of temperature 1 and 2 falls below this value"
    ::= { cmcTcMasterCmc6Setpoints 3 }

  cmcTcMasterCmc6SetpointHighTemperature1 OBJECT-TYPE
    SYNTAX INTEGER 
    ACCESS read-write
    STATUS mandatory
    DESCRIPTION
      "Setpoint high value alarm temperature 1"
    ::= { cmcTcMasterCmc6Setpoints 4 }

  cmcTcMasterCmc6SetpointLowTemperature1 OBJECT-TYPE
    SYNTAX INTEGER 
    ACCESS read-write
    STATUS mandatory
    DESCRIPTION
      "Setpoint low value alarm temperature 1"
    ::= { cmcTcMasterCmc6Setpoints 5 }

  cmcTcMasterCmc6SetpointHighTemperature2 OBJECT-TYPE
    SYNTAX INTEGER 
    ACCESS read-write
    STATUS mandatory
    DESCRIPTION
      "Setpoint high value alarm temperature 2"
    ::= { cmcTcMasterCmc6Setpoints 6 }

  cmcTcMasterCmc6SetpointLowTemperature2 OBJECT-TYPE
    SYNTAX INTEGER 
    ACCESS read-write
    STATUS mandatory
    DESCRIPTION
      "Setpoint low value alarm temperature 2"
    ::= { cmcTcMasterCmc6Setpoints 7 }

  cmcTcMasterCmc6SetpointHighVoltage OBJECT-TYPE
    SYNTAX INTEGER 
    ACCESS read-write
    STATUS mandatory
    DESCRIPTION
      "Setpoint high value supply voltage alarm"
    ::= { cmcTcMasterCmc6Setpoints 8 }

  cmcTcMasterCmc6SetpointLowVoltage OBJECT-TYPE
    SYNTAX INTEGER
    ACCESS read-write
    STATUS mandatory
    DESCRIPTION
      "Setpoint low value supply voltage alarm"
    ::= { cmcTcMasterCmc6Setpoints 9 }

  cmcTcMasterCmc6SetpointLowAux1 OBJECT-TYPE
    SYNTAX INTEGER 
    ACCESS read-write
    STATUS mandatory
    DESCRIPTION
      "Setpoint low value Aux input 1 alarm"
    ::= { cmcTcMasterCmc6Setpoints 10 }

  cmcTcMasterCmc6SetpointHighAux1 OBJECT-TYPE
    SYNTAX INTEGER 
    ACCESS read-write
    STATUS mandatory
    DESCRIPTION
      "Setpoint high value Aux input 1 alarm"
    ::= { cmcTcMasterCmc6Setpoints 11 }

  cmcTcMasterCmc6SetpointLowAux2 OBJECT-TYPE
    SYNTAX INTEGER 
    ACCESS read-write
    STATUS mandatory
    DESCRIPTION
      "Setpoint low value Aux input 2 alarm"
    ::= { cmcTcMasterCmc6Setpoints 12 }

  cmcTcMasterCmc6SetpointHighAux2 OBJECT-TYPE
    SYNTAX INTEGER 
    ACCESS read-write
    STATUS mandatory
    DESCRIPTION
      "Setpoint high value Aux input alarm"
    ::= { cmcTcMasterCmc6Setpoints 13 }

--cmcTcMasterCmc6TrapControl-group

  cmcTcMasterCmc6SetTrapRepeat OBJECT-TYPE
    SYNTAX INTEGER {
      disableTrapRepeat(1),
      enableTrapRepeat(2)
    }
    ACCESS read-write
    STATUS mandatory
    DESCRIPTION
      "Enable/disable repeating of traps. If enabled, traps will
       be repeated after a repeat time, set in setTrapRepeatTime.
       Repeating can be stopped by setting setTrapQuit to quitTrap"
    ::= { cmcTcMasterCmc6TrapControl 1 }

  cmcTcMasterCmc6SetTrapRepeatTime OBJECT-TYPE
    SYNTAX INTEGER 
    ACCESS read-write
    STATUS mandatory
    DESCRIPTION
      "Time value (sec) for trap-repeating, if setTrapRepeat is enabled"
    ::= { cmcTcMasterCmc6TrapControl 2 }

  cmcTcMasterCmc6SetTrapQuit OBJECT-TYPE
    SYNTAX INTEGER {
      quitTrap(1),
      quitTrapOK(2),
      noTrapToQuit(3),
      trapToQuit(4)
    }
    ACCESS read-write
    STATUS mandatory
    DESCRIPTION
      "Quit trap to stop repeating."
    ::= { cmcTcMasterCmc6TrapControl 3 }

--cmcTcMasterCmc6TrapTable-group

  cmcTcMasterCmc6TraptableNumber OBJECT-TYPE
    SYNTAX INTEGER 
    ACCESS read-only
    STATUS mandatory
    DESCRIPTION
      "Number of trapTable entries. The number of trap-receiver"
    ::= { cmcTcMasterCmc6Traps 1 }

  cmcTcMasterCmc6TrapTable OBJECT-TYPE
    SYNTAX SEQUENCE OF CmcTcMasterCmc6TrapEntry
    ACCESS not-accessible
    STATUS mandatory
    DESCRIPTION
      "A list of trap-receiver entries"
    ::= { cmcTcMasterCmc6Traps 2 }

  cmcTcMasterCmc6TrapEntry OBJECT-TYPE
    SYNTAX CmcTcMasterCmc6TrapEntry
    ACCESS not-accessible
    STATUS mandatory
    DESCRIPTION
      "Entries of trapTable"
    INDEX { cmcTcMasterCmc6TrapIndex }
    ::= { cmcTcMasterCmc6TrapTable 1 }

  CmcTcMasterCmc6TrapEntry ::=
    SEQUENCE {
      cmcTcMasterCmc6TrapIndex
        INTEGER,
      cmcTcMasterCmc6TrapStatus
        INTEGER,
      cmcTcMasterCmc6TrapIPaddress
        DisplayString
    }

    cmcTcMasterCmc6TrapIndex OBJECT-TYPE
      SYNTAX INTEGER (1..32000)
      ACCESS read-only
      STATUS mandatory
      DESCRIPTION
        "Index for the trap-receiver-table. Its value ranges between
         1 and the value of cmcTcMasterCmc6TraptableNumber "
      ::= { cmcTcMasterCmc6TrapEntry 1 }

    cmcTcMasterCmc6TrapStatus OBJECT-TYPE
      SYNTAX INTEGER  {
        enabled(1),
        disabled(2)
      }
      ACCESS read-write
      STATUS mandatory
      DESCRIPTION
        "Enable or disable trap receiver"
      ::= { cmcTcMasterCmc6TrapEntry 2 }

    cmcTcMasterCmc6TrapIPaddress OBJECT-TYPE
      SYNTAX DisplayString (SIZE (0..31))
      ACCESS read-write
      STATUS mandatory
      DESCRIPTION
        "IP-address of trap-receiver"
      ::= { cmcTcMasterCmc6TrapEntry 3 }

--cmcTcMasterPcu6MibRev-group
          
  cmcTcMasterPcu6MibMajRev OBJECT-TYPE
    SYNTAX INTEGER (1..32000)
    ACCESS read-only
    STATUS mandatory
    DESCRIPTION
      "The Major Revision level.
       A change in the major revision level represents a major change
       in the architecture of the MIB. A change in the major revision 
       level may indicate a significant change in the information,
       correct interpretation of data may require a MIB document
       with the same major revision level."
    ::= { cmcTcMasterPcu6MibRev 1 }

  cmcTcMasterPcu6MibMinRev OBJECT-TYPE
    SYNTAX INTEGER (0..32000)
    ACCESS read-only
    STATUS mandatory
    DESCRIPTION
      "The Minor Revision level.
       A change in the minor revision level may represent some minor
       additional support, no changes to any pre-existing information
       has occurred."
    ::= { cmcTcMasterPcu6MibRev 2 }

  cmcTcMasterPcu6MibCondition OBJECT-TYPE
    SYNTAX INTEGER {
      other (1),
      ok (2),
      degraded (3),
      failed (4)
    }
    ACCESS read-only
    STATUS mandatory
    DESCRIPTION
      "The overall condition (status) of the system represented by
       this MIB. 
       (2) OK
       (3) a minor problem, warning condition (yellow LED on PCU)
       (4) a major problem (red LED on PCU)"
    ::= { cmcTcMasterPcu6MibRev 3 }

--cmcTcMasterPcu6Values-group

  cmcTcMasterPcu6ValueEnergy1 OBJECT-TYPE
    SYNTAX INTEGER 
    ACCESS read-only
    STATUS mandatory
    DESCRIPTION
      "Total value of the Energy (Wh), measured on IEC input 1"
    ::= { cmcTcMasterPcu6Values 1 }

  cmcTcMasterPcu6ValueEnergy2 OBJECT-TYPE
    SYNTAX INTEGER 
    ACCESS read-only
    STATUS mandatory
    DESCRIPTION
      "Actual value of the Energy (Wh), measured on IEC input 2"
    ::= { cmcTcMasterPcu6Values 2 }

  cmcTcMasterPcu6ValueEnergy1Time OBJECT-TYPE
    SYNTAX INTEGER 
    ACCESS read-only
    STATUS mandatory
    DESCRIPTION
      "Actual value of the Energy (Wh), measured on IEC input 1, can be set to 0
       Value can be used to calculate the energy over a fixed time"
    ::= { cmcTcMasterPcu6Values 3 }

  cmcTcMasterPcu6ValueEnergy2Time OBJECT-TYPE
    SYNTAX INTEGER 
    ACCESS read-only
    STATUS mandatory
    DESCRIPTION
      "Actual value of the Energy (Wh), measured on IEC input 2, can be set to 0.
       Value can be used to calculate the energy over a fixed time"
    ::= { cmcTcMasterPcu6Values 4 }

  cmcTcMasterPcu6ValuePower1 OBJECT-TYPE
    SYNTAX INTEGER 
    ACCESS read-only
    STATUS mandatory
    DESCRIPTION
      "Calculated actual power 1 (W). Calculated from cmcTcMasterPcu6ValueEnergy1/time"
    ::= { cmcTcMasterPcu6Values 5 }
          
  cmcTcMasterPcu6ValuePower2 OBJECT-TYPE
    SYNTAX INTEGER 
    ACCESS read-only
    STATUS mandatory
    DESCRIPTION
      "Calculated actual power 2 (W). Calculated from cmcTcMasterPcu6ValueEnergy2/time"
    ::= { cmcTcMasterPcu6Values 6 }
          
  cmcTcMasterPcu6ValueTemperature OBJECT-TYPE
    SYNTAX INTEGER 
    ACCESS read-only
    STATUS mandatory
    DESCRIPTION
      "Actual value of temperature 1 in deg C or deg F"
    ::= { cmcTcMasterPcu6Values 7 }
          
--cmcTcMasterPcu6Status-group

  cmcTcMasterPcu6StatusInput1 OBJECT-TYPE
    SYNTAX INTEGER {
      false(1),
      true(2),
      pending(3),
      notAvail(4)
    }
    ACCESS read-only
    STATUS mandatory
    DESCRIPTION
      "Status of digital Input 1
       (1) digital signal is true (contact closed if setup is NO)
       (2) digital signal is false(contact opened if setup is NO),
       note setup of input (NO/NC)
       (3) digital input is pending, note setup of delay"
    ::= { cmcTcMasterPcu6Status 1 }

  cmcTcMasterPcu6StatusInput2 OBJECT-TYPE
    SYNTAX INTEGER {
      false(1),
      true(2),
      pending(3),
      notAvail(4)
    }
    ACCESS read-only
    STATUS mandatory
    DESCRIPTION
      "Status of digital Input 2
       (1) digital signal is true (contact closed if setup is NO)
       (2) digital signal is false(contact opened if setup is NO),
       note setup of input (NO/NC)
       (3) digital input is pending, note setup of delay"
    ::= { cmcTcMasterPcu6Status 2 }

  cmcTcMasterPcu6StatusPower1 OBJECT-TYPE
    SYNTAX INTEGER {
      ok(1),
      tooHigh(2),
      tooLow(3),
      warning(4),
      error(5),
      notAvail(6)
    }
    ACCESS read-only
    STATUS mandatory
    DESCRIPTION
      "Status Power 1, see setpoints"
    ::= { cmcTcMasterPcu6Status 3 }

  cmcTcMasterPcu6StatusPower2 OBJECT-TYPE
    SYNTAX INTEGER {
      ok(1),
      tooHigh(2),
      tooLow(3),
      warning(4),
      error(5),
      notAvail(6)
    }
    ACCESS read-only
    STATUS mandatory
    DESCRIPTION
      "Status Power 2, see setpoints"
    ::= { cmcTcMasterPcu6Status 4 }

  cmcTcMasterPcu6StatusTemperature OBJECT-TYPE
    SYNTAX INTEGER {
      ok(1),
      tooHigh(2),
      tooLow(3),
      warning(4),
      error(5)
    }
    ACCESS read-only
    STATUS mandatory
    DESCRIPTION
      "Status temperature 1, OK/ too high/ too low
       (see setpoints of temperature 1)"
    ::= { cmcTcMasterPcu6Status 5 }

--cmcTcMasterPcu6Status-table-group

  cmcTcMasterPcu6OutletsNumber OBJECT-TYPE
    SYNTAX INTEGER 
    ACCESS read-only
    STATUS mandatory
    DESCRIPTION
      "Number of value-table entries=number of outlets available on this unit"
    ::= { cmcTcMasterPcu6StatusTable1 1 }

  cmcTcMasterPcu6StatusTable OBJECT-TYPE
    SYNTAX SEQUENCE OF CmcTcMasterPcu6StatusEntry
    ACCESS not-accessible
    STATUS mandatory
    DESCRIPTION
      "Headline of status-table"
    ::= { cmcTcMasterPcu6StatusTable1 2 }

  cmcTcMasterPcu6StatusEntry OBJECT-TYPE
    SYNTAX CmcTcMasterPcu6StatusEntry
    ACCESS not-accessible
    STATUS mandatory
    DESCRIPTION
      "Entries of status-table"
    INDEX { cmcTcMasterPcu6StatusIndex }
    ::= { cmcTcMasterPcu6StatusTable 1 }

    CmcTcMasterPcu6StatusEntry ::=
      SEQUENCE {
        cmcTcMasterPcu6StatusIndex
          INTEGER,
        cmcTcMasterPcu6StatusText
          DisplayString (SIZE (0..31)),                
        cmcTcMasterPcu6StatusStatus
          INTEGER,
        cmcTcMasterPcu6ControlSNMP
          INTEGER,
        cmcTcMasterPcu6FrontSwitch
          INTEGER,
        cmcTcMasterPcu6Delay
          INTEGER,
        cmcTcMasterPcu6Input1
          INTEGER,
        cmcTcMasterPcu6Input2
          INTEGER,
        cmcTcMasterPcu6Temperature
          INTEGER,          
        cmcTcMasterPcu6Power
          INTEGER,          
        cmcTcMasterPcu6RestoreOutputStatus
          INTEGER           
      }

    cmcTcMasterPcu6StatusIndex OBJECT-TYPE
      SYNTAX INTEGER (1..32000)
      ACCESS read-only
      STATUS mandatory
      DESCRIPTION
        "Index for the list of value entries. Its value ranges
         between 1 and the value of cmcTcMasterPcu6OutletsNumber."
      ::= { cmcTcMasterPcu6StatusEntry 1 }

    cmcTcMasterPcu6StatusText OBJECT-TYPE
      SYNTAX DisplayString (SIZE (0..31))
      ACCESS read-write
      STATUS mandatory
      DESCRIPTION
        "Descriptional text for each outlet (entry in the table)"
      ::= { cmcTcMasterPcu6StatusEntry 2 }
              
    cmcTcMasterPcu6StatusStatus OBJECT-TYPE
      SYNTAX INTEGER {
        ok(1),
        onFrontKey(2),
        offFrontKey(3),
        onWEB(4),
        offWEB(5),
        onInput1(6),
        offInput1(7),
        onInput2(8),
        offInput2(9),
        onTemp(10),
        offTemp(11),
        onSNMP(12),
        offSNMP(13),
        onTimer(14),
        offTimer(15),
        onDelay(16),
        onConsole(17),
        offConsole(18),
        onReboot(19), 
        offReboot(20),
        onPower(21),
        offPower(22)
      }
      ACCESS read-only
      STATUS mandatory
      DESCRIPTION
        "Actual status of the outlet"
      ::= { cmcTcMasterPcu6StatusEntry 3 }

    cmcTcMasterPcu6ControlSNMP OBJECT-TYPE
      SYNTAX INTEGER  {
        on(1),
        off(2)
      }
      ACCESS read-write
      STATUS mandatory
      DESCRIPTION
        "Control via SNMP"
      ::= { cmcTcMasterPcu6StatusEntry 4 }

    cmcTcMasterPcu6FrontSwitch OBJECT-TYPE
      SYNTAX INTEGER {
        disabled(1),
        enabled(2)
      }
      ACCESS read-write
      STATUS mandatory
      DESCRIPTION
        "Control via front switch"
      ::= { cmcTcMasterPcu6StatusEntry 5 }
 
    cmcTcMasterPcu6Delay OBJECT-TYPE
      SYNTAX INTEGER (0..300)
      ACCESS read-write
      STATUS mandatory
      DESCRIPTION
        "Value for delay time in seconds.
         Value>0: Output is switched off for this time (in sec)"
      ::= { cmcTcMasterPcu6StatusEntry 6 }

    cmcTcMasterPcu6Input1 OBJECT-TYPE
      SYNTAX INTEGER {
        disabled(1),
        switchOn(2),
        switchOff(3),
        switchOnOff(4)
      }
      ACCESS read-write
      STATUS mandatory
      DESCRIPTION
        "Control via digital input 1
         (1): disabled
         (2): output is switched on in case of input 1 alarm
         (3): output is switched off in case of input 1 alarm
         (4): output has same status as input 1"
      ::= { cmcTcMasterPcu6StatusEntry 7 }

    cmcTcMasterPcu6Input2 OBJECT-TYPE
      SYNTAX INTEGER {
        disabled(1),
        switchOn(2),
        switchOff(3),
        switchOnOff(4)
      }
      ACCESS read-write
      STATUS mandatory
      DESCRIPTION
        "Control via digital input 2
         (1): disabled
         (2): output is switched on in case of input 2 alarm
         (3): output is switched off in case of input 2 alarm
         (4): output has same status as input 2"             
      ::= { cmcTcMasterPcu6StatusEntry 8 }

    cmcTcMasterPcu6Temperature OBJECT-TYPE
      SYNTAX INTEGER {
        disabled(1),
        switchOffAlarm(2),
        switchOnAlarm(3),
        switchOffSetpoint(4),
        switchOnSetpoint(5)
      }
      ACCESS read-write
      STATUS mandatory
      DESCRIPTION
        "Control via temperature alarm or setpoint
         (1): disabled
         (2): output is switched off in case of temperature alarm
         (3): output is switched on in case of temperature alarm
         (4): output is switched off if temperature setpoint (cmcTcMasterPcu6SetpointTemperature)
              is reached
         (5): output is switched on if temperature setpoint (cmcTcMasterPcu6SetpointTemperature)
              is reached"
      ::= { cmcTcMasterPcu6StatusEntry 9 }   
    
    cmcTcMasterPcu6Power OBJECT-TYPE
      SYNTAX INTEGER {
        disabled(1),
        switchOffAlarm(2),
        switchOffWarning(3),
        switchOnAlarm(4),
        switchOnWarning(5)
      }
      ACCESS read-write
      STATUS mandatory
      DESCRIPTION
        "Control via power setpoint
         (1): disabled
         (2): output is switched off upon power high alarm (cmcTcMasterPcu6SetpointHighPower1)
         (3): output is switched off upon power warning (cmcTcMasterPcu6SetpointWarningPower1)
         (4): output is switched on upon power alarm (cmcTcMasterPcu6SetpointHigh(Low)Power1)
         (5): output is switched on upon power warning (cmcTcMasterPcu6SetpointWarningPower1)             "
      ::= { cmcTcMasterPcu6StatusEntry 10 }                

    cmcTcMasterPcu6RestoreOutputStatus OBJECT-TYPE
      SYNTAX INTEGER {
        disabled(1),
        enabled(2)
      }
      ACCESS read-write
      STATUS mandatory
      DESCRIPTION
        "Save last output status and switch output to this status after reboot"
      ::= { cmcTcMasterPcu6StatusEntry 11 }
                
--cmcTcMasterPcu6SetupGeneral-group

  cmcTcMasterPcu6SetTempUnit OBJECT-TYPE
    SYNTAX INTEGER {
      celsius(1),
      fahrenheit(2)
    }
    ACCESS read-write
    STATUS mandatory
    DESCRIPTION
      "Unit of all temperature values and setpoints, Celsius or Fahrenheit"
    ::= { cmcTcMasterPcu6SetupGeneral 1 }

  cmcTcMasterPcu6SetBeeper OBJECT-TYPE
    SYNTAX INTEGER {
      off(1),
      on(2),
      enableClear(3)
    }
    ACCESS read-write
    STATUS mandatory
    DESCRIPTION
      "Audible alarm in PCU unit:
       (1): beeper is off (general)
       (2): beeper is on (Alarm)
       (3): enable Clear (cmcTcMasterPcu6ClearAlarm)"
    ::= { cmcTcMasterPcu6SetupGeneral 2 }

  cmcTcMasterPcu6LogicRelay OBJECT-TYPE
    SYNTAX INTEGER {
      closeAtAlarm(1),
      openAtAlarm(2),
      off(3),
      enableRemote(4)
    }
    ACCESS read-write
    STATUS mandatory
    DESCRIPTION
      "Logic of alarm relay: 
       (1): Relay will pick up in case of an alarm
       (2): Relay will release in case of an alarm
       (3): Relay off (general)
       (4): enable remote relay control (SNMP set)"
    ::= { cmcTcMasterPcu6SetupGeneral 3 }
 
  cmcTcMasterPcu6ClearRelay OBJECT-TYPE
    SYNTAX INTEGER {
      disabled(1),
      enabled(2)
    }
    ACCESS read-write
    STATUS mandatory
    DESCRIPTION
      "Enable clear of alarm relay: 
       (1): Relay cannot be cleared by cmcTcMasterPcu6ClearAlarm
       (2): Relay can be cleared by cmcTcMasterPcu6ClearAlarm"
    ::= { cmcTcMasterPcu6SetupGeneral 4 }                  

  cmcTcMasterPcu6WebAccess OBJECT-TYPE
    SYNTAX INTEGER {
      viewOnly(1),
      fullAccess(2),
      off(3)
    }
    ACCESS read-write
    STATUS mandatory
    DESCRIPTION
      "Web access via HTTP: 
       (1): view only
       (2): full Access, read and set
       (3): Web disabled (general)"
    ::= { cmcTcMasterPcu6SetupGeneral 5 }
 
  cmcTcMasterPcu6SetupDate OBJECT-TYPE
    SYNTAX DisplayString (SIZE (0..10))
    ACCESS read-write
    STATUS mandatory
    DESCRIPTION
      "actual Date in format DD.MM.YYYY"
    ::= { cmcTcMasterPcu6SetupGeneral 6 }

  cmcTcMasterPcu6SetupTime OBJECT-TYPE
    SYNTAX DisplayString (SIZE (0..8))
    ACCESS read-write
    STATUS mandatory
    DESCRIPTION
      "actual Time in format HH:MM:SS, HH (0-23), MM (0-59), SS (0-59)"
    ::= { cmcTcMasterPcu6SetupGeneral 7 }

--cmcTcMasterPcu6TimerTable1-group
 
  cmcTcMasterPcu6TimerNumber OBJECT-TYPE
    SYNTAX INTEGER 
    ACCESS read-only
    STATUS mandatory
    DESCRIPTION
      "Number of timers available on this unit"
    ::= { cmcTcMasterPcu6TimerTable1 1 }

  cmcTcMasterPcu6TimerTable OBJECT-TYPE
    SYNTAX SEQUENCE OF CmcTcMasterPcu6TimerEntry
    ACCESS not-accessible
    STATUS mandatory
    DESCRIPTION
      "Headline of timer-table"
    ::= { cmcTcMasterPcu6TimerTable1 2 }

  cmcTcMasterPcu6TimerEntry OBJECT-TYPE
    SYNTAX CmcTcMasterPcu6TimerEntry
    ACCESS not-accessible
    STATUS mandatory
    DESCRIPTION
      "Entries of timer-table"
    INDEX { cmcTcMasterPcu6TimerIndex }
    ::= { cmcTcMasterPcu6TimerTable 1 }

    CmcTcMasterPcu6TimerEntry ::=
      SEQUENCE {
        cmcTcMasterPcu6TimerIndex
          INTEGER,
        cmcTcMasterPcu6TimerStatus
          INTEGER,
        cmcTcMasterPcu6TimerDayOfWeek
          INTEGER,  
        cmcTcMasterPcu6TimeOn 
          DisplayString (SIZE (0..5)),                              
        cmcTcMasterPcu6TimeOff 
          DisplayString (SIZE (0..5)),                              
        cmcTcMasterPcu6TimeControl
          INTEGER,
        cmcTcMasterPcu6TimerOutput1
          INTEGER,
        cmcTcMasterPcu6TimerOutput2
          INTEGER         
      }

    cmcTcMasterPcu6TimerIndex OBJECT-TYPE
      SYNTAX INTEGER (1..32000)
      ACCESS read-only
      STATUS mandatory
      DESCRIPTION
        "Index for the list of timer entries. Its value ranges
         between 1 and the value of cmcTcMasterPcu6TimerNumber." 
      ::= { cmcTcMasterPcu6TimerEntry 1 }

    cmcTcMasterPcu6TimerStatus OBJECT-TYPE
      SYNTAX INTEGER {
        switchedOff(1),
        switchedOn(2),
        noTime(3) 
      }
      ACCESS read-only
      STATUS mandatory
      DESCRIPTION
        "Actual status of the timer"
      ::= { cmcTcMasterPcu6TimerEntry 2 }

    cmcTcMasterPcu6TimerDayOfWeek OBJECT-TYPE
      SYNTAX INTEGER {
        sun(1),
        mon(2),
        tue(3) ,
        wed(4),
        thu(5),
        fre(6),
        sat(7),
        sat-sun(8),
        mo-fr(9),
        mo-su(10)
      }
      ACCESS read-write
      STATUS mandatory
      DESCRIPTION
        "Day when the timer is active"
      ::= { cmcTcMasterPcu6TimerEntry 3 }
             
    cmcTcMasterPcu6TimeOn OBJECT-TYPE
      SYNTAX DisplayString (SIZE (0..5))
      ACCESS read-write
      STATUS mandatory
      DESCRIPTION
        "Time to switch on current outlet, 
         Format: HH:MM"
      ::= { cmcTcMasterPcu6TimerEntry 4 }

    cmcTcMasterPcu6TimeOff OBJECT-TYPE
      SYNTAX DisplayString (SIZE (0..5))
      ACCESS read-write
      STATUS mandatory
      DESCRIPTION
        "Time to switch off current outlet,
         Format: HH:MM"
      ::= { cmcTcMasterPcu6TimerEntry 5 }

    cmcTcMasterPcu6TimeControl OBJECT-TYPE
      SYNTAX INTEGER {
        disabled(1),
        enabled(2)
      }
      ACCESS read-write
      STATUS mandatory
      DESCRIPTION
        "Control via RTC"
      ::= { cmcTcMasterPcu6TimerEntry 6 }

    cmcTcMasterPcu6TimerOutput1 OBJECT-TYPE
      SYNTAX INTEGER 
      ACCESS read-write
      STATUS mandatory
      DESCRIPTION
        "Output which is controlled via timer"
      ::= { cmcTcMasterPcu6TimerEntry 7 }

    cmcTcMasterPcu6TimerOutput2 OBJECT-TYPE
      SYNTAX INTEGER 
      ACCESS read-write
      STATUS mandatory
      DESCRIPTION
        "Output which is controlled via timer"
      ::= { cmcTcMasterPcu6TimerEntry 8 }

--cmcTcMasterPcu6SetupPower1-group                     

  cmcTcMasterPcu6SetupPower1Avail OBJECT-TYPE
    SYNTAX INTEGER {
      notAvailable(1),
      available(2)
    }
    ACCESS read-write
    STATUS mandatory
    DESCRIPTION
      "Energy sensor 1 sensor:   
       (1) not available
       (2) available"
    ::= { cmcTcMasterPcu6SetupPower1 1 }

  cmcTcMasterPcu6SetupPower1Relay OBJECT-TYPE
    SYNTAX INTEGER {
      disabled(1),
      enabled(2)
    }
    ACCESS read-write
    STATUS mandatory
    DESCRIPTION
      "Alert handling of Alarm Relay in case of an alarm condition
       of Power 1:  
       (1) no switching of Relays
       (2) Relay will switch"
    ::= { cmcTcMasterPcu6SetupPower1 2 }

  cmcTcMasterPcu6SetupPower1Beeper OBJECT-TYPE
    SYNTAX INTEGER {
      disabled(1),
      enabled(2)
    }
    ACCESS read-write
    STATUS mandatory
    DESCRIPTION
      "Alert handling of beeper of in case of an alarm condition
       of Power 1: 
       (1) No Audible Alarm
       (2) Start Audible Alarm"
    ::= { cmcTcMasterPcu6SetupPower1 3 }

--cmcTcMasterPcu6SetupPower2-group                     

  cmcTcMasterPcu6SetupPower2Avail OBJECT-TYPE
    SYNTAX INTEGER {
      notAvailable(1),
      available(2)
    }
    ACCESS read-write
    STATUS mandatory
    DESCRIPTION
      "Energy sensor 2:   
       (1) not available
       (2) available"
    ::= { cmcTcMasterPcu6SetupPower2 1 }

  cmcTcMasterPcu6SetupPower2Relay OBJECT-TYPE
    SYNTAX INTEGER {
      disabled(1),
      enabled(2)
    }
    ACCESS read-write
    STATUS mandatory
    DESCRIPTION
      "Alert handling of Alarm Relay in case of an alarm condition
       of Power 2:  
       (1) no switching of Relay
       (2) Relay will switch"
    ::= { cmcTcMasterPcu6SetupPower2 2 }

  cmcTcMasterPcu6SetupPower2Beeper OBJECT-TYPE
    SYNTAX INTEGER {
      disabled(1),
      enabled(2)
    }
    ACCESS read-write
    STATUS mandatory
    DESCRIPTION
      "Alert handling of beeper of in case of an alarm condition
       of Power 2: 
       (1) No Audible Alarm
       (2) Start Audible Alarm"
    ::= { cmcTcMasterPcu6SetupPower2 3 }

--cmcTcMasterPcu6SetupInput1-group

  cmcTcMasterPcu6SetupInput1Avail OBJECT-TYPE
    SYNTAX INTEGER {
      notAvailable(1),
      available(2)
    }
    ACCESS read-write
    STATUS mandatory
    DESCRIPTION
      "Input 1 sensor:   
       (1) not available
       (2) available"
    ::= { cmcTcMasterPcu6SetupInput1 1 }

  cmcTcMasterPcu6SetupInput1Relay OBJECT-TYPE
    SYNTAX INTEGER {
      disabled(1),
      enabled(2)
    }
    ACCESS read-write
    STATUS mandatory
    DESCRIPTION
      "Alert handling of Alarm Relay in case of an alarm condition
       of Input 1:  
       (1) no switching of Relay
       (2) Relay will switch"
    ::= { cmcTcMasterPcu6SetupInput1 2 }

  cmcTcMasterPcu6SetupInput1Beeper OBJECT-TYPE
    SYNTAX INTEGER {
      disabled(1),
      enabled(2)
    }
    ACCESS read-write
    STATUS mandatory
    DESCRIPTION
      "Alert handling of beeper of in case of an alarm condition
       of Input 1: 
       (1) No Audible Alarm
       (2) Start Audible Alarm"
    ::= { cmcTcMasterPcu6SetupInput1 3 }

  cmcTcMasterPcu6SetupInput1Contact OBJECT-TYPE
    SYNTAX INTEGER {
      contactNO(1),
      contactNC(2),
      notAvail(3)
    }
    ACCESS read-write
    STATUS mandatory
    DESCRIPTION
      "Setup of digital input 1"
    ::= { cmcTcMasterPcu6SetupInput1 4 }

  cmcTcMasterPcu6SetupInput1Delay OBJECT-TYPE
    SYNTAX INTEGER (0..60)
    ACCESS read-write
    STATUS mandatory
    DESCRIPTION
      "Delay for changing of input state"
    ::= { cmcTcMasterPcu6SetupInput1 5 }

--cmcTcMasterPcu6SetupInput2-group

  cmcTcMasterPcu6SetupInput2Avail OBJECT-TYPE
    SYNTAX INTEGER {
      notAvailable(1),
      available(2)
    }
    ACCESS read-write
    STATUS mandatory
    DESCRIPTION
      "Input 2 sensor:   
       (2) available
       (1) not available"
    ::= { cmcTcMasterPcu6SetupInput2 1 }

  cmcTcMasterPcu6SetupInput2Relay OBJECT-TYPE
    SYNTAX INTEGER {
      disabled(1),
      enabled(2)
    }
    ACCESS read-write
    STATUS mandatory
    DESCRIPTION
      "Alert handling of Alarm Relay in case of an alarm condition
       of Input 1:  
       (1) no switching of Relays
       (2) Relay will switch"
    ::= { cmcTcMasterPcu6SetupInput2 2 }

  cmcTcMasterPcu6SetupInput2Beeper OBJECT-TYPE
    SYNTAX INTEGER {
      disabled(1),
      enabled(2)
    }
    ACCESS read-write
    STATUS mandatory
    DESCRIPTION
      "Alert handling of beeper of in case of an alarm condition
       of Input 2: 
       (1) No Audible Alarm
       (2) Start Audible Alarm"
    ::= { cmcTcMasterPcu6SetupInput2 3 }

  cmcTcMasterPcu6SetupInput2Contact OBJECT-TYPE
    SYNTAX INTEGER {
      contactNO(1),
      contactNC(2),
      notAvail(3)
    }
    ACCESS read-write
    STATUS mandatory
    DESCRIPTION
      "Setup of digital input 2"
    ::= { cmcTcMasterPcu6SetupInput2 4 }

  cmcTcMasterPcu6SetupInput2Delay OBJECT-TYPE
    SYNTAX INTEGER (0..60)
    ACCESS read-write
    STATUS mandatory
    DESCRIPTION
      "Delay for changing of input state"
    ::= { cmcTcMasterPcu6SetupInput2 5 }

--cmcTcMasterPcu6SetupTemperature-group                     

  cmcTcMasterPcu6SetupTemperatureAvail OBJECT-TYPE
    SYNTAX INTEGER {
      notAvailable(1),
      available(2)
    }
    ACCESS read-write
    STATUS mandatory
    DESCRIPTION
      "Temp sensor 1:   
       (1) not available
       (2) available"
    ::= { cmcTcMasterPcu6SetupTemperature 1 }

  cmcTcMasterPcu6SetupTemperatureRelay OBJECT-TYPE
    SYNTAX INTEGER {
      disabled(1),
      enabled(2)
    }
    ACCESS read-write
    STATUS mandatory
    DESCRIPTION
      "Alert handling of Alarm Relay in case of an alarm condition
       of Temperature:  
       (1) no switching of Relays
       (2) Relay will switch"
    ::= { cmcTcMasterPcu6SetupTemperature 2 }

  cmcTcMasterPcu6SetupTemperatureBeeper OBJECT-TYPE
    SYNTAX INTEGER {
      disabled(1),
      enabled(2)
    }
    ACCESS read-write
    STATUS mandatory
    DESCRIPTION
      "Alert handling of beeper of in case of an alarm condition
       of Temperature: 
       (1) No Audible Alarm
       (2) Start Audible Alarm"
    ::= { cmcTcMasterPcu6SetupTemperature 3 }

--cmcTcMasterPcu6SetupGeneral-group

  cmcTcMasterPcu6SetMessage OBJECT-TYPE
    SYNTAX DisplayString (SIZE (0..31))
    ACCESS read-write
    STATUS mandatory
    DESCRIPTION
      "Set message"
    ::= { cmcTcMasterPcu6SetupDevice 1 }

--cmcTcMasterPcu6Setpoints-group

  cmcTcMasterPcu6SetpointHighPower1 OBJECT-TYPE
    SYNTAX INTEGER 
    ACCESS read-write
    STATUS mandatory
    DESCRIPTION
      "Setpoint high value power consumption 1 alarm"
    ::= { cmcTcMasterPcu6Setpoints 1 }

  cmcTcMasterPcu6SetpointWarningPower1 OBJECT-TYPE
    SYNTAX INTEGER 
    ACCESS read-write
    STATUS mandatory
    DESCRIPTION
      "Setpoint warning value power consumption 1 alarm"
    ::= { cmcTcMasterPcu6Setpoints 2 }

  cmcTcMasterPcu6SetpointLowPower1 OBJECT-TYPE
    SYNTAX INTEGER
    ACCESS read-write
    STATUS mandatory
    DESCRIPTION
      "Setpoint low value power consumption 1 alarm"
    ::= { cmcTcMasterPcu6Setpoints 3 }

  cmcTcMasterPcu6SetpointHighPower2 OBJECT-TYPE
    SYNTAX INTEGER 
    ACCESS read-write
    STATUS mandatory
    DESCRIPTION
      "Setpoint high value power consumption 2 alarm"
    ::= { cmcTcMasterPcu6Setpoints 4 }

  cmcTcMasterPcu6SetpointWarningPower2 OBJECT-TYPE
    SYNTAX INTEGER 
    ACCESS read-write
    STATUS mandatory
    DESCRIPTION
      "Setpoint warning value power consumption 2 alarm"
    ::= { cmcTcMasterPcu6Setpoints 5 }

  cmcTcMasterPcu6SetpointLowPower2 OBJECT-TYPE
    SYNTAX INTEGER
    ACCESS read-write
    STATUS mandatory
    DESCRIPTION
      "Setpoint low value power consumption 2 alarm"
    ::= { cmcTcMasterPcu6Setpoints 6 }

  cmcTcMasterPcu6SetpointHighTemperature OBJECT-TYPE
    SYNTAX INTEGER (0..200)
    ACCESS read-write
    STATUS mandatory
    DESCRIPTION
      "Setpoint high value alarm temperature "
    ::= { cmcTcMasterPcu6Setpoints 7 }

  cmcTcMasterPcu6SetpointLowTemperature OBJECT-TYPE
    SYNTAX INTEGER (0..50)
    ACCESS read-write
    STATUS mandatory
    DESCRIPTION
      "Setpoint low value alarm temperature "
    ::= { cmcTcMasterPcu6Setpoints 8 }
 
  cmcTcMasterPcu6SetpointTemperature OBJECT-TYPE
    SYNTAX INTEGER (0..200)
    ACCESS read-write
    STATUS mandatory
    DESCRIPTION
      "Setpoint temperature for outlet control 
       and temperature warning"
    ::= { cmcTcMasterPcu6Setpoints 9 }

  cmcTcMasterPcu6SetpointTemperatureHyst OBJECT-TYPE
    SYNTAX INTEGER (0..15)
    ACCESS read-write
    STATUS mandatory
    DESCRIPTION
      "Hysteresis for cmcTcMasterPcu6SetpointTemperature"
    ::= { cmcTcMasterPcu6Setpoints 10 }
 
--cmcTcMasterPcu6Control-group

  cmcTcMasterPcu6ResetEnergy1 OBJECT-TYPE
    SYNTAX INTEGER {
      noReset(1),
      reset(2)
    }
    ACCESS read-write
    STATUS mandatory
    DESCRIPTION
      "Reset value of cmcTcMasterPcu6ValueEnergy1Time"
    ::= { cmcTcMasterPcu6Control 1 }

  cmcTcMasterPcu6ResetEnergy2 OBJECT-TYPE
    SYNTAX INTEGER {
      noReset(1),
      reset(2)
    }
    ACCESS read-write
    STATUS mandatory
    DESCRIPTION
      "Reset value of cmcTcMasterPcu6ValueEnergy2Time"
    ::= { cmcTcMasterPcu6Control 2 }

  cmcTcMasterPcu6ControlAlarmRelay OBJECT-TYPE
    SYNTAX INTEGER {
      relayOff(1),
      relayOn(2)
    }
    ACCESS read-write
    STATUS mandatory
    DESCRIPTION
      "Control of Alarm relay"
    ::= { cmcTcMasterPcu6Control 3 }

  cmcTcMasterPcu6ClearAlarm OBJECT-TYPE
    SYNTAX INTEGER {
      noClear(1),
      clear(2)
    }
    ACCESS read-write
    STATUS mandatory
    DESCRIPTION
      "Clear alarm, beeper and relay"
    ::= { cmcTcMasterPcu6Control 4 }

--cmcTcMasterPcu6TrapTable-group

  cmcTcMasterPcu6TrapTableNumber OBJECT-TYPE
    SYNTAX INTEGER 
    ACCESS read-only
    STATUS mandatory
    DESCRIPTION
      "Number of cmcTcMasterPcu6TrapTable entries. The number of trap-receivers avail."
    ::= { cmcTcMasterPcu6Traps 1 }

  cmcTcMasterPcu6TrapTable OBJECT-TYPE
    SYNTAX SEQUENCE OF CmcTcMasterPcu6TrapEntry
    ACCESS not-accessible
    STATUS mandatory
    DESCRIPTION
      "A list of trap-receiver entries"
    ::= { cmcTcMasterPcu6Traps 2 }

  cmcTcMasterPcu6TrapEntry OBJECT-TYPE
    SYNTAX CmcTcMasterPcu6TrapEntry
    ACCESS not-accessible
    STATUS mandatory
    DESCRIPTION
      "Entries of cmcTcMasterPcu6TrapTable"
    INDEX { cmcTcMasterPcu6TrapIndex }
    ::= { cmcTcMasterPcu6TrapTable 1 }

    CmcTcMasterPcu6TrapEntry ::=
      SEQUENCE {
        cmcTcMasterPcu6TrapIndex
          INTEGER,
        cmcTcMasterPcu6TrapStatus
          INTEGER,
        cmcTcMasterPcu6TrapIPaddress
          DisplayString
      }

    cmcTcMasterPcu6TrapIndex OBJECT-TYPE
      SYNTAX INTEGER (1..32000)
      ACCESS read-only
      STATUS mandatory
      DESCRIPTION
        "Index for the trap-receiver-table. Its value ranges between
         1 and the value of cmcTcMasterPcu6TrapTableNumber "
      ::= { cmcTcMasterPcu6TrapEntry 1 }

    cmcTcMasterPcu6TrapStatus OBJECT-TYPE
      SYNTAX INTEGER {
        disabled(1),
        enabled(2)
      }
      ACCESS read-write
      STATUS mandatory
      DESCRIPTION
        "Enable or disable trap receiver"
      ::= { cmcTcMasterPcu6TrapEntry 2 }

    cmcTcMasterPcu6TrapIPaddress OBJECT-TYPE
      SYNTAX DisplayString (SIZE (0..15))
      ACCESS read-write
      STATUS mandatory
      DESCRIPTION
        "IP-address of trap-receiver"
      ::= { cmcTcMasterPcu6TrapEntry 3 }

--cmcTcMasterTc6MibRev-group
          
  cmcTcMasterTc6MibMajRev OBJECT-TYPE
    SYNTAX INTEGER (1..32000)
    ACCESS read-only
    STATUS mandatory
    DESCRIPTION
      "The Major Revision level.
       A change in the major revision level represents a major change
       in the architecture of the MIB. A change in the major revision 
       level may indicate a significant change in the information,
       correct interpretation of data may require a MIB document
       with the same major revision level."
    ::= { cmcTcMasterTc6MibRev 1 }

  cmcTcMasterTc6MibMinRev OBJECT-TYPE
    SYNTAX INTEGER (0..32000)
    ACCESS read-only
    STATUS mandatory
    DESCRIPTION
      "The Minor Revision level.
       A change in the minor revision level may represent some minor
       additional support, no changes to any pre-existing information
       has occurred."
    ::= { cmcTcMasterTc6MibRev 2 }

  cmcTcMasterTc6MibCondition OBJECT-TYPE
    SYNTAX INTEGER {
      other (1),
      ok (2),
      degraded (3),
      failed (4),
      configChanged (5)
    }
    ACCESS read-only
    STATUS mandatory
    DESCRIPTION
      "The overall condition (status) of the system represented by
       this MIB. 
       (2) OK
       (3) a minor problem, warning condition (yellow LED on CMC-TC)
       (4) a major problem (red LED on CMC-TC)
       (5) configuration of sensor units changed or
           unit detected (red/yellow/green LED on CMC-TC)"
    ::= { cmcTcMasterTc6MibRev 3 }
          
--cmcTcMasterTc6Status-group

  cmcTcMasterTc6StatusDeviceCMC OBJECT-TYPE
    SYNTAX INTEGER {
      failed(1),
      ok(2)
    }
    ACCESS read-only
    STATUS mandatory
    DESCRIPTION
      "General Status of CMC-TC unit itself
       (1) failed
       (2) OK"
    ::= { cmcTcMasterTc6Status 1 }

  cmcTcMasterTc6UnitsConnected OBJECT-TYPE
    SYNTAX INTEGER 
    ACCESS read-only
    STATUS mandatory
    DESCRIPTION
      "Number of sensor units connected to the CMC-TC, Port 1 to 4"
    ::= { cmcTcMasterTc6Status 2 }

--unit 1

  cmcTcMasterTc6Unit1TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 1"
    ::= { cmcTcMasterTc6StatusSensorUnit1 1 }

  cmcTcMasterTc6Unit1Text OBJECT-TYPE
    SYNTAX DisplayString (SIZE (0..10))
    ACCESS read-write
    STATUS mandatory
    DESCRIPTION
      "Descriptional text for sensor unit connected to port 1"
    ::= { cmcTcMasterTc6StatusSensorUnit1 2 }

  cmcTcMasterTc6Unit1Serial OBJECT-TYPE
    SYNTAX INTEGER 
    ACCESS read-only
    STATUS mandatory
    DESCRIPTION
      "Serialnumber of sensor unit connected to port 1"
    ::= { cmcTcMasterTc6StatusSensorUnit1 3 }

  cmcTcMasterTc6Unit1Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 1
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc6StatusSensorUnit1 4 }

-- Sensors
              
  cmcTcMasterTc6Unit1NumberOfSensors OBJECT-TYPE
    SYNTAX INTEGER 
    ACCESS read-only
    STATUS mandatory
    DESCRIPTION
      "Number of sensors connected to sensor unit 1"
    ::= { cmcTcMasterTc6StatusUnit1Sensors 1 }

-- table with entry for each sensor available on this unit              

  cmcTcMasterTc6Unit1SensorTable OBJECT-TYPE
    SYNTAX SEQUENCE OF CmcTcMasterTc6Unit1SensorEntry
    ACCESS not-accessible
    STATUS mandatory
    DESCRIPTION
      "Headline of sensor table"
    ::= { cmcTcMasterTc6StatusUnit1Sensors 2 }

  cmcTcMasterTc6Unit1SensorEntry OBJECT-TYPE
    SYNTAX CmcTcMasterTc6Unit1SensorEntry
    ACCESS not-accessible
    STATUS mandatory
    DESCRIPTION
      "Entries of sensor table"
    INDEX { cmcTcMasterTc6Unit1SensorIndex }
    ::= { cmcTcMasterTc6Unit1SensorTable 1 }

    CmcTcMasterTc6Unit1SensorEntry ::=
      SEQUENCE {
        cmcTcMasterTc6Unit1SensorIndex
          INTEGER,
        cmcTcMasterTc6Unit1SensorType
          INTEGER,
        cmcTcMasterTc6Unit1SensorText
          DisplayString (SIZE (0..20)),                
        cmcTcMasterTc6Unit1SensorStatus
          INTEGER,
        cmcTcMasterTc6Unit1SensorValue
          INTEGER,
        cmcTcMasterTc6Unit1SensorSetHigh
          INTEGER,
        cmcTcMasterTc6Unit1SensorSetLow
          INTEGER,
        cmcTcMasterTc6Unit1SensorSetWarn
          INTEGER                
      }

    cmcTcMasterTc6Unit1SensorIndex OBJECT-TYPE
      SYNTAX INTEGER (1..32000)
      ACCESS read-only
      STATUS mandatory
      DESCRIPTION
        "Index for the list of value entries. Its value ranges
         between 1 and the value of cmcTcMasterTc6Unit1NumberOfSensors." 
      ::= { cmcTcMasterTc6Unit1SensorEntry 1 }

    cmcTcMasterTc6Unit1SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 1 to sensor[cmcTcMasterTc6Unit1SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc6Unit1SensorEntry 2 }

    cmcTcMasterTc6Unit1SensorText OBJECT-TYPE
      SYNTAX DisplayString (SIZE (0..20))
      ACCESS read-write
      STATUS mandatory
      DESCRIPTION
        "Descriptional text for each sensor (entry in the table)"
      ::= { cmcTcMasterTc6Unit1SensorEntry 3 }
              
    cmcTcMasterTc6Unit1SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc6Unit1SensorEntry 4 }

    cmcTcMasterTc6Unit1SensorValue OBJECT-TYPE
      SYNTAX INTEGER 
      ACCESS read-only
      STATUS mandatory
      DESCRIPTION
        "Value of sensor"
      ::= { cmcTcMasterTc6Unit1SensorEntry 5 }

    cmcTcMasterTc6Unit1SensorSetHigh OBJECT-TYPE
      SYNTAX INTEGER (0..300) 
      ACCESS read-write
      STATUS mandatory
      DESCRIPTION
        "Value for high setpoint of sensor"
      ::= { cmcTcMasterTc6Unit1SensorEntry 6 }

    cmcTcMasterTc6Unit1SensorSetLow OBJECT-TYPE
      SYNTAX INTEGER (0..300) 
      ACCESS read-write
      STATUS mandatory
      DESCRIPTION
        "Value for low setpoint of sensor,
         also used as alarm delay"
      ::= { cmcTcMasterTc6Unit1SensorEntry 7 }

    cmcTcMasterTc6Unit1SensorSetWarn OBJECT-TYPE
      SYNTAX INTEGER (0..300) 
      ACCESS read-write
      STATUS mandatory
      DESCRIPTION
        "Value for warning setpoint of sensor, 
         also used as fan threshold"
      ::= { cmcTcMasterTc6Unit1SensorEntry 8 }
                
-- Outputs              

  cmcTcMasterTc6Unit1NumberOfOutputs OBJECT-TYPE
    SYNTAX INTEGER 
    ACCESS read-only
    STATUS mandatory
    DESCRIPTION
      "Number of outputs available on sensor unit 1"
    ::= { cmcTcMasterTc6StatusUnit1Outputs 1 }

-- table with entry for each output available on this unit              
                
  cmcTcMasterTc6Unit1OutputTable OBJECT-TYPE
    SYNTAX SEQUENCE OF CmcTcMasterTc6Unit1OutputEntry
    ACCESS not-accessible
    STATUS mandatory
    DESCRIPTION
      "Headline of output table"
    ::= { cmcTcMasterTc6StatusUnit1Outputs 2 }

  cmcTcMasterTc6Unit1OutputEntry OBJECT-TYPE
    SYNTAX CmcTcMasterTc6Unit1OutputEntry
    ACCESS not-accessible
    STATUS mandatory
    DESCRIPTION
      "Entries of output table"
    INDEX { cmcTcMasterTc6Unit1OutputIndex }
    ::= { cmcTcMasterTc6Unit1OutputTable 1 }

    CmcTcMasterTc6Unit1OutputEntry ::=
      SEQUENCE {
        cmcTcMasterTc6Unit1OutputIndex
          INTEGER,
        cmcTcMasterTc6Unit1OutputType
          INTEGER,
        cmcTcMasterTc6Unit1OutputText
          DisplayString (SIZE (0..20)),                
        cmcTcMasterTc6Unit1OutputStatus
          INTEGER,
        cmcTcMasterTc6Unit1OutputValue
          INTEGER,
        cmcTcMasterTc6Unit1OutputSet
          INTEGER,
        cmcTcMasterTc6Unit1OutputConfig
          INTEGER,                
        cmcTcMasterTc6Unit1OutputDelay
          INTEGER,
        cmcTcMasterTc6Unit1OutputTimeoutAction
          INTEGER
      }

    cmcTcMasterTc6Unit1OutputIndex OBJECT-TYPE
      SYNTAX INTEGER (1..32000)
      ACCESS read-only
      STATUS mandatory
      DESCRIPTION
        "Index for the list of output entries. Its value ranges
         between 1 and the value of cmcTcMasterTc6Unit1NumberOfOutputs." 
      ::= { cmcTcMasterTc6Unit1OutputEntry 1 }

    cmcTcMasterTc6Unit1OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 1 to output[cmcTcMasterTc6Unit1OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc6Unit1OutputEntry 2 }

    cmcTcMasterTc6Unit1OutputText OBJECT-TYPE
      SYNTAX DisplayString (SIZE (0..20))
      ACCESS read-write
      STATUS mandatory
      DESCRIPTION
        "Descriptional text for each output (entry in the table)"
      ::= { cmcTcMasterTc6Unit1OutputEntry 3 }
              
    cmcTcMasterTc6Unit1OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc6Unit1OutputEntry 4 }

    cmcTcMasterTc6Unit1OutputValue OBJECT-TYPE
      SYNTAX INTEGER (-32000..32000) 
      ACCESS read-write
      STATUS mandatory
      DESCRIPTION
        "Value for output"
      ::= { cmcTcMasterTc6Unit1OutputEntry 5 }

    cmcTcMasterTc6Unit1OutputSet OBJECT-TYPE
      SYNTAX INTEGER {
        off (1),
        on (2),
        lock (3),
        unlock (4),
        unlockDelay (5)
      }
      ACCESS read-write
      STATUS mandatory
      DESCRIPTION
        "Command for output"
      ::= { cmcTcMasterTc6Unit1OutputEntry 6 }

    cmcTcMasterTc6Unit1OutputConfig OBJECT-TYPE
      SYNTAX INTEGER {
        disRemote (1),
        enRemote (2)
      }
      ACCESS read-write
      STATUS mandatory
      DESCRIPTION
        "Configuration for output
         1: 	disable remote control (e.g. keypad)
         2: 	enable remote control"
      ::= { cmcTcMasterTc6Unit1OutputEntry 7 }

    cmcTcMasterTc6Unit1OutputDelay OBJECT-TYPE
      SYNTAX INTEGER (0..999) 
      ACCESS read-write
      STATUS mandatory
      DESCRIPTION
        "Unsigned Value for delay, 
         after this time the output will fall into the previous state"
      ::= { cmcTcMasterTc6Unit1OutputEntry 8 }

    cmcTcMasterTc6Unit1OutputTimeoutAction OBJECT-TYPE
      SYNTAX INTEGER {
        stay (1),
        off (2),
        on (3)
      }
      ACCESS read-write
      STATUS mandatory
      DESCRIPTION
        "State for output if timeout (RS422) occurs"
      ::= { cmcTcMasterTc6Unit1OutputEntry 9 }
 
-- Messages
              
  cmcTcMasterTc6Unit1NumberOfMsgs OBJECT-TYPE
    SYNTAX INTEGER 
    ACCESS read-only
    STATUS mandatory
    DESCRIPTION
      "Number of messages that can be created with sensor unit 1"
    ::= { cmcTcMasterTc6StatusUnit1Msg 1 }

-- table with entry for each alarm available on this unit               
                
  cmcTcMasterTc6Unit1MsgTable OBJECT-TYPE
    SYNTAX SEQUENCE OF CmcTcMasterTc6Unit1MsgEntry
    ACCESS not-accessible
    STATUS mandatory
    DESCRIPTION
      "Headline of message table"
    ::= { cmcTcMasterTc6StatusUnit1Msg 2 }

  cmcTcMasterTc6Unit1MsgEntry OBJECT-TYPE
    SYNTAX CmcTcMasterTc6Unit1MsgEntry
    ACCESS not-accessible
    STATUS mandatory
    DESCRIPTION
      "Entries of message table"
    INDEX { cmcTcMasterTc6Unit1MsgIndex }
    ::= { cmcTcMasterTc6Unit1MsgTable 1 }

    CmcTcMasterTc6Unit1MsgEntry ::=
      SEQUENCE {
        cmcTcMasterTc6Unit1MsgIndex
          INTEGER, 
        cmcTcMasterTc6Unit1MsgText
          DisplayString (SIZE (0..20)),                
        cmcTcMasterTc6Unit1MsgStatus
          INTEGER,                
        cmcTcMasterTc6Unit1MsgRelay
          INTEGER,
        cmcTcMasterTc6Unit1MsgBeeper
          INTEGER,
        cmcTcMasterTc6Unit1MsgTrap1
          INTEGER,
        cmcTcMasterTc6Unit1MsgTrap2
          INTEGER,
        cmcTcMasterTc6Unit1MsgTrap3
          INTEGER,
        cmcTcMasterTc6Unit1MsgTrap4
          INTEGER,                 
        cmcTcMasterTc6Unit1MsgQuit
          INTEGER              
      }

    cmcTcMasterTc6Unit1MsgIndex OBJECT-TYPE
      SYNTAX INTEGER (1..32000)
      ACCESS read-only
      STATUS mandatory
      DESCRIPTION
        "Index for the list of message entries. Its value ranges
         between 1 and the value of cmcTcMasterTc6Unit1NumberOfMsgs." 
      ::= { cmcTcMasterTc6Unit1MsgEntry 1 }

    cmcTcMasterTc6Unit1MsgText OBJECT-TYPE
      SYNTAX DisplayString (SIZE (0..20))
      ACCESS read-write
      STATUS mandatory
      DESCRIPTION
        "Descriptional text for each message (entry in the table)"
      ::= { cmcTcMasterTc6Unit1MsgEntry 2 }
              
    cmcTcMasterTc6Unit1MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc6Unit1OutputSet)
         17: door is unlocked by WEB
         18: door is unlocked by timer
         19: no access, wrong keycode or cardnumber
         20: orientation of PSM-Unit is circuit 1
         21: orientation of PSM-Unit is circuit 2"
      ::= { cmcTcMasterTc6Unit1MsgEntry 3 }
        
    cmcTcMasterTc6Unit1MsgRelay OBJECT-TYPE
      SYNTAX INTEGER {
        disable (1),
        enable (2)
      }
      ACCESS read-write
      STATUS mandatory
      DESCRIPTION
        "Setup of Alarm relay for this message/alarm
         1:        no switching of alarm relay             
         2:        switching of alarm relay" 
      ::= { cmcTcMasterTc6Unit1MsgEntry 4 }

    cmcTcMasterTc6Unit1MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc6Unit1MsgEntry 5 }

    cmcTcMasterTc6Unit1MsgTrap1 OBJECT-TYPE
      SYNTAX INTEGER {
        disable (1),
        enable (2)
      }
      ACCESS read-write
      STATUS mandatory
      DESCRIPTION
        "Trap receiver 1 activated"
      ::= { cmcTcMasterTc6Unit1MsgEntry 6 }

    cmcTcMasterTc6Unit1MsgTrap2 OBJECT-TYPE
      SYNTAX INTEGER {
        disable (1),
        enable (2)
      }
      ACCESS read-write
      STATUS mandatory
      DESCRIPTION
        "Trap receiver 2 activated"
      ::= { cmcTcMasterTc6Unit1MsgEntry 7 }
 
    cmcTcMasterTc6Unit1MsgTrap3 OBJECT-TYPE
      SYNTAX INTEGER {
        disable (1),
        enable (2)
      }
      ACCESS read-write
      STATUS mandatory
      DESCRIPTION
        "Trap receiver 3 activated"
      ::= { cmcTcMasterTc6Unit1MsgEntry 8 }

    cmcTcMasterTc6Unit1MsgTrap4 OBJECT-TYPE
      SYNTAX INTEGER {
        disable (1),
        enable (2)
      }
      ACCESS read-write
      STATUS mandatory
      DESCRIPTION
        "Trap receiver 4 and Event Logging activated"
      ::= { cmcTcMasterTc6Unit1MsgEntry 9 }

    cmcTcMasterTc6Unit1MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc6Unit1MsgEntry 10 }

-- unit2

  cmcTcMasterTc6Unit2TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 2"
    ::= { cmcTcMasterTc6StatusSensorUnit2 1 }

  cmcTcMasterTc6Unit2Text OBJECT-TYPE
    SYNTAX DisplayString (SIZE (0..10))
    ACCESS read-write
    STATUS mandatory
    DESCRIPTION
      "Descriptional text for sensor unit connected to port 2"
    ::= { cmcTcMasterTc6StatusSensorUnit2 2 }

  cmcTcMasterTc6Unit2Serial OBJECT-TYPE
    SYNTAX INTEGER 
    ACCESS read-only
    STATUS mandatory
    DESCRIPTION
      "Serialnumber of sensor unit connected to port 2"
    ::= { cmcTcMasterTc6StatusSensorUnit2 3 }

  cmcTcMasterTc6Unit2Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 2
       (1) OK
       (2) error
       (3) configuration of sensor unit has changed, confirmation required
       (4) Quit from sensor unit to confirm configuration changes
       (5) timeout of sensor unit, confirmation required
       (6) sensor unit detected, needs to be confirmed
       (8) supply voltage is too low"              
    ::= { cmcTcMasterTc6StatusSensorUnit2 4 }

-- unit 2 table

-- Sensors              

  cmcTcMasterTc6Unit2NumberOfSensors OBJECT-TYPE
    SYNTAX INTEGER 
    ACCESS read-only
    STATUS mandatory
    DESCRIPTION
      "Number of sensors connected to sensor unit 2"
    ::= { cmcTcMasterTc6StatusUnit2Sensors 1 }

-- table with entry for each sensor available on this unit              

  cmcTcMasterTc6Unit2SensorTable OBJECT-TYPE
    SYNTAX SEQUENCE OF CmcTcMasterTc6Unit2SensorEntry
    ACCESS not-accessible
    STATUS mandatory
    DESCRIPTION
      "Headline of sensor table"
    ::= { cmcTcMasterTc6StatusUnit2Sensors 2 }

  cmcTcMasterTc6Unit2SensorEntry OBJECT-TYPE
    SYNTAX CmcTcMasterTc6Unit2SensorEntry
    ACCESS not-accessible
    STATUS mandatory
    DESCRIPTION
      "Entries of sensor table"
    INDEX { cmcTcMasterTc6Unit2SensorIndex }
    ::= { cmcTcMasterTc6Unit2SensorTable 1 }

    CmcTcMasterTc6Unit2SensorEntry ::=
      SEQUENCE {
        cmcTcMasterTc6Unit2SensorIndex
          INTEGER,
        cmcTcMasterTc6Unit2SensorType
          INTEGER,
        cmcTcMasterTc6Unit2SensorText
          DisplayString (SIZE (0..20)),                
        cmcTcMasterTc6Unit2SensorStatus
          INTEGER,
        cmcTcMasterTc6Unit2SensorValue
          INTEGER,
        cmcTcMasterTc6Unit2SensorSetHigh
          INTEGER,
        cmcTcMasterTc6Unit2SensorSetLow
          INTEGER,                 
        cmcTcMasterTc6Unit2SensorSetWarn
          INTEGER  
      }

    cmcTcMasterTc6Unit2SensorIndex OBJECT-TYPE
      SYNTAX INTEGER (1..32000)
      ACCESS read-only
      STATUS mandatory
      DESCRIPTION
        "Index for the list of value entries. Its value ranges
         between 1 and the value of cmcTcMasterTc6Unit2NumberOfSensors." 
      ::= { cmcTcMasterTc6Unit2SensorEntry 1 }

    cmcTcMasterTc6Unit2SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 2 to sensor[cmcTcMasterTc6Unit2SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc6Unit2SensorEntry 2 }
        
    cmcTcMasterTc6Unit2SensorText OBJECT-TYPE
      SYNTAX DisplayString (SIZE (0..20))
      ACCESS read-write
      STATUS mandatory
      DESCRIPTION
        "Descriptional text for each sensor (entry in the table)"
      ::= { cmcTcMasterTc6Unit2SensorEntry 3 }
              
    cmcTcMasterTc6Unit2SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc6Unit2SensorEntry 4 }

    cmcTcMasterTc6Unit2SensorValue OBJECT-TYPE
      SYNTAX INTEGER 
      ACCESS read-only
      STATUS mandatory
      DESCRIPTION
        "Value of sensor"
      ::= { cmcTcMasterTc6Unit2SensorEntry 5 }

    cmcTcMasterTc6Unit2SensorSetHigh OBJECT-TYPE
      SYNTAX INTEGER (0..300) 
      ACCESS read-write
      STATUS mandatory
      DESCRIPTION
        "Value for high setpoint of sensor"
      ::= { cmcTcMasterTc6Unit2SensorEntry 6 }

    cmcTcMasterTc6Unit2SensorSetLow OBJECT-TYPE
      SYNTAX INTEGER (0..300) 
      ACCESS read-write
      STATUS mandatory
      DESCRIPTION
        "Value for low setpoint of sensor,
         also used as alarm delay"
      ::= { cmcTcMasterTc6Unit2SensorEntry 7 }

    cmcTcMasterTc6Unit2SensorSetWarn OBJECT-TYPE
      SYNTAX INTEGER (0..300) 
      ACCESS read-write
      STATUS mandatory
      DESCRIPTION
        "Value for warning setpoint of sensor,
         also used as fan threshold"
      ::= { cmcTcMasterTc6Unit2SensorEntry 8 }

-- Outputs              

  cmcTcMasterTc6Unit2NumberOfOutputs OBJECT-TYPE
    SYNTAX INTEGER 
    ACCESS read-only
    STATUS mandatory
    DESCRIPTION
      "Number of outputs available on sensor unit 2"
    ::= { cmcTcMasterTc6StatusUnit2Outputs 1 }

-- table with entry for each output available on this unit              
                
  cmcTcMasterTc6Unit2OutputTable OBJECT-TYPE
    SYNTAX SEQUENCE OF CmcTcMasterTc6Unit2OutputEntry
    ACCESS not-accessible
    STATUS mandatory
    DESCRIPTION
      "Headline of output table"
    ::= { cmcTcMasterTc6StatusUnit2Outputs 2 }

  cmcTcMasterTc6Unit2OutputEntry OBJECT-TYPE
    SYNTAX CmcTcMasterTc6Unit2OutputEntry
    ACCESS not-accessible
    STATUS mandatory
    DESCRIPTION
      "Entries of output table"
    INDEX { cmcTcMasterTc6Unit2OutputIndex }
    ::= { cmcTcMasterTc6Unit2OutputTable 1 }

    CmcTcMasterTc6Unit2OutputEntry ::=
      SEQUENCE {
        cmcTcMasterTc6Unit2OutputIndex
          INTEGER,
        cmcTcMasterTc6Unit2OutputType
          INTEGER,
        cmcTcMasterTc6Unit2OutputText
          DisplayString (SIZE (0..20)),                
        cmcTcMasterTc6Unit2OutputStatus
          INTEGER,
        cmcTcMasterTc6Unit2OutputValue
          INTEGER,
        cmcTcMasterTc6Unit2OutputSet
          INTEGER,
        cmcTcMasterTc6Unit2OutputConfig
          INTEGER,                
        cmcTcMasterTc6Unit2OutputDelay
          INTEGER,
        cmcTcMasterTc6Unit2OutputTimeoutAction
          INTEGER
      }

    cmcTcMasterTc6Unit2OutputIndex OBJECT-TYPE
      SYNTAX INTEGER (1..32000)
      ACCESS read-only
      STATUS mandatory
      DESCRIPTION
        "Index for the list of output entries. Its value ranges
         between 1 and the value of cmcTcMasterTc6Unit2NumberOfOutputs." 
      ::= { cmcTcMasterTc6Unit2OutputEntry 1 }

    cmcTcMasterTc6Unit2OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 2 to output[cmcTcMasterTc6Unit2OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc6Unit2OutputEntry 2 }

        
    cmcTcMasterTc6Unit2OutputText OBJECT-TYPE
      SYNTAX DisplayString (SIZE (0..20))
      ACCESS read-write
      STATUS mandatory
      DESCRIPTION
        "Descriptional text for each output (entry in the table)"
      ::= { cmcTcMasterTc6Unit2OutputEntry 3 }
              
    cmcTcMasterTc6Unit2OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc6Unit2OutputEntry 4 }

    cmcTcMasterTc6Unit2OutputValue OBJECT-TYPE
      SYNTAX INTEGER (-32000..32000) 
      ACCESS read-write
      STATUS mandatory
      DESCRIPTION
        "Value for output"
      ::= { cmcTcMasterTc6Unit2OutputEntry 5 }

    cmcTcMasterTc6Unit2OutputSet OBJECT-TYPE
      SYNTAX INTEGER {
        off (1),
        on (2),
        lock (3),
        unlock (4),
        unlockDelay (5)
      }
      ACCESS read-write
      STATUS mandatory
      DESCRIPTION
        "Command for output"
      ::= { cmcTcMasterTc6Unit2OutputEntry 6 }

    cmcTcMasterTc6Unit2OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc6Unit2OutputEntry 7 }

    cmcTcMasterTc6Unit2OutputDelay OBJECT-TYPE
      SYNTAX INTEGER (0..999) 
      ACCESS read-write
      STATUS mandatory
      DESCRIPTION
        "Unsigned Value for delay, 
         after this time the output will fall into the previous state"
      ::= { cmcTcMasterTc6Unit2OutputEntry 8 }

    cmcTcMasterTc6Unit2OutputTimeoutAction OBJECT-TYPE
      SYNTAX INTEGER {
        stay (1),
        off (2),
        on (3)
      }
      ACCESS read-write
      STATUS mandatory
      DESCRIPTION
        "State for output if timeout (RS422) occurs"
      ::= { cmcTcMasterTc6Unit2OutputEntry 9 }

-- Messages
              
  cmcTcMasterTc6Unit2NumberOfMsgs OBJECT-TYPE
    SYNTAX INTEGER 
    ACCESS read-only
    STATUS mandatory
    DESCRIPTION
      "Number of messages that can be created with sensor unit 2"
    ::= { cmcTcMasterTc6StatusUnit2Msg 1 }

-- table with entry for each alarm available on this unit               
                
  cmcTcMasterTc6Unit2MsgTable OBJECT-TYPE
    SYNTAX SEQUENCE OF CmcTcMasterTc6Unit2MsgEntry
    ACCESS not-accessible
    STATUS mandatory
    DESCRIPTION
      "Headline of message table"
    ::= { cmcTcMasterTc6StatusUnit2Msg 2 }

  cmcTcMasterTc6Unit2MsgEntry OBJECT-TYPE
    SYNTAX CmcTcMasterTc6Unit2MsgEntry
    ACCESS not-accessible
    STATUS mandatory
    DESCRIPTION
      "Entries of message table"
    INDEX { cmcTcMasterTc6Unit2MsgIndex }
    ::= { cmcTcMasterTc6Unit2MsgTable 1 }

    CmcTcMasterTc6Unit2MsgEntry ::=
      SEQUENCE {
        cmcTcMasterTc6Unit2MsgIndex
          INTEGER,
        cmcTcMasterTc6Unit2MsgText
          DisplayString (SIZE (0..20)),
        cmcTcMasterTc6Unit2MsgStatus
          INTEGER, 
        cmcTcMasterTc6Unit2MsgRelay
          INTEGER,
        cmcTcMasterTc6Unit2MsgBeeper
          INTEGER,
        cmcTcMasterTc6Unit2MsgTrap1
          INTEGER,
        cmcTcMasterTc6Unit2MsgTrap2
          INTEGER,
        cmcTcMasterTc6Unit2MsgTrap3
          INTEGER,
        cmcTcMasterTc6Unit2MsgTrap4
          INTEGER,                 
        cmcTcMasterTc6Unit2MsgQuit
          INTEGER              
      }

    cmcTcMasterTc6Unit2MsgIndex OBJECT-TYPE
      SYNTAX INTEGER (1..32000)
      ACCESS read-only
      STATUS mandatory
      DESCRIPTION
        "Index for the list of message entries. Its value ranges
         between 1 and the value of cmcTcMasterTc6Unit2NumberOfMsgs." 
      ::= { cmcTcMasterTc6Unit2MsgEntry 1 }

    cmcTcMasterTc6Unit2MsgText OBJECT-TYPE
      SYNTAX DisplayString (SIZE (0..20))
      ACCESS read-write
      STATUS mandatory
      DESCRIPTION
        "Descriptional text for each message (entry in the table)"
      ::= { cmcTcMasterTc6Unit2MsgEntry 2 }

    cmcTcMasterTc6Unit2MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc6Unit2OutputSet)
         17: door is unlocked by WEB
         18: door is unlocked by timer
         19: no access, wrong keycode or cardnumber
         20: orientation of PSM-Unit is circuit 1
         21: orientation of PSM-Unit is circuit 2"
      ::= { cmcTcMasterTc6Unit2MsgEntry 3 }

    cmcTcMasterTc6Unit2MsgRelay OBJECT-TYPE
      SYNTAX INTEGER {
        disable (1),
        enable (2)
      }
      ACCESS read-write
      STATUS mandatory
      DESCRIPTION
        "Setup of Alarm relay for this alarm
         2:        no switching of alarm relay             
         1:        switching of alarm relay" 
      ::= { cmcTcMasterTc6Unit2MsgEntry 4 }

    cmcTcMasterTc6Unit2MsgBeeper OBJECT-TYPE
      SYNTAX INTEGER {
        disable (1),
        enable (2)
      }
      ACCESS read-write
      STATUS mandatory
      DESCRIPTION
        "Setup of Alarm beeper for this alarm
         2:        no audible alarm
         1:        audible alarm" 
      ::= { cmcTcMasterTc6Unit2MsgEntry 5 }

    cmcTcMasterTc6Unit2MsgTrap1 OBJECT-TYPE
      SYNTAX INTEGER {
        disable (1),
        enable (2)
      }
      ACCESS read-write
      STATUS mandatory
      DESCRIPTION
        "Trap receiver 1 activated"
      ::= { cmcTcMasterTc6Unit2MsgEntry 6 }

    cmcTcMasterTc6Unit2MsgTrap2 OBJECT-TYPE
      SYNTAX INTEGER {
        disable (1),
        enable (2)
      }
      ACCESS read-write
      STATUS mandatory
      DESCRIPTION
        "Trap receiver 2 activated"
      ::= { cmcTcMasterTc6Unit2MsgEntry 7 }
 
    cmcTcMasterTc6Unit2MsgTrap3 OBJECT-TYPE
      SYNTAX INTEGER {
        disable (1),
        enable (2)
      }
      ACCESS read-write
      STATUS mandatory
      DESCRIPTION
        "Trap receiver 3 activated"
      ::= { cmcTcMasterTc6Unit2MsgEntry 8 }

    cmcTcMasterTc6Unit2MsgTrap4 OBJECT-TYPE
      SYNTAX INTEGER {
        disable (1),
        enable (2)
      }
      ACCESS read-write
      STATUS mandatory
      DESCRIPTION
        "Trap receiver 4 and Event Logging activated"
      ::= { cmcTcMasterTc6Unit2MsgEntry 9 }

    cmcTcMasterTc6Unit2MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc6Unit2MsgEntry 10 }

-- unit 3
  cmcTcMasterTc6Unit3TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 3"
    ::= { cmcTcMasterTc6StatusSensorUnit3 1 }

  cmcTcMasterTc6Unit3Text OBJECT-TYPE
    SYNTAX DisplayString (SIZE (0..10))
    ACCESS read-write
    STATUS mandatory
    DESCRIPTION
      "Descriptional text for sensor unit connected to port 3"
    ::= { cmcTcMasterTc6StatusSensorUnit3 2 }

  cmcTcMasterTc6Unit3Serial OBJECT-TYPE
    SYNTAX INTEGER 
    ACCESS  read-only
    STATUS  mandatory
    DESCRIPTION
      "Serialnumber of sensor unit connected to port 3"
    ::= { cmcTcMasterTc6StatusSensorUnit3 3 }

  cmcTcMasterTc6Unit3Status OBJECT-TYPE
    SYNTAX INTEGER {
      ok(1),
      error(2),
      changed(3),
      quit(4),
      timeout(5),
      detected(6),
      notAvail(7),
      lowPower(8)
    }
    ACCESS  read-only
    STATUS  mandatory
    DESCRIPTION
      "General Status sensor unit connected to port 3
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc6StatusSensorUnit3 4 }

-- Sensors              

  cmcTcMasterTc6Unit3NumberOfSensors OBJECT-TYPE
    SYNTAX INTEGER 
    ACCESS read-only
    STATUS mandatory
    DESCRIPTION
      "Number of sensors connected to sensor unit 3"
    ::= { cmcTcMasterTc6StatusUnit3Sensors 1 }

-- table with entry for each sensor available on this unit              
        
  cmcTcMasterTc6Unit3SensorTable OBJECT-TYPE
    SYNTAX SEQUENCE OF CmcTcMasterTc6Unit3SensorEntry
    ACCESS not-accessible
    STATUS mandatory
    DESCRIPTION
      "Headline of sensor table"
    ::= { cmcTcMasterTc6StatusUnit3Sensors 2 }

  cmcTcMasterTc6Unit3SensorEntry OBJECT-TYPE
    SYNTAX CmcTcMasterTc6Unit3SensorEntry
    ACCESS not-accessible
    STATUS mandatory
    DESCRIPTION
      "Entries of sensor table"
    INDEX { cmcTcMasterTc6Unit3SensorIndex }
    ::= { cmcTcMasterTc6Unit3SensorTable 1 }

    CmcTcMasterTc6Unit3SensorEntry ::=
      SEQUENCE {
        cmcTcMasterTc6Unit3SensorIndex
          INTEGER,
        cmcTcMasterTc6Unit3SensorType
          INTEGER,
        cmcTcMasterTc6Unit3SensorText
          DisplayString (SIZE (0..20)),                
        cmcTcMasterTc6Unit3SensorStatus
          INTEGER,
        cmcTcMasterTc6Unit3SensorValue
          INTEGER,
        cmcTcMasterTc6Unit3SensorSetHigh
          INTEGER,
        cmcTcMasterTc6Unit3SensorSetLow
          INTEGER,                 
        cmcTcMasterTc6Unit3SensorSetWarn
          INTEGER  
      }

    cmcTcMasterTc6Unit3SensorIndex OBJECT-TYPE
      SYNTAX INTEGER (1..32000)
      ACCESS read-only
      STATUS mandatory
      DESCRIPTION
        "Index for the list of value entries. Its value ranges
         between 1 and the value of cmcTcMasterTc6Unit3NumberOfSensors." 
      ::= { cmcTcMasterTc6Unit3SensorEntry 1 }

    cmcTcMasterTc6Unit3SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 3 to sensor[cmcTcMasterTc6Unit3SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc6Unit3SensorEntry 2 }

    cmcTcMasterTc6Unit3SensorText OBJECT-TYPE
      SYNTAX DisplayString (SIZE (0..20))
      ACCESS read-write
      STATUS mandatory
      DESCRIPTION
        "Descriptional text for each sensor (entry in the table)"
      ::= { cmcTcMasterTc6Unit3SensorEntry 3 }
              
    cmcTcMasterTc6Unit3SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc6Unit3SensorEntry 4 }

    cmcTcMasterTc6Unit3SensorValue OBJECT-TYPE
      SYNTAX INTEGER 
      ACCESS read-only
      STATUS mandatory
      DESCRIPTION
        "Value of sensor"
      ::= { cmcTcMasterTc6Unit3SensorEntry 5 }

    cmcTcMasterTc6Unit3SensorSetHigh OBJECT-TYPE
      SYNTAX INTEGER (0..300) 
      ACCESS read-write
      STATUS mandatory
      DESCRIPTION
        "Value for high setpoint of sensor"
      ::= { cmcTcMasterTc6Unit3SensorEntry 6 }

    cmcTcMasterTc6Unit3SensorSetLow OBJECT-TYPE
      SYNTAX INTEGER (0..300) 
      ACCESS read-write
      STATUS mandatory
      DESCRIPTION
        "Value for low setpoint of sensor,
         also used as alarm delay"
      ::= { cmcTcMasterTc6Unit3SensorEntry 7 }

    cmcTcMasterTc6Unit3SensorSetWarn OBJECT-TYPE
      SYNTAX INTEGER (0..300) 
      ACCESS read-write
      STATUS mandatory
      DESCRIPTION
        "Value for warning setpoint of sensor,
         also used as fan threshold"
      ::= { cmcTcMasterTc6Unit3SensorEntry 8 }
                
-- Outputs              

  cmcTcMasterTc6Unit3NumberOfOutputs OBJECT-TYPE
    SYNTAX INTEGER 
    ACCESS read-only
    STATUS mandatory
    DESCRIPTION
      "Number of outputs available on sensor unit 3"
    ::= { cmcTcMasterTc6StatusUnit3Outputs 1 }

-- table with entry for each output available on this unit              
                
  cmcTcMasterTc6Unit3OutputTable OBJECT-TYPE
    SYNTAX SEQUENCE OF CmcTcMasterTc6Unit3OutputEntry
    ACCESS not-accessible
    STATUS mandatory
    DESCRIPTION
      "Headline of output table"
    ::= { cmcTcMasterTc6StatusUnit3Outputs 2 }

  cmcTcMasterTc6Unit3OutputEntry OBJECT-TYPE
    SYNTAX CmcTcMasterTc6Unit3OutputEntry
    ACCESS not-accessible
    STATUS mandatory
    DESCRIPTION
      "Entries of output table"
    INDEX { cmcTcMasterTc6Unit3OutputIndex }
    ::= { cmcTcMasterTc6Unit3OutputTable 1 }

    CmcTcMasterTc6Unit3OutputEntry ::=
      SEQUENCE {
        cmcTcMasterTc6Unit3OutputIndex
          INTEGER,
        cmcTcMasterTc6Unit3OutputType
          INTEGER,
        cmcTcMasterTc6Unit3OutputText
          DisplayString (SIZE (0..20)),                
        cmcTcMasterTc6Unit3OutputStatus
          INTEGER,
        cmcTcMasterTc6Unit3OutputValue
          INTEGER,
        cmcTcMasterTc6Unit3OutputSet
          INTEGER,
        cmcTcMasterTc6Unit3OutputConfig
          INTEGER,
        cmcTcMasterTc6Unit3OutputDelay
          INTEGER,
        cmcTcMasterTc6Unit3OutputTimeoutAction
          INTEGER
      }

    cmcTcMasterTc6Unit3OutputIndex OBJECT-TYPE
      SYNTAX INTEGER (1..32000)
      ACCESS read-only
      STATUS mandatory
      DESCRIPTION
        "Index for the list of output entries. Its value ranges
         between 1 and the value of cmcTcMasterTc6Unit3NumberOfOutputs." 
      ::= { cmcTcMasterTc6Unit3OutputEntry 1 }

    cmcTcMasterTc6Unit3OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 3 to output[cmcTcMasterTc6Unit3OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc6Unit3OutputEntry 2 }

        
    cmcTcMasterTc6Unit3OutputText OBJECT-TYPE
      SYNTAX DisplayString (SIZE (0..20))
      ACCESS read-write
      STATUS mandatory
      DESCRIPTION
        "Descriptional text for each output (entry in the table)"
      ::= { cmcTcMasterTc6Unit3OutputEntry 3 }
              
    cmcTcMasterTc6Unit3OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc6Unit3OutputEntry 4 }

    cmcTcMasterTc6Unit3OutputValue OBJECT-TYPE
      SYNTAX INTEGER (-32000..32000) 
      ACCESS read-write
      STATUS mandatory
      DESCRIPTION
        "Value for output"
      ::= { cmcTcMasterTc6Unit3OutputEntry 5 }

    cmcTcMasterTc6Unit3OutputSet OBJECT-TYPE
      SYNTAX INTEGER {
        off (1),
        on (2),
        lock (3),
        unlock (4),
        unlockDelay (5)
      }
      ACCESS read-write
      STATUS mandatory
      DESCRIPTION
        "Command for output"
      ::= { cmcTcMasterTc6Unit3OutputEntry 6 }

    cmcTcMasterTc6Unit3OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc6Unit3OutputEntry 7 }

    cmcTcMasterTc6Unit3OutputDelay OBJECT-TYPE
      SYNTAX INTEGER (0..999) 
      ACCESS read-write
      STATUS mandatory
      DESCRIPTION
        "Unsigned Value for delay, 
         after this time the output will fall into the previous state"
      ::= { cmcTcMasterTc6Unit3OutputEntry 8 }

    cmcTcMasterTc6Unit3OutputTimeoutAction OBJECT-TYPE
      SYNTAX INTEGER {
        stay (1),
        off (2),
        on (3)
      }
      ACCESS read-write
      STATUS mandatory
      DESCRIPTION
        "State for output if timeout (RS422) occurs"
      ::= { cmcTcMasterTc6Unit3OutputEntry 9 }

-- Messages
              
  cmcTcMasterTc6Unit3NumberOfMsgs OBJECT-TYPE
    SYNTAX INTEGER 
    ACCESS read-only
    STATUS mandatory
    DESCRIPTION
      "Number of messages that can be created with sensor unit 3"
    ::= { cmcTcMasterTc6StatusUnit3Msg 1 }

-- table with entry for each alarm available on this unit               
                
  cmcTcMasterTc6Unit3MsgTable OBJECT-TYPE
    SYNTAX SEQUENCE OF CmcTcMasterTc6Unit3MsgEntry
    ACCESS not-accessible
    STATUS mandatory
    DESCRIPTION
      "Headline of message table"
    ::= { cmcTcMasterTc6StatusUnit3Msg 2 }

  cmcTcMasterTc6Unit3MsgEntry OBJECT-TYPE
    SYNTAX CmcTcMasterTc6Unit3MsgEntry
    ACCESS not-accessible
    STATUS mandatory
    DESCRIPTION
      "Entries of message table"
    INDEX { cmcTcMasterTc6Unit3MsgIndex }
    ::= { cmcTcMasterTc6Unit3MsgTable 1 }

    CmcTcMasterTc6Unit3MsgEntry ::=
      SEQUENCE {
        cmcTcMasterTc6Unit3MsgIndex
          INTEGER,
        cmcTcMasterTc6Unit3MsgText
          DisplayString (SIZE (0..20)),
        cmcTcMasterTc6Unit3MsgStatus
          INTEGER, 
        cmcTcMasterTc6Unit3MsgRelay
          INTEGER,
        cmcTcMasterTc6Unit3MsgBeeper
          INTEGER,
        cmcTcMasterTc6Unit3MsgTrap1
          INTEGER,
        cmcTcMasterTc6Unit3MsgTrap2
          INTEGER,
        cmcTcMasterTc6Unit3MsgTrap3
          INTEGER,
        cmcTcMasterTc6Unit3MsgTrap4
          INTEGER,                 
        cmcTcMasterTc6Unit3MsgQuit
          INTEGER              
      }

    cmcTcMasterTc6Unit3MsgIndex OBJECT-TYPE
      SYNTAX INTEGER (1..32000)
      ACCESS read-only
      STATUS mandatory
      DESCRIPTION
        "Index for the list of message entries. Its value ranges
         between 1 and the value of cmcTcMasterTc6Unit3NumberOfMsgs." 
      ::= { cmcTcMasterTc6Unit3MsgEntry 1 }

    cmcTcMasterTc6Unit3MsgText OBJECT-TYPE
      SYNTAX DisplayString (SIZE (0..20))
      ACCESS read-write
      STATUS mandatory
      DESCRIPTION
        "Descriptional text for each message (entry in the table)"
      ::= { cmcTcMasterTc6Unit3MsgEntry 2 }

    cmcTcMasterTc6Unit3MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc6Unit3OutputSet)
         17: door is unlocked by WEB
         18: door is unlocked by timer
         19: no access, wrong keycode or cardnumber
         20: orientation of PSM-Unit is circuit 1
         21: orientation of PSM-Unit is circuit 2"
      ::= { cmcTcMasterTc6Unit3MsgEntry 3 }

    cmcTcMasterTc6Unit3MsgRelay OBJECT-TYPE
      SYNTAX INTEGER {
        disable (1),
        enable (2)
      }
      ACCESS read-write
      STATUS mandatory
      DESCRIPTION
        "Setup of Alarm relay for this alarm
         1:        no switching of alarm relay             
         2:        switching of alarm relay" 
      ::= { cmcTcMasterTc6Unit3MsgEntry 4 }

    cmcTcMasterTc6Unit3MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc6Unit3MsgEntry 5 }

    cmcTcMasterTc6Unit3MsgTrap1 OBJECT-TYPE
      SYNTAX INTEGER {
        disable (1),
        enable (2)
      }
      ACCESS read-write
      STATUS mandatory
      DESCRIPTION
        "Trap receiver 1 activated"
      ::= { cmcTcMasterTc6Unit3MsgEntry 6 }

    cmcTcMasterTc6Unit3MsgTrap2 OBJECT-TYPE
      SYNTAX INTEGER {
        disable (1),
        enable (2)
      }
      ACCESS read-write
      STATUS mandatory
      DESCRIPTION
        "Trap receiver 2 activated"
      ::= { cmcTcMasterTc6Unit3MsgEntry 7 }
 
    cmcTcMasterTc6Unit3MsgTrap3 OBJECT-TYPE
      SYNTAX INTEGER {
        disable (1),
        enable (2)
      }
      ACCESS read-write
      STATUS mandatory
      DESCRIPTION
        "Trap receiver 3 activated"
      ::= { cmcTcMasterTc6Unit3MsgEntry 8 }

    cmcTcMasterTc6Unit3MsgTrap4 OBJECT-TYPE
      SYNTAX INTEGER {
        disable (1),
        enable (2)
      }
      ACCESS read-write
      STATUS mandatory
      DESCRIPTION
        "Trap receiver 4 and Event Logging activated"
      ::= { cmcTcMasterTc6Unit3MsgEntry 9 }

    cmcTcMasterTc6Unit3MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc6Unit3MsgEntry 10 }

-- unit4

  cmcTcMasterTc6Unit4TypeOfDevice OBJECT-TYPE
    SYNTAX INTEGER {
      notAvail (1),
      unitIO (2),
      unitAccess (3),
      unitClimate (4),
      unitFCS (5),
      unitRTT (6),
      unitRLCP (7),
      unitPSM (8)
    }
    ACCESS  read-only
    STATUS  mandatory
    DESCRIPTION
      "Type of sensor unit connected to port 4"
    ::= { cmcTcMasterTc6StatusSensorUnit4 1 }

  cmcTcMasterTc6Unit4Text OBJECT-TYPE
    SYNTAX DisplayString (SIZE (0..10))
    ACCESS read-write
    STATUS mandatory
    DESCRIPTION
      "Descriptional text for sensor unit connected to port 4"
    ::= { cmcTcMasterTc6StatusSensorUnit4 2 }

  cmcTcMasterTc6Unit4Serial OBJECT-TYPE
    SYNTAX INTEGER 
    ACCESS read-only
    STATUS mandatory
    DESCRIPTION
      "Serialnumber of sensor unit connected to port 4"
    ::= { cmcTcMasterTc6StatusSensorUnit4 3 }

  cmcTcMasterTc6Unit4Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 4
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc6StatusSensorUnit4 4 }

-- Sensors
              
  cmcTcMasterTc6Unit4NumberOfSensors OBJECT-TYPE
    SYNTAX INTEGER 
    ACCESS read-only
    STATUS mandatory
    DESCRIPTION
      "Number of sensors connected to sensor unit 4"
    ::= { cmcTcMasterTc6StatusUnit4Sensors 1 }

-- table with entry for each sensor available on this unit              
                
  cmcTcMasterTc6Unit4SensorTable OBJECT-TYPE
    SYNTAX SEQUENCE OF CmcTcMasterTc6Unit4SensorEntry
    ACCESS not-accessible
    STATUS mandatory
    DESCRIPTION
      "Headline of sensor table"
    ::= { cmcTcMasterTc6StatusUnit4Sensors 2 }

  cmcTcMasterTc6Unit4SensorEntry OBJECT-TYPE
    SYNTAX CmcTcMasterTc6Unit4SensorEntry
    ACCESS not-accessible
    STATUS mandatory
    DESCRIPTION
      "Entries of sensor table"
    INDEX { cmcTcMasterTc6Unit4SensorIndex }
    ::= { cmcTcMasterTc6Unit4SensorTable 1 }

    CmcTcMasterTc6Unit4SensorEntry ::=
      SEQUENCE {
        cmcTcMasterTc6Unit4SensorIndex
          INTEGER,
        cmcTcMasterTc6Unit4SensorType
          INTEGER,
        cmcTcMasterTc6Unit4SensorText
          DisplayString (SIZE (0..20)),                
        cmcTcMasterTc6Unit4SensorStatus
          INTEGER,
        cmcTcMasterTc6Unit4SensorValue
          INTEGER,
        cmcTcMasterTc6Unit4SensorSetHigh
          INTEGER,
        cmcTcMasterTc6Unit4SensorSetLow
          INTEGER,                 
        cmcTcMasterTc6Unit4SensorSetWarn
          INTEGER  
      }

    cmcTcMasterTc6Unit4SensorIndex OBJECT-TYPE
      SYNTAX INTEGER (1..32000)
      ACCESS read-only
      STATUS mandatory
      DESCRIPTION
        "Index for the list of value entries. Its value ranges
         between 1 and the value of cmcTcMasterTc6Unit4NumberOfSensors." 
      ::= { cmcTcMasterTc6Unit4SensorEntry 1 }

    cmcTcMasterTc6Unit4SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 4 to sensor[cmcTcMasterTc6Unit4SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc6Unit4SensorEntry 2 }

    cmcTcMasterTc6Unit4SensorText OBJECT-TYPE
      SYNTAX DisplayString (SIZE (0..20))
      ACCESS read-write
      STATUS mandatory
      DESCRIPTION
        "Descriptional text for each sensor (entry in the table)"
      ::= { cmcTcMasterTc6Unit4SensorEntry 3 }
              
    cmcTcMasterTc6Unit4SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc6Unit4SensorEntry 4 }

    cmcTcMasterTc6Unit4SensorValue OBJECT-TYPE
      SYNTAX INTEGER 
      ACCESS read-only
      STATUS mandatory
      DESCRIPTION
        "Value of sensor"
      ::= { cmcTcMasterTc6Unit4SensorEntry 5 }

    cmcTcMasterTc6Unit4SensorSetHigh OBJECT-TYPE
      SYNTAX INTEGER (0..300) 
      ACCESS read-write
      STATUS mandatory
      DESCRIPTION
        "Value for high setpoint of sensor"
      ::= { cmcTcMasterTc6Unit4SensorEntry 6 }

    cmcTcMasterTc6Unit4SensorSetLow OBJECT-TYPE
      SYNTAX INTEGER (0..300) 
      ACCESS read-write
      STATUS mandatory
      DESCRIPTION
        "Value for low setpoint of sensor,
         also used as alarm delay"
      ::= { cmcTcMasterTc6Unit4SensorEntry 7 }

    cmcTcMasterTc6Unit4SensorSetWarn OBJECT-TYPE
      SYNTAX INTEGER (0..300) 
      ACCESS read-write
      STATUS mandatory
      DESCRIPTION
        "Value for warning setpoint of sensor,
         also used as fan threshold"
      ::= { cmcTcMasterTc6Unit4SensorEntry 8 }

-- Outputs              

  cmcTcMasterTc6Unit4NumberOfOutputs OBJECT-TYPE
    SYNTAX INTEGER 
    ACCESS read-only
    STATUS mandatory
    DESCRIPTION
      "Number of outputs available on sensor unit 4"
    ::= { cmcTcMasterTc6StatusUnit4Outputs 1 }

-- table with entry for each output available on this unit              
                
  cmcTcMasterTc6Unit4OutputTable OBJECT-TYPE
    SYNTAX SEQUENCE OF CmcTcMasterTc6Unit4OutputEntry
    ACCESS not-accessible
    STATUS mandatory
    DESCRIPTION
      "Headline of output table"
    ::= { cmcTcMasterTc6StatusUnit4Outputs 2 }

  cmcTcMasterTc6Unit4OutputEntry OBJECT-TYPE
    SYNTAX CmcTcMasterTc6Unit4OutputEntry
    ACCESS not-accessible
    STATUS mandatory
    DESCRIPTION
      "Entries of output table"
    INDEX { cmcTcMasterTc6Unit4OutputIndex }
    ::= { cmcTcMasterTc6Unit4OutputTable 1 }

    CmcTcMasterTc6Unit4OutputEntry ::=
      SEQUENCE {
        cmcTcMasterTc6Unit4OutputIndex
          INTEGER,
        cmcTcMasterTc6Unit4OutputType
          INTEGER,
        cmcTcMasterTc6Unit4OutputText
          DisplayString (SIZE (0..20)),                
        cmcTcMasterTc6Unit4OutputStatus
          INTEGER,
        cmcTcMasterTc6Unit4OutputValue
          INTEGER,
        cmcTcMasterTc6Unit4OutputSet
          INTEGER,
        cmcTcMasterTc6Unit4OutputConfig
          INTEGER,
        cmcTcMasterTc6Unit4OutputDelay
          INTEGER,
        cmcTcMasterTc6Unit4OutputTimeoutAction
          INTEGER
      }

    cmcTcMasterTc6Unit4OutputIndex OBJECT-TYPE
      SYNTAX INTEGER (1..32000)
      ACCESS read-only
      STATUS mandatory
      DESCRIPTION
        "Index for the list of output entries. Its value ranges
         between 1 and the value of cmcTcMasterTc6Unit4NumberOfOutputs." 
      ::= { cmcTcMasterTc6Unit4OutputEntry 1 }

    cmcTcMasterTc6Unit4OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 4 to output[cmcTcMasterTc6Unit4OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc6Unit4OutputEntry 2 }

    cmcTcMasterTc6Unit4OutputText OBJECT-TYPE
      SYNTAX DisplayString (SIZE (0..20))
      ACCESS read-write
      STATUS mandatory
      DESCRIPTION
        "Descriptional text for each output (entry in the table)"
      ::= { cmcTcMasterTc6Unit4OutputEntry 3 }
              
    cmcTcMasterTc6Unit4OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc6Unit4OutputEntry 4 }

    cmcTcMasterTc6Unit4OutputValue OBJECT-TYPE
      SYNTAX INTEGER (-32000..32000) 
      ACCESS read-write
      STATUS mandatory
      DESCRIPTION
        "Value for output"
      ::= { cmcTcMasterTc6Unit4OutputEntry 5 }

    cmcTcMasterTc6Unit4OutputSet OBJECT-TYPE
      SYNTAX INTEGER {
        off (1),
        on (2),
        lock (3),
        unlock (4),
        unlockDelay (5)
      }
      ACCESS read-write
      STATUS mandatory
      DESCRIPTION
        "Command for output"
      ::= { cmcTcMasterTc6Unit4OutputEntry 6 }

    cmcTcMasterTc6Unit4OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc6Unit4OutputEntry 7 }

    cmcTcMasterTc6Unit4OutputDelay OBJECT-TYPE
      SYNTAX INTEGER (0..999) 
      ACCESS read-write
      STATUS mandatory
      DESCRIPTION
        "Unsigned Value for delay, 
         after this time the output will fall into the previous state"
      ::= { cmcTcMasterTc6Unit4OutputEntry 8 }

    cmcTcMasterTc6Unit4OutputTimeoutAction OBJECT-TYPE
      SYNTAX INTEGER {
        stay (1),
        off (2),
        on (3)
      }
      ACCESS read-write
      STATUS mandatory
      DESCRIPTION
        "State for output if timeout (RS422) occurs"
      ::= { cmcTcMasterTc6Unit4OutputEntry 9 }

-- Messages
              
  cmcTcMasterTc6Unit4NumberOfMsgs OBJECT-TYPE
    SYNTAX INTEGER 
    ACCESS read-only
    STATUS mandatory
    DESCRIPTION
      "Number of messages that can be created with sensor unit 4"
    ::= { cmcTcMasterTc6StatusUnit4Msg 1 }

-- table with entry for each alarm available on this unit               
                
  cmcTcMasterTc6Unit4MsgTable OBJECT-TYPE
    SYNTAX SEQUENCE OF CmcTcMasterTc6Unit4MsgEntry
    ACCESS not-accessible
    STATUS mandatory
    DESCRIPTION
      "Headline of message table"
    ::= { cmcTcMasterTc6StatusUnit4Msg 2 }

  cmcTcMasterTc6Unit4MsgEntry OBJECT-TYPE
    SYNTAX CmcTcMasterTc6Unit4MsgEntry
    ACCESS not-accessible
    STATUS mandatory
    DESCRIPTION
      "Entries of message table"
    INDEX { cmcTcMasterTc6Unit4MsgIndex }
    ::= { cmcTcMasterTc6Unit4MsgTable 1 }

    CmcTcMasterTc6Unit4MsgEntry ::=
      SEQUENCE {
        cmcTcMasterTc6Unit4MsgIndex
          INTEGER,
        cmcTcMasterTc6Unit4MsgText
          DisplayString (SIZE (0..20)),                
        cmcTcMasterTc6Unit4MsgStatus
          INTEGER, 
        cmcTcMasterTc6Unit4MsgRelay
          INTEGER,
        cmcTcMasterTc6Unit4MsgBeeper
          INTEGER,
        cmcTcMasterTc6Unit4MsgTrap1
          INTEGER,
        cmcTcMasterTc6Unit4MsgTrap2
          INTEGER,
        cmcTcMasterTc6Unit4MsgTrap3
          INTEGER,
        cmcTcMasterTc6Unit4MsgTrap4
          INTEGER,                 
        cmcTcMasterTc6Unit4MsgQuit
          INTEGER              
      }

    cmcTcMasterTc6Unit4MsgIndex OBJECT-TYPE
      SYNTAX INTEGER (1..32000)
      ACCESS read-only
      STATUS mandatory
      DESCRIPTION
        "Index for the list of message entries. Its value ranges
         between 1 and the value of cmcTcMasterTc6Unit4NumberOfMsgs." 
      ::= { cmcTcMasterTc6Unit4MsgEntry 1 }

    cmcTcMasterTc6Unit4MsgText OBJECT-TYPE
      SYNTAX DisplayString (SIZE (0..20))
      ACCESS read-write
      STATUS mandatory
      DESCRIPTION
        "Descriptional text for each message (entry in the table)"
      ::= { cmcTcMasterTc6Unit4MsgEntry 2 }

    cmcTcMasterTc6Unit4MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc6Unit4OutputSet)
         17: door is unlocked by WEB
         18: door is unlocked by timer
         19: no access, wrong keycode or cardnumber
         20: orientation of PSM-Unit is circuit 1
         21: orientation of PSM-Unit is circuit 2"
      ::= { cmcTcMasterTc6Unit4MsgEntry 3 }

    cmcTcMasterTc6Unit4MsgRelay OBJECT-TYPE
      SYNTAX INTEGER {
        disable (1),
        enable (2)
      }
      ACCESS read-write
      STATUS mandatory
      DESCRIPTION
        "Setup of Alarm relay for this alarm
         1:        no switching of alarm relay             
         2:        switching of alarm relay" 
      ::= { cmcTcMasterTc6Unit4MsgEntry 4 }

    cmcTcMasterTc6Unit4MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc6Unit4MsgEntry 5 }

    cmcTcMasterTc6Unit4MsgTrap1 OBJECT-TYPE
      SYNTAX INTEGER {
        disable (1),
        enable (2)
      }
      ACCESS read-write
      STATUS mandatory
      DESCRIPTION
        "Trap receiver 1 activated"
      ::= { cmcTcMasterTc6Unit4MsgEntry 6 }

    cmcTcMasterTc6Unit4MsgTrap2 OBJECT-TYPE
      SYNTAX INTEGER {
        disable (1),
        enable (2)
      }
      ACCESS read-write
      STATUS mandatory
      DESCRIPTION
        "Trap receiver 2 activated"
      ::= { cmcTcMasterTc6Unit4MsgEntry 7 }
 
    cmcTcMasterTc6Unit4MsgTrap3 OBJECT-TYPE
      SYNTAX INTEGER {
        disable (1),
        enable (2)
      }
      ACCESS read-write
      STATUS mandatory
      DESCRIPTION
        "Trap receiver 3 activated"
      ::= { cmcTcMasterTc6Unit4MsgEntry 8 }

    cmcTcMasterTc6Unit4MsgTrap4 OBJECT-TYPE
      SYNTAX INTEGER {
        disable (1),
        enable (2)
      }
      ACCESS read-write
      STATUS mandatory
      DESCRIPTION
        "Trap receiver 4 and Event Logging activated"
      ::= { cmcTcMasterTc6Unit4MsgEntry 9 }

    cmcTcMasterTc6Unit4MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc6Unit4MsgEntry 10 }

--Status extension unit

  cmcTcMasterTc6ValuesRelay OBJECT-TYPE
    SYNTAX INTEGER {
      disable (1),
      enable (2)
    }
    ACCESS read-write
    STATUS mandatory
    DESCRIPTION
      "Setup of Alarm relay for alarm ext. unit(s)
       1:        no switching of alarm relay             
       2:        switching of alarm relay" 
    ::= { cmcTcMasterTc6StatusExtUnit 1 }

  cmcTcMasterTc6ValuesBeeper OBJECT-TYPE
    SYNTAX INTEGER {
      disable (1),
      enable (2)
    }
    ACCESS read-write
    STATUS mandatory
    DESCRIPTION
      "Setup of Alarm beeper for alarm ext. unit(s)
       1:        no audible alarm
       2:        audible alarm" 
    ::= { cmcTcMasterTc6StatusExtUnit 2 }

  cmcTcMasterTc6ValuesTrap1 OBJECT-TYPE
    SYNTAX INTEGER {
      disable (1),
      enable (2)
    }
    ACCESS read-write
    STATUS mandatory
    DESCRIPTION
      "Trap receiver 1 activated"
    ::= { cmcTcMasterTc6StatusExtUnit 3 }

  cmcTcMasterTc6ValuesTrap2 OBJECT-TYPE
    SYNTAX INTEGER {
      disable (1),
      enable (2)
    }
    ACCESS read-write
    STATUS mandatory
    DESCRIPTION
      "Trap receiver 2 activated"
    ::= { cmcTcMasterTc6StatusExtUnit 4 }
 
  cmcTcMasterTc6ValuesTrap3 OBJECT-TYPE
    SYNTAX INTEGER {
      disable (1),
      enable (2)
    }
    ACCESS read-write
    STATUS mandatory
    DESCRIPTION
      "Trap receiver 3 activated"
    ::= { cmcTcMasterTc6StatusExtUnit 5 }

  cmcTcMasterTc6ValuesTrap4 OBJECT-TYPE
    SYNTAX INTEGER {
      disable (1),
      enable (2)
    }
    ACCESS read-write
    STATUS mandatory
    DESCRIPTION
      "Trap receiver 4 and Event Logging activated"
    ::= { cmcTcMasterTc6StatusExtUnit 6 }
 
  cmcTcMasterTc6NumberOfValues OBJECT-TYPE
    SYNTAX INTEGER 
    ACCESS  read-only
    STATUS  mandatory
    DESCRIPTION
      "Number of values availabel on extension units connected to the CMC-TC"
    ::= { cmcTcMasterTc6StatusExtUnit 7 }

-- table with entry for each value available on extension units              

  cmcTcMasterTc6ValuesTable OBJECT-TYPE
    SYNTAX SEQUENCE OF CmcTcMasterTc6ValuesEntry
    ACCESS not-accessible
    STATUS mandatory
    DESCRIPTION
      "Headline of values-table"
    ::= { cmcTcMasterTc6StatusExtUnit 8 }

  cmcTcMasterTc6ValuesEntry OBJECT-TYPE
    SYNTAX CmcTcMasterTc6ValuesEntry
    ACCESS not-accessible
    STATUS mandatory
    DESCRIPTION
      "Entries of values-table"
    INDEX { cmcTcMasterTc6ValuesIndex }
    ::= { cmcTcMasterTc6ValuesTable 1 }

    CmcTcMasterTc6ValuesEntry ::=
      SEQUENCE {
        cmcTcMasterTc6ValuesIndex
          INTEGER,
        cmcTcMasterTc6ValuesText
          DisplayString (SIZE (0..20)),                
        cmcTcMasterTc6ValuesStatus
          INTEGER,
        cmcTcMasterTc6ValuesValue
          INTEGER,
        cmcTcMasterTc6ValuesSetHigh
          INTEGER,
        cmcTcMasterTc6ValuesSetLow
          INTEGER
      }

    cmcTcMasterTc6ValuesIndex OBJECT-TYPE
      SYNTAX INTEGER (1..32000)
      ACCESS read-only
      STATUS mandatory
      DESCRIPTION
        "Index for the list of value entries. Its value ranges
         between 1 and the value of cmcTcMasterTc6NumberOfValues." 
      ::= { cmcTcMasterTc6ValuesEntry 1 }

        
    cmcTcMasterTc6ValuesText OBJECT-TYPE
      SYNTAX DisplayString (SIZE (0..20))
      ACCESS read-write
      STATUS mandatory
      DESCRIPTION
        "Descriptional text for each value (entry in the table)
         of the extension card"
      ::= { cmcTcMasterTc6ValuesEntry 2 }
              
    cmcTcMasterTc6ValuesStatus OBJECT-TYPE
      SYNTAX INTEGER {
        notAvail(1),
        lost(2),
        changed(3),
        ok(4),
        tooLow(5),
        tooHigh(6),
        error(7)
      }
      ACCESS read-only
      STATUS mandatory
      DESCRIPTION
        "Actual status of the value of the extension card"
      ::= { cmcTcMasterTc6ValuesEntry 3 }

    cmcTcMasterTc6ValuesValue OBJECT-TYPE
      SYNTAX INTEGER 
      ACCESS read-only
      STATUS mandatory
      DESCRIPTION
        "Value of sensor"
      ::= { cmcTcMasterTc6ValuesEntry 4 }

    cmcTcMasterTc6ValuesSetHigh OBJECT-TYPE
      SYNTAX INTEGER (0..255) 
      ACCESS read-write
      STATUS mandatory
      DESCRIPTION
        "Value for high setpoint of sensor"
      ::= { cmcTcMasterTc6ValuesEntry 5 }

    cmcTcMasterTc6ValuesSetLow OBJECT-TYPE
      SYNTAX INTEGER (0..255) 
      ACCESS read-write
      STATUS mandatory
      DESCRIPTION
        "Value for low setpoint of sensor"
      ::= { cmcTcMasterTc6ValuesEntry 6 }

--cmcTcMasterTc6SetupGeneral-group

  cmcTcMasterTc6SetTempUnit OBJECT-TYPE
    SYNTAX INTEGER {
      celsius(1),
      fahrenheit(2)
    }
    ACCESS read-write
    STATUS mandatory
    DESCRIPTION
      "Unit of all temperature values and setpoints, Celsius or Fahrenheit"
   ::= { cmcTcMasterTc6SetupGeneral 1 }

  cmcTcMasterTc6SetBeeper OBJECT-TYPE
    SYNTAX INTEGER {
      off(1),
      on(2)
    }
    ACCESS read-write
    STATUS mandatory
    DESCRIPTION
      "Audible alarm in CMC-TC unit:
       (2): beeper is on
       (1): beeper is off (general)"
    ::= { cmcTcMasterTc6SetupGeneral 2 }


  cmcTcMasterTc6QuitRelay OBJECT-TYPE
    SYNTAX INTEGER {
      disabled(1),
      enabled(2)
    }
    ACCESS read-write
    STATUS mandatory
    DESCRIPTION
      "Enable or disable acknowledging currently active alarm relay 
       (with 'C' on CMC-TC)."
    ::= { cmcTcMasterTc6SetupGeneral 3 }

  cmcTcMasterTc6LogicRelay OBJECT-TYPE
    SYNTAX INTEGER {
      closeAtAlarm(1),
      openAtAlarm(2),
      off(3)
    }
    ACCESS read-write
    STATUS mandatory
    DESCRIPTION
      "Logic of alarm relay: 
       (1) Relay will pick up in case of an alarm
       (2) Relay will release in case of an alarm
       (3) Relay off (general)"
    ::= { cmcTcMasterTc6SetupGeneral 4 }

  cmcTcMasterTc6WebAccess OBJECT-TYPE
    SYNTAX INTEGER {
      viewOnly(1),
      fullAccess(2),
      off(3)
    }
    ACCESS read-write
    STATUS mandatory
    DESCRIPTION
      "Web access via HTTP: 
       (1) view only
       (2) full Access, read and set
       (3) Web disabled (general)"
    ::= { cmcTcMasterTc6SetupGeneral 5 }
 
  cmcTcMasterTc6SetupDate OBJECT-TYPE
    SYNTAX DisplayString (SIZE (0..10))
    ACCESS read-write
    STATUS mandatory
    DESCRIPTION
      "actual Date in format DD.MM.YYYY"
    ::= { cmcTcMasterTc6SetupGeneral 6 }

  cmcTcMasterTc6SetupTime OBJECT-TYPE
    SYNTAX DisplayString (SIZE (0..8))
    ACCESS read-write
    STATUS mandatory
    DESCRIPTION
      "actual Time in format HH:MM:SS, HH (0-23), MM (0-59), SS (0-59)"
    ::= { cmcTcMasterTc6SetupGeneral 7 }
 
-- table for timer function
 
  cmcTcMasterTc6TimerNumber OBJECT-TYPE
    SYNTAX INTEGER 
    ACCESS read-only
    STATUS mandatory
    DESCRIPTION
      "Number of timers available on this unit"
    ::= { cmcTcMasterTc6TimerTable1 1 }

  cmcTcMasterTc6TimerTable OBJECT-TYPE
    SYNTAX SEQUENCE OF CmcTcMasterTc6TimerEntry
    ACCESS not-accessible
    STATUS mandatory
    DESCRIPTION
      "Headline of timer-table"
    ::= { cmcTcMasterTc6TimerTable1 2 }

  cmcTcMasterTc6TimerEntry OBJECT-TYPE
    SYNTAX CmcTcMasterTc6TimerEntry
    ACCESS not-accessible
    STATUS mandatory
    DESCRIPTION
      "Entries of timer-table"
    INDEX { cmcTcMasterTc6TimerIndex }
    ::= { cmcTcMasterTc6TimerTable 1 }

    CmcTcMasterTc6TimerEntry ::=
      SEQUENCE {
        cmcTcMasterTc6TimerIndex
          INTEGER,
        cmcTcMasterTc6TimerStatus
          INTEGER,
        cmcTcMasterTc6TimerDayOfWeek
          INTEGER,  
        cmcTcMasterTc6TimeOn 
          DisplayString (SIZE (0..5)),                              
        cmcTcMasterTc6TimeOff 
          DisplayString (SIZE (0..5)),                              
        cmcTcMasterTc6TimeControl
          INTEGER,
        cmcTcMasterTc6TimerFunction
           INTEGER
      }

    cmcTcMasterTc6TimerIndex OBJECT-TYPE
      SYNTAX INTEGER (1..32000)
      ACCESS read-only
      STATUS mandatory
      DESCRIPTION
        "Index for the list of timer entries. Its value ranges
         between 1 and the value of cmcTcMasterTc6TimerNumber." 
      ::= { cmcTcMasterTc6TimerEntry 1 }

    cmcTcMasterTc6TimerStatus OBJECT-TYPE
      SYNTAX INTEGER {
        switchedOff(1),
        switchedOn(2),
        noTime(3) 
      }
      ACCESS read-only
      STATUS mandatory
      DESCRIPTION
        "Actual status of the timer"
      ::= { cmcTcMasterTc6TimerEntry 2 }

    cmcTcMasterTc6TimerDayOfWeek OBJECT-TYPE
      SYNTAX INTEGER {
        sun(1),
        mon(2),
        tue(3) ,
        wed(4),
        thu(5),
        fri(6),
        sat(7),
        sat-sun(8),
        mon-fri(9),
        mon-sun(10)
      }
      ACCESS read-write
      STATUS mandatory
      DESCRIPTION
        "Selection of day of week for timer to switch"
      ::= { cmcTcMasterTc6TimerEntry 3 }
             
    cmcTcMasterTc6TimeOn OBJECT-TYPE
      SYNTAX DisplayString (SIZE (0..5))
      ACCESS read-write
      STATUS mandatory
      DESCRIPTION
        "Time to switch on current function, 
         Format: HH:MM"
      ::= { cmcTcMasterTc6TimerEntry 4 }

    cmcTcMasterTc6TimeOff OBJECT-TYPE
      SYNTAX DisplayString (SIZE (0..5))
      ACCESS read-write
      STATUS mandatory
      DESCRIPTION
        "Time to switch off current function,
         Format: HH:MM"
      ::= { cmcTcMasterTc6TimerEntry 5 }

    cmcTcMasterTc6TimeControl OBJECT-TYPE
      SYNTAX INTEGER  {
        disabled(1),
        enabled(2)
      }
      ACCESS read-write
      STATUS mandatory
      DESCRIPTION
        "Control via RTC"
      ::= { cmcTcMasterTc6TimerEntry 6 }

    cmcTcMasterTc6TimerFunction OBJECT-TYPE
      SYNTAX INTEGER {
        disKeypad1-1 (1),
        disKeypad2-1 (2),
        disKeypad1-2 (3),
        disKeypad2-2 (4),
        disKeypad1-3 (5),
        disKeypad2-3 (6),
        disKeypad1-4 (7),
        disKeypad2-4 (8),
        unlDoor1-1 (9),
        unlDoor2-1 (10),
        unlDoor1-2 (11),
        unlDoor2-2 (12),
        unlDoor1-3 (13),
        unlDoor2-3 (14),
        unlDoor1-4 (15),
        unlDoor2-5 (16),
        disTrapRec1 (17),
        disTrapRec2 (18),
        disTrapRec3 (19),
        disTrapRec4 (20),
        disSMS (21),
        schedule1 (22),
        schedule2 (23),
        schedule3 (24),
        schedule4 (25)
      }
      ACCESS read-write
      STATUS mandatory
      DESCRIPTION
        "Function which is controlled via timer
         1:     unlock via keypad 1 on unit 1 or remote input lock 1 is disabled
         2:     unlock via keypad 2 on unit 1 or remote input lock 2 is disabled
         3      unlock via keypad 1 on unit 2 or remote input lock 1 is disabled
         4:     unlock via keypad 2 on unit 2 or remote input lock 2 is disabled
         5:     unlock via keypad 1 on unit 3 or remote input lock 1 is disabled
         6:     unlock via keypad 2 on unit 3 or remote input lock 2 is disabled
         7:     unlock via keypad 1 on unit 4 or remote input lock 1 is disabled
         8:     unlock via keypad 2 on unit 4 or remote input lock 2 is disabled
         9:     Lock of door 1 on unit 1 will be unlocked
         10:    Lock of door 2 on unit 1 will be unlocked
         11:    Lock of door 1 on unit 2 will be unlocked
         12:    Lock of door 2 on unit 2 will be unlocked
         13:    Lock of door 1 on unit 3 will be unlocked
         14:    Lock of door 2 on unit 3 will be unlocked
         15:    Lock of door 1 on unit 4 will be unlocked
         16:    Lock of door 2 on unit 4 will be unlocked
         17-20: sending Traps to this Trap receiver will be disabled
         21:    sending SMS will be disabled
         22-25: Scheduled alarm off"
      ::= { cmcTcMasterTc6TimerEntry 7 }

--cmcTcMasterTc6TrapTable-group

  cmcTcMasterTc6TraptableNumber OBJECT-TYPE
    SYNTAX INTEGER 
    ACCESS read-only
    STATUS mandatory
    DESCRIPTION
      "Number of trapTable entries. The number of trap-receiver"
    ::= { cmcTcMasterTc6Traps 1 }

  cmcTcMasterTc6TrapTableTable OBJECT-TYPE    
    SYNTAX SEQUENCE OF CmcTcMasterTc6TrapTableEntry
    ACCESS not-accessible
    STATUS mandatory
    DESCRIPTION
     "A list of trap-receiver entries"
    ::= { cmcTcMasterTc6Traps 2 }

  cmcTcMasterTc6TrapTableEntry OBJECT-TYPE
    SYNTAX CmcTcMasterTc6TrapTableEntry
    ACCESS not-accessible
    STATUS mandatory
    DESCRIPTION
      "Entries of cmcTcMasterTc6TrapTable"
    INDEX   { cmcTcMasterTc6TrapIndex }
    ::= { cmcTcMasterTc6TrapTableTable 1 }      
              
    CmcTcMasterTc6TrapTableEntry ::=
      SEQUENCE {
        cmcTcMasterTc6TrapIndex
          INTEGER,
        cmcTcMasterTc6TrapStatus
          INTEGER,
        cmcTcMasterTc6TrapIPaddress
          DisplayString
      }

    cmcTcMasterTc6TrapIndex OBJECT-TYPE
      SYNTAX INTEGER (1..32000)
      ACCESS read-only
      STATUS mandatory
      DESCRIPTION
        "Index for the trap-receiver-table. Its value ranges between
         1 and the value of cmcTcMasterTc6TraptableNumber "
      ::= { cmcTcMasterTc6TrapTableEntry 1 }

    cmcTcMasterTc6TrapStatus OBJECT-TYPE
      SYNTAX INTEGER {
        disabled(1),
        enabled(2)
      }
      ACCESS read-write
      STATUS mandatory
      DESCRIPTION
        "Enable or disable trap receiver"
      ::= { cmcTcMasterTc6TrapTableEntry 2 }

    cmcTcMasterTc6TrapIPaddress OBJECT-TYPE
      SYNTAX DisplayString (SIZE (0..15))
      ACCESS read-write
      STATUS mandatory
      DESCRIPTION
        "IP-address of trap-receiver"
      ::= { cmcTcMasterTc6TrapTableEntry 3 }

--cmcTcMasterTc1Control-group (Added in Version 1.1)

  cmcTcMasterTc6QuitUnit OBJECT-TYPE
    SYNTAX INTEGER {
      noQuit(1),
      quit(2),
    }
    ACCESS read-write
    STATUS mandatory
    DESCRIPTION
      "Command to quit (acknowledge) alarms of CMC-TC unit.
       Setting to 'quit' (2) will have same result as pressing 'C' on Units.
       Variable is automatically set back to 'noQuit' (1)."
    ::= { cmcTcMasterTc6Control 1 }

--cmcTcMasterDevice7-group

  cmcTcMasterDev7Type OBJECT-TYPE
    SYNTAX INTEGER {
      other (0),
      cmc (1),
      pcu (3),
      tc (4)
    }
    ACCESS read-only
    STATUS mandatory
    DESCRIPTION
      "Type of device7"
    ::= { cmcTcMasterDevice7 1 }

  cmcTcMasterDev7Status OBJECT-TYPE
    SYNTAX INTEGER {
      other (1),
      notConnected (2),
      normal (3),
      minor (4),
      major (5),
      configChanged (6),
      connectionLost (10)
    }
    ACCESS read-only
    STATUS mandatory
    DESCRIPTION
      "Status of device7"
    ::= { cmcTcMasterDevice7 2 }

  cmcTcMasterDev7Descr OBJECT-TYPE
    SYNTAX DisplayString (SIZE (0..255))
    ACCESS read-only
    STATUS mandatory
    DESCRIPTION
      "A textual description of the entity.  This value
       should include the full name and version
       identification of the system's hardware type,
       software operating-system, and networking
       software.  It is mandatory that this only contain
       printable ASCII characters."
    ::= { cmcTcMasterDevice7 3 }

  cmcTcMasterDev7UpTime OBJECT-TYPE
    SYNTAX TimeTicks
    ACCESS read-only
    STATUS mandatory
    DESCRIPTION
      "The time (in hundredths of a second) since the
       network management portion of the system was last
       re-initialized."
    ::= { cmcTcMasterDevice7 4 }

  cmcTcMasterDev7Contact OBJECT-TYPE
    SYNTAX DisplayString (SIZE (0..255))
    ACCESS read-write
    STATUS mandatory
    DESCRIPTION
      "The textual identification of the contact person
       for this managed node, together with information
       on how to contact this person."
    ::= { cmcTcMasterDevice7 5 }

  cmcTcMasterDev7Name OBJECT-TYPE
    SYNTAX DisplayString (SIZE (0..255))
    ACCESS read-write
    STATUS mandatory
    DESCRIPTION
      "An administratively-assigned name for this
       managed node.  By convention, this is the node's
       fully-qualified domain name."
    ::= { cmcTcMasterDevice7 6 }

  cmcTcMasterDev7Location OBJECT-TYPE
    SYNTAX DisplayString (SIZE (0..255))
    ACCESS read-write
    STATUS mandatory
    DESCRIPTION
      "The physical location of this node (e.g.,
       `telephone closet, 3rd floor')."
    ::= { cmcTcMasterDevice7 7 }

--cmcTcMasterCmc7Values-group

  cmcTcMasterCmc7ValueTemperature1 OBJECT-TYPE
    SYNTAX INTEGER
    ACCESS read-only
    STATUS mandatory
    DESCRIPTION
      "Actual value of temperature 1 in deg C"
    ::= { cmcTcMasterCmc7Values 1 }

  cmcTcMasterCmc7ValueTemperature2 OBJECT-TYPE
    SYNTAX INTEGER
    ACCESS read-only
    STATUS mandatory
    DESCRIPTION
      "Actual value of temperature 2 in deg C"
    ::= { cmcTcMasterCmc7Values 2 }

  cmcTcMasterCmc7ValuePowerSupply OBJECT-TYPE
    SYNTAX INTEGER
    ACCESS read-only
    STATUS mandatory
    DESCRIPTION
      "Actual value of power supply in V"
    ::= { cmcTcMasterCmc7Values 3 }

  cmcTcMasterCmc7ValueAnalogAux1 OBJECT-TYPE
    SYNTAX INTEGER
    ACCESS read-only
    STATUS mandatory
    DESCRIPTION
      "Actual value of aux. analog input 1
      (4-20mA = 0-100%)"
    ::= { cmcTcMasterCmc7Values 4 }

  cmcTcMasterCmc7ValueAnalogAux2 OBJECT-TYPE
    SYNTAX INTEGER
    ACCESS read-only
    STATUS mandatory
    DESCRIPTION
      "Actual value of aux. analog input 2
      (4-20mA = 0-100%)"
    ::= { cmcTcMasterCmc7Values 5 }

--cmcTcMasterCmc7Values-table-group

  cmcTcMasterCmc7ValuesNumber OBJECT-TYPE
    SYNTAX INTEGER
    ACCESS read-only
    STATUS mandatory
    DESCRIPTION
      "Number of value-table entries"
    ::= { cmcTcMasterCmc7Table1 1 }

  cmcTcMasterCmc7ValuesTable OBJECT-TYPE
    SYNTAX SEQUENCE OF CmcTcMasterCmc7ValuesEntry
    ACCESS not-accessible
    STATUS mandatory
    DESCRIPTION
      "Headline of value-table"
    ::= { cmcTcMasterCmc7Table1 2 }

  cmcTcMasterCmc7ValuesEntry OBJECT-TYPE
    SYNTAX CmcTcMasterCmc7ValuesEntry
    ACCESS not-accessible
    STATUS mandatory
    DESCRIPTION
      "Entries of value-table"
    INDEX { cmcTcMasterCmc7ValuesIndex }
    ::= { cmcTcMasterCmc7ValuesTable 1 }

  CmcTcMasterCmc7ValuesEntry ::=
    SEQUENCE {
      cmcTcMasterCmc7ValuesIndex
        INTEGER,
      cmcTcMasterCmc7ValuesText
        DisplayString (SIZE (0..31)),
      cmcTcMasterCmc7ValuesValue
        INTEGER,
      cmcTcMasterCmc7ValuesStatus
        INTEGER,
      cmcTcMasterCmc7ValuesMaxValue
        INTEGER,
      cmcTcMasterCmc7ValuesMinValue
        INTEGER
    }

    cmcTcMasterCmc7ValuesIndex OBJECT-TYPE
      SYNTAX INTEGER (1..32000)
      ACCESS read-only
      STATUS mandatory
      DESCRIPTION
        "Index for the list of value entries. Its value ranges
        between 1 and the value of valuesNumber."
      ::= { cmcTcMasterCmc7ValuesEntry 1 }

    cmcTcMasterCmc7ValuesText OBJECT-TYPE
      SYNTAX DisplayString (SIZE (0..31))
      ACCESS read-write
      STATUS mandatory
      DESCRIPTION
        "Text of the entry in the value-table"
      ::= { cmcTcMasterCmc7ValuesEntry 2 }

    cmcTcMasterCmc7ValuesValue OBJECT-TYPE
      SYNTAX INTEGER
      ACCESS read-only
      STATUS mandatory
      DESCRIPTION
        "Actual value of the value-table"
      ::= { cmcTcMasterCmc7ValuesEntry 3 }

    cmcTcMasterCmc7ValuesStatus OBJECT-TYPE
      SYNTAX INTEGER {
        valueOK(1),
        valueTooLow(2),
        valueTooHigh(3),
        valueERROR(4),
        notAvail(5)
      }
      ACCESS read-only
      STATUS mandatory
      DESCRIPTION
        "Status of the value"
      ::= { cmcTcMasterCmc7ValuesEntry 4 }

    cmcTcMasterCmc7ValuesMaxValue OBJECT-TYPE
      SYNTAX INTEGER
      ACCESS read-write
      STATUS mandatory
      DESCRIPTION
        "Value for max. alarm"
      ::= { cmcTcMasterCmc7ValuesEntry 5 }

    cmcTcMasterCmc7ValuesMinValue OBJECT-TYPE
      SYNTAX INTEGER
      ACCESS read-write
      STATUS mandatory
      DESCRIPTION
        "Value for min. alarm"
      ::= { cmcTcMasterCmc7ValuesEntry 6 }

--cmcTcMasterCmc7status-group

  cmcTcMasterCmc7StatusTemperature1 OBJECT-TYPE
    SYNTAX DisplayString (SIZE (0..31))
    ACCESS read-only
    STATUS mandatory
    DESCRIPTION
      "Status temperature 1, OK/ too low/ too high
       (see setpoints of temperature 1)"
    ::= { cmcTcMasterCmc7Status 1 }

  cmcTcMasterCmc7StatusTemperature2 OBJECT-TYPE
    SYNTAX DisplayString (SIZE (0..31))
    ACCESS read-only
    STATUS mandatory
    DESCRIPTION
      "Status temperature 2, OK/ too low/ too high
       (see setpoints of temperature 2)"
    ::= { cmcTcMasterCmc7Status 2 }

  cmcTcMasterCmc7StatusFan1 OBJECT-TYPE
    SYNTAX DisplayString (SIZE (0..31))
    ACCESS read-only
    STATUS mandatory
    DESCRIPTION
      "Status fan 1, Stop/ running/ fault"
    ::= { cmcTcMasterCmc7Status 3 }

  cmcTcMasterCmc7StatusFan2 OBJECT-TYPE
    SYNTAX DisplayString (SIZE (0..31))
    ACCESS read-only
    STATUS mandatory
    DESCRIPTION
      "Status fan 2, Stop/ running/ fault"
    ::= { cmcTcMasterCmc7Status 4 }

  cmcTcMasterCmc7StatusHeating OBJECT-TYPE
    SYNTAX DisplayString (SIZE (0..31))
    ACCESS read-only
    STATUS mandatory
    DESCRIPTION
      "Status heating, On/Off"
    ::= { cmcTcMasterCmc7Status 5 }

  cmcTcMasterCmc7StatusPowerSupply OBJECT-TYPE
    SYNTAX DisplayString (SIZE (0..31))
    ACCESS read-only
    STATUS mandatory
    DESCRIPTION
      "Status power supply, OK/ too low/ too high
       (see setpoints of power supply)"
    ::= { cmcTcMasterCmc7Status 6 }

  cmcTcMasterCmc7StatusAnalogAux1 OBJECT-TYPE
    SYNTAX DisplayString (SIZE (0..31))
    ACCESS read-only
    STATUS mandatory
    DESCRIPTION
      "Status aux analog input 1, OK/ too low/ too high"
    ::= { cmcTcMasterCmc7Status 7 }

  cmcTcMasterCmc7StatusAnalogAux2 OBJECT-TYPE
    SYNTAX DisplayString (SIZE (0..31))
    ACCESS read-only
    STATUS mandatory
    DESCRIPTION
      "Status aux analog input 2, OK/ too low/ too high"
    ::= { cmcTcMasterCmc7Status 8 }

  cmcTcMasterCmc7StatusDoor OBJECT-TYPE
    SYNTAX DisplayString (SIZE (0..31))
    ACCESS read-only
    STATUS mandatory
    DESCRIPTION
      "Status door, open/closed/locked"
    ::= { cmcTcMasterCmc7Status 9 }

  cmcTcMasterCmc7StatusUps1 OBJECT-TYPE
    SYNTAX DisplayString (SIZE (0..31))
    ACCESS read-only
    STATUS mandatory
    DESCRIPTION
      "Status UPS 1, OK/ fault"
    ::= { cmcTcMasterCmc7Status 10 }

  cmcTcMasterCmc7StatusUps2 OBJECT-TYPE
    SYNTAX DisplayString (SIZE (0..31))
    ACCESS read-only
    STATUS mandatory
    DESCRIPTION
      "Status UPS 2, OK/ fault"
    ::= { cmcTcMasterCmc7Status 11 }

  cmcTcMasterCmc7StatusSmokeSensor OBJECT-TYPE
    SYNTAX DisplayString (SIZE (0..31))
    ACCESS read-only
    STATUS mandatory
    DESCRIPTION
      "Status smoke-sensor, OK/ smoke"
    ::= { cmcTcMasterCmc7Status 12 }

  cmcTcMasterCmc7StatusVibrationSensor OBJECT-TYPE
    SYNTAX DisplayString (SIZE (0..31))
    ACCESS read-only
    STATUS mandatory
    DESCRIPTION
      "Status vibration sensor, OK/ vibration"
    ::= { cmcTcMasterCmc7Status 13 }

  cmcTcMasterCmc7StatusMessage OBJECT-TYPE
    SYNTAX DisplayString (SIZE (0..31))
    ACCESS read-only
    STATUS mandatory
    DESCRIPTION
      "Message from CMC"
    ::= { cmcTcMasterCmc7Status 14 }

  cmcTcMasterCmc7ValueOperatingTime OBJECT-TYPE
    SYNTAX DisplayString (SIZE (0..31))
    ACCESS read-only
    STATUS mandatory
    DESCRIPTION
      "Operating time CMC-unit"
    ::= { cmcTcMasterCmc7Status 15 }

  cmcTcMasterCmc7StatusUnit OBJECT-TYPE
    SYNTAX INTEGER {
      unitCelsius(1),
      unitFahrenheit(2)
    }
    ACCESS read-only
    STATUS mandatory
    DESCRIPTION
      "Unit of temperature-values, Celsius or Fahrenheit"
   ::= { cmcTcMasterCmc7Status 16 }


--cmcTcMasterCmc7Status-table-group

  cmcTcMasterCmc7StatusNumber OBJECT-TYPE
    SYNTAX INTEGER 
    ACCESS read-only
    STATUS mandatory
    DESCRIPTION
      "Number of status-table entries"
    ::= { cmcTcMasterCmc7Table 1 }

  cmcTcMasterCmc7StatusTable OBJECT-TYPE
    SYNTAX SEQUENCE OF CmcTcMasterCmc7StatusEntry
    ACCESS not-accessible
    STATUS mandatory
    DESCRIPTION
      "Headline of table"
    ::= { cmcTcMasterCmc7Table 2 }

  cmcTcMasterCmc7StatusEntry OBJECT-TYPE
    SYNTAX CmcTcMasterCmc7StatusEntry
    ACCESS not-accessible
    STATUS mandatory
    DESCRIPTION
      "A list of status entries.  The number of
       entries is given by the value of cmcTcMasterCmc7StatusNumber." 
    INDEX { cmcTcMasterCmc7StatusIndex }
    ::= { cmcTcMasterCmc7StatusTable 1 }

  CmcTcMasterCmc7StatusEntry ::=
    SEQUENCE {
      cmcTcMasterCmc7StatusIndex
        INTEGER,
      cmcTcMasterCmc7StatusText
        DisplayString (SIZE (0..31)),
      cmcTcMasterCmc7StatusStatus
        INTEGER              
    }

    cmcTcMasterCmc7StatusIndex OBJECT-TYPE
      SYNTAX INTEGER (1..32000)
      ACCESS read-only
      STATUS mandatory
      DESCRIPTION
        "Index fo the list of status entries. Its value ranges
         between 1 and the value of cmcTcMasterCmc7StatusNumber." 
      ::= { cmcTcMasterCmc7StatusEntry 1 }

    cmcTcMasterCmc7StatusText OBJECT-TYPE
      SYNTAX DisplayString (SIZE (0..31))
      ACCESS read-write
      STATUS mandatory
      DESCRIPTION
        "Text of the entry in the status-table"
      ::= { cmcTcMasterCmc7StatusEntry 2 }

    cmcTcMasterCmc7StatusStatus OBJECT-TYPE
      SYNTAX INTEGER  {
        statusOK(1),
        alarm(2),
        security(3),
        notAvail(4)
      }
      ACCESS read-only
      STATUS mandatory
      DESCRIPTION
        "Status of the table entry"
      ::= { cmcTcMasterCmc7StatusEntry 3 }

--******************************************************************************

--cmcTCMasterCmc7Set-group

  cmcTcMasterCmc7StatusAccess OBJECT-TYPE
    SYNTAX DisplayString (SIZE (0..31))
    ACCESS read-write
    STATUS mandatory
    DESCRIPTION
      "Status access"
    ::= { cmcTcMasterCmc7Set 1 }

  cmcTcMasterCmc7SetDoor OBJECT-TYPE
    SYNTAX INTEGER {
      lockDoor(1),
      openDoorTime(2),
      openDoorAccess(3),
      openDoor(4)
    }
    ACCESS read-write
    STATUS mandatory
    DESCRIPTION
      "Set door, see table"
    ::= { cmcTcMasterCmc7Set 2 }

  cmcTcMasterCmc7SetMessage OBJECT-TYPE
    SYNTAX DisplayString (SIZE (0..31))
    ACCESS read-write
    STATUS mandatory
    DESCRIPTION
      "Set message"
    ::= { cmcTcMasterCmc7Set 3 }

  cmcTcMasterCmc7SetFault        OBJECT-TYPE
    SYNTAX INTEGER {
      clearFault(1),
      setFault(2)
    }
    ACCESS read-write
    STATUS mandatory
    DESCRIPTION
      "Set fault, see table"
    ::= { cmcTcMasterCmc7Set 4 }

--cmcTcMasterCmc7RelayControl-group

  cmcTcMasterCmc7RelaytableMaxNum OBJECT-TYPE
    SYNTAX INTEGER 
    ACCESS read-only
    STATUS mandatory
    DESCRIPTION
      "Number of table entries"
    ::= { cmcTcMasterCmc7RelayControl 1 }

  cmcTcMasterCmc7RelayTable OBJECT-TYPE
    SYNTAX SEQUENCE OF CmcTcMasterCmc7RelayEntry
    ACCESS not-accessible
    STATUS mandatory
    DESCRIPTION
      "Headline of table for relay control"
    ::= { cmcTcMasterCmc7RelayControl 2 }

  cmcTcMasterCmc7RelayEntry OBJECT-TYPE
    SYNTAX CmcTcMasterCmc7RelayEntry
    ACCESS not-accessible
    STATUS mandatory
    DESCRIPTION
      "Entries"
    INDEX { cmcTcMasterCmc7RelaytableIndex }
    ::= { cmcTcMasterCmc7RelayTable 1 }

  CmcTcMasterCmc7RelayEntry ::=
    SEQUENCE {
      cmcTcMasterCmc7RelaytableIndex
        INTEGER,
      cmcTcMasterCmc7RelaytableText
	DisplayString (SIZE (0..31)),
      cmcTcMasterCmc7RelaytableStatus
        INTEGER              
    }

    cmcTcMasterCmc7RelaytableIndex OBJECT-TYPE
      SYNTAX INTEGER (1..32000)
      ACCESS read-only
      STATUS mandatory
      DESCRIPTION
        "Index for the relay-table. Its value ranges
         between 1 and cmcTcMasterCmc7RelaytableMaxNum"
      ::= { cmcTcMasterCmc7RelayEntry 1 }

    cmcTcMasterCmc7RelaytableText OBJECT-TYPE
      SYNTAX DisplayString (SIZE (0..31))
      ACCESS read-write
      STATUS mandatory
      DESCRIPTION
        "Description-Text for each relay in the table"
      ::= { cmcTcMasterCmc7RelayEntry 2 }

    cmcTcMasterCmc7RelaytableStatus OBJECT-TYPE
      SYNTAX INTEGER  {
        relayOFF(1),
        relayON(2),
        notAvail(3)
      }
      ACCESS read-write
      STATUS mandatory
      DESCRIPTION
        "Status of relays in the table"
      ::= { cmcTcMasterCmc7RelayEntry 3 }

--cmcTcMasterCmc7Setpoints-group

  cmcTcMasterCmc7SetpointFan1 OBJECT-TYPE
    SYNTAX INTEGER 
    ACCESS read-write
    STATUS mandatory
    DESCRIPTION
      "Setpoint Fan 1 in C, Fan 1 will start
       if temperature 1 exceeds this value"
    ::= { cmcTcMasterCmc7Setpoints 1 }

  cmcTcMasterCmc7SetpointFan2 OBJECT-TYPE
    SYNTAX INTEGER 
    ACCESS read-write
    STATUS mandatory
    DESCRIPTION
      "Setpoint Fan 2 in C, Fan 2 will start
       if temperature 2 exceeds this value"
    ::= { cmcTcMasterCmc7Setpoints 2 }

  cmcTcMasterCmc7SetpointHeating OBJECT-TYPE
    SYNTAX INTEGER 
    ACCESS read-write
    STATUS mandatory
    DESCRIPTION
      "Setpoint heating in C, heating will start
       if lowest value of temperature 1 and 2 falls below this value"
    ::= { cmcTcMasterCmc7Setpoints 3 }

  cmcTcMasterCmc7SetpointHighTemperature1 OBJECT-TYPE
    SYNTAX INTEGER 
    ACCESS read-write
    STATUS mandatory
    DESCRIPTION
      "Setpoint high value alarm temperature 1"
    ::= { cmcTcMasterCmc7Setpoints 4 }

  cmcTcMasterCmc7SetpointLowTemperature1 OBJECT-TYPE
    SYNTAX INTEGER 
    ACCESS read-write
    STATUS mandatory
    DESCRIPTION
      "Setpoint low value alarm temperature 1"
    ::= { cmcTcMasterCmc7Setpoints 5 }

  cmcTcMasterCmc7SetpointHighTemperature2 OBJECT-TYPE
    SYNTAX INTEGER 
    ACCESS read-write
    STATUS mandatory
    DESCRIPTION
      "Setpoint high value alarm temperature 2"
    ::= { cmcTcMasterCmc7Setpoints 6 }

  cmcTcMasterCmc7SetpointLowTemperature2 OBJECT-TYPE
    SYNTAX INTEGER 
    ACCESS read-write
    STATUS mandatory
    DESCRIPTION
      "Setpoint low value alarm temperature 2"
    ::= { cmcTcMasterCmc7Setpoints 7 }

  cmcTcMasterCmc7SetpointHighVoltage OBJECT-TYPE
    SYNTAX INTEGER 
    ACCESS read-write
    STATUS mandatory
    DESCRIPTION
      "Setpoint high value supply voltage alarm"
    ::= { cmcTcMasterCmc7Setpoints 8 }

  cmcTcMasterCmc7SetpointLowVoltage OBJECT-TYPE
    SYNTAX INTEGER
    ACCESS read-write
    STATUS mandatory
    DESCRIPTION
      "Setpoint low value supply voltage alarm"
    ::= { cmcTcMasterCmc7Setpoints 9 }

  cmcTcMasterCmc7SetpointLowAux1 OBJECT-TYPE
    SYNTAX INTEGER 
    ACCESS read-write
    STATUS mandatory
    DESCRIPTION
      "Setpoint low value Aux input 1 alarm"
    ::= { cmcTcMasterCmc7Setpoints 10 }

  cmcTcMasterCmc7SetpointHighAux1 OBJECT-TYPE
    SYNTAX INTEGER 
    ACCESS read-write
    STATUS mandatory
    DESCRIPTION
      "Setpoint high value Aux input 1 alarm"
    ::= { cmcTcMasterCmc7Setpoints 11 }

  cmcTcMasterCmc7SetpointLowAux2 OBJECT-TYPE
    SYNTAX INTEGER 
    ACCESS read-write
    STATUS mandatory
    DESCRIPTION
      "Setpoint low value Aux input 2 alarm"
    ::= { cmcTcMasterCmc7Setpoints 12 }

  cmcTcMasterCmc7SetpointHighAux2 OBJECT-TYPE
    SYNTAX INTEGER 
    ACCESS read-write
    STATUS mandatory
    DESCRIPTION
      "Setpoint high value Aux input alarm"
    ::= { cmcTcMasterCmc7Setpoints 13 }

--cmcTcMasterCmc7TrapControl-group

  cmcTcMasterCmc7SetTrapRepeat OBJECT-TYPE
    SYNTAX INTEGER {
      disableTrapRepeat(1),
      enableTrapRepeat(2)
    }
    ACCESS read-write
    STATUS mandatory
    DESCRIPTION
      "Enable/disable repeating of traps. If enabled, traps will
       be repeated after a repeat time, set in setTrapRepeatTime.
       Repeating can be stopped by setting setTrapQuit to quitTrap"
    ::= { cmcTcMasterCmc7TrapControl 1 }

  cmcTcMasterCmc7SetTrapRepeatTime OBJECT-TYPE
    SYNTAX INTEGER 
    ACCESS read-write
    STATUS mandatory
    DESCRIPTION
      "Time value (sec) for trap-repeating, if setTrapRepeat is enabled"
    ::= { cmcTcMasterCmc7TrapControl 2 }

  cmcTcMasterCmc7SetTrapQuit OBJECT-TYPE
    SYNTAX INTEGER {
      quitTrap(1),
      quitTrapOK(2),
      noTrapToQuit(3),
      trapToQuit(4)
    }
    ACCESS read-write
    STATUS mandatory
    DESCRIPTION
      "Quit trap to stop repeating."
    ::= { cmcTcMasterCmc7TrapControl 3 }

--cmcTcMasterCmc7TrapTable-group

  cmcTcMasterCmc7TraptableNumber OBJECT-TYPE
    SYNTAX INTEGER 
    ACCESS read-only
    STATUS mandatory
    DESCRIPTION
      "Number of trapTable entries. The number of trap-receiver"
    ::= { cmcTcMasterCmc7Traps 1 }

  cmcTcMasterCmc7TrapTable OBJECT-TYPE
    SYNTAX SEQUENCE OF CmcTcMasterCmc7TrapEntry
    ACCESS not-accessible
    STATUS mandatory
    DESCRIPTION
      "A list of trap-receiver entries"
    ::= { cmcTcMasterCmc7Traps 2 }

  cmcTcMasterCmc7TrapEntry OBJECT-TYPE
    SYNTAX CmcTcMasterCmc7TrapEntry
    ACCESS not-accessible
    STATUS mandatory
    DESCRIPTION
      "Entries of trapTable"
    INDEX { cmcTcMasterCmc7TrapIndex }
    ::= { cmcTcMasterCmc7TrapTable 1 }

  CmcTcMasterCmc7TrapEntry ::=
    SEQUENCE {
      cmcTcMasterCmc7TrapIndex
        INTEGER,
      cmcTcMasterCmc7TrapStatus
        INTEGER,
      cmcTcMasterCmc7TrapIPaddress
        DisplayString
    }

    cmcTcMasterCmc7TrapIndex OBJECT-TYPE
      SYNTAX INTEGER (1..32000)
      ACCESS read-only
      STATUS mandatory
      DESCRIPTION
        "Index for the trap-receiver-table. Its value ranges between
         1 and the value of cmcTcMasterCmc7TraptableNumber "
      ::= { cmcTcMasterCmc7TrapEntry 1 }

    cmcTcMasterCmc7TrapStatus OBJECT-TYPE
      SYNTAX INTEGER  {
        enabled(1),
        disabled(2)
      }
      ACCESS read-write
      STATUS mandatory
      DESCRIPTION
        "Enable or disable trap receiver"
      ::= { cmcTcMasterCmc7TrapEntry 2 }

    cmcTcMasterCmc7TrapIPaddress OBJECT-TYPE
      SYNTAX DisplayString (SIZE (0..31))
      ACCESS read-write
      STATUS mandatory
      DESCRIPTION
        "IP-address of trap-receiver"
      ::= { cmcTcMasterCmc7TrapEntry 3 }

--cmcTcMasterPcu7MibRev-group
          
  cmcTcMasterPcu7MibMajRev OBJECT-TYPE
    SYNTAX INTEGER (1..32000)
    ACCESS read-only
    STATUS mandatory
    DESCRIPTION
      "The Major Revision level.
       A change in the major revision level represents a major change
       in the architecture of the MIB. A change in the major revision 
       level may indicate a significant change in the information,
       correct interpretation of data may require a MIB document
       with the same major revision level."
    ::= { cmcTcMasterPcu7MibRev 1 }

  cmcTcMasterPcu7MibMinRev OBJECT-TYPE
    SYNTAX INTEGER (0..32000)
    ACCESS read-only
    STATUS mandatory
    DESCRIPTION
      "The Minor Revision level.
       A change in the minor revision level may represent some minor
       additional support, no changes to any pre-existing information
       has occurred."
    ::= { cmcTcMasterPcu7MibRev 2 }

  cmcTcMasterPcu7MibCondition OBJECT-TYPE
    SYNTAX INTEGER {
      other (1),
      ok (2),
      degraded (3),
      failed (4)
    }
    ACCESS read-only
    STATUS mandatory
    DESCRIPTION
      "The overall condition (status) of the system represented by
       this MIB. 
       (2) OK
       (3) a minor problem, warning condition (yellow LED on PCU)
       (4) a major problem (red LED on PCU)"
    ::= { cmcTcMasterPcu7MibRev 3 }

--cmcTcMasterPcu7Values-group

  cmcTcMasterPcu7ValueEnergy1 OBJECT-TYPE
    SYNTAX INTEGER 
    ACCESS read-only
    STATUS mandatory
    DESCRIPTION
      "Total value of the Energy (Wh), measured on IEC input 1"
    ::= { cmcTcMasterPcu7Values 1 }

  cmcTcMasterPcu7ValueEnergy2 OBJECT-TYPE
    SYNTAX INTEGER 
    ACCESS read-only
    STATUS mandatory
    DESCRIPTION
      "Actual value of the Energy (Wh), measured on IEC input 2"
    ::= { cmcTcMasterPcu7Values 2 }

  cmcTcMasterPcu7ValueEnergy1Time OBJECT-TYPE
    SYNTAX INTEGER 
    ACCESS read-only
    STATUS mandatory
    DESCRIPTION
      "Actual value of the Energy (Wh), measured on IEC input 1, can be set to 0
       Value can be used to calculate the energy over a fixed time"
    ::= { cmcTcMasterPcu7Values 3 }

  cmcTcMasterPcu7ValueEnergy2Time OBJECT-TYPE
    SYNTAX INTEGER 
    ACCESS read-only
    STATUS mandatory
    DESCRIPTION
      "Actual value of the Energy (Wh), measured on IEC input 2, can be set to 0.
       Value can be used to calculate the energy over a fixed time"
    ::= { cmcTcMasterPcu7Values 4 }

  cmcTcMasterPcu7ValuePower1 OBJECT-TYPE
    SYNTAX INTEGER 
    ACCESS read-only
    STATUS mandatory
    DESCRIPTION
      "Calculated actual power 1 (W). Calculated from cmcTcMasterPcu7ValueEnergy1/time"
    ::= { cmcTcMasterPcu7Values 5 }
          
  cmcTcMasterPcu7ValuePower2 OBJECT-TYPE
    SYNTAX INTEGER 
    ACCESS read-only
    STATUS mandatory
    DESCRIPTION
      "Calculated actual power 2 (W). Calculated from cmcTcMasterPcu7ValueEnergy2/time"
    ::= { cmcTcMasterPcu7Values 6 }
          
  cmcTcMasterPcu7ValueTemperature OBJECT-TYPE
    SYNTAX INTEGER 
    ACCESS read-only
    STATUS mandatory
    DESCRIPTION
      "Actual value of temperature 1 in deg C or deg F"
    ::= { cmcTcMasterPcu7Values 7 }
          
--cmcTcMasterPcu7Status-group

  cmcTcMasterPcu7StatusInput1 OBJECT-TYPE
    SYNTAX INTEGER {
      false(1),
      true(2),
      pending(3),
      notAvail(4)
    }
    ACCESS read-only
    STATUS mandatory
    DESCRIPTION
      "Status of digital Input 1
       (1) digital signal is true (contact closed if setup is NO)
       (2) digital signal is false(contact opened if setup is NO),
       note setup of input (NO/NC)
       (3) digital input is pending, note setup of delay"
    ::= { cmcTcMasterPcu7Status 1 }

  cmcTcMasterPcu7StatusInput2 OBJECT-TYPE
    SYNTAX INTEGER {
      false(1),
      true(2),
      pending(3),
      notAvail(4)
    }
    ACCESS read-only
    STATUS mandatory
    DESCRIPTION
      "Status of digital Input 2
       (1) digital signal is true (contact closed if setup is NO)
       (2) digital signal is false(contact opened if setup is NO),
       note setup of input (NO/NC)
       (3) digital input is pending, note setup of delay"
    ::= { cmcTcMasterPcu7Status 2 }

  cmcTcMasterPcu7StatusPower1 OBJECT-TYPE
    SYNTAX INTEGER {
      ok(1),
      tooHigh(2),
      tooLow(3),
      warning(4),
      error(5),
      notAvail(6)
    }
    ACCESS read-only
    STATUS mandatory
    DESCRIPTION
      "Status Power 1, see setpoints"
    ::= { cmcTcMasterPcu7Status 3 }

  cmcTcMasterPcu7StatusPower2 OBJECT-TYPE
    SYNTAX INTEGER {
      ok(1),
      tooHigh(2),
      tooLow(3),
      warning(4),
      error(5),
      notAvail(6)
    }
    ACCESS read-only
    STATUS mandatory
    DESCRIPTION
      "Status Power 2, see setpoints"
    ::= { cmcTcMasterPcu7Status 4 }

  cmcTcMasterPcu7StatusTemperature OBJECT-TYPE
    SYNTAX INTEGER {
      ok(1),
      tooHigh(2),
      tooLow(3),
      warning(4),
      error(5)
    }
    ACCESS read-only
    STATUS mandatory
    DESCRIPTION
      "Status temperature 1, OK/ too high/ too low
       (see setpoints of temperature 1)"
    ::= { cmcTcMasterPcu7Status 5 }

--cmcTcMasterPcu7Status-table-group

  cmcTcMasterPcu7OutletsNumber OBJECT-TYPE
    SYNTAX INTEGER 
    ACCESS read-only
    STATUS mandatory
    DESCRIPTION
      "Number of value-table entries=number of outlets available on this unit"
    ::= { cmcTcMasterPcu7StatusTable1 1 }

  cmcTcMasterPcu7StatusTable OBJECT-TYPE
    SYNTAX SEQUENCE OF CmcTcMasterPcu7StatusEntry
    ACCESS not-accessible
    STATUS mandatory
    DESCRIPTION
      "Headline of status-table"
    ::= { cmcTcMasterPcu7StatusTable1 2 }

  cmcTcMasterPcu7StatusEntry OBJECT-TYPE
    SYNTAX CmcTcMasterPcu7StatusEntry
    ACCESS not-accessible
    STATUS mandatory
    DESCRIPTION
      "Entries of status-table"
    INDEX { cmcTcMasterPcu7StatusIndex }
    ::= { cmcTcMasterPcu7StatusTable 1 }

    CmcTcMasterPcu7StatusEntry ::=
      SEQUENCE {
        cmcTcMasterPcu7StatusIndex
          INTEGER,
        cmcTcMasterPcu7StatusText
          DisplayString (SIZE (0..31)),                
        cmcTcMasterPcu7StatusStatus
          INTEGER,
        cmcTcMasterPcu7ControlSNMP
          INTEGER,
        cmcTcMasterPcu7FrontSwitch
          INTEGER,
        cmcTcMasterPcu7Delay
          INTEGER,
        cmcTcMasterPcu7Input1
          INTEGER,
        cmcTcMasterPcu7Input2
          INTEGER,
        cmcTcMasterPcu7Temperature
          INTEGER,          
        cmcTcMasterPcu7Power
          INTEGER,          
        cmcTcMasterPcu7RestoreOutputStatus
          INTEGER           
      }

    cmcTcMasterPcu7StatusIndex OBJECT-TYPE
      SYNTAX INTEGER (1..32000)
      ACCESS read-only
      STATUS mandatory
      DESCRIPTION
        "Index for the list of value entries. Its value ranges
         between 1 and the value of cmcTcMasterPcu7OutletsNumber."
      ::= { cmcTcMasterPcu7StatusEntry 1 }

    cmcTcMasterPcu7StatusText OBJECT-TYPE
      SYNTAX DisplayString (SIZE (0..31))
      ACCESS read-write
      STATUS mandatory
      DESCRIPTION
        "Descriptional text for each outlet (entry in the table)"
      ::= { cmcTcMasterPcu7StatusEntry 2 }
              
    cmcTcMasterPcu7StatusStatus OBJECT-TYPE
      SYNTAX INTEGER {
        ok(1),
        onFrontKey(2),
        offFrontKey(3),
        onWEB(4),
        offWEB(5),
        onInput1(6),
        offInput1(7),
        onInput2(8),
        offInput2(9),
        onTemp(10),
        offTemp(11),
        onSNMP(12),
        offSNMP(13),
        onTimer(14),
        offTimer(15),
        onDelay(16),
        onConsole(17),
        offConsole(18),
        onReboot(19), 
        offReboot(20),
        onPower(21),
        offPower(22)
      }
      ACCESS read-only
      STATUS mandatory
      DESCRIPTION
        "Actual status of the outlet"
      ::= { cmcTcMasterPcu7StatusEntry 3 }

    cmcTcMasterPcu7ControlSNMP OBJECT-TYPE
      SYNTAX INTEGER  {
        on(1),
        off(2)
      }
      ACCESS read-write
      STATUS mandatory
      DESCRIPTION
        "Control via SNMP"
      ::= { cmcTcMasterPcu7StatusEntry 4 }

    cmcTcMasterPcu7FrontSwitch OBJECT-TYPE
      SYNTAX INTEGER {
        disabled(1),
        enabled(2)
      }
      ACCESS read-write
      STATUS mandatory
      DESCRIPTION
        "Control via front switch"
      ::= { cmcTcMasterPcu7StatusEntry 5 }
 
    cmcTcMasterPcu7Delay OBJECT-TYPE
      SYNTAX INTEGER (0..300)
      ACCESS read-write
      STATUS mandatory
      DESCRIPTION
        "Value for delay time in seconds.
         Value>0: Output is switched off for this time (in sec)"
      ::= { cmcTcMasterPcu7StatusEntry 6 }

    cmcTcMasterPcu7Input1 OBJECT-TYPE
      SYNTAX INTEGER {
        disabled(1),
        switchOn(2),
        switchOff(3),
        switchOnOff(4)
      }
      ACCESS read-write
      STATUS mandatory
      DESCRIPTION
        "Control via digital input 1
         (1): disabled
         (2): output is switched on in case of input 1 alarm
         (3): output is switched off in case of input 1 alarm
         (4): output has same status as input 1"
      ::= { cmcTcMasterPcu7StatusEntry 7 }

    cmcTcMasterPcu7Input2 OBJECT-TYPE
      SYNTAX INTEGER {
        disabled(1),
        switchOn(2),
        switchOff(3),
        switchOnOff(4)
      }
      ACCESS read-write
      STATUS mandatory
      DESCRIPTION
        "Control via digital input 2
         (1): disabled
         (2): output is switched on in case of input 2 alarm
         (3): output is switched off in case of input 2 alarm
         (4): output has same status as input 2"             
      ::= { cmcTcMasterPcu7StatusEntry 8 }

    cmcTcMasterPcu7Temperature OBJECT-TYPE
      SYNTAX INTEGER {
        disabled(1),
        switchOffAlarm(2),
        switchOnAlarm(3),
        switchOffSetpoint(4),
        switchOnSetpoint(5)
      }
      ACCESS read-write
      STATUS mandatory
      DESCRIPTION
        "Control via temperature alarm or setpoint
         (1): disabled
         (2): output is switched off in case of temperature alarm
         (3): output is switched on in case of temperature alarm
         (4): output is switched off if temperature setpoint (cmcTcMasterPcu7SetpointTemperature)
              is reached
         (5): output is switched on if temperature setpoint (cmcTcMasterPcu7SetpointTemperature)
              is reached"
      ::= { cmcTcMasterPcu7StatusEntry 9 }   
    
    cmcTcMasterPcu7Power OBJECT-TYPE
      SYNTAX INTEGER {
        disabled(1),
        switchOffAlarm(2),
        switchOffWarning(3),
        switchOnAlarm(4),
        switchOnWarning(5)
      }
      ACCESS read-write
      STATUS mandatory
      DESCRIPTION
        "Control via power setpoint
         (1): disabled
         (2): output is switched off upon power high alarm (cmcTcMasterPcu7SetpointHighPower1)
         (3): output is switched off upon power warning (cmcTcMasterPcu7SetpointWarningPower1)
         (4): output is switched on upon power alarm (cmcTcMasterPcu7SetpointHigh(Low)Power1)
         (5): output is switched on upon power warning (cmcTcMasterPcu7SetpointWarningPower1)             "
      ::= { cmcTcMasterPcu7StatusEntry 10 }                

    cmcTcMasterPcu7RestoreOutputStatus OBJECT-TYPE
      SYNTAX INTEGER {
        disabled(1),
        enabled(2)
      }
      ACCESS read-write
      STATUS mandatory
      DESCRIPTION
        "Save last output status and switch output to this status after reboot"
      ::= { cmcTcMasterPcu7StatusEntry 11 }
                
--cmcTcMasterPcu7SetupGeneral-group

  cmcTcMasterPcu7SetTempUnit OBJECT-TYPE
    SYNTAX INTEGER {
      celsius(1),
      fahrenheit(2)
    }
    ACCESS read-write
    STATUS mandatory
    DESCRIPTION
      "Unit of all temperature values and setpoints, Celsius or Fahrenheit"
    ::= { cmcTcMasterPcu7SetupGeneral 1 }

  cmcTcMasterPcu7SetBeeper OBJECT-TYPE
    SYNTAX INTEGER {
      off(1),
      on(2),
      enableClear(3)
    }
    ACCESS read-write
    STATUS mandatory
    DESCRIPTION
      "Audible alarm in PCU unit:
       (1): beeper is off (general)
       (2): beeper is on (Alarm)
       (3): enable Clear (cmcTcMasterPcu7ClearAlarm)"
    ::= { cmcTcMasterPcu7SetupGeneral 2 }

  cmcTcMasterPcu7LogicRelay OBJECT-TYPE
    SYNTAX INTEGER {
      closeAtAlarm(1),
      openAtAlarm(2),
      off(3),
      enableRemote(4)
    }
    ACCESS read-write
    STATUS mandatory
    DESCRIPTION
      "Logic of alarm relay: 
       (1): Relay will pick up in case of an alarm
       (2): Relay will release in case of an alarm
       (3): Relay off (general)
       (4): enable remote relay control (SNMP set)"
    ::= { cmcTcMasterPcu7SetupGeneral 3 }
 
  cmcTcMasterPcu7ClearRelay OBJECT-TYPE
    SYNTAX INTEGER {
      disabled(1),
      enabled(2)
    }
    ACCESS read-write
    STATUS mandatory
    DESCRIPTION
      "Enable clear of alarm relay: 
       (1): Relay cannot be cleared by cmcTcMasterPcu7ClearAlarm
       (2): Relay can be cleared by cmcTcMasterPcu7ClearAlarm"
    ::= { cmcTcMasterPcu7SetupGeneral 4 }                  

  cmcTcMasterPcu7WebAccess OBJECT-TYPE
    SYNTAX INTEGER {
      viewOnly(1),
      fullAccess(2),
      off(3)
    }
    ACCESS read-write
    STATUS mandatory
    DESCRIPTION
      "Web access via HTTP: 
       (1): view only
       (2): full Access, read and set
       (3): Web disabled (general)"
    ::= { cmcTcMasterPcu7SetupGeneral 5 }
 
  cmcTcMasterPcu7SetupDate OBJECT-TYPE
    SYNTAX DisplayString (SIZE (0..10))
    ACCESS read-write
    STATUS mandatory
    DESCRIPTION
      "actual Date in format DD.MM.YYYY"
    ::= { cmcTcMasterPcu7SetupGeneral 6 }

  cmcTcMasterPcu7SetupTime OBJECT-TYPE
    SYNTAX DisplayString (SIZE (0..8))
    ACCESS read-write
    STATUS mandatory
    DESCRIPTION
      "actual Time in format HH:MM:SS, HH (0-23), MM (0-59), SS (0-59)"
    ::= { cmcTcMasterPcu7SetupGeneral 7 }

--cmcTcMasterPcu7TimerTable1-group
 
  cmcTcMasterPcu7TimerNumber OBJECT-TYPE
    SYNTAX INTEGER 
    ACCESS read-only
    STATUS mandatory
    DESCRIPTION
      "Number of timers available on this unit"
    ::= { cmcTcMasterPcu7TimerTable1 1 }

  cmcTcMasterPcu7TimerTable OBJECT-TYPE
    SYNTAX SEQUENCE OF CmcTcMasterPcu7TimerEntry
    ACCESS not-accessible
    STATUS mandatory
    DESCRIPTION
      "Headline of timer-table"
    ::= { cmcTcMasterPcu7TimerTable1 2 }

  cmcTcMasterPcu7TimerEntry OBJECT-TYPE
    SYNTAX CmcTcMasterPcu7TimerEntry
    ACCESS not-accessible
    STATUS mandatory
    DESCRIPTION
      "Entries of timer-table"
    INDEX { cmcTcMasterPcu7TimerIndex }
    ::= { cmcTcMasterPcu7TimerTable 1 }

    CmcTcMasterPcu7TimerEntry ::=
      SEQUENCE {
        cmcTcMasterPcu7TimerIndex
          INTEGER,
        cmcTcMasterPcu7TimerStatus
          INTEGER,
        cmcTcMasterPcu7TimerDayOfWeek
          INTEGER,  
        cmcTcMasterPcu7TimeOn 
          DisplayString (SIZE (0..5)),                              
        cmcTcMasterPcu7TimeOff 
          DisplayString (SIZE (0..5)),                              
        cmcTcMasterPcu7TimeControl
          INTEGER,
        cmcTcMasterPcu7TimerOutput1
          INTEGER,
        cmcTcMasterPcu7TimerOutput2
          INTEGER         
      }

    cmcTcMasterPcu7TimerIndex OBJECT-TYPE
      SYNTAX INTEGER (1..32000)
      ACCESS read-only
      STATUS mandatory
      DESCRIPTION
        "Index for the list of timer entries. Its value ranges
         between 1 and the value of cmcTcMasterPcu7TimerNumber." 
      ::= { cmcTcMasterPcu7TimerEntry 1 }

    cmcTcMasterPcu7TimerStatus OBJECT-TYPE
      SYNTAX INTEGER {
        switchedOff(1),
        switchedOn(2),
        noTime(3) 
      }
      ACCESS read-only
      STATUS mandatory
      DESCRIPTION
        "Actual status of the timer"
      ::= { cmcTcMasterPcu7TimerEntry 2 }

    cmcTcMasterPcu7TimerDayOfWeek OBJECT-TYPE
      SYNTAX INTEGER {
        sun(1),
        mon(2),
        tue(3) ,
        wed(4),
        thu(5),
        fre(6),
        sat(7),
        sat-sun(8),
        mo-fr(9),
        mo-su(10)
      }
      ACCESS read-write
      STATUS mandatory
      DESCRIPTION
        "Day when the timer is active"
      ::= { cmcTcMasterPcu7TimerEntry 3 }
             
    cmcTcMasterPcu7TimeOn OBJECT-TYPE
      SYNTAX DisplayString (SIZE (0..5))
      ACCESS read-write
      STATUS mandatory
      DESCRIPTION
        "Time to switch on current outlet, 
         Format: HH:MM"
      ::= { cmcTcMasterPcu7TimerEntry 4 }

    cmcTcMasterPcu7TimeOff OBJECT-TYPE
      SYNTAX DisplayString (SIZE (0..5))
      ACCESS read-write
      STATUS mandatory
      DESCRIPTION
        "Time to switch off current outlet,
         Format: HH:MM"
      ::= { cmcTcMasterPcu7TimerEntry 5 }

    cmcTcMasterPcu7TimeControl OBJECT-TYPE
      SYNTAX INTEGER {
        disabled(1),
        enabled(2)
      }
      ACCESS read-write
      STATUS mandatory
      DESCRIPTION
        "Control via RTC"
      ::= { cmcTcMasterPcu7TimerEntry 6 }

    cmcTcMasterPcu7TimerOutput1 OBJECT-TYPE
      SYNTAX INTEGER 
      ACCESS read-write
      STATUS mandatory
      DESCRIPTION
        "Output which is controlled via timer"
      ::= { cmcTcMasterPcu7TimerEntry 7 }

    cmcTcMasterPcu7TimerOutput2 OBJECT-TYPE
      SYNTAX INTEGER 
      ACCESS read-write
      STATUS mandatory
      DESCRIPTION
        "Output which is controlled via timer"
      ::= { cmcTcMasterPcu7TimerEntry 8 }

--cmcTcMasterPcu7SetupPower1-group                     

  cmcTcMasterPcu7SetupPower1Avail OBJECT-TYPE
    SYNTAX INTEGER {
      notAvailable(1),
      available(2)
    }
    ACCESS read-write
    STATUS mandatory
    DESCRIPTION
      "Energy sensor 1 sensor:   
       (1) not available
       (2) available"
    ::= { cmcTcMasterPcu7SetupPower1 1 }

  cmcTcMasterPcu7SetupPower1Relay OBJECT-TYPE
    SYNTAX INTEGER {
      disabled(1),
      enabled(2)
    }
    ACCESS read-write
    STATUS mandatory
    DESCRIPTION
      "Alert handling of Alarm Relay in case of an alarm condition
       of Power 1:  
       (1) no switching of Relays
       (2) Relay will switch"
    ::= { cmcTcMasterPcu7SetupPower1 2 }

  cmcTcMasterPcu7SetupPower1Beeper OBJECT-TYPE
    SYNTAX INTEGER {
      disabled(1),
      enabled(2)
    }
    ACCESS read-write
    STATUS mandatory
    DESCRIPTION
      "Alert handling of beeper of in case of an alarm condition
       of Power 1: 
       (1) No Audible Alarm
       (2) Start Audible Alarm"
    ::= { cmcTcMasterPcu7SetupPower1 3 }

--cmcTcMasterPcu7SetupPower2-group                     

  cmcTcMasterPcu7SetupPower2Avail OBJECT-TYPE
    SYNTAX INTEGER {
      notAvailable(1),
      available(2)
    }
    ACCESS read-write
    STATUS mandatory
    DESCRIPTION
      "Energy sensor 2:   
       (1) not available
       (2) available"
    ::= { cmcTcMasterPcu7SetupPower2 1 }

  cmcTcMasterPcu7SetupPower2Relay OBJECT-TYPE
    SYNTAX INTEGER {
      disabled(1),
      enabled(2)
    }
    ACCESS read-write
    STATUS mandatory
    DESCRIPTION
      "Alert handling of Alarm Relay in case of an alarm condition
       of Power 2:  
       (1) no switching of Relay
       (2) Relay will switch"
    ::= { cmcTcMasterPcu7SetupPower2 2 }

  cmcTcMasterPcu7SetupPower2Beeper OBJECT-TYPE
    SYNTAX INTEGER {
      disabled(1),
      enabled(2)
    }
    ACCESS read-write
    STATUS mandatory
    DESCRIPTION
      "Alert handling of beeper of in case of an alarm condition
       of Power 2: 
       (1) No Audible Alarm
       (2) Start Audible Alarm"
    ::= { cmcTcMasterPcu7SetupPower2 3 }

--cmcTcMasterPcu7SetupInput1-group

  cmcTcMasterPcu7SetupInput1Avail OBJECT-TYPE
    SYNTAX INTEGER {
      notAvailable(1),
      available(2)
    }
    ACCESS read-write
    STATUS mandatory
    DESCRIPTION
      "Input 1 sensor:   
       (1) not available
       (2) available"
    ::= { cmcTcMasterPcu7SetupInput1 1 }

  cmcTcMasterPcu7SetupInput1Relay OBJECT-TYPE
    SYNTAX INTEGER {
      disabled(1),
      enabled(2)
    }
    ACCESS read-write
    STATUS mandatory
    DESCRIPTION
      "Alert handling of Alarm Relay in case of an alarm condition
       of Input 1:  
       (1) no switching of Relay
       (2) Relay will switch"
    ::= { cmcTcMasterPcu7SetupInput1 2 }

  cmcTcMasterPcu7SetupInput1Beeper OBJECT-TYPE
    SYNTAX INTEGER {
      disabled(1),
      enabled(2)
    }
    ACCESS read-write
    STATUS mandatory
    DESCRIPTION
      "Alert handling of beeper of in case of an alarm condition
       of Input 1: 
       (1) No Audible Alarm
       (2) Start Audible Alarm"
    ::= { cmcTcMasterPcu7SetupInput1 3 }

  cmcTcMasterPcu7SetupInput1Contact OBJECT-TYPE
    SYNTAX INTEGER {
      contactNO(1),
      contactNC(2),
      notAvail(3)
    }
    ACCESS read-write
    STATUS mandatory
    DESCRIPTION
      "Setup of digital input 1"
    ::= { cmcTcMasterPcu7SetupInput1 4 }

  cmcTcMasterPcu7SetupInput1Delay OBJECT-TYPE
    SYNTAX INTEGER (0..60)
    ACCESS read-write
    STATUS mandatory
    DESCRIPTION
      "Delay for changing of input state"
    ::= { cmcTcMasterPcu7SetupInput1 5 }

--cmcTcMasterPcu7SetupInput2-group

  cmcTcMasterPcu7SetupInput2Avail OBJECT-TYPE
    SYNTAX INTEGER {
      notAvailable(1),
      available(2)
    }
    ACCESS read-write
    STATUS mandatory
    DESCRIPTION
      "Input 2 sensor:   
       (2) available
       (1) not available"
    ::= { cmcTcMasterPcu7SetupInput2 1 }

  cmcTcMasterPcu7SetupInput2Relay OBJECT-TYPE
    SYNTAX INTEGER {
      disabled(1),
      enabled(2)
    }
    ACCESS read-write
    STATUS mandatory
    DESCRIPTION
      "Alert handling of Alarm Relay in case of an alarm condition
       of Input 1:  
       (1) no switching of Relays
       (2) Relay will switch"
    ::= { cmcTcMasterPcu7SetupInput2 2 }

  cmcTcMasterPcu7SetupInput2Beeper OBJECT-TYPE
    SYNTAX INTEGER {
      disabled(1),
      enabled(2)
    }
    ACCESS read-write
    STATUS mandatory
    DESCRIPTION
      "Alert handling of beeper of in case of an alarm condition
       of Input 2: 
       (1) No Audible Alarm
       (2) Start Audible Alarm"
    ::= { cmcTcMasterPcu7SetupInput2 3 }

  cmcTcMasterPcu7SetupInput2Contact OBJECT-TYPE
    SYNTAX INTEGER {
      contactNO(1),
      contactNC(2),
      notAvail(3)
    }
    ACCESS read-write
    STATUS mandatory
    DESCRIPTION
      "Setup of digital input 2"
    ::= { cmcTcMasterPcu7SetupInput2 4 }

  cmcTcMasterPcu7SetupInput2Delay OBJECT-TYPE
    SYNTAX INTEGER (0..60)
    ACCESS read-write
    STATUS mandatory
    DESCRIPTION
      "Delay for changing of input state"
    ::= { cmcTcMasterPcu7SetupInput2 5 }

--cmcTcMasterPcu7SetupTemperature-group                     

  cmcTcMasterPcu7SetupTemperatureAvail OBJECT-TYPE
    SYNTAX INTEGER {
      notAvailable(1),
      available(2)
    }
    ACCESS read-write
    STATUS mandatory
    DESCRIPTION
      "Temp sensor 1:   
       (1) not available
       (2) available"
    ::= { cmcTcMasterPcu7SetupTemperature 1 }

  cmcTcMasterPcu7SetupTemperatureRelay OBJECT-TYPE
    SYNTAX INTEGER {
      disabled(1),
      enabled(2)
    }
    ACCESS read-write
    STATUS mandatory
    DESCRIPTION
      "Alert handling of Alarm Relay in case of an alarm condition
       of Temperature:  
       (1) no switching of Relays
       (2) Relay will switch"
    ::= { cmcTcMasterPcu7SetupTemperature 2 }

  cmcTcMasterPcu7SetupTemperatureBeeper OBJECT-TYPE
    SYNTAX INTEGER {
      disabled(1),
      enabled(2)
    }
    ACCESS read-write
    STATUS mandatory
    DESCRIPTION
      "Alert handling of beeper of in case of an alarm condition
       of Temperature: 
       (1) No Audible Alarm
       (2) Start Audible Alarm"
    ::= { cmcTcMasterPcu7SetupTemperature 3 }

--cmcTcMasterPcu7SetupGeneral-group

  cmcTcMasterPcu7SetMessage OBJECT-TYPE
    SYNTAX DisplayString (SIZE (0..31))
    ACCESS read-write
    STATUS mandatory
    DESCRIPTION
      "Set message"
    ::= { cmcTcMasterPcu7SetupDevice 1 }

--cmcTcMasterPcu7Setpoints-group

  cmcTcMasterPcu7SetpointHighPower1 OBJECT-TYPE
    SYNTAX INTEGER 
    ACCESS read-write
    STATUS mandatory
    DESCRIPTION
      "Setpoint high value power consumption 1 alarm"
    ::= { cmcTcMasterPcu7Setpoints 1 }

  cmcTcMasterPcu7SetpointWarningPower1 OBJECT-TYPE
    SYNTAX INTEGER 
    ACCESS read-write
    STATUS mandatory
    DESCRIPTION
      "Setpoint warning value power consumption 1 alarm"
    ::= { cmcTcMasterPcu7Setpoints 2 }

  cmcTcMasterPcu7SetpointLowPower1 OBJECT-TYPE
    SYNTAX INTEGER
    ACCESS read-write
    STATUS mandatory
    DESCRIPTION
      "Setpoint low value power consumption 1 alarm"
    ::= { cmcTcMasterPcu7Setpoints 3 }

  cmcTcMasterPcu7SetpointHighPower2 OBJECT-TYPE
    SYNTAX INTEGER 
    ACCESS read-write
    STATUS mandatory
    DESCRIPTION
      "Setpoint high value power consumption 2 alarm"
    ::= { cmcTcMasterPcu7Setpoints 4 }

  cmcTcMasterPcu7SetpointWarningPower2 OBJECT-TYPE
    SYNTAX INTEGER 
    ACCESS read-write
    STATUS mandatory
    DESCRIPTION
      "Setpoint warning value power consumption 2 alarm"
    ::= { cmcTcMasterPcu7Setpoints 5 }

  cmcTcMasterPcu7SetpointLowPower2 OBJECT-TYPE
    SYNTAX INTEGER
    ACCESS read-write
    STATUS mandatory
    DESCRIPTION
      "Setpoint low value power consumption 2 alarm"
    ::= { cmcTcMasterPcu7Setpoints 6 }

  cmcTcMasterPcu7SetpointHighTemperature OBJECT-TYPE
    SYNTAX INTEGER (0..200)
    ACCESS read-write
    STATUS mandatory
    DESCRIPTION
      "Setpoint high value alarm temperature "
    ::= { cmcTcMasterPcu7Setpoints 7 }

  cmcTcMasterPcu7SetpointLowTemperature OBJECT-TYPE
    SYNTAX INTEGER (0..50)
    ACCESS read-write
    STATUS mandatory
    DESCRIPTION
      "Setpoint low value alarm temperature "
    ::= { cmcTcMasterPcu7Setpoints 8 }
 
  cmcTcMasterPcu7SetpointTemperature OBJECT-TYPE
    SYNTAX INTEGER (0..200)
    ACCESS read-write
    STATUS mandatory
    DESCRIPTION
      "Setpoint temperature for outlet control 
       and temperature warning"
    ::= { cmcTcMasterPcu7Setpoints 9 }

  cmcTcMasterPcu7SetpointTemperatureHyst OBJECT-TYPE
    SYNTAX INTEGER (0..15)
    ACCESS read-write
    STATUS mandatory
    DESCRIPTION
      "Hysteresis for cmcTcMasterPcu7SetpointTemperature"
    ::= { cmcTcMasterPcu7Setpoints 10 }
 
--cmcTcMasterPcu7Control-group

  cmcTcMasterPcu7ResetEnergy1 OBJECT-TYPE
    SYNTAX INTEGER {
      noReset(1),
      reset(2)
    }
    ACCESS read-write
    STATUS mandatory
    DESCRIPTION
      "Reset value of cmcTcMasterPcu7ValueEnergy1Time"
    ::= { cmcTcMasterPcu7Control 1 }

  cmcTcMasterPcu7ResetEnergy2 OBJECT-TYPE
    SYNTAX INTEGER {
      noReset(1),
      reset(2)
    }
    ACCESS read-write
    STATUS mandatory
    DESCRIPTION
      "Reset value of cmcTcMasterPcu7ValueEnergy2Time"
    ::= { cmcTcMasterPcu7Control 2 }

  cmcTcMasterPcu7ControlAlarmRelay OBJECT-TYPE
    SYNTAX INTEGER {
      relayOff(1),
      relayOn(2)
    }
    ACCESS read-write
    STATUS mandatory
    DESCRIPTION
      "Control of Alarm relay"
    ::= { cmcTcMasterPcu7Control 3 }

  cmcTcMasterPcu7ClearAlarm OBJECT-TYPE
    SYNTAX INTEGER {
      noClear(1),
      clear(2)
    }
    ACCESS read-write
    STATUS mandatory
    DESCRIPTION
      "Clear alarm, beeper and relay"
    ::= { cmcTcMasterPcu7Control 4 }

--cmcTcMasterPcu7TrapTable-group

  cmcTcMasterPcu7TrapTableNumber OBJECT-TYPE
    SYNTAX INTEGER 
    ACCESS read-only
    STATUS mandatory
    DESCRIPTION
      "Number of cmcTcMasterPcu7TrapTable entries. The number of trap-receivers avail."
    ::= { cmcTcMasterPcu7Traps 1 }

  cmcTcMasterPcu7TrapTable OBJECT-TYPE
    SYNTAX SEQUENCE OF CmcTcMasterPcu7TrapEntry
    ACCESS not-accessible
    STATUS mandatory
    DESCRIPTION
      "A list of trap-receiver entries"
    ::= { cmcTcMasterPcu7Traps 2 }

  cmcTcMasterPcu7TrapEntry OBJECT-TYPE
    SYNTAX CmcTcMasterPcu7TrapEntry
    ACCESS not-accessible
    STATUS mandatory
    DESCRIPTION
      "Entries of cmcTcMasterPcu7TrapTable"
    INDEX { cmcTcMasterPcu7TrapIndex }
    ::= { cmcTcMasterPcu7TrapTable 1 }

    CmcTcMasterPcu7TrapEntry ::=
      SEQUENCE {
        cmcTcMasterPcu7TrapIndex
          INTEGER,
        cmcTcMasterPcu7TrapStatus
          INTEGER,
        cmcTcMasterPcu7TrapIPaddress
          DisplayString
      }

    cmcTcMasterPcu7TrapIndex OBJECT-TYPE
      SYNTAX INTEGER (1..32000)
      ACCESS read-only
      STATUS mandatory
      DESCRIPTION
        "Index for the trap-receiver-table. Its value ranges between
         1 and the value of cmcTcMasterPcu7TrapTableNumber "
      ::= { cmcTcMasterPcu7TrapEntry 1 }

    cmcTcMasterPcu7TrapStatus OBJECT-TYPE
      SYNTAX INTEGER {
        disabled(1),
        enabled(2)
      }
      ACCESS read-write
      STATUS mandatory
      DESCRIPTION
        "Enable or disable trap receiver"
      ::= { cmcTcMasterPcu7TrapEntry 2 }

    cmcTcMasterPcu7TrapIPaddress OBJECT-TYPE
      SYNTAX DisplayString (SIZE (0..15))
      ACCESS read-write
      STATUS mandatory
      DESCRIPTION
        "IP-address of trap-receiver"
      ::= { cmcTcMasterPcu7TrapEntry 3 }

--cmcTcMasterTc7MibRev-group
          
  cmcTcMasterTc7MibMajRev OBJECT-TYPE
    SYNTAX INTEGER (1..32000)
    ACCESS read-only
    STATUS mandatory
    DESCRIPTION
      "The Major Revision level.
       A change in the major revision level represents a major change
       in the architecture of the MIB. A change in the major revision 
       level may indicate a significant change in the information,
       correct interpretation of data may require a MIB document
       with the same major revision level."
    ::= { cmcTcMasterTc7MibRev 1 }

  cmcTcMasterTc7MibMinRev OBJECT-TYPE
    SYNTAX INTEGER (0..32000)
    ACCESS read-only
    STATUS mandatory
    DESCRIPTION
      "The Minor Revision level.
       A change in the minor revision level may represent some minor
       additional support, no changes to any pre-existing information
       has occurred."
    ::= { cmcTcMasterTc7MibRev 2 }

  cmcTcMasterTc7MibCondition OBJECT-TYPE
    SYNTAX INTEGER {
      other (1),
      ok (2),
      degraded (3),
      failed (4),
      configChanged (5)
    }
    ACCESS read-only
    STATUS mandatory
    DESCRIPTION
      "The overall condition (status) of the system represented by
       this MIB. 
       (2) OK
       (3) a minor problem, warning condition (yellow LED on CMC-TC)
       (4) a major problem (red LED on CMC-TC)
       (5) configuration of sensor units changed or
           unit detected (red/yellow/green LED on CMC-TC)"
    ::= { cmcTcMasterTc7MibRev 3 }
          
--cmcTcMasterTc7Status-group

  cmcTcMasterTc7StatusDeviceCMC OBJECT-TYPE
    SYNTAX INTEGER {
      failed(1),
      ok(2)
    }
    ACCESS read-only
    STATUS mandatory
    DESCRIPTION
      "General Status of CMC-TC unit itself
       (1) failed
       (2) OK"
    ::= { cmcTcMasterTc7Status 1 }

  cmcTcMasterTc7UnitsConnected OBJECT-TYPE
    SYNTAX INTEGER 
    ACCESS read-only
    STATUS mandatory
    DESCRIPTION
      "Number of sensor units connected to the CMC-TC, Port 1 to 4"
    ::= { cmcTcMasterTc7Status 2 }

--unit 1

  cmcTcMasterTc7Unit1TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 1"
    ::= { cmcTcMasterTc7StatusSensorUnit1 1 }

  cmcTcMasterTc7Unit1Text OBJECT-TYPE
    SYNTAX DisplayString (SIZE (0..10))
    ACCESS read-write
    STATUS mandatory
    DESCRIPTION
      "Descriptional text for sensor unit connected to port 1"
    ::= { cmcTcMasterTc7StatusSensorUnit1 2 }

  cmcTcMasterTc7Unit1Serial OBJECT-TYPE
    SYNTAX INTEGER 
    ACCESS read-only
    STATUS mandatory
    DESCRIPTION
      "Serialnumber of sensor unit connected to port 1"
    ::= { cmcTcMasterTc7StatusSensorUnit1 3 }

  cmcTcMasterTc7Unit1Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 1
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc7StatusSensorUnit1 4 }

-- Sensors
              
  cmcTcMasterTc7Unit1NumberOfSensors OBJECT-TYPE
    SYNTAX INTEGER 
    ACCESS read-only
    STATUS mandatory
    DESCRIPTION
      "Number of sensors connected to sensor unit 1"
    ::= { cmcTcMasterTc7StatusUnit1Sensors 1 }

-- table with entry for each sensor available on this unit              

  cmcTcMasterTc7Unit1SensorTable OBJECT-TYPE
    SYNTAX SEQUENCE OF CmcTcMasterTc7Unit1SensorEntry
    ACCESS not-accessible
    STATUS mandatory
    DESCRIPTION
      "Headline of sensor table"
    ::= { cmcTcMasterTc7StatusUnit1Sensors 2 }

  cmcTcMasterTc7Unit1SensorEntry OBJECT-TYPE
    SYNTAX CmcTcMasterTc7Unit1SensorEntry
    ACCESS not-accessible
    STATUS mandatory
    DESCRIPTION
      "Entries of sensor table"
    INDEX { cmcTcMasterTc7Unit1SensorIndex }
    ::= { cmcTcMasterTc7Unit1SensorTable 1 }

    CmcTcMasterTc7Unit1SensorEntry ::=
      SEQUENCE {
        cmcTcMasterTc7Unit1SensorIndex
          INTEGER,
        cmcTcMasterTc7Unit1SensorType
          INTEGER,
        cmcTcMasterTc7Unit1SensorText
          DisplayString (SIZE (0..20)),                
        cmcTcMasterTc7Unit1SensorStatus
          INTEGER,
        cmcTcMasterTc7Unit1SensorValue
          INTEGER,
        cmcTcMasterTc7Unit1SensorSetHigh
          INTEGER,
        cmcTcMasterTc7Unit1SensorSetLow
          INTEGER,
        cmcTcMasterTc7Unit1SensorSetWarn
          INTEGER                
      }

    cmcTcMasterTc7Unit1SensorIndex OBJECT-TYPE
      SYNTAX INTEGER (1..32000)
      ACCESS read-only
      STATUS mandatory
      DESCRIPTION
        "Index for the list of value entries. Its value ranges
         between 1 and the value of cmcTcMasterTc7Unit1NumberOfSensors." 
      ::= { cmcTcMasterTc7Unit1SensorEntry 1 }

    cmcTcMasterTc7Unit1SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 1 to sensor[cmcTcMasterTc7Unit1SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc7Unit1SensorEntry 2 }

    cmcTcMasterTc7Unit1SensorText OBJECT-TYPE
      SYNTAX DisplayString (SIZE (0..20))
      ACCESS read-write
      STATUS mandatory
      DESCRIPTION
        "Descriptional text for each sensor (entry in the table)"
      ::= { cmcTcMasterTc7Unit1SensorEntry 3 }
              
    cmcTcMasterTc7Unit1SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc7Unit1SensorEntry 4 }

    cmcTcMasterTc7Unit1SensorValue OBJECT-TYPE
      SYNTAX INTEGER 
      ACCESS read-only
      STATUS mandatory
      DESCRIPTION
        "Value of sensor"
      ::= { cmcTcMasterTc7Unit1SensorEntry 5 }

    cmcTcMasterTc7Unit1SensorSetHigh OBJECT-TYPE
      SYNTAX INTEGER (0..300) 
      ACCESS read-write
      STATUS mandatory
      DESCRIPTION
        "Value for high setpoint of sensor"
      ::= { cmcTcMasterTc7Unit1SensorEntry 6 }

    cmcTcMasterTc7Unit1SensorSetLow OBJECT-TYPE
      SYNTAX INTEGER (0..300) 
      ACCESS read-write
      STATUS mandatory
      DESCRIPTION
        "Value for low setpoint of sensor,
         also used as alarm delay"
      ::= { cmcTcMasterTc7Unit1SensorEntry 7 }

    cmcTcMasterTc7Unit1SensorSetWarn OBJECT-TYPE
      SYNTAX INTEGER (0..300) 
      ACCESS read-write
      STATUS mandatory
      DESCRIPTION
        "Value for warning setpoint of sensor, 
         also used as fan threshold"
      ::= { cmcTcMasterTc7Unit1SensorEntry 8 }
                
-- Outputs              

  cmcTcMasterTc7Unit1NumberOfOutputs OBJECT-TYPE
    SYNTAX INTEGER 
    ACCESS read-only
    STATUS mandatory
    DESCRIPTION
      "Number of outputs available on sensor unit 1"
    ::= { cmcTcMasterTc7StatusUnit1Outputs 1 }

-- table with entry for each output available on this unit              
                
  cmcTcMasterTc7Unit1OutputTable OBJECT-TYPE
    SYNTAX SEQUENCE OF CmcTcMasterTc7Unit1OutputEntry
    ACCESS not-accessible
    STATUS mandatory
    DESCRIPTION
      "Headline of output table"
    ::= { cmcTcMasterTc7StatusUnit1Outputs 2 }

  cmcTcMasterTc7Unit1OutputEntry OBJECT-TYPE
    SYNTAX CmcTcMasterTc7Unit1OutputEntry
    ACCESS not-accessible
    STATUS mandatory
    DESCRIPTION
      "Entries of output table"
    INDEX { cmcTcMasterTc7Unit1OutputIndex }
    ::= { cmcTcMasterTc7Unit1OutputTable 1 }

    CmcTcMasterTc7Unit1OutputEntry ::=
      SEQUENCE {
        cmcTcMasterTc7Unit1OutputIndex
          INTEGER,
        cmcTcMasterTc7Unit1OutputType
          INTEGER,
        cmcTcMasterTc7Unit1OutputText
          DisplayString (SIZE (0..20)),                
        cmcTcMasterTc7Unit1OutputStatus
          INTEGER,
        cmcTcMasterTc7Unit1OutputValue
          INTEGER,
        cmcTcMasterTc7Unit1OutputSet
          INTEGER,
        cmcTcMasterTc7Unit1OutputConfig
          INTEGER,                
        cmcTcMasterTc7Unit1OutputDelay
          INTEGER,
        cmcTcMasterTc7Unit1OutputTimeoutAction
          INTEGER
      }

    cmcTcMasterTc7Unit1OutputIndex OBJECT-TYPE
      SYNTAX INTEGER (1..32000)
      ACCESS read-only
      STATUS mandatory
      DESCRIPTION
        "Index for the list of output entries. Its value ranges
         between 1 and the value of cmcTcMasterTc7Unit1NumberOfOutputs." 
      ::= { cmcTcMasterTc7Unit1OutputEntry 1 }

    cmcTcMasterTc7Unit1OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 1 to output[cmcTcMasterTc7Unit1OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc7Unit1OutputEntry 2 }

    cmcTcMasterTc7Unit1OutputText OBJECT-TYPE
      SYNTAX DisplayString (SIZE (0..20))
      ACCESS read-write
      STATUS mandatory
      DESCRIPTION
        "Descriptional text for each output (entry in the table)"
      ::= { cmcTcMasterTc7Unit1OutputEntry 3 }
              
    cmcTcMasterTc7Unit1OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc7Unit1OutputEntry 4 }

    cmcTcMasterTc7Unit1OutputValue OBJECT-TYPE
      SYNTAX INTEGER (-32000..32000) 
      ACCESS read-write
      STATUS mandatory
      DESCRIPTION
        "Value for output"
      ::= { cmcTcMasterTc7Unit1OutputEntry 5 }

    cmcTcMasterTc7Unit1OutputSet OBJECT-TYPE
      SYNTAX INTEGER {
        off (1),
        on (2),
        lock (3),
        unlock (4),
        unlockDelay (5)
      }
      ACCESS read-write
      STATUS mandatory
      DESCRIPTION
        "Command for output"
      ::= { cmcTcMasterTc7Unit1OutputEntry 6 }

    cmcTcMasterTc7Unit1OutputConfig OBJECT-TYPE
      SYNTAX INTEGER {
        disRemote (1),
        enRemote (2)
      }
      ACCESS read-write
      STATUS mandatory
      DESCRIPTION
        "Configuration for output
         1: 	disable remote control (e.g. keypad)
         2: 	enable remote control"
      ::= { cmcTcMasterTc7Unit1OutputEntry 7 }

    cmcTcMasterTc7Unit1OutputDelay OBJECT-TYPE
      SYNTAX INTEGER (0..999) 
      ACCESS read-write
      STATUS mandatory
      DESCRIPTION
        "Unsigned Value for delay, 
         after this time the output will fall into the previous state"
      ::= { cmcTcMasterTc7Unit1OutputEntry 8 }

    cmcTcMasterTc7Unit1OutputTimeoutAction OBJECT-TYPE
      SYNTAX INTEGER {
        stay (1),
        off (2),
        on (3)
      }
      ACCESS read-write
      STATUS mandatory
      DESCRIPTION
        "State for output if timeout (RS422) occurs"
      ::= { cmcTcMasterTc7Unit1OutputEntry 9 }
 
-- Messages
              
  cmcTcMasterTc7Unit1NumberOfMsgs OBJECT-TYPE
    SYNTAX INTEGER 
    ACCESS read-only
    STATUS mandatory
    DESCRIPTION
      "Number of messages that can be created with sensor unit 1"
    ::= { cmcTcMasterTc7StatusUnit1Msg 1 }

-- table with entry for each alarm available on this unit               
                
  cmcTcMasterTc7Unit1MsgTable OBJECT-TYPE
    SYNTAX SEQUENCE OF CmcTcMasterTc7Unit1MsgEntry
    ACCESS not-accessible
    STATUS mandatory
    DESCRIPTION
      "Headline of message table"
    ::= { cmcTcMasterTc7StatusUnit1Msg 2 }

  cmcTcMasterTc7Unit1MsgEntry OBJECT-TYPE
    SYNTAX CmcTcMasterTc7Unit1MsgEntry
    ACCESS not-accessible
    STATUS mandatory
    DESCRIPTION
      "Entries of message table"
    INDEX { cmcTcMasterTc7Unit1MsgIndex }
    ::= { cmcTcMasterTc7Unit1MsgTable 1 }

    CmcTcMasterTc7Unit1MsgEntry ::=
      SEQUENCE {
        cmcTcMasterTc7Unit1MsgIndex
          INTEGER, 
        cmcTcMasterTc7Unit1MsgText
          DisplayString (SIZE (0..20)),                
        cmcTcMasterTc7Unit1MsgStatus
          INTEGER,                
        cmcTcMasterTc7Unit1MsgRelay
          INTEGER,
        cmcTcMasterTc7Unit1MsgBeeper
          INTEGER,
        cmcTcMasterTc7Unit1MsgTrap1
          INTEGER,
        cmcTcMasterTc7Unit1MsgTrap2
          INTEGER,
        cmcTcMasterTc7Unit1MsgTrap3
          INTEGER,
        cmcTcMasterTc7Unit1MsgTrap4
          INTEGER,                 
        cmcTcMasterTc7Unit1MsgQuit
          INTEGER              
      }

    cmcTcMasterTc7Unit1MsgIndex OBJECT-TYPE
      SYNTAX INTEGER (1..32000)
      ACCESS read-only
      STATUS mandatory
      DESCRIPTION
        "Index for the list of message entries. Its value ranges
         between 1 and the value of cmcTcMasterTc7Unit1NumberOfMsgs." 
      ::= { cmcTcMasterTc7Unit1MsgEntry 1 }

    cmcTcMasterTc7Unit1MsgText OBJECT-TYPE
      SYNTAX DisplayString (SIZE (0..20))
      ACCESS read-write
      STATUS mandatory
      DESCRIPTION
        "Descriptional text for each message (entry in the table)"
      ::= { cmcTcMasterTc7Unit1MsgEntry 2 }
              
    cmcTcMasterTc7Unit1MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc7Unit1OutputSet)
         17: door is unlocked by WEB
         18: door is unlocked by timer
         19: no access, wrong keycode or cardnumber
         20: orientation of PSM-Unit is circuit 1
         21: orientation of PSM-Unit is circuit 2"
      ::= { cmcTcMasterTc7Unit1MsgEntry 3 }
        
    cmcTcMasterTc7Unit1MsgRelay OBJECT-TYPE
      SYNTAX INTEGER {
        disable (1),
        enable (2)
      }
      ACCESS read-write
      STATUS mandatory
      DESCRIPTION
        "Setup of Alarm relay for this message/alarm
         1:        no switching of alarm relay             
         2:        switching of alarm relay" 
      ::= { cmcTcMasterTc7Unit1MsgEntry 4 }

    cmcTcMasterTc7Unit1MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc7Unit1MsgEntry 5 }

    cmcTcMasterTc7Unit1MsgTrap1 OBJECT-TYPE
      SYNTAX INTEGER {
        disable (1),
        enable (2)
      }
      ACCESS read-write
      STATUS mandatory
      DESCRIPTION
        "Trap receiver 1 activated"
      ::= { cmcTcMasterTc7Unit1MsgEntry 6 }

    cmcTcMasterTc7Unit1MsgTrap2 OBJECT-TYPE
      SYNTAX INTEGER {
        disable (1),
        enable (2)
      }
      ACCESS read-write
      STATUS mandatory
      DESCRIPTION
        "Trap receiver 2 activated"
      ::= { cmcTcMasterTc7Unit1MsgEntry 7 }
 
    cmcTcMasterTc7Unit1MsgTrap3 OBJECT-TYPE
      SYNTAX INTEGER {
        disable (1),
        enable (2)
      }
      ACCESS read-write
      STATUS mandatory
      DESCRIPTION
        "Trap receiver 3 activated"
      ::= { cmcTcMasterTc7Unit1MsgEntry 8 }

    cmcTcMasterTc7Unit1MsgTrap4 OBJECT-TYPE
      SYNTAX INTEGER {
        disable (1),
        enable (2)
      }
      ACCESS read-write
      STATUS mandatory
      DESCRIPTION
        "Trap receiver 4 and Event Logging activated"
      ::= { cmcTcMasterTc7Unit1MsgEntry 9 }

    cmcTcMasterTc7Unit1MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc7Unit1MsgEntry 10 }

-- unit2

  cmcTcMasterTc7Unit2TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 2"
    ::= { cmcTcMasterTc7StatusSensorUnit2 1 }

  cmcTcMasterTc7Unit2Text OBJECT-TYPE
    SYNTAX DisplayString (SIZE (0..10))
    ACCESS read-write
    STATUS mandatory
    DESCRIPTION
      "Descriptional text for sensor unit connected to port 2"
    ::= { cmcTcMasterTc7StatusSensorUnit2 2 }

  cmcTcMasterTc7Unit2Serial OBJECT-TYPE
    SYNTAX INTEGER 
    ACCESS read-only
    STATUS mandatory
    DESCRIPTION
      "Serialnumber of sensor unit connected to port 2"
    ::= { cmcTcMasterTc7StatusSensorUnit2 3 }

  cmcTcMasterTc7Unit2Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 2
       (1) OK
       (2) error
       (3) configuration of sensor unit has changed, confirmation required
       (4) Quit from sensor unit to confirm configuration changes
       (5) timeout of sensor unit, confirmation required
       (6) sensor unit detected, needs to be confirmed
       (8) supply voltage is too low"              
    ::= { cmcTcMasterTc7StatusSensorUnit2 4 }

-- unit 2 table

-- Sensors              

  cmcTcMasterTc7Unit2NumberOfSensors OBJECT-TYPE
    SYNTAX INTEGER 
    ACCESS read-only
    STATUS mandatory
    DESCRIPTION
      "Number of sensors connected to sensor unit 2"
    ::= { cmcTcMasterTc7StatusUnit2Sensors 1 }

-- table with entry for each sensor available on this unit              

  cmcTcMasterTc7Unit2SensorTable OBJECT-TYPE
    SYNTAX SEQUENCE OF CmcTcMasterTc7Unit2SensorEntry
    ACCESS not-accessible
    STATUS mandatory
    DESCRIPTION
      "Headline of sensor table"
    ::= { cmcTcMasterTc7StatusUnit2Sensors 2 }

  cmcTcMasterTc7Unit2SensorEntry OBJECT-TYPE
    SYNTAX CmcTcMasterTc7Unit2SensorEntry
    ACCESS not-accessible
    STATUS mandatory
    DESCRIPTION
      "Entries of sensor table"
    INDEX { cmcTcMasterTc7Unit2SensorIndex }
    ::= { cmcTcMasterTc7Unit2SensorTable 1 }

    CmcTcMasterTc7Unit2SensorEntry ::=
      SEQUENCE {
        cmcTcMasterTc7Unit2SensorIndex
          INTEGER,
        cmcTcMasterTc7Unit2SensorType
          INTEGER,
        cmcTcMasterTc7Unit2SensorText
          DisplayString (SIZE (0..20)),                
        cmcTcMasterTc7Unit2SensorStatus
          INTEGER,
        cmcTcMasterTc7Unit2SensorValue
          INTEGER,
        cmcTcMasterTc7Unit2SensorSetHigh
          INTEGER,
        cmcTcMasterTc7Unit2SensorSetLow
          INTEGER,                 
        cmcTcMasterTc7Unit2SensorSetWarn
          INTEGER  
      }

    cmcTcMasterTc7Unit2SensorIndex OBJECT-TYPE
      SYNTAX INTEGER (1..32000)
      ACCESS read-only
      STATUS mandatory
      DESCRIPTION
        "Index for the list of value entries. Its value ranges
         between 1 and the value of cmcTcMasterTc7Unit2NumberOfSensors." 
      ::= { cmcTcMasterTc7Unit2SensorEntry 1 }

    cmcTcMasterTc7Unit2SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 2 to sensor[cmcTcMasterTc7Unit2SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc7Unit2SensorEntry 2 }
        
    cmcTcMasterTc7Unit2SensorText OBJECT-TYPE
      SYNTAX DisplayString (SIZE (0..20))
      ACCESS read-write
      STATUS mandatory
      DESCRIPTION
        "Descriptional text for each sensor (entry in the table)"
      ::= { cmcTcMasterTc7Unit2SensorEntry 3 }
              
    cmcTcMasterTc7Unit2SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc7Unit2SensorEntry 4 }

    cmcTcMasterTc7Unit2SensorValue OBJECT-TYPE
      SYNTAX INTEGER 
      ACCESS read-only
      STATUS mandatory
      DESCRIPTION
        "Value of sensor"
      ::= { cmcTcMasterTc7Unit2SensorEntry 5 }

    cmcTcMasterTc7Unit2SensorSetHigh OBJECT-TYPE
      SYNTAX INTEGER (0..300) 
      ACCESS read-write
      STATUS mandatory
      DESCRIPTION
        "Value for high setpoint of sensor"
      ::= { cmcTcMasterTc7Unit2SensorEntry 6 }

    cmcTcMasterTc7Unit2SensorSetLow OBJECT-TYPE
      SYNTAX INTEGER (0..300) 
      ACCESS read-write
      STATUS mandatory
      DESCRIPTION
        "Value for low setpoint of sensor,
         also used as alarm delay"
      ::= { cmcTcMasterTc7Unit2SensorEntry 7 }

    cmcTcMasterTc7Unit2SensorSetWarn OBJECT-TYPE
      SYNTAX INTEGER (0..300) 
      ACCESS read-write
      STATUS mandatory
      DESCRIPTION
        "Value for warning setpoint of sensor,
         also used as fan threshold"
      ::= { cmcTcMasterTc7Unit2SensorEntry 8 }

-- Outputs              

  cmcTcMasterTc7Unit2NumberOfOutputs OBJECT-TYPE
    SYNTAX INTEGER 
    ACCESS read-only
    STATUS mandatory
    DESCRIPTION
      "Number of outputs available on sensor unit 2"
    ::= { cmcTcMasterTc7StatusUnit2Outputs 1 }

-- table with entry for each output available on this unit              
                
  cmcTcMasterTc7Unit2OutputTable OBJECT-TYPE
    SYNTAX SEQUENCE OF CmcTcMasterTc7Unit2OutputEntry
    ACCESS not-accessible
    STATUS mandatory
    DESCRIPTION
      "Headline of output table"
    ::= { cmcTcMasterTc7StatusUnit2Outputs 2 }

  cmcTcMasterTc7Unit2OutputEntry OBJECT-TYPE
    SYNTAX CmcTcMasterTc7Unit2OutputEntry
    ACCESS not-accessible
    STATUS mandatory
    DESCRIPTION
      "Entries of output table"
    INDEX { cmcTcMasterTc7Unit2OutputIndex }
    ::= { cmcTcMasterTc7Unit2OutputTable 1 }

    CmcTcMasterTc7Unit2OutputEntry ::=
      SEQUENCE {
        cmcTcMasterTc7Unit2OutputIndex
          INTEGER,
        cmcTcMasterTc7Unit2OutputType
          INTEGER,
        cmcTcMasterTc7Unit2OutputText
          DisplayString (SIZE (0..20)),                
        cmcTcMasterTc7Unit2OutputStatus
          INTEGER,
        cmcTcMasterTc7Unit2OutputValue
          INTEGER,
        cmcTcMasterTc7Unit2OutputSet
          INTEGER,
        cmcTcMasterTc7Unit2OutputConfig
          INTEGER,                
        cmcTcMasterTc7Unit2OutputDelay
          INTEGER,
        cmcTcMasterTc7Unit2OutputTimeoutAction
          INTEGER
      }

    cmcTcMasterTc7Unit2OutputIndex OBJECT-TYPE
      SYNTAX INTEGER (1..32000)
      ACCESS read-only
      STATUS mandatory
      DESCRIPTION
        "Index for the list of output entries. Its value ranges
         between 1 and the value of cmcTcMasterTc7Unit2NumberOfOutputs." 
      ::= { cmcTcMasterTc7Unit2OutputEntry 1 }

    cmcTcMasterTc7Unit2OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 2 to output[cmcTcMasterTc7Unit2OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc7Unit2OutputEntry 2 }

        
    cmcTcMasterTc7Unit2OutputText OBJECT-TYPE
      SYNTAX DisplayString (SIZE (0..20))
      ACCESS read-write
      STATUS mandatory
      DESCRIPTION
        "Descriptional text for each output (entry in the table)"
      ::= { cmcTcMasterTc7Unit2OutputEntry 3 }
              
    cmcTcMasterTc7Unit2OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc7Unit2OutputEntry 4 }

    cmcTcMasterTc7Unit2OutputValue OBJECT-TYPE
      SYNTAX INTEGER (-32000..32000) 
      ACCESS read-write
      STATUS mandatory
      DESCRIPTION
        "Value for output"
      ::= { cmcTcMasterTc7Unit2OutputEntry 5 }

    cmcTcMasterTc7Unit2OutputSet OBJECT-TYPE
      SYNTAX INTEGER {
        off (1),
        on (2),
        lock (3),
        unlock (4),
        unlockDelay (5)
      }
      ACCESS read-write
      STATUS mandatory
      DESCRIPTION
        "Command for output"
      ::= { cmcTcMasterTc7Unit2OutputEntry 6 }

    cmcTcMasterTc7Unit2OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc7Unit2OutputEntry 7 }

    cmcTcMasterTc7Unit2OutputDelay OBJECT-TYPE
      SYNTAX INTEGER (0..999) 
      ACCESS read-write
      STATUS mandatory
      DESCRIPTION
        "Unsigned Value for delay, 
         after this time the output will fall into the previous state"
      ::= { cmcTcMasterTc7Unit2OutputEntry 8 }

    cmcTcMasterTc7Unit2OutputTimeoutAction OBJECT-TYPE
      SYNTAX INTEGER {
        stay (1),
        off (2),
        on (3)
      }
      ACCESS read-write
      STATUS mandatory
      DESCRIPTION
        "State for output if timeout (RS422) occurs"
      ::= { cmcTcMasterTc7Unit2OutputEntry 9 }

-- Messages
              
  cmcTcMasterTc7Unit2NumberOfMsgs OBJECT-TYPE
    SYNTAX INTEGER 
    ACCESS read-only
    STATUS mandatory
    DESCRIPTION
      "Number of messages that can be created with sensor unit 2"
    ::= { cmcTcMasterTc7StatusUnit2Msg 1 }

-- table with entry for each alarm available on this unit               
                
  cmcTcMasterTc7Unit2MsgTable OBJECT-TYPE
    SYNTAX SEQUENCE OF CmcTcMasterTc7Unit2MsgEntry
    ACCESS not-accessible
    STATUS mandatory
    DESCRIPTION
      "Headline of message table"
    ::= { cmcTcMasterTc7StatusUnit2Msg 2 }

  cmcTcMasterTc7Unit2MsgEntry OBJECT-TYPE
    SYNTAX CmcTcMasterTc7Unit2MsgEntry
    ACCESS not-accessible
    STATUS mandatory
    DESCRIPTION
      "Entries of message table"
    INDEX { cmcTcMasterTc7Unit2MsgIndex }
    ::= { cmcTcMasterTc7Unit2MsgTable 1 }

    CmcTcMasterTc7Unit2MsgEntry ::=
      SEQUENCE {
        cmcTcMasterTc7Unit2MsgIndex
          INTEGER,
        cmcTcMasterTc7Unit2MsgText
          DisplayString (SIZE (0..20)),
        cmcTcMasterTc7Unit2MsgStatus
          INTEGER, 
        cmcTcMasterTc7Unit2MsgRelay
          INTEGER,
        cmcTcMasterTc7Unit2MsgBeeper
          INTEGER,
        cmcTcMasterTc7Unit2MsgTrap1
          INTEGER,
        cmcTcMasterTc7Unit2MsgTrap2
          INTEGER,
        cmcTcMasterTc7Unit2MsgTrap3
          INTEGER,
        cmcTcMasterTc7Unit2MsgTrap4
          INTEGER,                 
        cmcTcMasterTc7Unit2MsgQuit
          INTEGER              
      }

    cmcTcMasterTc7Unit2MsgIndex OBJECT-TYPE
      SYNTAX INTEGER (1..32000)
      ACCESS read-only
      STATUS mandatory
      DESCRIPTION
        "Index for the list of message entries. Its value ranges
         between 1 and the value of cmcTcMasterTc7Unit2NumberOfMsgs." 
      ::= { cmcTcMasterTc7Unit2MsgEntry 1 }

    cmcTcMasterTc7Unit2MsgText OBJECT-TYPE
      SYNTAX DisplayString (SIZE (0..20))
      ACCESS read-write
      STATUS mandatory
      DESCRIPTION
        "Descriptional text for each message (entry in the table)"
      ::= { cmcTcMasterTc7Unit2MsgEntry 2 }

    cmcTcMasterTc7Unit2MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc7Unit2OutputSet)
         17: door is unlocked by WEB
         18: door is unlocked by timer
         19: no access, wrong keycode or cardnumber
         20: orientation of PSM-Unit is circuit 1
         21: orientation of PSM-Unit is circuit 2"
      ::= { cmcTcMasterTc7Unit2MsgEntry 3 }

    cmcTcMasterTc7Unit2MsgRelay OBJECT-TYPE
      SYNTAX INTEGER {
        disable (1),
        enable (2)
      }
      ACCESS read-write
      STATUS mandatory
      DESCRIPTION
        "Setup of Alarm relay for this alarm
         2:        no switching of alarm relay             
         1:        switching of alarm relay" 
      ::= { cmcTcMasterTc7Unit2MsgEntry 4 }

    cmcTcMasterTc7Unit2MsgBeeper OBJECT-TYPE
      SYNTAX INTEGER {
        disable (1),
        enable (2)
      }
      ACCESS read-write
      STATUS mandatory
      DESCRIPTION
        "Setup of Alarm beeper for this alarm
         2:        no audible alarm
         1:        audible alarm" 
      ::= { cmcTcMasterTc7Unit2MsgEntry 5 }

    cmcTcMasterTc7Unit2MsgTrap1 OBJECT-TYPE
      SYNTAX INTEGER {
        disable (1),
        enable (2)
      }
      ACCESS read-write
      STATUS mandatory
      DESCRIPTION
        "Trap receiver 1 activated"
      ::= { cmcTcMasterTc7Unit2MsgEntry 6 }

    cmcTcMasterTc7Unit2MsgTrap2 OBJECT-TYPE
      SYNTAX INTEGER {
        disable (1),
        enable (2)
      }
      ACCESS read-write
      STATUS mandatory
      DESCRIPTION
        "Trap receiver 2 activated"
      ::= { cmcTcMasterTc7Unit2MsgEntry 7 }
 
    cmcTcMasterTc7Unit2MsgTrap3 OBJECT-TYPE
      SYNTAX INTEGER {
        disable (1),
        enable (2)
      }
      ACCESS read-write
      STATUS mandatory
      DESCRIPTION
        "Trap receiver 3 activated"
      ::= { cmcTcMasterTc7Unit2MsgEntry 8 }

    cmcTcMasterTc7Unit2MsgTrap4 OBJECT-TYPE
      SYNTAX INTEGER {
        disable (1),
        enable (2)
      }
      ACCESS read-write
      STATUS mandatory
      DESCRIPTION
        "Trap receiver 4 and Event Logging activated"
      ::= { cmcTcMasterTc7Unit2MsgEntry 9 }

    cmcTcMasterTc7Unit2MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc7Unit2MsgEntry 10 }

-- unit 3
  cmcTcMasterTc7Unit3TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 3"
    ::= { cmcTcMasterTc7StatusSensorUnit3 1 }

  cmcTcMasterTc7Unit3Text OBJECT-TYPE
    SYNTAX DisplayString (SIZE (0..10))
    ACCESS read-write
    STATUS mandatory
    DESCRIPTION
      "Descriptional text for sensor unit connected to port 3"
    ::= { cmcTcMasterTc7StatusSensorUnit3 2 }

  cmcTcMasterTc7Unit3Serial OBJECT-TYPE
    SYNTAX INTEGER 
    ACCESS  read-only
    STATUS  mandatory
    DESCRIPTION
      "Serialnumber of sensor unit connected to port 3"
    ::= { cmcTcMasterTc7StatusSensorUnit3 3 }

  cmcTcMasterTc7Unit3Status OBJECT-TYPE
    SYNTAX INTEGER {
      ok(1),
      error(2),
      changed(3),
      quit(4),
      timeout(5),
      detected(6),
      notAvail(7),
      lowPower(8)
    }
    ACCESS  read-only
    STATUS  mandatory
    DESCRIPTION
      "General Status sensor unit connected to port 3
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc7StatusSensorUnit3 4 }

-- Sensors              

  cmcTcMasterTc7Unit3NumberOfSensors OBJECT-TYPE
    SYNTAX INTEGER 
    ACCESS read-only
    STATUS mandatory
    DESCRIPTION
      "Number of sensors connected to sensor unit 3"
    ::= { cmcTcMasterTc7StatusUnit3Sensors 1 }

-- table with entry for each sensor available on this unit              
        
  cmcTcMasterTc7Unit3SensorTable OBJECT-TYPE
    SYNTAX SEQUENCE OF CmcTcMasterTc7Unit3SensorEntry
    ACCESS not-accessible
    STATUS mandatory
    DESCRIPTION
      "Headline of sensor table"
    ::= { cmcTcMasterTc7StatusUnit3Sensors 2 }

  cmcTcMasterTc7Unit3SensorEntry OBJECT-TYPE
    SYNTAX CmcTcMasterTc7Unit3SensorEntry
    ACCESS not-accessible
    STATUS mandatory
    DESCRIPTION
      "Entries of sensor table"
    INDEX { cmcTcMasterTc7Unit3SensorIndex }
    ::= { cmcTcMasterTc7Unit3SensorTable 1 }

    CmcTcMasterTc7Unit3SensorEntry ::=
      SEQUENCE {
        cmcTcMasterTc7Unit3SensorIndex
          INTEGER,
        cmcTcMasterTc7Unit3SensorType
          INTEGER,
        cmcTcMasterTc7Unit3SensorText
          DisplayString (SIZE (0..20)),                
        cmcTcMasterTc7Unit3SensorStatus
          INTEGER,
        cmcTcMasterTc7Unit3SensorValue
          INTEGER,
        cmcTcMasterTc7Unit3SensorSetHigh
          INTEGER,
        cmcTcMasterTc7Unit3SensorSetLow
          INTEGER,                 
        cmcTcMasterTc7Unit3SensorSetWarn
          INTEGER  
      }

    cmcTcMasterTc7Unit3SensorIndex OBJECT-TYPE
      SYNTAX INTEGER (1..32000)
      ACCESS read-only
      STATUS mandatory
      DESCRIPTION
        "Index for the list of value entries. Its value ranges
         between 1 and the value of cmcTcMasterTc7Unit3NumberOfSensors." 
      ::= { cmcTcMasterTc7Unit3SensorEntry 1 }

    cmcTcMasterTc7Unit3SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 3 to sensor[cmcTcMasterTc7Unit3SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc7Unit3SensorEntry 2 }

    cmcTcMasterTc7Unit3SensorText OBJECT-TYPE
      SYNTAX DisplayString (SIZE (0..20))
      ACCESS read-write
      STATUS mandatory
      DESCRIPTION
        "Descriptional text for each sensor (entry in the table)"
      ::= { cmcTcMasterTc7Unit3SensorEntry 3 }
              
    cmcTcMasterTc7Unit3SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc7Unit3SensorEntry 4 }

    cmcTcMasterTc7Unit3SensorValue OBJECT-TYPE
      SYNTAX INTEGER 
      ACCESS read-only
      STATUS mandatory
      DESCRIPTION
        "Value of sensor"
      ::= { cmcTcMasterTc7Unit3SensorEntry 5 }

    cmcTcMasterTc7Unit3SensorSetHigh OBJECT-TYPE
      SYNTAX INTEGER (0..300) 
      ACCESS read-write
      STATUS mandatory
      DESCRIPTION
        "Value for high setpoint of sensor"
      ::= { cmcTcMasterTc7Unit3SensorEntry 6 }

    cmcTcMasterTc7Unit3SensorSetLow OBJECT-TYPE
      SYNTAX INTEGER (0..300) 
      ACCESS read-write
      STATUS mandatory
      DESCRIPTION
        "Value for low setpoint of sensor,
         also used as alarm delay"
      ::= { cmcTcMasterTc7Unit3SensorEntry 7 }

    cmcTcMasterTc7Unit3SensorSetWarn OBJECT-TYPE
      SYNTAX INTEGER (0..300) 
      ACCESS read-write
      STATUS mandatory
      DESCRIPTION
        "Value for warning setpoint of sensor,
         also used as fan threshold"
      ::= { cmcTcMasterTc7Unit3SensorEntry 8 }
                
-- Outputs              

  cmcTcMasterTc7Unit3NumberOfOutputs OBJECT-TYPE
    SYNTAX INTEGER 
    ACCESS read-only
    STATUS mandatory
    DESCRIPTION
      "Number of outputs available on sensor unit 3"
    ::= { cmcTcMasterTc7StatusUnit3Outputs 1 }

-- table with entry for each output available on this unit              
                
  cmcTcMasterTc7Unit3OutputTable OBJECT-TYPE
    SYNTAX SEQUENCE OF CmcTcMasterTc7Unit3OutputEntry
    ACCESS not-accessible
    STATUS mandatory
    DESCRIPTION
      "Headline of output table"
    ::= { cmcTcMasterTc7StatusUnit3Outputs 2 }

  cmcTcMasterTc7Unit3OutputEntry OBJECT-TYPE
    SYNTAX CmcTcMasterTc7Unit3OutputEntry
    ACCESS not-accessible
    STATUS mandatory
    DESCRIPTION
      "Entries of output table"
    INDEX { cmcTcMasterTc7Unit3OutputIndex }
    ::= { cmcTcMasterTc7Unit3OutputTable 1 }

    CmcTcMasterTc7Unit3OutputEntry ::=
      SEQUENCE {
        cmcTcMasterTc7Unit3OutputIndex
          INTEGER,
        cmcTcMasterTc7Unit3OutputType
          INTEGER,
        cmcTcMasterTc7Unit3OutputText
          DisplayString (SIZE (0..20)),                
        cmcTcMasterTc7Unit3OutputStatus
          INTEGER,
        cmcTcMasterTc7Unit3OutputValue
          INTEGER,
        cmcTcMasterTc7Unit3OutputSet
          INTEGER,
        cmcTcMasterTc7Unit3OutputConfig
          INTEGER,
        cmcTcMasterTc7Unit3OutputDelay
          INTEGER,
        cmcTcMasterTc7Unit3OutputTimeoutAction
          INTEGER
      }

    cmcTcMasterTc7Unit3OutputIndex OBJECT-TYPE
      SYNTAX INTEGER (1..32000)
      ACCESS read-only
      STATUS mandatory
      DESCRIPTION
        "Index for the list of output entries. Its value ranges
         between 1 and the value of cmcTcMasterTc7Unit3NumberOfOutputs." 
      ::= { cmcTcMasterTc7Unit3OutputEntry 1 }

    cmcTcMasterTc7Unit3OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 3 to output[cmcTcMasterTc7Unit3OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc7Unit3OutputEntry 2 }

        
    cmcTcMasterTc7Unit3OutputText OBJECT-TYPE
      SYNTAX DisplayString (SIZE (0..20))
      ACCESS read-write
      STATUS mandatory
      DESCRIPTION
        "Descriptional text for each output (entry in the table)"
      ::= { cmcTcMasterTc7Unit3OutputEntry 3 }
              
    cmcTcMasterTc7Unit3OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc7Unit3OutputEntry 4 }

    cmcTcMasterTc7Unit3OutputValue OBJECT-TYPE
      SYNTAX INTEGER (-32000..32000) 
      ACCESS read-write
      STATUS mandatory
      DESCRIPTION
        "Value for output"
      ::= { cmcTcMasterTc7Unit3OutputEntry 5 }

    cmcTcMasterTc7Unit3OutputSet OBJECT-TYPE
      SYNTAX INTEGER {
        off (1),
        on (2),
        lock (3),
        unlock (4),
        unlockDelay (5)
      }
      ACCESS read-write
      STATUS mandatory
      DESCRIPTION
        "Command for output"
      ::= { cmcTcMasterTc7Unit3OutputEntry 6 }

    cmcTcMasterTc7Unit3OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc7Unit3OutputEntry 7 }

    cmcTcMasterTc7Unit3OutputDelay OBJECT-TYPE
      SYNTAX INTEGER (0..999) 
      ACCESS read-write
      STATUS mandatory
      DESCRIPTION
        "Unsigned Value for delay, 
         after this time the output will fall into the previous state"
      ::= { cmcTcMasterTc7Unit3OutputEntry 8 }

    cmcTcMasterTc7Unit3OutputTimeoutAction OBJECT-TYPE
      SYNTAX INTEGER {
        stay (1),
        off (2),
        on (3)
      }
      ACCESS read-write
      STATUS mandatory
      DESCRIPTION
        "State for output if timeout (RS422) occurs"
      ::= { cmcTcMasterTc7Unit3OutputEntry 9 }

-- Messages
              
  cmcTcMasterTc7Unit3NumberOfMsgs OBJECT-TYPE
    SYNTAX INTEGER 
    ACCESS read-only
    STATUS mandatory
    DESCRIPTION
      "Number of messages that can be created with sensor unit 3"
    ::= { cmcTcMasterTc7StatusUnit3Msg 1 }

-- table with entry for each alarm available on this unit               
                
  cmcTcMasterTc7Unit3MsgTable OBJECT-TYPE
    SYNTAX SEQUENCE OF CmcTcMasterTc7Unit3MsgEntry
    ACCESS not-accessible
    STATUS mandatory
    DESCRIPTION
      "Headline of message table"
    ::= { cmcTcMasterTc7StatusUnit3Msg 2 }

  cmcTcMasterTc7Unit3MsgEntry OBJECT-TYPE
    SYNTAX CmcTcMasterTc7Unit3MsgEntry
    ACCESS not-accessible
    STATUS mandatory
    DESCRIPTION
      "Entries of message table"
    INDEX { cmcTcMasterTc7Unit3MsgIndex }
    ::= { cmcTcMasterTc7Unit3MsgTable 1 }

    CmcTcMasterTc7Unit3MsgEntry ::=
      SEQUENCE {
        cmcTcMasterTc7Unit3MsgIndex
          INTEGER,
        cmcTcMasterTc7Unit3MsgText
          DisplayString (SIZE (0..20)),
        cmcTcMasterTc7Unit3MsgStatus
          INTEGER, 
        cmcTcMasterTc7Unit3MsgRelay
          INTEGER,
        cmcTcMasterTc7Unit3MsgBeeper
          INTEGER,
        cmcTcMasterTc7Unit3MsgTrap1
          INTEGER,
        cmcTcMasterTc7Unit3MsgTrap2
          INTEGER,
        cmcTcMasterTc7Unit3MsgTrap3
          INTEGER,
        cmcTcMasterTc7Unit3MsgTrap4
          INTEGER,                 
        cmcTcMasterTc7Unit3MsgQuit
          INTEGER              
      }

    cmcTcMasterTc7Unit3MsgIndex OBJECT-TYPE
      SYNTAX INTEGER (1..32000)
      ACCESS read-only
      STATUS mandatory
      DESCRIPTION
        "Index for the list of message entries. Its value ranges
         between 1 and the value of cmcTcMasterTc7Unit3NumberOfMsgs." 
      ::= { cmcTcMasterTc7Unit3MsgEntry 1 }

    cmcTcMasterTc7Unit3MsgText OBJECT-TYPE
      SYNTAX DisplayString (SIZE (0..20))
      ACCESS read-write
      STATUS mandatory
      DESCRIPTION
        "Descriptional text for each message (entry in the table)"
      ::= { cmcTcMasterTc7Unit3MsgEntry 2 }

    cmcTcMasterTc7Unit3MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc7Unit3OutputSet)
         17: door is unlocked by WEB
         18: door is unlocked by timer
         19: no access, wrong keycode or cardnumber
         20: orientation of PSM-Unit is circuit 1
         21: orientation of PSM-Unit is circuit 2"
      ::= { cmcTcMasterTc7Unit3MsgEntry 3 }

    cmcTcMasterTc7Unit3MsgRelay OBJECT-TYPE
      SYNTAX INTEGER {
        disable (1),
        enable (2)
      }
      ACCESS read-write
      STATUS mandatory
      DESCRIPTION
        "Setup of Alarm relay for this alarm
         1:        no switching of alarm relay             
         2:        switching of alarm relay" 
      ::= { cmcTcMasterTc7Unit3MsgEntry 4 }

    cmcTcMasterTc7Unit3MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc7Unit3MsgEntry 5 }

    cmcTcMasterTc7Unit3MsgTrap1 OBJECT-TYPE
      SYNTAX INTEGER {
        disable (1),
        enable (2)
      }
      ACCESS read-write
      STATUS mandatory
      DESCRIPTION
        "Trap receiver 1 activated"
      ::= { cmcTcMasterTc7Unit3MsgEntry 6 }

    cmcTcMasterTc7Unit3MsgTrap2 OBJECT-TYPE
      SYNTAX INTEGER {
        disable (1),
        enable (2)
      }
      ACCESS read-write
      STATUS mandatory
      DESCRIPTION
        "Trap receiver 2 activated"
      ::= { cmcTcMasterTc7Unit3MsgEntry 7 }
 
    cmcTcMasterTc7Unit3MsgTrap3 OBJECT-TYPE
      SYNTAX INTEGER {
        disable (1),
        enable (2)
      }
      ACCESS read-write
      STATUS mandatory
      DESCRIPTION
        "Trap receiver 3 activated"
      ::= { cmcTcMasterTc7Unit3MsgEntry 8 }

    cmcTcMasterTc7Unit3MsgTrap4 OBJECT-TYPE
      SYNTAX INTEGER {
        disable (1),
        enable (2)
      }
      ACCESS read-write
      STATUS mandatory
      DESCRIPTION
        "Trap receiver 4 and Event Logging activated"
      ::= { cmcTcMasterTc7Unit3MsgEntry 9 }

    cmcTcMasterTc7Unit3MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc7Unit3MsgEntry 10 }

-- unit4

  cmcTcMasterTc7Unit4TypeOfDevice OBJECT-TYPE
    SYNTAX INTEGER {
      notAvail (1),
      unitIO (2),
      unitAccess (3),
      unitClimate (4),
      unitFCS (5),
      unitRTT (6),
      unitRLCP (7),
      unitPSM (8)
    }
    ACCESS  read-only
    STATUS  mandatory
    DESCRIPTION
      "Type of sensor unit connected to port 4"
    ::= { cmcTcMasterTc7StatusSensorUnit4 1 }

  cmcTcMasterTc7Unit4Text OBJECT-TYPE
    SYNTAX DisplayString (SIZE (0..10))
    ACCESS read-write
    STATUS mandatory
    DESCRIPTION
      "Descriptional text for sensor unit connected to port 4"
    ::= { cmcTcMasterTc7StatusSensorUnit4 2 }

  cmcTcMasterTc7Unit4Serial OBJECT-TYPE
    SYNTAX INTEGER 
    ACCESS read-only
    STATUS mandatory
    DESCRIPTION
      "Serialnumber of sensor unit connected to port 4"
    ::= { cmcTcMasterTc7StatusSensorUnit4 3 }

  cmcTcMasterTc7Unit4Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 4
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc7StatusSensorUnit4 4 }

-- Sensors
              
  cmcTcMasterTc7Unit4NumberOfSensors OBJECT-TYPE
    SYNTAX INTEGER 
    ACCESS read-only
    STATUS mandatory
    DESCRIPTION
      "Number of sensors connected to sensor unit 4"
    ::= { cmcTcMasterTc7StatusUnit4Sensors 1 }

-- table with entry for each sensor available on this unit              
                
  cmcTcMasterTc7Unit4SensorTable OBJECT-TYPE
    SYNTAX SEQUENCE OF CmcTcMasterTc7Unit4SensorEntry
    ACCESS not-accessible
    STATUS mandatory
    DESCRIPTION
      "Headline of sensor table"
    ::= { cmcTcMasterTc7StatusUnit4Sensors 2 }

  cmcTcMasterTc7Unit4SensorEntry OBJECT-TYPE
    SYNTAX CmcTcMasterTc7Unit4SensorEntry
    ACCESS not-accessible
    STATUS mandatory
    DESCRIPTION
      "Entries of sensor table"
    INDEX { cmcTcMasterTc7Unit4SensorIndex }
    ::= { cmcTcMasterTc7Unit4SensorTable 1 }

    CmcTcMasterTc7Unit4SensorEntry ::=
      SEQUENCE {
        cmcTcMasterTc7Unit4SensorIndex
          INTEGER,
        cmcTcMasterTc7Unit4SensorType
          INTEGER,
        cmcTcMasterTc7Unit4SensorText
          DisplayString (SIZE (0..20)),                
        cmcTcMasterTc7Unit4SensorStatus
          INTEGER,
        cmcTcMasterTc7Unit4SensorValue
          INTEGER,
        cmcTcMasterTc7Unit4SensorSetHigh
          INTEGER,
        cmcTcMasterTc7Unit4SensorSetLow
          INTEGER,                 
        cmcTcMasterTc7Unit4SensorSetWarn
          INTEGER  
      }

    cmcTcMasterTc7Unit4SensorIndex OBJECT-TYPE
      SYNTAX INTEGER (1..32000)
      ACCESS read-only
      STATUS mandatory
      DESCRIPTION
        "Index for the list of value entries. Its value ranges
         between 1 and the value of cmcTcMasterTc7Unit4NumberOfSensors." 
      ::= { cmcTcMasterTc7Unit4SensorEntry 1 }

    cmcTcMasterTc7Unit4SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 4 to sensor[cmcTcMasterTc7Unit4SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc7Unit4SensorEntry 2 }

    cmcTcMasterTc7Unit4SensorText OBJECT-TYPE
      SYNTAX DisplayString (SIZE (0..20))
      ACCESS read-write
      STATUS mandatory
      DESCRIPTION
        "Descriptional text for each sensor (entry in the table)"
      ::= { cmcTcMasterTc7Unit4SensorEntry 3 }
              
    cmcTcMasterTc7Unit4SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc7Unit4SensorEntry 4 }

    cmcTcMasterTc7Unit4SensorValue OBJECT-TYPE
      SYNTAX INTEGER 
      ACCESS read-only
      STATUS mandatory
      DESCRIPTION
        "Value of sensor"
      ::= { cmcTcMasterTc7Unit4SensorEntry 5 }

    cmcTcMasterTc7Unit4SensorSetHigh OBJECT-TYPE
      SYNTAX INTEGER (0..300) 
      ACCESS read-write
      STATUS mandatory
      DESCRIPTION
        "Value for high setpoint of sensor"
      ::= { cmcTcMasterTc7Unit4SensorEntry 6 }

    cmcTcMasterTc7Unit4SensorSetLow OBJECT-TYPE
      SYNTAX INTEGER (0..300) 
      ACCESS read-write
      STATUS mandatory
      DESCRIPTION
        "Value for low setpoint of sensor,
         also used as alarm delay"
      ::= { cmcTcMasterTc7Unit4SensorEntry 7 }

    cmcTcMasterTc7Unit4SensorSetWarn OBJECT-TYPE
      SYNTAX INTEGER (0..300) 
      ACCESS read-write
      STATUS mandatory
      DESCRIPTION
        "Value for warning setpoint of sensor,
         also used as fan threshold"
      ::= { cmcTcMasterTc7Unit4SensorEntry 8 }

-- Outputs              

  cmcTcMasterTc7Unit4NumberOfOutputs OBJECT-TYPE
    SYNTAX INTEGER 
    ACCESS read-only
    STATUS mandatory
    DESCRIPTION
      "Number of outputs available on sensor unit 4"
    ::= { cmcTcMasterTc7StatusUnit4Outputs 1 }

-- table with entry for each output available on this unit              
                
  cmcTcMasterTc7Unit4OutputTable OBJECT-TYPE
    SYNTAX SEQUENCE OF CmcTcMasterTc7Unit4OutputEntry
    ACCESS not-accessible
    STATUS mandatory
    DESCRIPTION
      "Headline of output table"
    ::= { cmcTcMasterTc7StatusUnit4Outputs 2 }

  cmcTcMasterTc7Unit4OutputEntry OBJECT-TYPE
    SYNTAX CmcTcMasterTc7Unit4OutputEntry
    ACCESS not-accessible
    STATUS mandatory
    DESCRIPTION
      "Entries of output table"
    INDEX { cmcTcMasterTc7Unit4OutputIndex }
    ::= { cmcTcMasterTc7Unit4OutputTable 1 }

    CmcTcMasterTc7Unit4OutputEntry ::=
      SEQUENCE {
        cmcTcMasterTc7Unit4OutputIndex
          INTEGER,
        cmcTcMasterTc7Unit4OutputType
          INTEGER,
        cmcTcMasterTc7Unit4OutputText
          DisplayString (SIZE (0..20)),                
        cmcTcMasterTc7Unit4OutputStatus
          INTEGER,
        cmcTcMasterTc7Unit4OutputValue
          INTEGER,
        cmcTcMasterTc7Unit4OutputSet
          INTEGER,
        cmcTcMasterTc7Unit4OutputConfig
          INTEGER,
        cmcTcMasterTc7Unit4OutputDelay
          INTEGER,
        cmcTcMasterTc7Unit4OutputTimeoutAction
          INTEGER
      }

    cmcTcMasterTc7Unit4OutputIndex OBJECT-TYPE
      SYNTAX INTEGER (1..32000)
      ACCESS read-only
      STATUS mandatory
      DESCRIPTION
        "Index for the list of output entries. Its value ranges
         between 1 and the value of cmcTcMasterTc7Unit4NumberOfOutputs." 
      ::= { cmcTcMasterTc7Unit4OutputEntry 1 }

    cmcTcMasterTc7Unit4OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 4 to output[cmcTcMasterTc7Unit4OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc7Unit4OutputEntry 2 }

    cmcTcMasterTc7Unit4OutputText OBJECT-TYPE
      SYNTAX DisplayString (SIZE (0..20))
      ACCESS read-write
      STATUS mandatory
      DESCRIPTION
        "Descriptional text for each output (entry in the table)"
      ::= { cmcTcMasterTc7Unit4OutputEntry 3 }
              
    cmcTcMasterTc7Unit4OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc7Unit4OutputEntry 4 }

    cmcTcMasterTc7Unit4OutputValue OBJECT-TYPE
      SYNTAX INTEGER (-32000..32000) 
      ACCESS read-write
      STATUS mandatory
      DESCRIPTION
        "Value for output"
      ::= { cmcTcMasterTc7Unit4OutputEntry 5 }

    cmcTcMasterTc7Unit4OutputSet OBJECT-TYPE
      SYNTAX INTEGER {
        off (1),
        on (2),
        lock (3),
        unlock (4),
        unlockDelay (5)
      }
      ACCESS read-write
      STATUS mandatory
      DESCRIPTION
        "Command for output"
      ::= { cmcTcMasterTc7Unit4OutputEntry 6 }

    cmcTcMasterTc7Unit4OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc7Unit4OutputEntry 7 }

    cmcTcMasterTc7Unit4OutputDelay OBJECT-TYPE
      SYNTAX INTEGER (0..999) 
      ACCESS read-write
      STATUS mandatory
      DESCRIPTION
        "Unsigned Value for delay, 
         after this time the output will fall into the previous state"
      ::= { cmcTcMasterTc7Unit4OutputEntry 8 }

    cmcTcMasterTc7Unit4OutputTimeoutAction OBJECT-TYPE
      SYNTAX INTEGER {
        stay (1),
        off (2),
        on (3)
      }
      ACCESS read-write
      STATUS mandatory
      DESCRIPTION
        "State for output if timeout (RS422) occurs"
      ::= { cmcTcMasterTc7Unit4OutputEntry 9 }

-- Messages
              
  cmcTcMasterTc7Unit4NumberOfMsgs OBJECT-TYPE
    SYNTAX INTEGER 
    ACCESS read-only
    STATUS mandatory
    DESCRIPTION
      "Number of messages that can be created with sensor unit 4"
    ::= { cmcTcMasterTc7StatusUnit4Msg 1 }

-- table with entry for each alarm available on this unit               
                
  cmcTcMasterTc7Unit4MsgTable OBJECT-TYPE
    SYNTAX SEQUENCE OF CmcTcMasterTc7Unit4MsgEntry
    ACCESS not-accessible
    STATUS mandatory
    DESCRIPTION
      "Headline of message table"
    ::= { cmcTcMasterTc7StatusUnit4Msg 2 }

  cmcTcMasterTc7Unit4MsgEntry OBJECT-TYPE
    SYNTAX CmcTcMasterTc7Unit4MsgEntry
    ACCESS not-accessible
    STATUS mandatory
    DESCRIPTION
      "Entries of message table"
    INDEX { cmcTcMasterTc7Unit4MsgIndex }
    ::= { cmcTcMasterTc7Unit4MsgTable 1 }

    CmcTcMasterTc7Unit4MsgEntry ::=
      SEQUENCE {
        cmcTcMasterTc7Unit4MsgIndex
          INTEGER,
        cmcTcMasterTc7Unit4MsgText
          DisplayString (SIZE (0..20)),                
        cmcTcMasterTc7Unit4MsgStatus
          INTEGER, 
        cmcTcMasterTc7Unit4MsgRelay
          INTEGER,
        cmcTcMasterTc7Unit4MsgBeeper
          INTEGER,
        cmcTcMasterTc7Unit4MsgTrap1
          INTEGER,
        cmcTcMasterTc7Unit4MsgTrap2
          INTEGER,
        cmcTcMasterTc7Unit4MsgTrap3
          INTEGER,
        cmcTcMasterTc7Unit4MsgTrap4
          INTEGER,                 
        cmcTcMasterTc7Unit4MsgQuit
          INTEGER              
      }

    cmcTcMasterTc7Unit4MsgIndex OBJECT-TYPE
      SYNTAX INTEGER (1..32000)
      ACCESS read-only
      STATUS mandatory
      DESCRIPTION
        "Index for the list of message entries. Its value ranges
         between 1 and the value of cmcTcMasterTc7Unit4NumberOfMsgs." 
      ::= { cmcTcMasterTc7Unit4MsgEntry 1 }

    cmcTcMasterTc7Unit4MsgText OBJECT-TYPE
      SYNTAX DisplayString (SIZE (0..20))
      ACCESS read-write
      STATUS mandatory
      DESCRIPTION
        "Descriptional text for each message (entry in the table)"
      ::= { cmcTcMasterTc7Unit4MsgEntry 2 }

    cmcTcMasterTc7Unit4MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc7Unit4OutputSet)
         17: door is unlocked by WEB
         18: door is unlocked by timer
         19: no access, wrong keycode or cardnumber
         20: orientation of PSM-Unit is circuit 1
         21: orientation of PSM-Unit is circuit 2"
      ::= { cmcTcMasterTc7Unit4MsgEntry 3 }

    cmcTcMasterTc7Unit4MsgRelay OBJECT-TYPE
      SYNTAX INTEGER {
        disable (1),
        enable (2)
      }
      ACCESS read-write
      STATUS mandatory
      DESCRIPTION
        "Setup of Alarm relay for this alarm
         1:        no switching of alarm relay             
         2:        switching of alarm relay" 
      ::= { cmcTcMasterTc7Unit4MsgEntry 4 }

    cmcTcMasterTc7Unit4MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc7Unit4MsgEntry 5 }

    cmcTcMasterTc7Unit4MsgTrap1 OBJECT-TYPE
      SYNTAX INTEGER {
        disable (1),
        enable (2)
      }
      ACCESS read-write
      STATUS mandatory
      DESCRIPTION
        "Trap receiver 1 activated"
      ::= { cmcTcMasterTc7Unit4MsgEntry 6 }

    cmcTcMasterTc7Unit4MsgTrap2 OBJECT-TYPE
      SYNTAX INTEGER {
        disable (1),
        enable (2)
      }
      ACCESS read-write
      STATUS mandatory
      DESCRIPTION
        "Trap receiver 2 activated"
      ::= { cmcTcMasterTc7Unit4MsgEntry 7 }
 
    cmcTcMasterTc7Unit4MsgTrap3 OBJECT-TYPE
      SYNTAX INTEGER {
        disable (1),
        enable (2)
      }
      ACCESS read-write
      STATUS mandatory
      DESCRIPTION
        "Trap receiver 3 activated"
      ::= { cmcTcMasterTc7Unit4MsgEntry 8 }

    cmcTcMasterTc7Unit4MsgTrap4 OBJECT-TYPE
      SYNTAX INTEGER {
        disable (1),
        enable (2)
      }
      ACCESS read-write
      STATUS mandatory
      DESCRIPTION
        "Trap receiver 4 and Event Logging activated"
      ::= { cmcTcMasterTc7Unit4MsgEntry 9 }

    cmcTcMasterTc7Unit4MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc7Unit4MsgEntry 10 }

--Status extension unit

  cmcTcMasterTc7ValuesRelay OBJECT-TYPE
    SYNTAX INTEGER {
      disable (1),
      enable (2)
    }
    ACCESS read-write
    STATUS mandatory
    DESCRIPTION
      "Setup of Alarm relay for alarm ext. unit(s)
       1:        no switching of alarm relay             
       2:        switching of alarm relay" 
    ::= { cmcTcMasterTc7StatusExtUnit 1 }

  cmcTcMasterTc7ValuesBeeper OBJECT-TYPE
    SYNTAX INTEGER {
      disable (1),
      enable (2)
    }
    ACCESS read-write
    STATUS mandatory
    DESCRIPTION
      "Setup of Alarm beeper for alarm ext. unit(s)
       1:        no audible alarm
       2:        audible alarm" 
    ::= { cmcTcMasterTc7StatusExtUnit 2 }

  cmcTcMasterTc7ValuesTrap1 OBJECT-TYPE
    SYNTAX INTEGER {
      disable (1),
      enable (2)
    }
    ACCESS read-write
    STATUS mandatory
    DESCRIPTION
      "Trap receiver 1 activated"
    ::= { cmcTcMasterTc7StatusExtUnit 3 }

  cmcTcMasterTc7ValuesTrap2 OBJECT-TYPE
    SYNTAX INTEGER {
      disable (1),
      enable (2)
    }
    ACCESS read-write
    STATUS mandatory
    DESCRIPTION
      "Trap receiver 2 activated"
    ::= { cmcTcMasterTc7StatusExtUnit 4 }
 
  cmcTcMasterTc7ValuesTrap3 OBJECT-TYPE
    SYNTAX INTEGER {
      disable (1),
      enable (2)
    }
    ACCESS read-write
    STATUS mandatory
    DESCRIPTION
      "Trap receiver 3 activated"
    ::= { cmcTcMasterTc7StatusExtUnit 5 }

  cmcTcMasterTc7ValuesTrap4 OBJECT-TYPE
    SYNTAX INTEGER {
      disable (1),
      enable (2)
    }
    ACCESS read-write
    STATUS mandatory
    DESCRIPTION
      "Trap receiver 4 and Event Logging activated"
    ::= { cmcTcMasterTc7StatusExtUnit 6 }
 
  cmcTcMasterTc7NumberOfValues OBJECT-TYPE
    SYNTAX INTEGER 
    ACCESS  read-only
    STATUS  mandatory
    DESCRIPTION
      "Number of values availabel on extension units connected to the CMC-TC"
    ::= { cmcTcMasterTc7StatusExtUnit 7 }

-- table with entry for each value available on extension units              

  cmcTcMasterTc7ValuesTable OBJECT-TYPE
    SYNTAX SEQUENCE OF CmcTcMasterTc7ValuesEntry
    ACCESS not-accessible
    STATUS mandatory
    DESCRIPTION
      "Headline of values-table"
    ::= { cmcTcMasterTc7StatusExtUnit 8 }

  cmcTcMasterTc7ValuesEntry OBJECT-TYPE
    SYNTAX CmcTcMasterTc7ValuesEntry
    ACCESS not-accessible
    STATUS mandatory
    DESCRIPTION
      "Entries of values-table"
    INDEX { cmcTcMasterTc7ValuesIndex }
    ::= { cmcTcMasterTc7ValuesTable 1 }

    CmcTcMasterTc7ValuesEntry ::=
      SEQUENCE {
        cmcTcMasterTc7ValuesIndex
          INTEGER,
        cmcTcMasterTc7ValuesText
          DisplayString (SIZE (0..20)),                
        cmcTcMasterTc7ValuesStatus
          INTEGER,
        cmcTcMasterTc7ValuesValue
          INTEGER,
        cmcTcMasterTc7ValuesSetHigh
          INTEGER,
        cmcTcMasterTc7ValuesSetLow
          INTEGER
      }

    cmcTcMasterTc7ValuesIndex OBJECT-TYPE
      SYNTAX INTEGER (1..32000)
      ACCESS read-only
      STATUS mandatory
      DESCRIPTION
        "Index for the list of value entries. Its value ranges
         between 1 and the value of cmcTcMasterTc7NumberOfValues." 
      ::= { cmcTcMasterTc7ValuesEntry 1 }

        
    cmcTcMasterTc7ValuesText OBJECT-TYPE
      SYNTAX DisplayString (SIZE (0..20))
      ACCESS read-write
      STATUS mandatory
      DESCRIPTION
        "Descriptional text for each value (entry in the table)
         of the extension card"
      ::= { cmcTcMasterTc7ValuesEntry 2 }
              
    cmcTcMasterTc7ValuesStatus OBJECT-TYPE
      SYNTAX INTEGER {
        notAvail(1),
        lost(2),
        changed(3),
        ok(4),
        tooLow(5),
        tooHigh(6),
        error(7)
      }
      ACCESS read-only
      STATUS mandatory
      DESCRIPTION
        "Actual status of the value of the extension card"
      ::= { cmcTcMasterTc7ValuesEntry 3 }

    cmcTcMasterTc7ValuesValue OBJECT-TYPE
      SYNTAX INTEGER 
      ACCESS read-only
      STATUS mandatory
      DESCRIPTION
        "Value of sensor"
      ::= { cmcTcMasterTc7ValuesEntry 4 }

    cmcTcMasterTc7ValuesSetHigh OBJECT-TYPE
      SYNTAX INTEGER (0..255) 
      ACCESS read-write
      STATUS mandatory
      DESCRIPTION
        "Value for high setpoint of sensor"
      ::= { cmcTcMasterTc7ValuesEntry 5 }

    cmcTcMasterTc7ValuesSetLow OBJECT-TYPE
      SYNTAX INTEGER (0..255) 
      ACCESS read-write
      STATUS mandatory
      DESCRIPTION
        "Value for low setpoint of sensor"
      ::= { cmcTcMasterTc7ValuesEntry 6 }

--cmcTcMasterTc7SetupGeneral-group

  cmcTcMasterTc7SetTempUnit OBJECT-TYPE
    SYNTAX INTEGER {
      celsius(1),
      fahrenheit(2)
    }
    ACCESS read-write
    STATUS mandatory
    DESCRIPTION
      "Unit of all temperature values and setpoints, Celsius or Fahrenheit"
   ::= { cmcTcMasterTc7SetupGeneral 1 }

  cmcTcMasterTc7SetBeeper OBJECT-TYPE
    SYNTAX INTEGER {
      off(1),
      on(2)
    }
    ACCESS read-write
    STATUS mandatory
    DESCRIPTION
      "Audible alarm in CMC-TC unit:
       (2): beeper is on
       (1): beeper is off (general)"
    ::= { cmcTcMasterTc7SetupGeneral 2 }


  cmcTcMasterTc7QuitRelay OBJECT-TYPE
    SYNTAX INTEGER {
      disabled(1),
      enabled(2)
    }
    ACCESS read-write
    STATUS mandatory
    DESCRIPTION
      "Enable or disable acknowledging currently active alarm relay 
       (with 'C' on CMC-TC)."
    ::= { cmcTcMasterTc7SetupGeneral 3 }

  cmcTcMasterTc7LogicRelay OBJECT-TYPE
    SYNTAX INTEGER {
      closeAtAlarm(1),
      openAtAlarm(2),
      off(3)
    }
    ACCESS read-write
    STATUS mandatory
    DESCRIPTION
      "Logic of alarm relay: 
       (1) Relay will pick up in case of an alarm
       (2) Relay will release in case of an alarm
       (3) Relay off (general)"
    ::= { cmcTcMasterTc7SetupGeneral 4 }

  cmcTcMasterTc7WebAccess OBJECT-TYPE
    SYNTAX INTEGER {
      viewOnly(1),
      fullAccess(2),
      off(3)
    }
    ACCESS read-write
    STATUS mandatory
    DESCRIPTION
      "Web access via HTTP: 
       (1) view only
       (2) full Access, read and set
       (3) Web disabled (general)"
    ::= { cmcTcMasterTc7SetupGeneral 5 }
 
  cmcTcMasterTc7SetupDate OBJECT-TYPE
    SYNTAX DisplayString (SIZE (0..10))
    ACCESS read-write
    STATUS mandatory
    DESCRIPTION
      "actual Date in format DD.MM.YYYY"
    ::= { cmcTcMasterTc7SetupGeneral 6 }

  cmcTcMasterTc7SetupTime OBJECT-TYPE
    SYNTAX DisplayString (SIZE (0..8))
    ACCESS read-write
    STATUS mandatory
    DESCRIPTION
      "actual Time in format HH:MM:SS, HH (0-23), MM (0-59), SS (0-59)"
    ::= { cmcTcMasterTc7SetupGeneral 7 }
 
-- table for timer function
 
  cmcTcMasterTc7TimerNumber OBJECT-TYPE
    SYNTAX INTEGER 
    ACCESS read-only
    STATUS mandatory
    DESCRIPTION
      "Number of timers available on this unit"
    ::= { cmcTcMasterTc7TimerTable1 1 }

  cmcTcMasterTc7TimerTable OBJECT-TYPE
    SYNTAX SEQUENCE OF CmcTcMasterTc7TimerEntry
    ACCESS not-accessible
    STATUS mandatory
    DESCRIPTION
      "Headline of timer-table"
    ::= { cmcTcMasterTc7TimerTable1 2 }

  cmcTcMasterTc7TimerEntry OBJECT-TYPE
    SYNTAX CmcTcMasterTc7TimerEntry
    ACCESS not-accessible
    STATUS mandatory
    DESCRIPTION
      "Entries of timer-table"
    INDEX { cmcTcMasterTc7TimerIndex }
    ::= { cmcTcMasterTc7TimerTable 1 }

    CmcTcMasterTc7TimerEntry ::=
      SEQUENCE {
        cmcTcMasterTc7TimerIndex
          INTEGER,
        cmcTcMasterTc7TimerStatus
          INTEGER,
        cmcTcMasterTc7TimerDayOfWeek
          INTEGER,  
        cmcTcMasterTc7TimeOn 
          DisplayString (SIZE (0..5)),                              
        cmcTcMasterTc7TimeOff 
          DisplayString (SIZE (0..5)),                              
        cmcTcMasterTc7TimeControl
          INTEGER,
        cmcTcMasterTc7TimerFunction
           INTEGER
      }

    cmcTcMasterTc7TimerIndex OBJECT-TYPE
      SYNTAX INTEGER (1..32000)
      ACCESS read-only
      STATUS mandatory
      DESCRIPTION
        "Index for the list of timer entries. Its value ranges
         between 1 and the value of cmcTcMasterTc7TimerNumber." 
      ::= { cmcTcMasterTc7TimerEntry 1 }

    cmcTcMasterTc7TimerStatus OBJECT-TYPE
      SYNTAX INTEGER {
        switchedOff(1),
        switchedOn(2),
        noTime(3) 
      }
      ACCESS read-only
      STATUS mandatory
      DESCRIPTION
        "Actual status of the timer"
      ::= { cmcTcMasterTc7TimerEntry 2 }

    cmcTcMasterTc7TimerDayOfWeek OBJECT-TYPE
      SYNTAX INTEGER {
        sun(1),
        mon(2),
        tue(3) ,
        wed(4),
        thu(5),
        fri(6),
        sat(7),
        sat-sun(8),
        mon-fri(9),
        mon-sun(10)
      }
      ACCESS read-write
      STATUS mandatory
      DESCRIPTION
        "Selection of day of week for timer to switch"
      ::= { cmcTcMasterTc7TimerEntry 3 }
             
    cmcTcMasterTc7TimeOn OBJECT-TYPE
      SYNTAX DisplayString (SIZE (0..5))
      ACCESS read-write
      STATUS mandatory
      DESCRIPTION
        "Time to switch on current function, 
         Format: HH:MM"
      ::= { cmcTcMasterTc7TimerEntry 4 }

    cmcTcMasterTc7TimeOff OBJECT-TYPE
      SYNTAX DisplayString (SIZE (0..5))
      ACCESS read-write
      STATUS mandatory
      DESCRIPTION
        "Time to switch off current function,
         Format: HH:MM"
      ::= { cmcTcMasterTc7TimerEntry 5 }

    cmcTcMasterTc7TimeControl OBJECT-TYPE
      SYNTAX INTEGER  {
        disabled(1),
        enabled(2)
      }
      ACCESS read-write
      STATUS mandatory
      DESCRIPTION
        "Control via RTC"
      ::= { cmcTcMasterTc7TimerEntry 6 }

    cmcTcMasterTc7TimerFunction OBJECT-TYPE
      SYNTAX INTEGER {
        disKeypad1-1 (1),
        disKeypad2-1 (2),
        disKeypad1-2 (3),
        disKeypad2-2 (4),
        disKeypad1-3 (5),
        disKeypad2-3 (6),
        disKeypad1-4 (7),
        disKeypad2-4 (8),
        unlDoor1-1 (9),
        unlDoor2-1 (10),
        unlDoor1-2 (11),
        unlDoor2-2 (12),
        unlDoor1-3 (13),
        unlDoor2-3 (14),
        unlDoor1-4 (15),
        unlDoor2-5 (16),
        disTrapRec1 (17),
        disTrapRec2 (18),
        disTrapRec3 (19),
        disTrapRec4 (20),
        disSMS (21),
        schedule1 (22),
        schedule2 (23),
        schedule3 (24),
        schedule4 (25)
      }
      ACCESS read-write
      STATUS mandatory
      DESCRIPTION
        "Function which is controlled via timer
         1:     unlock via keypad 1 on unit 1 or remote input lock 1 is disabled
         2:     unlock via keypad 2 on unit 1 or remote input lock 2 is disabled
         3      unlock via keypad 1 on unit 2 or remote input lock 1 is disabled
         4:     unlock via keypad 2 on unit 2 or remote input lock 2 is disabled
         5:     unlock via keypad 1 on unit 3 or remote input lock 1 is disabled
         6:     unlock via keypad 2 on unit 3 or remote input lock 2 is disabled
         7:     unlock via keypad 1 on unit 4 or remote input lock 1 is disabled
         8:     unlock via keypad 2 on unit 4 or remote input lock 2 is disabled
         9:     Lock of door 1 on unit 1 will be unlocked
         10:    Lock of door 2 on unit 1 will be unlocked
         11:    Lock of door 1 on unit 2 will be unlocked
         12:    Lock of door 2 on unit 2 will be unlocked
         13:    Lock of door 1 on unit 3 will be unlocked
         14:    Lock of door 2 on unit 3 will be unlocked
         15:    Lock of door 1 on unit 4 will be unlocked
         16:    Lock of door 2 on unit 4 will be unlocked
         17-20: sending Traps to this Trap receiver will be disabled
         21:    sending SMS will be disabled
         22-25: Scheduled alarm off"
      ::= { cmcTcMasterTc7TimerEntry 7 }

--cmcTcMasterTc7TrapTable-group

  cmcTcMasterTc7TraptableNumber OBJECT-TYPE
    SYNTAX INTEGER 
    ACCESS read-only
    STATUS mandatory
    DESCRIPTION
      "Number of trapTable entries. The number of trap-receiver"
    ::= { cmcTcMasterTc7Traps 1 }

  cmcTcMasterTc7TrapTableTable OBJECT-TYPE    
    SYNTAX SEQUENCE OF CmcTcMasterTc7TrapTableEntry
    ACCESS not-accessible
    STATUS mandatory
    DESCRIPTION
     "A list of trap-receiver entries"
    ::= { cmcTcMasterTc7Traps 2 }

  cmcTcMasterTc7TrapTableEntry OBJECT-TYPE
    SYNTAX CmcTcMasterTc7TrapTableEntry
    ACCESS not-accessible
    STATUS mandatory
    DESCRIPTION
      "Entries of cmcTcMasterTc7TrapTable"
    INDEX   { cmcTcMasterTc7TrapIndex }
    ::= { cmcTcMasterTc7TrapTableTable 1 }      
              
    CmcTcMasterTc7TrapTableEntry ::=
      SEQUENCE {
        cmcTcMasterTc7TrapIndex
          INTEGER,
        cmcTcMasterTc7TrapStatus
          INTEGER,
        cmcTcMasterTc7TrapIPaddress
          DisplayString
      }

    cmcTcMasterTc7TrapIndex OBJECT-TYPE
      SYNTAX INTEGER (1..32000)
      ACCESS read-only
      STATUS mandatory
      DESCRIPTION
        "Index for the trap-receiver-table. Its value ranges between
         1 and the value of cmcTcMasterTc7TraptableNumber "
      ::= { cmcTcMasterTc7TrapTableEntry 1 }

    cmcTcMasterTc7TrapStatus OBJECT-TYPE
      SYNTAX INTEGER {
        disabled(1),
        enabled(2)
      }
      ACCESS read-write
      STATUS mandatory
      DESCRIPTION
        "Enable or disable trap receiver"
      ::= { cmcTcMasterTc7TrapTableEntry 2 }

    cmcTcMasterTc7TrapIPaddress OBJECT-TYPE
      SYNTAX DisplayString (SIZE (0..15))
      ACCESS read-write
      STATUS mandatory
      DESCRIPTION
        "IP-address of trap-receiver"
      ::= { cmcTcMasterTc7TrapTableEntry 3 }

--cmcTcMasterTc7Control-group (Added in Version 1.1)

  cmcTcMasterTc1QuitUnit OBJECT-TYPE
    SYNTAX INTEGER {
      noQuit(1),
      quit(2),
    }
    ACCESS read-write
    STATUS mandatory
    DESCRIPTION
      "Command to quit (acknowledge) alarms of CMC-TC unit.
       Setting to 'quit' (2) will have same result as pressing 'C' on Units.
       Variable is automatically set back to 'noQuit' (1)."
    ::= { cmcTcMasterTc7Control 1 }

--cmcTcMasterDevice8-group

  cmcTcMasterDev8Type OBJECT-TYPE
    SYNTAX INTEGER {
      other (0),
      cmc (1),
      pcu (3),
      tc (4)
    }
    ACCESS read-only
    STATUS mandatory
    DESCRIPTION
      "Type of device8"
    ::= { cmcTcMasterDevice8 1 }

  cmcTcMasterDev8Status OBJECT-TYPE
    SYNTAX INTEGER {
      other (1),
      notConnected (2),
      normal (3),
      minor (4),
      major (5),
      configChanged (6),
      connectionLost (10)
    }
    ACCESS read-only
    STATUS mandatory
    DESCRIPTION
      "Status of device8"
    ::= { cmcTcMasterDevice8 2 }

  cmcTcMasterDev8Descr OBJECT-TYPE
    SYNTAX DisplayString (SIZE (0..255))
    ACCESS read-only
    STATUS mandatory
    DESCRIPTION
      "A textual description of the entity.  This value
       should include the full name and version
       identification of the system's hardware type,
       software operating-system, and networking
       software.  It is mandatory that this only contain
       printable ASCII characters."
    ::= { cmcTcMasterDevice8 3 }

  cmcTcMasterDev8UpTime OBJECT-TYPE
    SYNTAX TimeTicks
    ACCESS read-only
    STATUS mandatory
    DESCRIPTION
      "The time (in hundredths of a second) since the
       network management portion of the system was last
       re-initialized."
    ::= { cmcTcMasterDevice8 4 }

  cmcTcMasterDev8Contact OBJECT-TYPE
    SYNTAX DisplayString (SIZE (0..255))
    ACCESS read-write
    STATUS mandatory
    DESCRIPTION
      "The textual identification of the contact person
       for this managed node, together with information
       on how to contact this person."
    ::= { cmcTcMasterDevice8 5 }

  cmcTcMasterDev8Name OBJECT-TYPE
    SYNTAX DisplayString (SIZE (0..255))
    ACCESS read-write
    STATUS mandatory
    DESCRIPTION
      "An administratively-assigned name for this
       managed node.  By convention, this is the node's
       fully-qualified domain name."
    ::= { cmcTcMasterDevice8 6 }

  cmcTcMasterDev8Location OBJECT-TYPE
    SYNTAX DisplayString (SIZE (0..255))
    ACCESS read-write
    STATUS mandatory
    DESCRIPTION
      "The physical location of this node (e.g.,
       `telephone closet, 3rd floor')."
    ::= { cmcTcMasterDevice8 7 }

--cmcTcMasterCmc8Values-group

  cmcTcMasterCmc8ValueTemperature1 OBJECT-TYPE
    SYNTAX INTEGER
    ACCESS read-only
    STATUS mandatory
    DESCRIPTION
      "Actual value of temperature 1 in deg C"
    ::= { cmcTcMasterCmc8Values 1 }

  cmcTcMasterCmc8ValueTemperature2 OBJECT-TYPE
    SYNTAX INTEGER
    ACCESS read-only
    STATUS mandatory
    DESCRIPTION
      "Actual value of temperature 2 in deg C"
    ::= { cmcTcMasterCmc8Values 2 }

  cmcTcMasterCmc8ValuePowerSupply OBJECT-TYPE
    SYNTAX INTEGER
    ACCESS read-only
    STATUS mandatory
    DESCRIPTION
      "Actual value of power supply in V"
    ::= { cmcTcMasterCmc8Values 3 }

  cmcTcMasterCmc8ValueAnalogAux1 OBJECT-TYPE
    SYNTAX INTEGER
    ACCESS read-only
    STATUS mandatory
    DESCRIPTION
      "Actual value of aux. analog input 1
      (4-20mA = 0-100%)"
    ::= { cmcTcMasterCmc8Values 4 }

  cmcTcMasterCmc8ValueAnalogAux2 OBJECT-TYPE
    SYNTAX INTEGER
    ACCESS read-only
    STATUS mandatory
    DESCRIPTION
      "Actual value of aux. analog input 2
      (4-20mA = 0-100%)"
    ::= { cmcTcMasterCmc8Values 5 }

--cmcTcMasterCmc8Values-table-group

  cmcTcMasterCmc8ValuesNumber OBJECT-TYPE
    SYNTAX INTEGER
    ACCESS read-only
    STATUS mandatory
    DESCRIPTION
      "Number of value-table entries"
    ::= { cmcTcMasterCmc8Table1 1 }

  cmcTcMasterCmc8ValuesTable OBJECT-TYPE
    SYNTAX SEQUENCE OF CmcTcMasterCmc8ValuesEntry
    ACCESS not-accessible
    STATUS mandatory
    DESCRIPTION
      "Headline of value-table"
    ::= { cmcTcMasterCmc8Table1 2 }

  cmcTcMasterCmc8ValuesEntry OBJECT-TYPE
    SYNTAX CmcTcMasterCmc8ValuesEntry
    ACCESS not-accessible
    STATUS mandatory
    DESCRIPTION
      "Entries of value-table"
    INDEX { cmcTcMasterCmc8ValuesIndex }
    ::= { cmcTcMasterCmc8ValuesTable 1 }

  CmcTcMasterCmc8ValuesEntry ::=
    SEQUENCE {
      cmcTcMasterCmc8ValuesIndex
        INTEGER,
      cmcTcMasterCmc8ValuesText
        DisplayString (SIZE (0..31)),
      cmcTcMasterCmc8ValuesValue
        INTEGER,
      cmcTcMasterCmc8ValuesStatus
        INTEGER,
      cmcTcMasterCmc8ValuesMaxValue
        INTEGER,
      cmcTcMasterCmc8ValuesMinValue
        INTEGER
    }

    cmcTcMasterCmc8ValuesIndex OBJECT-TYPE
      SYNTAX INTEGER (1..32000)
      ACCESS read-only
      STATUS mandatory
      DESCRIPTION
        "Index for the list of value entries. Its value ranges
        between 1 and the value of valuesNumber."
      ::= { cmcTcMasterCmc8ValuesEntry 1 }

    cmcTcMasterCmc8ValuesText OBJECT-TYPE
      SYNTAX DisplayString (SIZE (0..31))
      ACCESS read-write
      STATUS mandatory
      DESCRIPTION
        "Text of the entry in the value-table"
      ::= { cmcTcMasterCmc8ValuesEntry 2 }

    cmcTcMasterCmc8ValuesValue OBJECT-TYPE
      SYNTAX INTEGER
      ACCESS read-only
      STATUS mandatory
      DESCRIPTION
        "Actual value of the value-table"
      ::= { cmcTcMasterCmc8ValuesEntry 3 }

    cmcTcMasterCmc8ValuesStatus OBJECT-TYPE
      SYNTAX INTEGER {
        valueOK(1),
        valueTooLow(2),
        valueTooHigh(3),
        valueERROR(4),
        notAvail(5)
      }
      ACCESS read-only
      STATUS mandatory
      DESCRIPTION
        "Status of the value"
      ::= { cmcTcMasterCmc8ValuesEntry 4 }

    cmcTcMasterCmc8ValuesMaxValue OBJECT-TYPE
      SYNTAX INTEGER
      ACCESS read-write
      STATUS mandatory
      DESCRIPTION
        "Value for max. alarm"
      ::= { cmcTcMasterCmc8ValuesEntry 5 }

    cmcTcMasterCmc8ValuesMinValue OBJECT-TYPE
      SYNTAX INTEGER
      ACCESS read-write
      STATUS mandatory
      DESCRIPTION
        "Value for min. alarm"
      ::= { cmcTcMasterCmc8ValuesEntry 6 }

--cmcTcMasterCmc8status-group

  cmcTcMasterCmc8StatusTemperature1 OBJECT-TYPE
    SYNTAX DisplayString (SIZE (0..31))
    ACCESS read-only
    STATUS mandatory
    DESCRIPTION
      "Status temperature 1, OK/ too low/ too high
       (see setpoints of temperature 1)"
    ::= { cmcTcMasterCmc8Status 1 }

  cmcTcMasterCmc8StatusTemperature2 OBJECT-TYPE
    SYNTAX DisplayString (SIZE (0..31))
    ACCESS read-only
    STATUS mandatory
    DESCRIPTION
      "Status temperature 2, OK/ too low/ too high
       (see setpoints of temperature 2)"
    ::= { cmcTcMasterCmc8Status 2 }

  cmcTcMasterCmc8StatusFan1 OBJECT-TYPE
    SYNTAX DisplayString (SIZE (0..31))
    ACCESS read-only
    STATUS mandatory
    DESCRIPTION
      "Status fan 1, Stop/ running/ fault"
    ::= { cmcTcMasterCmc8Status 3 }

  cmcTcMasterCmc8StatusFan2 OBJECT-TYPE
    SYNTAX DisplayString (SIZE (0..31))
    ACCESS read-only
    STATUS mandatory
    DESCRIPTION
      "Status fan 2, Stop/ running/ fault"
    ::= { cmcTcMasterCmc8Status 4 }

  cmcTcMasterCmc8StatusHeating OBJECT-TYPE
    SYNTAX DisplayString (SIZE (0..31))
    ACCESS read-only
    STATUS mandatory
    DESCRIPTION
      "Status heating, On/Off"
    ::= { cmcTcMasterCmc8Status 5 }

  cmcTcMasterCmc8StatusPowerSupply OBJECT-TYPE
    SYNTAX DisplayString (SIZE (0..31))
    ACCESS read-only
    STATUS mandatory
    DESCRIPTION
      "Status power supply, OK/ too low/ too high
       (see setpoints of power supply)"
    ::= { cmcTcMasterCmc8Status 6 }

  cmcTcMasterCmc8StatusAnalogAux1 OBJECT-TYPE
    SYNTAX DisplayString (SIZE (0..31))
    ACCESS read-only
    STATUS mandatory
    DESCRIPTION
      "Status aux analog input 1, OK/ too low/ too high"
    ::= { cmcTcMasterCmc8Status 7 }

  cmcTcMasterCmc8StatusAnalogAux2 OBJECT-TYPE
    SYNTAX DisplayString (SIZE (0..31))
    ACCESS read-only
    STATUS mandatory
    DESCRIPTION
      "Status aux analog input 2, OK/ too low/ too high"
    ::= { cmcTcMasterCmc8Status 8 }

  cmcTcMasterCmc8StatusDoor OBJECT-TYPE
    SYNTAX DisplayString (SIZE (0..31))
    ACCESS read-only
    STATUS mandatory
    DESCRIPTION
      "Status door, open/closed/locked"
    ::= { cmcTcMasterCmc8Status 9 }

  cmcTcMasterCmc8StatusUps1 OBJECT-TYPE
    SYNTAX DisplayString (SIZE (0..31))
    ACCESS read-only
    STATUS mandatory
    DESCRIPTION
      "Status UPS 1, OK/ fault"
    ::= { cmcTcMasterCmc8Status 10 }

  cmcTcMasterCmc8StatusUps2 OBJECT-TYPE
    SYNTAX DisplayString (SIZE (0..31))
    ACCESS read-only
    STATUS mandatory
    DESCRIPTION
      "Status UPS 2, OK/ fault"
    ::= { cmcTcMasterCmc8Status 11 }

  cmcTcMasterCmc8StatusSmokeSensor OBJECT-TYPE
    SYNTAX DisplayString (SIZE (0..31))
    ACCESS read-only
    STATUS mandatory
    DESCRIPTION
      "Status smoke-sensor, OK/ smoke"
    ::= { cmcTcMasterCmc8Status 12 }

  cmcTcMasterCmc8StatusVibrationSensor OBJECT-TYPE
    SYNTAX DisplayString (SIZE (0..31))
    ACCESS read-only
    STATUS mandatory
    DESCRIPTION
      "Status vibration sensor, OK/ vibration"
    ::= { cmcTcMasterCmc8Status 13 }

  cmcTcMasterCmc8StatusMessage OBJECT-TYPE
    SYNTAX DisplayString (SIZE (0..31))
    ACCESS read-only
    STATUS mandatory
    DESCRIPTION
      "Message from CMC"
    ::= { cmcTcMasterCmc8Status 14 }

  cmcTcMasterCmc8ValueOperatingTime OBJECT-TYPE
    SYNTAX DisplayString (SIZE (0..31))
    ACCESS read-only
    STATUS mandatory
    DESCRIPTION
      "Operating time CMC-unit"
    ::= { cmcTcMasterCmc8Status 15 }

  cmcTcMasterCmc8StatusUnit OBJECT-TYPE
    SYNTAX INTEGER {
      unitCelsius(1),
      unitFahrenheit(2)
    }
    ACCESS read-only
    STATUS mandatory
    DESCRIPTION
      "Unit of temperature-values, Celsius or Fahrenheit"
   ::= { cmcTcMasterCmc8Status 16 }


--cmcTcMasterCmc8Status-table-group

  cmcTcMasterCmc8StatusNumber OBJECT-TYPE
    SYNTAX INTEGER 
    ACCESS read-only
    STATUS mandatory
    DESCRIPTION
      "Number of status-table entries"
    ::= { cmcTcMasterCmc8Table 1 }

  cmcTcMasterCmc8StatusTable OBJECT-TYPE
    SYNTAX SEQUENCE OF CmcTcMasterCmc8StatusEntry
    ACCESS not-accessible
    STATUS mandatory
    DESCRIPTION
      "Headline of table"
    ::= { cmcTcMasterCmc8Table 2 }

  cmcTcMasterCmc8StatusEntry OBJECT-TYPE
    SYNTAX CmcTcMasterCmc8StatusEntry
    ACCESS not-accessible
    STATUS mandatory
    DESCRIPTION
      "A list of status entries.  The number of
       entries is given by the value of cmcTcMasterCmc8StatusNumber." 
    INDEX { cmcTcMasterCmc8StatusIndex }
    ::= { cmcTcMasterCmc8StatusTable 1 }

  CmcTcMasterCmc8StatusEntry ::=
    SEQUENCE {
      cmcTcMasterCmc8StatusIndex
        INTEGER,
      cmcTcMasterCmc8StatusText
        DisplayString (SIZE (0..31)),
      cmcTcMasterCmc8StatusStatus
        INTEGER              
    }

    cmcTcMasterCmc8StatusIndex OBJECT-TYPE
      SYNTAX INTEGER (1..32000)
      ACCESS read-only
      STATUS mandatory
      DESCRIPTION
        "Index fo the list of status entries. Its value ranges
         between 1 and the value of cmcTcMasterCmc8StatusNumber." 
      ::= { cmcTcMasterCmc8StatusEntry 1 }

    cmcTcMasterCmc8StatusText OBJECT-TYPE
      SYNTAX DisplayString (SIZE (0..31))
      ACCESS read-write
      STATUS mandatory
      DESCRIPTION
        "Text of the entry in the status-table"
      ::= { cmcTcMasterCmc8StatusEntry 2 }

    cmcTcMasterCmc8StatusStatus OBJECT-TYPE
      SYNTAX INTEGER  {
        statusOK(1),
        alarm(2),
        security(3),
        notAvail(4)
      }
      ACCESS read-only
      STATUS mandatory
      DESCRIPTION
        "Status of the table entry"
      ::= { cmcTcMasterCmc8StatusEntry 3 }

--******************************************************************************

--cmcTCMasterCmc8Set-group

  cmcTcMasterCmc8StatusAccess OBJECT-TYPE
    SYNTAX DisplayString (SIZE (0..31))
    ACCESS read-write
    STATUS mandatory
    DESCRIPTION
      "Status access"
    ::= { cmcTcMasterCmc8Set 1 }

  cmcTcMasterCmc8SetDoor OBJECT-TYPE
    SYNTAX INTEGER {
      lockDoor(1),
      openDoorTime(2),
      openDoorAccess(3),
      openDoor(4)
    }
    ACCESS read-write
    STATUS mandatory
    DESCRIPTION
      "Set door, see table"
    ::= { cmcTcMasterCmc8Set 2 }

  cmcTcMasterCmc8SetMessage OBJECT-TYPE
    SYNTAX DisplayString (SIZE (0..31))
    ACCESS read-write
    STATUS mandatory
    DESCRIPTION
      "Set message"
    ::= { cmcTcMasterCmc8Set 3 }

  cmcTcMasterCmc8SetFault        OBJECT-TYPE
    SYNTAX INTEGER {
      clearFault(1),
      setFault(2)
    }
    ACCESS read-write
    STATUS mandatory
    DESCRIPTION
      "Set fault, see table"
    ::= { cmcTcMasterCmc8Set 4 }

--cmcTcMasterCmc8RelayControl-group

  cmcTcMasterCmc8RelaytableMaxNum OBJECT-TYPE
    SYNTAX INTEGER 
    ACCESS read-only
    STATUS mandatory
    DESCRIPTION
      "Number of table entries"
    ::= { cmcTcMasterCmc8RelayControl 1 }

  cmcTcMasterCmc8RelayTable OBJECT-TYPE
    SYNTAX SEQUENCE OF CmcTcMasterCmc8RelayEntry
    ACCESS not-accessible
    STATUS mandatory
    DESCRIPTION
      "Headline of table for relay control"
    ::= { cmcTcMasterCmc8RelayControl 2 }

  cmcTcMasterCmc8RelayEntry OBJECT-TYPE
    SYNTAX CmcTcMasterCmc8RelayEntry
    ACCESS not-accessible
    STATUS mandatory
    DESCRIPTION
      "Entries"
    INDEX { cmcTcMasterCmc8RelaytableIndex }
    ::= { cmcTcMasterCmc8RelayTable 1 }

  CmcTcMasterCmc8RelayEntry ::=
    SEQUENCE {
      cmcTcMasterCmc8RelaytableIndex
        INTEGER,
      cmcTcMasterCmc8RelaytableText
	DisplayString (SIZE (0..31)),
      cmcTcMasterCmc8RelaytableStatus
        INTEGER              
    }

    cmcTcMasterCmc8RelaytableIndex OBJECT-TYPE
      SYNTAX INTEGER (1..32000)
      ACCESS read-only
      STATUS mandatory
      DESCRIPTION
        "Index for the relay-table. Its value ranges
         between 1 and cmcTcMasterCmc8RelaytableMaxNum"
      ::= { cmcTcMasterCmc8RelayEntry 1 }

    cmcTcMasterCmc8RelaytableText OBJECT-TYPE
      SYNTAX DisplayString (SIZE (0..31))
      ACCESS read-write
      STATUS mandatory
      DESCRIPTION
        "Description-Text for each relay in the table"
      ::= { cmcTcMasterCmc8RelayEntry 2 }

    cmcTcMasterCmc8RelaytableStatus OBJECT-TYPE
      SYNTAX INTEGER  {
        relayOFF(1),
        relayON(2),
        notAvail(3)
      }
      ACCESS read-write
      STATUS mandatory
      DESCRIPTION
        "Status of relays in the table"
      ::= { cmcTcMasterCmc8RelayEntry 3 }

--cmcTcMasterCmc8Setpoints-group

  cmcTcMasterCmc8SetpointFan1 OBJECT-TYPE
    SYNTAX INTEGER 
    ACCESS read-write
    STATUS mandatory
    DESCRIPTION
      "Setpoint Fan 1 in C, Fan 1 will start
       if temperature 1 exceeds this value"
    ::= { cmcTcMasterCmc8Setpoints 1 }

  cmcTcMasterCmc8SetpointFan2 OBJECT-TYPE
    SYNTAX INTEGER 
    ACCESS read-write
    STATUS mandatory
    DESCRIPTION
      "Setpoint Fan 2 in C, Fan 2 will start
       if temperature 2 exceeds this value"
    ::= { cmcTcMasterCmc8Setpoints 2 }

  cmcTcMasterCmc8SetpointHeating OBJECT-TYPE
    SYNTAX INTEGER 
    ACCESS read-write
    STATUS mandatory
    DESCRIPTION
      "Setpoint heating in C, heating will start
       if lowest value of temperature 1 and 2 falls below this value"
    ::= { cmcTcMasterCmc8Setpoints 3 }

  cmcTcMasterCmc8SetpointHighTemperature1 OBJECT-TYPE
    SYNTAX INTEGER 
    ACCESS read-write
    STATUS mandatory
    DESCRIPTION
      "Setpoint high value alarm temperature 1"
    ::= { cmcTcMasterCmc8Setpoints 4 }

  cmcTcMasterCmc8SetpointLowTemperature1 OBJECT-TYPE
    SYNTAX INTEGER 
    ACCESS read-write
    STATUS mandatory
    DESCRIPTION
      "Setpoint low value alarm temperature 1"
    ::= { cmcTcMasterCmc8Setpoints 5 }

  cmcTcMasterCmc8SetpointHighTemperature2 OBJECT-TYPE
    SYNTAX INTEGER 
    ACCESS read-write
    STATUS mandatory
    DESCRIPTION
      "Setpoint high value alarm temperature 2"
    ::= { cmcTcMasterCmc8Setpoints 6 }

  cmcTcMasterCmc8SetpointLowTemperature2 OBJECT-TYPE
    SYNTAX INTEGER 
    ACCESS read-write
    STATUS mandatory
    DESCRIPTION
      "Setpoint low value alarm temperature 2"
    ::= { cmcTcMasterCmc8Setpoints 7 }

  cmcTcMasterCmc8SetpointHighVoltage OBJECT-TYPE
    SYNTAX INTEGER 
    ACCESS read-write
    STATUS mandatory
    DESCRIPTION
      "Setpoint high value supply voltage alarm"
    ::= { cmcTcMasterCmc8Setpoints 8 }

  cmcTcMasterCmc8SetpointLowVoltage OBJECT-TYPE
    SYNTAX INTEGER
    ACCESS read-write
    STATUS mandatory
    DESCRIPTION
      "Setpoint low value supply voltage alarm"
    ::= { cmcTcMasterCmc8Setpoints 9 }

  cmcTcMasterCmc8SetpointLowAux1 OBJECT-TYPE
    SYNTAX INTEGER 
    ACCESS read-write
    STATUS mandatory
    DESCRIPTION
      "Setpoint low value Aux input 1 alarm"
    ::= { cmcTcMasterCmc8Setpoints 10 }

  cmcTcMasterCmc8SetpointHighAux1 OBJECT-TYPE
    SYNTAX INTEGER 
    ACCESS read-write
    STATUS mandatory
    DESCRIPTION
      "Setpoint high value Aux input 1 alarm"
    ::= { cmcTcMasterCmc8Setpoints 11 }

  cmcTcMasterCmc8SetpointLowAux2 OBJECT-TYPE
    SYNTAX INTEGER 
    ACCESS read-write
    STATUS mandatory
    DESCRIPTION
      "Setpoint low value Aux input 2 alarm"
    ::= { cmcTcMasterCmc8Setpoints 12 }

  cmcTcMasterCmc8SetpointHighAux2 OBJECT-TYPE
    SYNTAX INTEGER 
    ACCESS read-write
    STATUS mandatory
    DESCRIPTION
      "Setpoint high value Aux input alarm"
    ::= { cmcTcMasterCmc8Setpoints 13 }

--cmcTcMasterCmc8TrapControl-group

  cmcTcMasterCmc8SetTrapRepeat OBJECT-TYPE
    SYNTAX INTEGER {
      disableTrapRepeat(1),
      enableTrapRepeat(2)
    }
    ACCESS read-write
    STATUS mandatory
    DESCRIPTION
      "Enable/disable repeating of traps. If enabled, traps will
       be repeated after a repeat time, set in setTrapRepeatTime.
       Repeating can be stopped by setting setTrapQuit to quitTrap"
    ::= { cmcTcMasterCmc8TrapControl 1 }

  cmcTcMasterCmc8SetTrapRepeatTime OBJECT-TYPE
    SYNTAX INTEGER 
    ACCESS read-write
    STATUS mandatory
    DESCRIPTION
      "Time value (sec) for trap-repeating, if setTrapRepeat is enabled"
    ::= { cmcTcMasterCmc8TrapControl 2 }

  cmcTcMasterCmc8SetTrapQuit OBJECT-TYPE
    SYNTAX INTEGER {
      quitTrap(1),
      quitTrapOK(2),
      noTrapToQuit(3),
      trapToQuit(4)
    }
    ACCESS read-write
    STATUS mandatory
    DESCRIPTION
      "Quit trap to stop repeating."
    ::= { cmcTcMasterCmc8TrapControl 3 }

--cmcTcMasterCmc8TrapTable-group

  cmcTcMasterCmc8TraptableNumber OBJECT-TYPE
    SYNTAX INTEGER 
    ACCESS read-only
    STATUS mandatory
    DESCRIPTION
      "Number of trapTable entries. The number of trap-receiver"
    ::= { cmcTcMasterCmc8Traps 1 }

  cmcTcMasterCmc8TrapTable OBJECT-TYPE
    SYNTAX SEQUENCE OF CmcTcMasterCmc8TrapEntry
    ACCESS not-accessible
    STATUS mandatory
    DESCRIPTION
      "A list of trap-receiver entries"
    ::= { cmcTcMasterCmc8Traps 2 }

  cmcTcMasterCmc8TrapEntry OBJECT-TYPE
    SYNTAX CmcTcMasterCmc8TrapEntry
    ACCESS not-accessible
    STATUS mandatory
    DESCRIPTION
      "Entries of trapTable"
    INDEX { cmcTcMasterCmc8TrapIndex }
    ::= { cmcTcMasterCmc8TrapTable 1 }

  CmcTcMasterCmc8TrapEntry ::=
    SEQUENCE {
      cmcTcMasterCmc8TrapIndex
        INTEGER,
      cmcTcMasterCmc8TrapStatus
        INTEGER,
      cmcTcMasterCmc8TrapIPaddress
        DisplayString
    }

    cmcTcMasterCmc8TrapIndex OBJECT-TYPE
      SYNTAX INTEGER (1..32000)
      ACCESS read-only
      STATUS mandatory
      DESCRIPTION
        "Index for the trap-receiver-table. Its value ranges between
         1 and the value of cmcTcMasterCmc8TraptableNumber "
      ::= { cmcTcMasterCmc8TrapEntry 1 }

    cmcTcMasterCmc8TrapStatus OBJECT-TYPE
      SYNTAX INTEGER  {
        enabled(1),
        disabled(2)
      }
      ACCESS read-write
      STATUS mandatory
      DESCRIPTION
        "Enable or disable trap receiver"
      ::= { cmcTcMasterCmc8TrapEntry 2 }

    cmcTcMasterCmc8TrapIPaddress OBJECT-TYPE
      SYNTAX DisplayString (SIZE (0..31))
      ACCESS read-write
      STATUS mandatory
      DESCRIPTION
        "IP-address of trap-receiver"
      ::= { cmcTcMasterCmc8TrapEntry 3 }

--cmcTcMasterPcu8MibRev-group
          
  cmcTcMasterPcu8MibMajRev OBJECT-TYPE
    SYNTAX INTEGER (1..32000)
    ACCESS read-only
    STATUS mandatory
    DESCRIPTION
      "The Major Revision level.
       A change in the major revision level represents a major change
       in the architecture of the MIB. A change in the major revision 
       level may indicate a significant change in the information,
       correct interpretation of data may require a MIB document
       with the same major revision level."
    ::= { cmcTcMasterPcu8MibRev 1 }

  cmcTcMasterPcu8MibMinRev OBJECT-TYPE
    SYNTAX INTEGER (0..32000)
    ACCESS read-only
    STATUS mandatory
    DESCRIPTION
      "The Minor Revision level.
       A change in the minor revision level may represent some minor
       additional support, no changes to any pre-existing information
       has occurred."
    ::= { cmcTcMasterPcu8MibRev 2 }

  cmcTcMasterPcu8MibCondition OBJECT-TYPE
    SYNTAX INTEGER {
      other (1),
      ok (2),
      degraded (3),
      failed (4)
    }
    ACCESS read-only
    STATUS mandatory
    DESCRIPTION
      "The overall condition (status) of the system represented by
       this MIB. 
       (2) OK
       (3) a minor problem, warning condition (yellow LED on PCU)
       (4) a major problem (red LED on PCU)"
    ::= { cmcTcMasterPcu8MibRev 3 }

--cmcTcMasterPcu8Values-group

  cmcTcMasterPcu8ValueEnergy1 OBJECT-TYPE
    SYNTAX INTEGER 
    ACCESS read-only
    STATUS mandatory
    DESCRIPTION
      "Total value of the Energy (Wh), measured on IEC input 1"
    ::= { cmcTcMasterPcu8Values 1 }

  cmcTcMasterPcu8ValueEnergy2 OBJECT-TYPE
    SYNTAX INTEGER 
    ACCESS read-only
    STATUS mandatory
    DESCRIPTION
      "Actual value of the Energy (Wh), measured on IEC input 2"
    ::= { cmcTcMasterPcu8Values 2 }

  cmcTcMasterPcu8ValueEnergy1Time OBJECT-TYPE
    SYNTAX INTEGER 
    ACCESS read-only
    STATUS mandatory
    DESCRIPTION
      "Actual value of the Energy (Wh), measured on IEC input 1, can be set to 0
       Value can be used to calculate the energy over a fixed time"
    ::= { cmcTcMasterPcu8Values 3 }

  cmcTcMasterPcu8ValueEnergy2Time OBJECT-TYPE
    SYNTAX INTEGER 
    ACCESS read-only
    STATUS mandatory
    DESCRIPTION
      "Actual value of the Energy (Wh), measured on IEC input 2, can be set to 0.
       Value can be used to calculate the energy over a fixed time"
    ::= { cmcTcMasterPcu8Values 4 }

  cmcTcMasterPcu8ValuePower1 OBJECT-TYPE
    SYNTAX INTEGER 
    ACCESS read-only
    STATUS mandatory
    DESCRIPTION
      "Calculated actual power 1 (W). Calculated from cmcTcMasterPcu8ValueEnergy1/time"
    ::= { cmcTcMasterPcu8Values 5 }
          
  cmcTcMasterPcu8ValuePower2 OBJECT-TYPE
    SYNTAX INTEGER 
    ACCESS read-only
    STATUS mandatory
    DESCRIPTION
      "Calculated actual power 2 (W). Calculated from cmcTcMasterPcu8ValueEnergy2/time"
    ::= { cmcTcMasterPcu8Values 6 }
          
  cmcTcMasterPcu8ValueTemperature OBJECT-TYPE
    SYNTAX INTEGER 
    ACCESS read-only
    STATUS mandatory
    DESCRIPTION
      "Actual value of temperature 1 in deg C or deg F"
    ::= { cmcTcMasterPcu8Values 7 }
          
--cmcTcMasterPcu8Status-group

  cmcTcMasterPcu8StatusInput1 OBJECT-TYPE
    SYNTAX INTEGER {
      false(1),
      true(2),
      pending(3),
      notAvail(4)
    }
    ACCESS read-only
    STATUS mandatory
    DESCRIPTION
      "Status of digital Input 1
       (1) digital signal is true (contact closed if setup is NO)
       (2) digital signal is false(contact opened if setup is NO),
       note setup of input (NO/NC)
       (3) digital input is pending, note setup of delay"
    ::= { cmcTcMasterPcu8Status 1 }

  cmcTcMasterPcu8StatusInput2 OBJECT-TYPE
    SYNTAX INTEGER {
      false(1),
      true(2),
      pending(3),
      notAvail(4)
    }
    ACCESS read-only
    STATUS mandatory
    DESCRIPTION
      "Status of digital Input 2
       (1) digital signal is true (contact closed if setup is NO)
       (2) digital signal is false(contact opened if setup is NO),
       note setup of input (NO/NC)
       (3) digital input is pending, note setup of delay"
    ::= { cmcTcMasterPcu8Status 2 }

  cmcTcMasterPcu8StatusPower1 OBJECT-TYPE
    SYNTAX INTEGER {
      ok(1),
      tooHigh(2),
      tooLow(3),
      warning(4),
      error(5),
      notAvail(6)
    }
    ACCESS read-only
    STATUS mandatory
    DESCRIPTION
      "Status Power 1, see setpoints"
    ::= { cmcTcMasterPcu8Status 3 }

  cmcTcMasterPcu8StatusPower2 OBJECT-TYPE
    SYNTAX INTEGER {
      ok(1),
      tooHigh(2),
      tooLow(3),
      warning(4),
      error(5),
      notAvail(6)
    }
    ACCESS read-only
    STATUS mandatory
    DESCRIPTION
      "Status Power 2, see setpoints"
    ::= { cmcTcMasterPcu8Status 4 }

  cmcTcMasterPcu8StatusTemperature OBJECT-TYPE
    SYNTAX INTEGER {
      ok(1),
      tooHigh(2),
      tooLow(3),
      warning(4),
      error(5)
    }
    ACCESS read-only
    STATUS mandatory
    DESCRIPTION
      "Status temperature 1, OK/ too high/ too low
       (see setpoints of temperature 1)"
    ::= { cmcTcMasterPcu8Status 5 }

--cmcTcMasterPcu8Status-table-group

  cmcTcMasterPcu8OutletsNumber OBJECT-TYPE
    SYNTAX INTEGER 
    ACCESS read-only
    STATUS mandatory
    DESCRIPTION
      "Number of value-table entries=number of outlets available on this unit"
    ::= { cmcTcMasterPcu8StatusTable1 1 }

  cmcTcMasterPcu8StatusTable OBJECT-TYPE
    SYNTAX SEQUENCE OF CmcTcMasterPcu8StatusEntry
    ACCESS not-accessible
    STATUS mandatory
    DESCRIPTION
      "Headline of status-table"
    ::= { cmcTcMasterPcu8StatusTable1 2 }

  cmcTcMasterPcu8StatusEntry OBJECT-TYPE
    SYNTAX CmcTcMasterPcu8StatusEntry
    ACCESS not-accessible
    STATUS mandatory
    DESCRIPTION
      "Entries of status-table"
    INDEX { cmcTcMasterPcu8StatusIndex }
    ::= { cmcTcMasterPcu8StatusTable 1 }

    CmcTcMasterPcu8StatusEntry ::=
      SEQUENCE {
        cmcTcMasterPcu8StatusIndex
          INTEGER,
        cmcTcMasterPcu8StatusText
          DisplayString (SIZE (0..31)),                
        cmcTcMasterPcu8StatusStatus
          INTEGER,
        cmcTcMasterPcu8ControlSNMP
          INTEGER,
        cmcTcMasterPcu8FrontSwitch
          INTEGER,
        cmcTcMasterPcu8Delay
          INTEGER,
        cmcTcMasterPcu8Input1
          INTEGER,
        cmcTcMasterPcu8Input2
          INTEGER,
        cmcTcMasterPcu8Temperature
          INTEGER,          
        cmcTcMasterPcu8Power
          INTEGER,          
        cmcTcMasterPcu8RestoreOutputStatus
          INTEGER           
      }

    cmcTcMasterPcu8StatusIndex OBJECT-TYPE
      SYNTAX INTEGER (1..32000)
      ACCESS read-only
      STATUS mandatory
      DESCRIPTION
        "Index for the list of value entries. Its value ranges
         between 1 and the value of cmcTcMasterPcu8OutletsNumber."
      ::= { cmcTcMasterPcu8StatusEntry 1 }

    cmcTcMasterPcu8StatusText OBJECT-TYPE
      SYNTAX DisplayString (SIZE (0..31))
      ACCESS read-write
      STATUS mandatory
      DESCRIPTION
        "Descriptional text for each outlet (entry in the table)"
      ::= { cmcTcMasterPcu8StatusEntry 2 }
              
    cmcTcMasterPcu8StatusStatus OBJECT-TYPE
      SYNTAX INTEGER {
        ok(1),
        onFrontKey(2),
        offFrontKey(3),
        onWEB(4),
        offWEB(5),
        onInput1(6),
        offInput1(7),
        onInput2(8),
        offInput2(9),
        onTemp(10),
        offTemp(11),
        onSNMP(12),
        offSNMP(13),
        onTimer(14),
        offTimer(15),
        onDelay(16),
        onConsole(17),
        offConsole(18),
        onReboot(19), 
        offReboot(20),
        onPower(21),
        offPower(22)
      }
      ACCESS read-only
      STATUS mandatory
      DESCRIPTION
        "Actual status of the outlet"
      ::= { cmcTcMasterPcu8StatusEntry 3 }

    cmcTcMasterPcu8ControlSNMP OBJECT-TYPE
      SYNTAX INTEGER  {
        on(1),
        off(2)
      }
      ACCESS read-write
      STATUS mandatory
      DESCRIPTION
        "Control via SNMP"
      ::= { cmcTcMasterPcu8StatusEntry 4 }

    cmcTcMasterPcu8FrontSwitch OBJECT-TYPE
      SYNTAX INTEGER {
        disabled(1),
        enabled(2)
      }
      ACCESS read-write
      STATUS mandatory
      DESCRIPTION
        "Control via front switch"
      ::= { cmcTcMasterPcu8StatusEntry 5 }
 
    cmcTcMasterPcu8Delay OBJECT-TYPE
      SYNTAX INTEGER (0..300)
      ACCESS read-write
      STATUS mandatory
      DESCRIPTION
        "Value for delay time in seconds.
         Value>0: Output is switched off for this time (in sec)"
      ::= { cmcTcMasterPcu8StatusEntry 6 }

    cmcTcMasterPcu8Input1 OBJECT-TYPE
      SYNTAX INTEGER {
        disabled(1),
        switchOn(2),
        switchOff(3),
        switchOnOff(4)
      }
      ACCESS read-write
      STATUS mandatory
      DESCRIPTION
        "Control via digital input 1
         (1): disabled
         (2): output is switched on in case of input 1 alarm
         (3): output is switched off in case of input 1 alarm
         (4): output has same status as input 1"
      ::= { cmcTcMasterPcu8StatusEntry 7 }

    cmcTcMasterPcu8Input2 OBJECT-TYPE
      SYNTAX INTEGER {
        disabled(1),
        switchOn(2),
        switchOff(3),
        switchOnOff(4)
      }
      ACCESS read-write
      STATUS mandatory
      DESCRIPTION
        "Control via digital input 2
         (1): disabled
         (2): output is switched on in case of input 2 alarm
         (3): output is switched off in case of input 2 alarm
         (4): output has same status as input 2"             
      ::= { cmcTcMasterPcu8StatusEntry 8 }

    cmcTcMasterPcu8Temperature OBJECT-TYPE
      SYNTAX INTEGER {
        disabled(1),
        switchOffAlarm(2),
        switchOnAlarm(3),
        switchOffSetpoint(4),
        switchOnSetpoint(5)
      }
      ACCESS read-write
      STATUS mandatory
      DESCRIPTION
        "Control via temperature alarm or setpoint
         (1): disabled
         (2): output is switched off in case of temperature alarm
         (3): output is switched on in case of temperature alarm
         (4): output is switched off if temperature setpoint (cmcTcMasterPcu8SetpointTemperature)
              is reached
         (5): output is switched on if temperature setpoint (cmcTcMasterPcu8SetpointTemperature)
              is reached"
      ::= { cmcTcMasterPcu8StatusEntry 9 }   
    
    cmcTcMasterPcu8Power OBJECT-TYPE
      SYNTAX INTEGER {
        disabled(1),
        switchOffAlarm(2),
        switchOffWarning(3),
        switchOnAlarm(4),
        switchOnWarning(5)
      }
      ACCESS read-write
      STATUS mandatory
      DESCRIPTION
        "Control via power setpoint
         (1): disabled
         (2): output is switched off upon power high alarm (cmcTcMasterPcu8SetpointHighPower1)
         (3): output is switched off upon power warning (cmcTcMasterPcu8SetpointWarningPower1)
         (4): output is switched on upon power alarm (cmcTcMasterPcu8SetpointHigh(Low)Power1)
         (5): output is switched on upon power warning (cmcTcMasterPcu8SetpointWarningPower1)             "
      ::= { cmcTcMasterPcu8StatusEntry 10 }                

    cmcTcMasterPcu8RestoreOutputStatus OBJECT-TYPE
      SYNTAX INTEGER {
        disabled(1),
        enabled(2)
      }
      ACCESS read-write
      STATUS mandatory
      DESCRIPTION
        "Save last output status and switch output to this status after reboot"
      ::= { cmcTcMasterPcu8StatusEntry 11 }
                
--cmcTcMasterPcu8SetupGeneral-group

  cmcTcMasterPcu8SetTempUnit OBJECT-TYPE
    SYNTAX INTEGER {
      celsius(1),
      fahrenheit(2)
    }
    ACCESS read-write
    STATUS mandatory
    DESCRIPTION
      "Unit of all temperature values and setpoints, Celsius or Fahrenheit"
    ::= { cmcTcMasterPcu8SetupGeneral 1 }

  cmcTcMasterPcu8SetBeeper OBJECT-TYPE
    SYNTAX INTEGER {
      off(1),
      on(2),
      enableClear(3)
    }
    ACCESS read-write
    STATUS mandatory
    DESCRIPTION
      "Audible alarm in PCU unit:
       (1): beeper is off (general)
       (2): beeper is on (Alarm)
       (3): enable Clear (cmcTcMasterPcu8ClearAlarm)"
    ::= { cmcTcMasterPcu8SetupGeneral 2 }

  cmcTcMasterPcu8LogicRelay OBJECT-TYPE
    SYNTAX INTEGER {
      closeAtAlarm(1),
      openAtAlarm(2),
      off(3),
      enableRemote(4)
    }
    ACCESS read-write
    STATUS mandatory
    DESCRIPTION
      "Logic of alarm relay: 
       (1): Relay will pick up in case of an alarm
       (2): Relay will release in case of an alarm
       (3): Relay off (general)
       (4): enable remote relay control (SNMP set)"
    ::= { cmcTcMasterPcu8SetupGeneral 3 }
 
  cmcTcMasterPcu8ClearRelay OBJECT-TYPE
    SYNTAX INTEGER {
      disabled(1),
      enabled(2)
    }
    ACCESS read-write
    STATUS mandatory
    DESCRIPTION
      "Enable clear of alarm relay: 
       (1): Relay cannot be cleared by cmcTcMasterPcu8ClearAlarm
       (2): Relay can be cleared by cmcTcMasterPcu8ClearAlarm"
    ::= { cmcTcMasterPcu8SetupGeneral 4 }                  

  cmcTcMasterPcu8WebAccess OBJECT-TYPE
    SYNTAX INTEGER {
      viewOnly(1),
      fullAccess(2),
      off(3)
    }
    ACCESS read-write
    STATUS mandatory
    DESCRIPTION
      "Web access via HTTP: 
       (1): view only
       (2): full Access, read and set
       (3): Web disabled (general)"
    ::= { cmcTcMasterPcu8SetupGeneral 5 }
 
  cmcTcMasterPcu8SetupDate OBJECT-TYPE
    SYNTAX DisplayString (SIZE (0..10))
    ACCESS read-write
    STATUS mandatory
    DESCRIPTION
      "actual Date in format DD.MM.YYYY"
    ::= { cmcTcMasterPcu8SetupGeneral 6 }

  cmcTcMasterPcu8SetupTime OBJECT-TYPE
    SYNTAX DisplayString (SIZE (0..8))
    ACCESS read-write
    STATUS mandatory
    DESCRIPTION
      "actual Time in format HH:MM:SS, HH (0-23), MM (0-59), SS (0-59)"
    ::= { cmcTcMasterPcu8SetupGeneral 7 }

--cmcTcMasterPcu8TimerTable1-group
 
  cmcTcMasterPcu8TimerNumber OBJECT-TYPE
    SYNTAX INTEGER 
    ACCESS read-only
    STATUS mandatory
    DESCRIPTION
      "Number of timers available on this unit"
    ::= { cmcTcMasterPcu8TimerTable1 1 }

  cmcTcMasterPcu8TimerTable OBJECT-TYPE
    SYNTAX SEQUENCE OF CmcTcMasterPcu8TimerEntry
    ACCESS not-accessible
    STATUS mandatory
    DESCRIPTION
      "Headline of timer-table"
    ::= { cmcTcMasterPcu8TimerTable1 2 }

  cmcTcMasterPcu8TimerEntry OBJECT-TYPE
    SYNTAX CmcTcMasterPcu8TimerEntry
    ACCESS not-accessible
    STATUS mandatory
    DESCRIPTION
      "Entries of timer-table"
    INDEX { cmcTcMasterPcu8TimerIndex }
    ::= { cmcTcMasterPcu8TimerTable 1 }

    CmcTcMasterPcu8TimerEntry ::=
      SEQUENCE {
        cmcTcMasterPcu8TimerIndex
          INTEGER,
        cmcTcMasterPcu8TimerStatus
          INTEGER,
        cmcTcMasterPcu8TimerDayOfWeek
          INTEGER,  
        cmcTcMasterPcu8TimeOn 
          DisplayString (SIZE (0..5)),                              
        cmcTcMasterPcu8TimeOff 
          DisplayString (SIZE (0..5)),                              
        cmcTcMasterPcu8TimeControl
          INTEGER,
        cmcTcMasterPcu8TimerOutput1
          INTEGER,
        cmcTcMasterPcu8TimerOutput2
          INTEGER         
      }

    cmcTcMasterPcu8TimerIndex OBJECT-TYPE
      SYNTAX INTEGER (1..32000)
      ACCESS read-only
      STATUS mandatory
      DESCRIPTION
        "Index for the list of timer entries. Its value ranges
         between 1 and the value of cmcTcMasterPcu8TimerNumber." 
      ::= { cmcTcMasterPcu8TimerEntry 1 }

    cmcTcMasterPcu8TimerStatus OBJECT-TYPE
      SYNTAX INTEGER {
        switchedOff(1),
        switchedOn(2),
        noTime(3) 
      }
      ACCESS read-only
      STATUS mandatory
      DESCRIPTION
        "Actual status of the timer"
      ::= { cmcTcMasterPcu8TimerEntry 2 }

    cmcTcMasterPcu8TimerDayOfWeek OBJECT-TYPE
      SYNTAX INTEGER {
        sun(1),
        mon(2),
        tue(3) ,
        wed(4),
        thu(5),
        fre(6),
        sat(7),
        sat-sun(8),
        mo-fr(9),
        mo-su(10)
      }
      ACCESS read-write
      STATUS mandatory
      DESCRIPTION
        "Day when the timer is active"
      ::= { cmcTcMasterPcu8TimerEntry 3 }
             
    cmcTcMasterPcu8TimeOn OBJECT-TYPE
      SYNTAX DisplayString (SIZE (0..5))
      ACCESS read-write
      STATUS mandatory
      DESCRIPTION
        "Time to switch on current outlet, 
         Format: HH:MM"
      ::= { cmcTcMasterPcu8TimerEntry 4 }

    cmcTcMasterPcu8TimeOff OBJECT-TYPE
      SYNTAX DisplayString (SIZE (0..5))
      ACCESS read-write
      STATUS mandatory
      DESCRIPTION
        "Time to switch off current outlet,
         Format: HH:MM"
      ::= { cmcTcMasterPcu8TimerEntry 5 }

    cmcTcMasterPcu8TimeControl OBJECT-TYPE
      SYNTAX INTEGER {
        disabled(1),
        enabled(2)
      }
      ACCESS read-write
      STATUS mandatory
      DESCRIPTION
        "Control via RTC"
      ::= { cmcTcMasterPcu8TimerEntry 6 }

    cmcTcMasterPcu8TimerOutput1 OBJECT-TYPE
      SYNTAX INTEGER 
      ACCESS read-write
      STATUS mandatory
      DESCRIPTION
        "Output which is controlled via timer"
      ::= { cmcTcMasterPcu8TimerEntry 7 }

    cmcTcMasterPcu8TimerOutput2 OBJECT-TYPE
      SYNTAX INTEGER 
      ACCESS read-write
      STATUS mandatory
      DESCRIPTION
        "Output which is controlled via timer"
      ::= { cmcTcMasterPcu8TimerEntry 8 }

--cmcTcMasterPcu8SetupPower1-group                     

  cmcTcMasterPcu8SetupPower1Avail OBJECT-TYPE
    SYNTAX INTEGER {
      notAvailable(1),
      available(2)
    }
    ACCESS read-write
    STATUS mandatory
    DESCRIPTION
      "Energy sensor 1 sensor:   
       (1) not available
       (2) available"
    ::= { cmcTcMasterPcu8SetupPower1 1 }

  cmcTcMasterPcu8SetupPower1Relay OBJECT-TYPE
    SYNTAX INTEGER {
      disabled(1),
      enabled(2)
    }
    ACCESS read-write
    STATUS mandatory
    DESCRIPTION
      "Alert handling of Alarm Relay in case of an alarm condition
       of Power 1:  
       (1) no switching of Relays
       (2) Relay will switch"
    ::= { cmcTcMasterPcu8SetupPower1 2 }

  cmcTcMasterPcu8SetupPower1Beeper OBJECT-TYPE
    SYNTAX INTEGER {
      disabled(1),
      enabled(2)
    }
    ACCESS read-write
    STATUS mandatory
    DESCRIPTION
      "Alert handling of beeper of in case of an alarm condition
       of Power 1: 
       (1) No Audible Alarm
       (2) Start Audible Alarm"
    ::= { cmcTcMasterPcu8SetupPower1 3 }

--cmcTcMasterPcu8SetupPower2-group                     

  cmcTcMasterPcu8SetupPower2Avail OBJECT-TYPE
    SYNTAX INTEGER {
      notAvailable(1),
      available(2)
    }
    ACCESS read-write
    STATUS mandatory
    DESCRIPTION
      "Energy sensor 2:   
       (1) not available
       (2) available"
    ::= { cmcTcMasterPcu8SetupPower2 1 }

  cmcTcMasterPcu8SetupPower2Relay OBJECT-TYPE
    SYNTAX INTEGER {
      disabled(1),
      enabled(2)
    }
    ACCESS read-write
    STATUS mandatory
    DESCRIPTION
      "Alert handling of Alarm Relay in case of an alarm condition
       of Power 2:  
       (1) no switching of Relay
       (2) Relay will switch"
    ::= { cmcTcMasterPcu8SetupPower2 2 }

  cmcTcMasterPcu8SetupPower2Beeper OBJECT-TYPE
    SYNTAX INTEGER {
      disabled(1),
      enabled(2)
    }
    ACCESS read-write
    STATUS mandatory
    DESCRIPTION
      "Alert handling of beeper of in case of an alarm condition
       of Power 2: 
       (1) No Audible Alarm
       (2) Start Audible Alarm"
    ::= { cmcTcMasterPcu8SetupPower2 3 }

--cmcTcMasterPcu8SetupInput1-group

  cmcTcMasterPcu8SetupInput1Avail OBJECT-TYPE
    SYNTAX INTEGER {
      notAvailable(1),
      available(2)
    }
    ACCESS read-write
    STATUS mandatory
    DESCRIPTION
      "Input 1 sensor:   
       (1) not available
       (2) available"
    ::= { cmcTcMasterPcu8SetupInput1 1 }

  cmcTcMasterPcu8SetupInput1Relay OBJECT-TYPE
    SYNTAX INTEGER {
      disabled(1),
      enabled(2)
    }
    ACCESS read-write
    STATUS mandatory
    DESCRIPTION
      "Alert handling of Alarm Relay in case of an alarm condition
       of Input 1:  
       (1) no switching of Relay
       (2) Relay will switch"
    ::= { cmcTcMasterPcu8SetupInput1 2 }

  cmcTcMasterPcu8SetupInput1Beeper OBJECT-TYPE
    SYNTAX INTEGER {
      disabled(1),
      enabled(2)
    }
    ACCESS read-write
    STATUS mandatory
    DESCRIPTION
      "Alert handling of beeper of in case of an alarm condition
       of Input 1: 
       (1) No Audible Alarm
       (2) Start Audible Alarm"
    ::= { cmcTcMasterPcu8SetupInput1 3 }

  cmcTcMasterPcu8SetupInput1Contact OBJECT-TYPE
    SYNTAX INTEGER {
      contactNO(1),
      contactNC(2),
      notAvail(3)
    }
    ACCESS read-write
    STATUS mandatory
    DESCRIPTION
      "Setup of digital input 1"
    ::= { cmcTcMasterPcu8SetupInput1 4 }

  cmcTcMasterPcu8SetupInput1Delay OBJECT-TYPE
    SYNTAX INTEGER (0..60)
    ACCESS read-write
    STATUS mandatory
    DESCRIPTION
      "Delay for changing of input state"
    ::= { cmcTcMasterPcu8SetupInput1 5 }

--cmcTcMasterPcu8SetupInput2-group

  cmcTcMasterPcu8SetupInput2Avail OBJECT-TYPE
    SYNTAX INTEGER {
      notAvailable(1),
      available(2)
    }
    ACCESS read-write
    STATUS mandatory
    DESCRIPTION
      "Input 2 sensor:   
       (2) available
       (1) not available"
    ::= { cmcTcMasterPcu8SetupInput2 1 }

  cmcTcMasterPcu8SetupInput2Relay OBJECT-TYPE
    SYNTAX INTEGER {
      disabled(1),
      enabled(2)
    }
    ACCESS read-write
    STATUS mandatory
    DESCRIPTION
      "Alert handling of Alarm Relay in case of an alarm condition
       of Input 1:  
       (1) no switching of Relays
       (2) Relay will switch"
    ::= { cmcTcMasterPcu8SetupInput2 2 }

  cmcTcMasterPcu8SetupInput2Beeper OBJECT-TYPE
    SYNTAX INTEGER {
      disabled(1),
      enabled(2)
    }
    ACCESS read-write
    STATUS mandatory
    DESCRIPTION
      "Alert handling of beeper of in case of an alarm condition
       of Input 2: 
       (1) No Audible Alarm
       (2) Start Audible Alarm"
    ::= { cmcTcMasterPcu8SetupInput2 3 }

  cmcTcMasterPcu8SetupInput2Contact OBJECT-TYPE
    SYNTAX INTEGER {
      contactNO(1),
      contactNC(2),
      notAvail(3)
    }
    ACCESS read-write
    STATUS mandatory
    DESCRIPTION
      "Setup of digital input 2"
    ::= { cmcTcMasterPcu8SetupInput2 4 }

  cmcTcMasterPcu8SetupInput2Delay OBJECT-TYPE
    SYNTAX INTEGER (0..60)
    ACCESS read-write
    STATUS mandatory
    DESCRIPTION
      "Delay for changing of input state"
    ::= { cmcTcMasterPcu8SetupInput2 5 }

--cmcTcMasterPcu8SetupTemperature-group                     

  cmcTcMasterPcu8SetupTemperatureAvail OBJECT-TYPE
    SYNTAX INTEGER {
      notAvailable(1),
      available(2)
    }
    ACCESS read-write
    STATUS mandatory
    DESCRIPTION
      "Temp sensor 1:   
       (1) not available
       (2) available"
    ::= { cmcTcMasterPcu8SetupTemperature 1 }

  cmcTcMasterPcu8SetupTemperatureRelay OBJECT-TYPE
    SYNTAX INTEGER {
      disabled(1),
      enabled(2)
    }
    ACCESS read-write
    STATUS mandatory
    DESCRIPTION
      "Alert handling of Alarm Relay in case of an alarm condition
       of Temperature:  
       (1) no switching of Relays
       (2) Relay will switch"
    ::= { cmcTcMasterPcu8SetupTemperature 2 }

  cmcTcMasterPcu8SetupTemperatureBeeper OBJECT-TYPE
    SYNTAX INTEGER {
      disabled(1),
      enabled(2)
    }
    ACCESS read-write
    STATUS mandatory
    DESCRIPTION
      "Alert handling of beeper of in case of an alarm condition
       of Temperature: 
       (1) No Audible Alarm
       (2) Start Audible Alarm"
    ::= { cmcTcMasterPcu8SetupTemperature 3 }

--cmcTcMasterPcu8SetupGeneral-group

  cmcTcMasterPcu8SetMessage OBJECT-TYPE
    SYNTAX DisplayString (SIZE (0..31))
    ACCESS read-write
    STATUS mandatory
    DESCRIPTION
      "Set message"
    ::= { cmcTcMasterPcu8SetupDevice 1 }

--cmcTcMasterPcu8Setpoints-group

  cmcTcMasterPcu8SetpointHighPower1 OBJECT-TYPE
    SYNTAX INTEGER 
    ACCESS read-write
    STATUS mandatory
    DESCRIPTION
      "Setpoint high value power consumption 1 alarm"
    ::= { cmcTcMasterPcu8Setpoints 1 }

  cmcTcMasterPcu8SetpointWarningPower1 OBJECT-TYPE
    SYNTAX INTEGER 
    ACCESS read-write
    STATUS mandatory
    DESCRIPTION
      "Setpoint warning value power consumption 1 alarm"
    ::= { cmcTcMasterPcu8Setpoints 2 }

  cmcTcMasterPcu8SetpointLowPower1 OBJECT-TYPE
    SYNTAX INTEGER
    ACCESS read-write
    STATUS mandatory
    DESCRIPTION
      "Setpoint low value power consumption 1 alarm"
    ::= { cmcTcMasterPcu8Setpoints 3 }

  cmcTcMasterPcu8SetpointHighPower2 OBJECT-TYPE
    SYNTAX INTEGER 
    ACCESS read-write
    STATUS mandatory
    DESCRIPTION
      "Setpoint high value power consumption 2 alarm"
    ::= { cmcTcMasterPcu8Setpoints 4 }

  cmcTcMasterPcu8SetpointWarningPower2 OBJECT-TYPE
    SYNTAX INTEGER 
    ACCESS read-write
    STATUS mandatory
    DESCRIPTION
      "Setpoint warning value power consumption 2 alarm"
    ::= { cmcTcMasterPcu8Setpoints 5 }

  cmcTcMasterPcu8SetpointLowPower2 OBJECT-TYPE
    SYNTAX INTEGER
    ACCESS read-write
    STATUS mandatory
    DESCRIPTION
      "Setpoint low value power consumption 2 alarm"
    ::= { cmcTcMasterPcu8Setpoints 6 }

  cmcTcMasterPcu8SetpointHighTemperature OBJECT-TYPE
    SYNTAX INTEGER (0..200)
    ACCESS read-write
    STATUS mandatory
    DESCRIPTION
      "Setpoint high value alarm temperature "
    ::= { cmcTcMasterPcu8Setpoints 7 }

  cmcTcMasterPcu8SetpointLowTemperature OBJECT-TYPE
    SYNTAX INTEGER (0..50)
    ACCESS read-write
    STATUS mandatory
    DESCRIPTION
      "Setpoint low value alarm temperature "
    ::= { cmcTcMasterPcu8Setpoints 8 }
 
  cmcTcMasterPcu8SetpointTemperature OBJECT-TYPE
    SYNTAX INTEGER (0..200)
    ACCESS read-write
    STATUS mandatory
    DESCRIPTION
      "Setpoint temperature for outlet control 
       and temperature warning"
    ::= { cmcTcMasterPcu8Setpoints 9 }

  cmcTcMasterPcu8SetpointTemperatureHyst OBJECT-TYPE
    SYNTAX INTEGER (0..15)
    ACCESS read-write
    STATUS mandatory
    DESCRIPTION
      "Hysteresis for cmcTcMasterPcu8SetpointTemperature"
    ::= { cmcTcMasterPcu8Setpoints 10 }
 
--cmcTcMasterPcu8Control-group

  cmcTcMasterPcu8ResetEnergy1 OBJECT-TYPE
    SYNTAX INTEGER {
      noReset(1),
      reset(2)
    }
    ACCESS read-write
    STATUS mandatory
    DESCRIPTION
      "Reset value of cmcTcMasterPcu8ValueEnergy1Time"
    ::= { cmcTcMasterPcu8Control 1 }

  cmcTcMasterPcu8ResetEnergy2 OBJECT-TYPE
    SYNTAX INTEGER {
      noReset(1),
      reset(2)
    }
    ACCESS read-write
    STATUS mandatory
    DESCRIPTION
      "Reset value of cmcTcMasterPcu8ValueEnergy2Time"
    ::= { cmcTcMasterPcu8Control 2 }

  cmcTcMasterPcu8ControlAlarmRelay OBJECT-TYPE
    SYNTAX INTEGER {
      relayOff(1),
      relayOn(2)
    }
    ACCESS read-write
    STATUS mandatory
    DESCRIPTION
      "Control of Alarm relay"
    ::= { cmcTcMasterPcu8Control 3 }

  cmcTcMasterPcu8ClearAlarm OBJECT-TYPE
    SYNTAX INTEGER {
      noClear(1),
      clear(2)
    }
    ACCESS read-write
    STATUS mandatory
    DESCRIPTION
      "Clear alarm, beeper and relay"
    ::= { cmcTcMasterPcu8Control 4 }

--cmcTcMasterPcu8TrapTable-group

  cmcTcMasterPcu8TrapTableNumber OBJECT-TYPE
    SYNTAX INTEGER 
    ACCESS read-only
    STATUS mandatory
    DESCRIPTION
      "Number of cmcTcMasterPcu8TrapTable entries. The number of trap-receivers avail."
    ::= { cmcTcMasterPcu8Traps 1 }

  cmcTcMasterPcu8TrapTable OBJECT-TYPE
    SYNTAX SEQUENCE OF CmcTcMasterPcu8TrapEntry
    ACCESS not-accessible
    STATUS mandatory
    DESCRIPTION
      "A list of trap-receiver entries"
    ::= { cmcTcMasterPcu8Traps 2 }

  cmcTcMasterPcu8TrapEntry OBJECT-TYPE
    SYNTAX CmcTcMasterPcu8TrapEntry
    ACCESS not-accessible
    STATUS mandatory
    DESCRIPTION
      "Entries of cmcTcMasterPcu8TrapTable"
    INDEX { cmcTcMasterPcu8TrapIndex }
    ::= { cmcTcMasterPcu8TrapTable 1 }

    CmcTcMasterPcu8TrapEntry ::=
      SEQUENCE {
        cmcTcMasterPcu8TrapIndex
          INTEGER,
        cmcTcMasterPcu8TrapStatus
          INTEGER,
        cmcTcMasterPcu8TrapIPaddress
          DisplayString
      }

    cmcTcMasterPcu8TrapIndex OBJECT-TYPE
      SYNTAX INTEGER (1..32000)
      ACCESS read-only
      STATUS mandatory
      DESCRIPTION
        "Index for the trap-receiver-table. Its value ranges between
         1 and the value of cmcTcMasterPcu8TrapTableNumber "
      ::= { cmcTcMasterPcu8TrapEntry 1 }

    cmcTcMasterPcu8TrapStatus OBJECT-TYPE
      SYNTAX INTEGER {
        disabled(1),
        enabled(2)
      }
      ACCESS read-write
      STATUS mandatory
      DESCRIPTION
        "Enable or disable trap receiver"
      ::= { cmcTcMasterPcu8TrapEntry 2 }

    cmcTcMasterPcu8TrapIPaddress OBJECT-TYPE
      SYNTAX DisplayString (SIZE (0..15))
      ACCESS read-write
      STATUS mandatory
      DESCRIPTION
        "IP-address of trap-receiver"
      ::= { cmcTcMasterPcu8TrapEntry 3 }

--cmcTcMasterTc8MibRev-group
          
  cmcTcMasterTc8MibMajRev OBJECT-TYPE
    SYNTAX INTEGER (1..32000)
    ACCESS read-only
    STATUS mandatory
    DESCRIPTION
      "The Major Revision level.
       A change in the major revision level represents a major change
       in the architecture of the MIB. A change in the major revision 
       level may indicate a significant change in the information,
       correct interpretation of data may require a MIB document
       with the same major revision level."
    ::= { cmcTcMasterTc8MibRev 1 }

  cmcTcMasterTc8MibMinRev OBJECT-TYPE
    SYNTAX INTEGER (0..32000)
    ACCESS read-only
    STATUS mandatory
    DESCRIPTION
      "The Minor Revision level.
       A change in the minor revision level may represent some minor
       additional support, no changes to any pre-existing information
       has occurred."
    ::= { cmcTcMasterTc8MibRev 2 }

  cmcTcMasterTc8MibCondition OBJECT-TYPE
    SYNTAX INTEGER {
      other (1),
      ok (2),
      degraded (3),
      failed (4),
      configChanged (5)
    }
    ACCESS read-only
    STATUS mandatory
    DESCRIPTION
      "The overall condition (status) of the system represented by
       this MIB. 
       (2) OK
       (3) a minor problem, warning condition (yellow LED on CMC-TC)
       (4) a major problem (red LED on CMC-TC)
       (5) configuration of sensor units changed or
           unit detected (red/yellow/green LED on CMC-TC)"
    ::= { cmcTcMasterTc8MibRev 3 }
          
--cmcTcMasterTc8Status-group

  cmcTcMasterTc8StatusDeviceCMC OBJECT-TYPE
    SYNTAX INTEGER {
      failed(1),
      ok(2)
    }
    ACCESS read-only
    STATUS mandatory
    DESCRIPTION
      "General Status of CMC-TC unit itself
       (1) failed
       (2) OK"
    ::= { cmcTcMasterTc8Status 1 }

  cmcTcMasterTc8UnitsConnected OBJECT-TYPE
    SYNTAX INTEGER 
    ACCESS read-only
    STATUS mandatory
    DESCRIPTION
      "Number of sensor units connected to the CMC-TC, Port 1 to 4"
    ::= { cmcTcMasterTc8Status 2 }

--unit 1

  cmcTcMasterTc8Unit1TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 1"
    ::= { cmcTcMasterTc8StatusSensorUnit1 1 }

  cmcTcMasterTc8Unit1Text OBJECT-TYPE
    SYNTAX DisplayString (SIZE (0..10))
    ACCESS read-write
    STATUS mandatory
    DESCRIPTION
      "Descriptional text for sensor unit connected to port 1"
    ::= { cmcTcMasterTc8StatusSensorUnit1 2 }

  cmcTcMasterTc8Unit1Serial OBJECT-TYPE
    SYNTAX INTEGER 
    ACCESS read-only
    STATUS mandatory
    DESCRIPTION
      "Serialnumber of sensor unit connected to port 1"
    ::= { cmcTcMasterTc8StatusSensorUnit1 3 }

  cmcTcMasterTc8Unit1Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 1
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc8StatusSensorUnit1 4 }

-- Sensors
              
  cmcTcMasterTc8Unit1NumberOfSensors OBJECT-TYPE
    SYNTAX INTEGER 
    ACCESS read-only
    STATUS mandatory
    DESCRIPTION
      "Number of sensors connected to sensor unit 1"
    ::= { cmcTcMasterTc8StatusUnit1Sensors 1 }

-- table with entry for each sensor available on this unit              

  cmcTcMasterTc8Unit1SensorTable OBJECT-TYPE
    SYNTAX SEQUENCE OF CmcTcMasterTc8Unit1SensorEntry
    ACCESS not-accessible
    STATUS mandatory
    DESCRIPTION
      "Headline of sensor table"
    ::= { cmcTcMasterTc8StatusUnit1Sensors 2 }

  cmcTcMasterTc8Unit1SensorEntry OBJECT-TYPE
    SYNTAX CmcTcMasterTc8Unit1SensorEntry
    ACCESS not-accessible
    STATUS mandatory
    DESCRIPTION
      "Entries of sensor table"
    INDEX { cmcTcMasterTc8Unit1SensorIndex }
    ::= { cmcTcMasterTc8Unit1SensorTable 1 }

    CmcTcMasterTc8Unit1SensorEntry ::=
      SEQUENCE {
        cmcTcMasterTc8Unit1SensorIndex
          INTEGER,
        cmcTcMasterTc8Unit1SensorType
          INTEGER,
        cmcTcMasterTc8Unit1SensorText
          DisplayString (SIZE (0..20)),                
        cmcTcMasterTc8Unit1SensorStatus
          INTEGER,
        cmcTcMasterTc8Unit1SensorValue
          INTEGER,
        cmcTcMasterTc8Unit1SensorSetHigh
          INTEGER,
        cmcTcMasterTc8Unit1SensorSetLow
          INTEGER,
        cmcTcMasterTc8Unit1SensorSetWarn
          INTEGER                
      }

    cmcTcMasterTc8Unit1SensorIndex OBJECT-TYPE
      SYNTAX INTEGER (1..32000)
      ACCESS read-only
      STATUS mandatory
      DESCRIPTION
        "Index for the list of value entries. Its value ranges
         between 1 and the value of cmcTcMasterTc8Unit1NumberOfSensors." 
      ::= { cmcTcMasterTc8Unit1SensorEntry 1 }

    cmcTcMasterTc8Unit1SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 1 to sensor[cmcTcMasterTc8Unit1SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc8Unit1SensorEntry 2 }

    cmcTcMasterTc8Unit1SensorText OBJECT-TYPE
      SYNTAX DisplayString (SIZE (0..20))
      ACCESS read-write
      STATUS mandatory
      DESCRIPTION
        "Descriptional text for each sensor (entry in the table)"
      ::= { cmcTcMasterTc8Unit1SensorEntry 3 }
              
    cmcTcMasterTc8Unit1SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc8Unit1SensorEntry 4 }

    cmcTcMasterTc8Unit1SensorValue OBJECT-TYPE
      SYNTAX INTEGER 
      ACCESS read-only
      STATUS mandatory
      DESCRIPTION
        "Value of sensor"
      ::= { cmcTcMasterTc8Unit1SensorEntry 5 }

    cmcTcMasterTc8Unit1SensorSetHigh OBJECT-TYPE
      SYNTAX INTEGER (0..300) 
      ACCESS read-write
      STATUS mandatory
      DESCRIPTION
        "Value for high setpoint of sensor"
      ::= { cmcTcMasterTc8Unit1SensorEntry 6 }

    cmcTcMasterTc8Unit1SensorSetLow OBJECT-TYPE
      SYNTAX INTEGER (0..300) 
      ACCESS read-write
      STATUS mandatory
      DESCRIPTION
        "Value for low setpoint of sensor,
         also used as alarm delay"
      ::= { cmcTcMasterTc8Unit1SensorEntry 7 }

    cmcTcMasterTc8Unit1SensorSetWarn OBJECT-TYPE
      SYNTAX INTEGER (0..300) 
      ACCESS read-write
      STATUS mandatory
      DESCRIPTION
        "Value for warning setpoint of sensor, 
         also used as fan threshold"
      ::= { cmcTcMasterTc8Unit1SensorEntry 8 }
                
-- Outputs              

  cmcTcMasterTc8Unit1NumberOfOutputs OBJECT-TYPE
    SYNTAX INTEGER 
    ACCESS read-only
    STATUS mandatory
    DESCRIPTION
      "Number of outputs available on sensor unit 1"
    ::= { cmcTcMasterTc8StatusUnit1Outputs 1 }

-- table with entry for each output available on this unit              
                
  cmcTcMasterTc8Unit1OutputTable OBJECT-TYPE
    SYNTAX SEQUENCE OF CmcTcMasterTc8Unit1OutputEntry
    ACCESS not-accessible
    STATUS mandatory
    DESCRIPTION
      "Headline of output table"
    ::= { cmcTcMasterTc8StatusUnit1Outputs 2 }

  cmcTcMasterTc8Unit1OutputEntry OBJECT-TYPE
    SYNTAX CmcTcMasterTc8Unit1OutputEntry
    ACCESS not-accessible
    STATUS mandatory
    DESCRIPTION
      "Entries of output table"
    INDEX { cmcTcMasterTc8Unit1OutputIndex }
    ::= { cmcTcMasterTc8Unit1OutputTable 1 }

    CmcTcMasterTc8Unit1OutputEntry ::=
      SEQUENCE {
        cmcTcMasterTc8Unit1OutputIndex
          INTEGER,
        cmcTcMasterTc8Unit1OutputType
          INTEGER,
        cmcTcMasterTc8Unit1OutputText
          DisplayString (SIZE (0..20)),                
        cmcTcMasterTc8Unit1OutputStatus
          INTEGER,
        cmcTcMasterTc8Unit1OutputValue
          INTEGER,
        cmcTcMasterTc8Unit1OutputSet
          INTEGER,
        cmcTcMasterTc8Unit1OutputConfig
          INTEGER,                
        cmcTcMasterTc8Unit1OutputDelay
          INTEGER,
        cmcTcMasterTc8Unit1OutputTimeoutAction
          INTEGER
      }

    cmcTcMasterTc8Unit1OutputIndex OBJECT-TYPE
      SYNTAX INTEGER (1..32000)
      ACCESS read-only
      STATUS mandatory
      DESCRIPTION
        "Index for the list of output entries. Its value ranges
         between 1 and the value of cmcTcMasterTc8Unit1NumberOfOutputs." 
      ::= { cmcTcMasterTc8Unit1OutputEntry 1 }

    cmcTcMasterTc8Unit1OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 1 to output[cmcTcMasterTc8Unit1OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc8Unit1OutputEntry 2 }

    cmcTcMasterTc8Unit1OutputText OBJECT-TYPE
      SYNTAX DisplayString (SIZE (0..20))
      ACCESS read-write
      STATUS mandatory
      DESCRIPTION
        "Descriptional text for each output (entry in the table)"
      ::= { cmcTcMasterTc8Unit1OutputEntry 3 }
              
    cmcTcMasterTc8Unit1OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc8Unit1OutputEntry 4 }

    cmcTcMasterTc8Unit1OutputValue OBJECT-TYPE
      SYNTAX INTEGER (-32000..32000) 
      ACCESS read-write
      STATUS mandatory
      DESCRIPTION
        "Value for output"
      ::= { cmcTcMasterTc8Unit1OutputEntry 5 }

    cmcTcMasterTc8Unit1OutputSet OBJECT-TYPE
      SYNTAX INTEGER {
        off (1),
        on (2),
        lock (3),
        unlock (4),
        unlockDelay (5)
      }
      ACCESS read-write
      STATUS mandatory
      DESCRIPTION
        "Command for output"
      ::= { cmcTcMasterTc8Unit1OutputEntry 6 }

    cmcTcMasterTc8Unit1OutputConfig OBJECT-TYPE
      SYNTAX INTEGER {
        disRemote (1),
        enRemote (2)
      }
      ACCESS read-write
      STATUS mandatory
      DESCRIPTION
        "Configuration for output
         1: 	disable remote control (e.g. keypad)
         2: 	enable remote control"
      ::= { cmcTcMasterTc8Unit1OutputEntry 7 }

    cmcTcMasterTc8Unit1OutputDelay OBJECT-TYPE
      SYNTAX INTEGER (0..999) 
      ACCESS read-write
      STATUS mandatory
      DESCRIPTION
        "Unsigned Value for delay, 
         after this time the output will fall into the previous state"
      ::= { cmcTcMasterTc8Unit1OutputEntry 8 }

    cmcTcMasterTc8Unit1OutputTimeoutAction OBJECT-TYPE
      SYNTAX INTEGER {
        stay (1),
        off (2),
        on (3)
      }
      ACCESS read-write
      STATUS mandatory
      DESCRIPTION
        "State for output if timeout (RS422) occurs"
      ::= { cmcTcMasterTc8Unit1OutputEntry 9 }
 
-- Messages
              
  cmcTcMasterTc8Unit1NumberOfMsgs OBJECT-TYPE
    SYNTAX INTEGER 
    ACCESS read-only
    STATUS mandatory
    DESCRIPTION
      "Number of messages that can be created with sensor unit 1"
    ::= { cmcTcMasterTc8StatusUnit1Msg 1 }

-- table with entry for each alarm available on this unit               
                
  cmcTcMasterTc8Unit1MsgTable OBJECT-TYPE
    SYNTAX SEQUENCE OF CmcTcMasterTc8Unit1MsgEntry
    ACCESS not-accessible
    STATUS mandatory
    DESCRIPTION
      "Headline of message table"
    ::= { cmcTcMasterTc8StatusUnit1Msg 2 }

  cmcTcMasterTc8Unit1MsgEntry OBJECT-TYPE
    SYNTAX CmcTcMasterTc8Unit1MsgEntry
    ACCESS not-accessible
    STATUS mandatory
    DESCRIPTION
      "Entries of message table"
    INDEX { cmcTcMasterTc8Unit1MsgIndex }
    ::= { cmcTcMasterTc8Unit1MsgTable 1 }

    CmcTcMasterTc8Unit1MsgEntry ::=
      SEQUENCE {
        cmcTcMasterTc8Unit1MsgIndex
          INTEGER, 
        cmcTcMasterTc8Unit1MsgText
          DisplayString (SIZE (0..20)),                
        cmcTcMasterTc8Unit1MsgStatus
          INTEGER,                
        cmcTcMasterTc8Unit1MsgRelay
          INTEGER,
        cmcTcMasterTc8Unit1MsgBeeper
          INTEGER,
        cmcTcMasterTc8Unit1MsgTrap1
          INTEGER,
        cmcTcMasterTc8Unit1MsgTrap2
          INTEGER,
        cmcTcMasterTc8Unit1MsgTrap3
          INTEGER,
        cmcTcMasterTc8Unit1MsgTrap4
          INTEGER,                 
        cmcTcMasterTc8Unit1MsgQuit
          INTEGER              
      }

    cmcTcMasterTc8Unit1MsgIndex OBJECT-TYPE
      SYNTAX INTEGER (1..32000)
      ACCESS read-only
      STATUS mandatory
      DESCRIPTION
        "Index for the list of message entries. Its value ranges
         between 1 and the value of cmcTcMasterTc8Unit1NumberOfMsgs." 
      ::= { cmcTcMasterTc8Unit1MsgEntry 1 }

    cmcTcMasterTc8Unit1MsgText OBJECT-TYPE
      SYNTAX DisplayString (SIZE (0..20))
      ACCESS read-write
      STATUS mandatory
      DESCRIPTION
        "Descriptional text for each message (entry in the table)"
      ::= { cmcTcMasterTc8Unit1MsgEntry 2 }
              
    cmcTcMasterTc8Unit1MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc8Unit1OutputSet)
         17: door is unlocked by WEB
         18: door is unlocked by timer
         19: no access, wrong keycode or cardnumber
         20: orientation of PSM-Unit is circuit 1
         21: orientation of PSM-Unit is circuit 2"
      ::= { cmcTcMasterTc8Unit1MsgEntry 3 }
        
    cmcTcMasterTc8Unit1MsgRelay OBJECT-TYPE
      SYNTAX INTEGER {
        disable (1),
        enable (2)
      }
      ACCESS read-write
      STATUS mandatory
      DESCRIPTION
        "Setup of Alarm relay for this message/alarm
         1:        no switching of alarm relay             
         2:        switching of alarm relay" 
      ::= { cmcTcMasterTc8Unit1MsgEntry 4 }

    cmcTcMasterTc8Unit1MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc8Unit1MsgEntry 5 }

    cmcTcMasterTc8Unit1MsgTrap1 OBJECT-TYPE
      SYNTAX INTEGER {
        disable (1),
        enable (2)
      }
      ACCESS read-write
      STATUS mandatory
      DESCRIPTION
        "Trap receiver 1 activated"
      ::= { cmcTcMasterTc8Unit1MsgEntry 6 }

    cmcTcMasterTc8Unit1MsgTrap2 OBJECT-TYPE
      SYNTAX INTEGER {
        disable (1),
        enable (2)
      }
      ACCESS read-write
      STATUS mandatory
      DESCRIPTION
        "Trap receiver 2 activated"
      ::= { cmcTcMasterTc8Unit1MsgEntry 7 }
 
    cmcTcMasterTc8Unit1MsgTrap3 OBJECT-TYPE
      SYNTAX INTEGER {
        disable (1),
        enable (2)
      }
      ACCESS read-write
      STATUS mandatory
      DESCRIPTION
        "Trap receiver 3 activated"
      ::= { cmcTcMasterTc8Unit1MsgEntry 8 }

    cmcTcMasterTc8Unit1MsgTrap4 OBJECT-TYPE
      SYNTAX INTEGER {
        disable (1),
        enable (2)
      }
      ACCESS read-write
      STATUS mandatory
      DESCRIPTION
        "Trap receiver 4 and Event Logging activated"
      ::= { cmcTcMasterTc8Unit1MsgEntry 9 }

    cmcTcMasterTc8Unit1MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc8Unit1MsgEntry 10 }

-- unit2

  cmcTcMasterTc8Unit2TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 2"
    ::= { cmcTcMasterTc8StatusSensorUnit2 1 }

  cmcTcMasterTc8Unit2Text OBJECT-TYPE
    SYNTAX DisplayString (SIZE (0..10))
    ACCESS read-write
    STATUS mandatory
    DESCRIPTION
      "Descriptional text for sensor unit connected to port 2"
    ::= { cmcTcMasterTc8StatusSensorUnit2 2 }

  cmcTcMasterTc8Unit2Serial OBJECT-TYPE
    SYNTAX INTEGER 
    ACCESS read-only
    STATUS mandatory
    DESCRIPTION
      "Serialnumber of sensor unit connected to port 2"
    ::= { cmcTcMasterTc8StatusSensorUnit2 3 }

  cmcTcMasterTc8Unit2Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 2
       (1) OK
       (2) error
       (3) configuration of sensor unit has changed, confirmation required
       (4) Quit from sensor unit to confirm configuration changes
       (5) timeout of sensor unit, confirmation required
       (6) sensor unit detected, needs to be confirmed
       (8) supply voltage is too low"              
    ::= { cmcTcMasterTc8StatusSensorUnit2 4 }

-- unit 2 table

-- Sensors              

  cmcTcMasterTc8Unit2NumberOfSensors OBJECT-TYPE
    SYNTAX INTEGER 
    ACCESS read-only
    STATUS mandatory
    DESCRIPTION
      "Number of sensors connected to sensor unit 2"
    ::= { cmcTcMasterTc8StatusUnit2Sensors 1 }

-- table with entry for each sensor available on this unit              

  cmcTcMasterTc8Unit2SensorTable OBJECT-TYPE
    SYNTAX SEQUENCE OF CmcTcMasterTc8Unit2SensorEntry
    ACCESS not-accessible
    STATUS mandatory
    DESCRIPTION
      "Headline of sensor table"
    ::= { cmcTcMasterTc8StatusUnit2Sensors 2 }

  cmcTcMasterTc8Unit2SensorEntry OBJECT-TYPE
    SYNTAX CmcTcMasterTc8Unit2SensorEntry
    ACCESS not-accessible
    STATUS mandatory
    DESCRIPTION
      "Entries of sensor table"
    INDEX { cmcTcMasterTc8Unit2SensorIndex }
    ::= { cmcTcMasterTc8Unit2SensorTable 1 }

    CmcTcMasterTc8Unit2SensorEntry ::=
      SEQUENCE {
        cmcTcMasterTc8Unit2SensorIndex
          INTEGER,
        cmcTcMasterTc8Unit2SensorType
          INTEGER,
        cmcTcMasterTc8Unit2SensorText
          DisplayString (SIZE (0..20)),                
        cmcTcMasterTc8Unit2SensorStatus
          INTEGER,
        cmcTcMasterTc8Unit2SensorValue
          INTEGER,
        cmcTcMasterTc8Unit2SensorSetHigh
          INTEGER,
        cmcTcMasterTc8Unit2SensorSetLow
          INTEGER,                 
        cmcTcMasterTc8Unit2SensorSetWarn
          INTEGER  
      }

    cmcTcMasterTc8Unit2SensorIndex OBJECT-TYPE
      SYNTAX INTEGER (1..32000)
      ACCESS read-only
      STATUS mandatory
      DESCRIPTION
        "Index for the list of value entries. Its value ranges
         between 1 and the value of cmcTcMasterTc8Unit2NumberOfSensors." 
      ::= { cmcTcMasterTc8Unit2SensorEntry 1 }

    cmcTcMasterTc8Unit2SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 2 to sensor[cmcTcMasterTc8Unit2SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc8Unit2SensorEntry 2 }
        
    cmcTcMasterTc8Unit2SensorText OBJECT-TYPE
      SYNTAX DisplayString (SIZE (0..20))
      ACCESS read-write
      STATUS mandatory
      DESCRIPTION
        "Descriptional text for each sensor (entry in the table)"
      ::= { cmcTcMasterTc8Unit2SensorEntry 3 }
              
    cmcTcMasterTc8Unit2SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc8Unit2SensorEntry 4 }

    cmcTcMasterTc8Unit2SensorValue OBJECT-TYPE
      SYNTAX INTEGER 
      ACCESS read-only
      STATUS mandatory
      DESCRIPTION
        "Value of sensor"
      ::= { cmcTcMasterTc8Unit2SensorEntry 5 }

    cmcTcMasterTc8Unit2SensorSetHigh OBJECT-TYPE
      SYNTAX INTEGER (0..300) 
      ACCESS read-write
      STATUS mandatory
      DESCRIPTION
        "Value for high setpoint of sensor"
      ::= { cmcTcMasterTc8Unit2SensorEntry 6 }

    cmcTcMasterTc8Unit2SensorSetLow OBJECT-TYPE
      SYNTAX INTEGER (0..300) 
      ACCESS read-write
      STATUS mandatory
      DESCRIPTION
        "Value for low setpoint of sensor,
         also used as alarm delay"
      ::= { cmcTcMasterTc8Unit2SensorEntry 7 }

    cmcTcMasterTc8Unit2SensorSetWarn OBJECT-TYPE
      SYNTAX INTEGER (0..300) 
      ACCESS read-write
      STATUS mandatory
      DESCRIPTION
        "Value for warning setpoint of sensor,
         also used as fan threshold"
      ::= { cmcTcMasterTc8Unit2SensorEntry 8 }

-- Outputs              

  cmcTcMasterTc8Unit2NumberOfOutputs OBJECT-TYPE
    SYNTAX INTEGER 
    ACCESS read-only
    STATUS mandatory
    DESCRIPTION
      "Number of outputs available on sensor unit 2"
    ::= { cmcTcMasterTc8StatusUnit2Outputs 1 }

-- table with entry for each output available on this unit              
                
  cmcTcMasterTc8Unit2OutputTable OBJECT-TYPE
    SYNTAX SEQUENCE OF CmcTcMasterTc8Unit2OutputEntry
    ACCESS not-accessible
    STATUS mandatory
    DESCRIPTION
      "Headline of output table"
    ::= { cmcTcMasterTc8StatusUnit2Outputs 2 }

  cmcTcMasterTc8Unit2OutputEntry OBJECT-TYPE
    SYNTAX CmcTcMasterTc8Unit2OutputEntry
    ACCESS not-accessible
    STATUS mandatory
    DESCRIPTION
      "Entries of output table"
    INDEX { cmcTcMasterTc8Unit2OutputIndex }
    ::= { cmcTcMasterTc8Unit2OutputTable 1 }

    CmcTcMasterTc8Unit2OutputEntry ::=
      SEQUENCE {
        cmcTcMasterTc8Unit2OutputIndex
          INTEGER,
        cmcTcMasterTc8Unit2OutputType
          INTEGER,
        cmcTcMasterTc8Unit2OutputText
          DisplayString (SIZE (0..20)),                
        cmcTcMasterTc8Unit2OutputStatus
          INTEGER,
        cmcTcMasterTc8Unit2OutputValue
          INTEGER,
        cmcTcMasterTc8Unit2OutputSet
          INTEGER,
        cmcTcMasterTc8Unit2OutputConfig
          INTEGER,                
        cmcTcMasterTc8Unit2OutputDelay
          INTEGER,
        cmcTcMasterTc8Unit2OutputTimeoutAction
          INTEGER
      }

    cmcTcMasterTc8Unit2OutputIndex OBJECT-TYPE
      SYNTAX INTEGER (1..32000)
      ACCESS read-only
      STATUS mandatory
      DESCRIPTION
        "Index for the list of output entries. Its value ranges
         between 1 and the value of cmcTcMasterTc8Unit2NumberOfOutputs." 
      ::= { cmcTcMasterTc8Unit2OutputEntry 1 }

    cmcTcMasterTc8Unit2OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 2 to output[cmcTcMasterTc8Unit2OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc8Unit2OutputEntry 2 }

        
    cmcTcMasterTc8Unit2OutputText OBJECT-TYPE
      SYNTAX DisplayString (SIZE (0..20))
      ACCESS read-write
      STATUS mandatory
      DESCRIPTION
        "Descriptional text for each output (entry in the table)"
      ::= { cmcTcMasterTc8Unit2OutputEntry 3 }
              
    cmcTcMasterTc8Unit2OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc8Unit2OutputEntry 4 }

    cmcTcMasterTc8Unit2OutputValue OBJECT-TYPE
      SYNTAX INTEGER (-32000..32000) 
      ACCESS read-write
      STATUS mandatory
      DESCRIPTION
        "Value for output"
      ::= { cmcTcMasterTc8Unit2OutputEntry 5 }

    cmcTcMasterTc8Unit2OutputSet OBJECT-TYPE
      SYNTAX INTEGER {
        off (1),
        on (2),
        lock (3),
        unlock (4),
        unlockDelay (5)
      }
      ACCESS read-write
      STATUS mandatory
      DESCRIPTION
        "Command for output"
      ::= { cmcTcMasterTc8Unit2OutputEntry 6 }

    cmcTcMasterTc8Unit2OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc8Unit2OutputEntry 7 }

    cmcTcMasterTc8Unit2OutputDelay OBJECT-TYPE
      SYNTAX INTEGER (0..999) 
      ACCESS read-write
      STATUS mandatory
      DESCRIPTION
        "Unsigned Value for delay, 
         after this time the output will fall into the previous state"
      ::= { cmcTcMasterTc8Unit2OutputEntry 8 }

    cmcTcMasterTc8Unit2OutputTimeoutAction OBJECT-TYPE
      SYNTAX INTEGER {
        stay (1),
        off (2),
        on (3)
      }
      ACCESS read-write
      STATUS mandatory
      DESCRIPTION
        "State for output if timeout (RS422) occurs"
      ::= { cmcTcMasterTc8Unit2OutputEntry 9 }

-- Messages
              
  cmcTcMasterTc8Unit2NumberOfMsgs OBJECT-TYPE
    SYNTAX INTEGER 
    ACCESS read-only
    STATUS mandatory
    DESCRIPTION
      "Number of messages that can be created with sensor unit 2"
    ::= { cmcTcMasterTc8StatusUnit2Msg 1 }

-- table with entry for each alarm available on this unit               
                
  cmcTcMasterTc8Unit2MsgTable OBJECT-TYPE
    SYNTAX SEQUENCE OF CmcTcMasterTc8Unit2MsgEntry
    ACCESS not-accessible
    STATUS mandatory
    DESCRIPTION
      "Headline of message table"
    ::= { cmcTcMasterTc8StatusUnit2Msg 2 }

  cmcTcMasterTc8Unit2MsgEntry OBJECT-TYPE
    SYNTAX CmcTcMasterTc8Unit2MsgEntry
    ACCESS not-accessible
    STATUS mandatory
    DESCRIPTION
      "Entries of message table"
    INDEX { cmcTcMasterTc8Unit2MsgIndex }
    ::= { cmcTcMasterTc8Unit2MsgTable 1 }

    CmcTcMasterTc8Unit2MsgEntry ::=
      SEQUENCE {
        cmcTcMasterTc8Unit2MsgIndex
          INTEGER,
        cmcTcMasterTc8Unit2MsgText
          DisplayString (SIZE (0..20)),
        cmcTcMasterTc8Unit2MsgStatus
          INTEGER, 
        cmcTcMasterTc8Unit2MsgRelay
          INTEGER,
        cmcTcMasterTc8Unit2MsgBeeper
          INTEGER,
        cmcTcMasterTc8Unit2MsgTrap1
          INTEGER,
        cmcTcMasterTc8Unit2MsgTrap2
          INTEGER,
        cmcTcMasterTc8Unit2MsgTrap3
          INTEGER,
        cmcTcMasterTc8Unit2MsgTrap4
          INTEGER,                 
        cmcTcMasterTc8Unit2MsgQuit
          INTEGER              
      }

    cmcTcMasterTc8Unit2MsgIndex OBJECT-TYPE
      SYNTAX INTEGER (1..32000)
      ACCESS read-only
      STATUS mandatory
      DESCRIPTION
        "Index for the list of message entries. Its value ranges
         between 1 and the value of cmcTcMasterTc8Unit2NumberOfMsgs." 
      ::= { cmcTcMasterTc8Unit2MsgEntry 1 }

    cmcTcMasterTc8Unit2MsgText OBJECT-TYPE
      SYNTAX DisplayString (SIZE (0..20))
      ACCESS read-write
      STATUS mandatory
      DESCRIPTION
        "Descriptional text for each message (entry in the table)"
      ::= { cmcTcMasterTc8Unit2MsgEntry 2 }

    cmcTcMasterTc8Unit2MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc8Unit2OutputSet)
         17: door is unlocked by WEB
         18: door is unlocked by timer
         19: no access, wrong keycode or cardnumber
         20: orientation of PSM-Unit is circuit 1
         21: orientation of PSM-Unit is circuit 2"
      ::= { cmcTcMasterTc8Unit2MsgEntry 3 }

    cmcTcMasterTc8Unit2MsgRelay OBJECT-TYPE
      SYNTAX INTEGER {
        disable (1),
        enable (2)
      }
      ACCESS read-write
      STATUS mandatory
      DESCRIPTION
        "Setup of Alarm relay for this alarm
         2:        no switching of alarm relay             
         1:        switching of alarm relay" 
      ::= { cmcTcMasterTc8Unit2MsgEntry 4 }

    cmcTcMasterTc8Unit2MsgBeeper OBJECT-TYPE
      SYNTAX INTEGER {
        disable (1),
        enable (2)
      }
      ACCESS read-write
      STATUS mandatory
      DESCRIPTION
        "Setup of Alarm beeper for this alarm
         2:        no audible alarm
         1:        audible alarm" 
      ::= { cmcTcMasterTc8Unit2MsgEntry 5 }

    cmcTcMasterTc8Unit2MsgTrap1 OBJECT-TYPE
      SYNTAX INTEGER {
        disable (1),
        enable (2)
      }
      ACCESS read-write
      STATUS mandatory
      DESCRIPTION
        "Trap receiver 1 activated"
      ::= { cmcTcMasterTc8Unit2MsgEntry 6 }

    cmcTcMasterTc8Unit2MsgTrap2 OBJECT-TYPE
      SYNTAX INTEGER {
        disable (1),
        enable (2)
      }
      ACCESS read-write
      STATUS mandatory
      DESCRIPTION
        "Trap receiver 2 activated"
      ::= { cmcTcMasterTc8Unit2MsgEntry 7 }
 
    cmcTcMasterTc8Unit2MsgTrap3 OBJECT-TYPE
      SYNTAX INTEGER {
        disable (1),
        enable (2)
      }
      ACCESS read-write
      STATUS mandatory
      DESCRIPTION
        "Trap receiver 3 activated"
      ::= { cmcTcMasterTc8Unit2MsgEntry 8 }

    cmcTcMasterTc8Unit2MsgTrap4 OBJECT-TYPE
      SYNTAX INTEGER {
        disable (1),
        enable (2)
      }
      ACCESS read-write
      STATUS mandatory
      DESCRIPTION
        "Trap receiver 4 and Event Logging activated"
      ::= { cmcTcMasterTc8Unit2MsgEntry 9 }

    cmcTcMasterTc8Unit2MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc8Unit2MsgEntry 10 }

-- unit 3
  cmcTcMasterTc8Unit3TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 3"
    ::= { cmcTcMasterTc8StatusSensorUnit3 1 }

  cmcTcMasterTc8Unit3Text OBJECT-TYPE
    SYNTAX DisplayString (SIZE (0..10))
    ACCESS read-write
    STATUS mandatory
    DESCRIPTION
      "Descriptional text for sensor unit connected to port 3"
    ::= { cmcTcMasterTc8StatusSensorUnit3 2 }

  cmcTcMasterTc8Unit3Serial OBJECT-TYPE
    SYNTAX INTEGER 
    ACCESS  read-only
    STATUS  mandatory
    DESCRIPTION
      "Serialnumber of sensor unit connected to port 3"
    ::= { cmcTcMasterTc8StatusSensorUnit3 3 }

  cmcTcMasterTc8Unit3Status OBJECT-TYPE
    SYNTAX INTEGER {
      ok(1),
      error(2),
      changed(3),
      quit(4),
      timeout(5),
      detected(6),
      notAvail(7),
      lowPower(8)
    }
    ACCESS  read-only
    STATUS  mandatory
    DESCRIPTION
      "General Status sensor unit connected to port 3
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc8StatusSensorUnit3 4 }

-- Sensors              

  cmcTcMasterTc8Unit3NumberOfSensors OBJECT-TYPE
    SYNTAX INTEGER 
    ACCESS read-only
    STATUS mandatory
    DESCRIPTION
      "Number of sensors connected to sensor unit 3"
    ::= { cmcTcMasterTc8StatusUnit3Sensors 1 }

-- table with entry for each sensor available on this unit              
        
  cmcTcMasterTc8Unit3SensorTable OBJECT-TYPE
    SYNTAX SEQUENCE OF CmcTcMasterTc8Unit3SensorEntry
    ACCESS not-accessible
    STATUS mandatory
    DESCRIPTION
      "Headline of sensor table"
    ::= { cmcTcMasterTc8StatusUnit3Sensors 2 }

  cmcTcMasterTc8Unit3SensorEntry OBJECT-TYPE
    SYNTAX CmcTcMasterTc8Unit3SensorEntry
    ACCESS not-accessible
    STATUS mandatory
    DESCRIPTION
      "Entries of sensor table"
    INDEX { cmcTcMasterTc8Unit3SensorIndex }
    ::= { cmcTcMasterTc8Unit3SensorTable 1 }

    CmcTcMasterTc8Unit3SensorEntry ::=
      SEQUENCE {
        cmcTcMasterTc8Unit3SensorIndex
          INTEGER,
        cmcTcMasterTc8Unit3SensorType
          INTEGER,
        cmcTcMasterTc8Unit3SensorText
          DisplayString (SIZE (0..20)),                
        cmcTcMasterTc8Unit3SensorStatus
          INTEGER,
        cmcTcMasterTc8Unit3SensorValue
          INTEGER,
        cmcTcMasterTc8Unit3SensorSetHigh
          INTEGER,
        cmcTcMasterTc8Unit3SensorSetLow
          INTEGER,                 
        cmcTcMasterTc8Unit3SensorSetWarn
          INTEGER  
      }

    cmcTcMasterTc8Unit3SensorIndex OBJECT-TYPE
      SYNTAX INTEGER (1..32000)
      ACCESS read-only
      STATUS mandatory
      DESCRIPTION
        "Index for the list of value entries. Its value ranges
         between 1 and the value of cmcTcMasterTc8Unit3NumberOfSensors." 
      ::= { cmcTcMasterTc8Unit3SensorEntry 1 }

    cmcTcMasterTc8Unit3SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 3 to sensor[cmcTcMasterTc8Unit3SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc8Unit3SensorEntry 2 }

    cmcTcMasterTc8Unit3SensorText OBJECT-TYPE
      SYNTAX DisplayString (SIZE (0..20))
      ACCESS read-write
      STATUS mandatory
      DESCRIPTION
        "Descriptional text for each sensor (entry in the table)"
      ::= { cmcTcMasterTc8Unit3SensorEntry 3 }
              
    cmcTcMasterTc8Unit3SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc8Unit3SensorEntry 4 }

    cmcTcMasterTc8Unit3SensorValue OBJECT-TYPE
      SYNTAX INTEGER 
      ACCESS read-only
      STATUS mandatory
      DESCRIPTION
        "Value of sensor"
      ::= { cmcTcMasterTc8Unit3SensorEntry 5 }

    cmcTcMasterTc8Unit3SensorSetHigh OBJECT-TYPE
      SYNTAX INTEGER (0..300) 
      ACCESS read-write
      STATUS mandatory
      DESCRIPTION
        "Value for high setpoint of sensor"
      ::= { cmcTcMasterTc8Unit3SensorEntry 6 }

    cmcTcMasterTc8Unit3SensorSetLow OBJECT-TYPE
      SYNTAX INTEGER (0..300) 
      ACCESS read-write
      STATUS mandatory
      DESCRIPTION
        "Value for low setpoint of sensor,
         also used as alarm delay"
      ::= { cmcTcMasterTc8Unit3SensorEntry 7 }

    cmcTcMasterTc8Unit3SensorSetWarn OBJECT-TYPE
      SYNTAX INTEGER (0..300) 
      ACCESS read-write
      STATUS mandatory
      DESCRIPTION
        "Value for warning setpoint of sensor,
         also used as fan threshold"
      ::= { cmcTcMasterTc8Unit3SensorEntry 8 }
                
-- Outputs              

  cmcTcMasterTc8Unit3NumberOfOutputs OBJECT-TYPE
    SYNTAX INTEGER 
    ACCESS read-only
    STATUS mandatory
    DESCRIPTION
      "Number of outputs available on sensor unit 3"
    ::= { cmcTcMasterTc8StatusUnit3Outputs 1 }

-- table with entry for each output available on this unit              
                
  cmcTcMasterTc8Unit3OutputTable OBJECT-TYPE
    SYNTAX SEQUENCE OF CmcTcMasterTc8Unit3OutputEntry
    ACCESS not-accessible
    STATUS mandatory
    DESCRIPTION
      "Headline of output table"
    ::= { cmcTcMasterTc8StatusUnit3Outputs 2 }

  cmcTcMasterTc8Unit3OutputEntry OBJECT-TYPE
    SYNTAX CmcTcMasterTc8Unit3OutputEntry
    ACCESS not-accessible
    STATUS mandatory
    DESCRIPTION
      "Entries of output table"
    INDEX { cmcTcMasterTc8Unit3OutputIndex }
    ::= { cmcTcMasterTc8Unit3OutputTable 1 }

    CmcTcMasterTc8Unit3OutputEntry ::=
      SEQUENCE {
        cmcTcMasterTc8Unit3OutputIndex
          INTEGER,
        cmcTcMasterTc8Unit3OutputType
          INTEGER,
        cmcTcMasterTc8Unit3OutputText
          DisplayString (SIZE (0..20)),                
        cmcTcMasterTc8Unit3OutputStatus
          INTEGER,
        cmcTcMasterTc8Unit3OutputValue
          INTEGER,
        cmcTcMasterTc8Unit3OutputSet
          INTEGER,
        cmcTcMasterTc8Unit3OutputConfig
          INTEGER,
        cmcTcMasterTc8Unit3OutputDelay
          INTEGER,
        cmcTcMasterTc8Unit3OutputTimeoutAction
          INTEGER
      }

    cmcTcMasterTc8Unit3OutputIndex OBJECT-TYPE
      SYNTAX INTEGER (1..32000)
      ACCESS read-only
      STATUS mandatory
      DESCRIPTION
        "Index for the list of output entries. Its value ranges
         between 1 and the value of cmcTcMasterTc8Unit3NumberOfOutputs." 
      ::= { cmcTcMasterTc8Unit3OutputEntry 1 }

    cmcTcMasterTc8Unit3OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 3 to output[cmcTcMasterTc8Unit3OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc8Unit3OutputEntry 2 }

        
    cmcTcMasterTc8Unit3OutputText OBJECT-TYPE
      SYNTAX DisplayString (SIZE (0..20))
      ACCESS read-write
      STATUS mandatory
      DESCRIPTION
        "Descriptional text for each output (entry in the table)"
      ::= { cmcTcMasterTc8Unit3OutputEntry 3 }
              
    cmcTcMasterTc8Unit3OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc8Unit3OutputEntry 4 }

    cmcTcMasterTc8Unit3OutputValue OBJECT-TYPE
      SYNTAX INTEGER (-32000..32000) 
      ACCESS read-write
      STATUS mandatory
      DESCRIPTION
        "Value for output"
      ::= { cmcTcMasterTc8Unit3OutputEntry 5 }

    cmcTcMasterTc8Unit3OutputSet OBJECT-TYPE
      SYNTAX INTEGER {
        off (1),
        on (2),
        lock (3),
        unlock (4),
        unlockDelay (5)
      }
      ACCESS read-write
      STATUS mandatory
      DESCRIPTION
        "Command for output"
      ::= { cmcTcMasterTc8Unit3OutputEntry 6 }

    cmcTcMasterTc8Unit3OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc8Unit3OutputEntry 7 }

    cmcTcMasterTc8Unit3OutputDelay OBJECT-TYPE
      SYNTAX INTEGER (0..999) 
      ACCESS read-write
      STATUS mandatory
      DESCRIPTION
        "Unsigned Value for delay, 
         after this time the output will fall into the previous state"
      ::= { cmcTcMasterTc8Unit3OutputEntry 8 }

    cmcTcMasterTc8Unit3OutputTimeoutAction OBJECT-TYPE
      SYNTAX INTEGER {
        stay (1),
        off (2),
        on (3)
      }
      ACCESS read-write
      STATUS mandatory
      DESCRIPTION
        "State for output if timeout (RS422) occurs"
      ::= { cmcTcMasterTc8Unit3OutputEntry 9 }

-- Messages
              
  cmcTcMasterTc8Unit3NumberOfMsgs OBJECT-TYPE
    SYNTAX INTEGER 
    ACCESS read-only
    STATUS mandatory
    DESCRIPTION
      "Number of messages that can be created with sensor unit 3"
    ::= { cmcTcMasterTc8StatusUnit3Msg 1 }

-- table with entry for each alarm available on this unit               
                
  cmcTcMasterTc8Unit3MsgTable OBJECT-TYPE
    SYNTAX SEQUENCE OF CmcTcMasterTc8Unit3MsgEntry
    ACCESS not-accessible
    STATUS mandatory
    DESCRIPTION
      "Headline of message table"
    ::= { cmcTcMasterTc8StatusUnit3Msg 2 }

  cmcTcMasterTc8Unit3MsgEntry OBJECT-TYPE
    SYNTAX CmcTcMasterTc8Unit3MsgEntry
    ACCESS not-accessible
    STATUS mandatory
    DESCRIPTION
      "Entries of message table"
    INDEX { cmcTcMasterTc8Unit3MsgIndex }
    ::= { cmcTcMasterTc8Unit3MsgTable 1 }

    CmcTcMasterTc8Unit3MsgEntry ::=
      SEQUENCE {
        cmcTcMasterTc8Unit3MsgIndex
          INTEGER,
        cmcTcMasterTc8Unit3MsgText
          DisplayString (SIZE (0..20)),
        cmcTcMasterTc8Unit3MsgStatus
          INTEGER, 
        cmcTcMasterTc8Unit3MsgRelay
          INTEGER,
        cmcTcMasterTc8Unit3MsgBeeper
          INTEGER,
        cmcTcMasterTc8Unit3MsgTrap1
          INTEGER,
        cmcTcMasterTc8Unit3MsgTrap2
          INTEGER,
        cmcTcMasterTc8Unit3MsgTrap3
          INTEGER,
        cmcTcMasterTc8Unit3MsgTrap4
          INTEGER,                 
        cmcTcMasterTc8Unit3MsgQuit
          INTEGER              
      }

    cmcTcMasterTc8Unit3MsgIndex OBJECT-TYPE
      SYNTAX INTEGER (1..32000)
      ACCESS read-only
      STATUS mandatory
      DESCRIPTION
        "Index for the list of message entries. Its value ranges
         between 1 and the value of cmcTcMasterTc8Unit3NumberOfMsgs." 
      ::= { cmcTcMasterTc8Unit3MsgEntry 1 }

    cmcTcMasterTc8Unit3MsgText OBJECT-TYPE
      SYNTAX DisplayString (SIZE (0..20))
      ACCESS read-write
      STATUS mandatory
      DESCRIPTION
        "Descriptional text for each message (entry in the table)"
      ::= { cmcTcMasterTc8Unit3MsgEntry 2 }

    cmcTcMasterTc8Unit3MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc8Unit3OutputSet)
         17: door is unlocked by WEB
         18: door is unlocked by timer
         19: no access, wrong keycode or cardnumber
         20: orientation of PSM-Unit is circuit 1
         21: orientation of PSM-Unit is circuit 2"
      ::= { cmcTcMasterTc8Unit3MsgEntry 3 }

    cmcTcMasterTc8Unit3MsgRelay OBJECT-TYPE
      SYNTAX INTEGER {
        disable (1),
        enable (2)
      }
      ACCESS read-write
      STATUS mandatory
      DESCRIPTION
        "Setup of Alarm relay for this alarm
         1:        no switching of alarm relay             
         2:        switching of alarm relay" 
      ::= { cmcTcMasterTc8Unit3MsgEntry 4 }

    cmcTcMasterTc8Unit3MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc8Unit3MsgEntry 5 }

    cmcTcMasterTc8Unit3MsgTrap1 OBJECT-TYPE
      SYNTAX INTEGER {
        disable (1),
        enable (2)
      }
      ACCESS read-write
      STATUS mandatory
      DESCRIPTION
        "Trap receiver 1 activated"
      ::= { cmcTcMasterTc8Unit3MsgEntry 6 }

    cmcTcMasterTc8Unit3MsgTrap2 OBJECT-TYPE
      SYNTAX INTEGER {
        disable (1),
        enable (2)
      }
      ACCESS read-write
      STATUS mandatory
      DESCRIPTION
        "Trap receiver 2 activated"
      ::= { cmcTcMasterTc8Unit3MsgEntry 7 }
 
    cmcTcMasterTc8Unit3MsgTrap3 OBJECT-TYPE
      SYNTAX INTEGER {
        disable (1),
        enable (2)
      }
      ACCESS read-write
      STATUS mandatory
      DESCRIPTION
        "Trap receiver 3 activated"
      ::= { cmcTcMasterTc8Unit3MsgEntry 8 }

    cmcTcMasterTc8Unit3MsgTrap4 OBJECT-TYPE
      SYNTAX INTEGER {
        disable (1),
        enable (2)
      }
      ACCESS read-write
      STATUS mandatory
      DESCRIPTION
        "Trap receiver 4 and Event Logging activated"
      ::= { cmcTcMasterTc8Unit3MsgEntry 9 }

    cmcTcMasterTc8Unit3MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc8Unit3MsgEntry 10 }

-- unit4

  cmcTcMasterTc8Unit4TypeOfDevice OBJECT-TYPE
    SYNTAX INTEGER {
      notAvail (1),
      unitIO (2),
      unitAccess (3),
      unitClimate (4),
      unitFCS (5),
      unitRTT (6),
      unitRLCP (7),
      unitPSM (8)
    }
    ACCESS  read-only
    STATUS  mandatory
    DESCRIPTION
      "Type of sensor unit connected to port 4"
    ::= { cmcTcMasterTc8StatusSensorUnit4 1 }

  cmcTcMasterTc8Unit4Text OBJECT-TYPE
    SYNTAX DisplayString (SIZE (0..10))
    ACCESS read-write
    STATUS mandatory
    DESCRIPTION
      "Descriptional text for sensor unit connected to port 4"
    ::= { cmcTcMasterTc8StatusSensorUnit4 2 }

  cmcTcMasterTc8Unit4Serial OBJECT-TYPE
    SYNTAX INTEGER 
    ACCESS read-only
    STATUS mandatory
    DESCRIPTION
      "Serialnumber of sensor unit connected to port 4"
    ::= { cmcTcMasterTc8StatusSensorUnit4 3 }

  cmcTcMasterTc8Unit4Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 4
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc8StatusSensorUnit4 4 }

-- Sensors
              
  cmcTcMasterTc8Unit4NumberOfSensors OBJECT-TYPE
    SYNTAX INTEGER 
    ACCESS read-only
    STATUS mandatory
    DESCRIPTION
      "Number of sensors connected to sensor unit 4"
    ::= { cmcTcMasterTc8StatusUnit4Sensors 1 }

-- table with entry for each sensor available on this unit              
                
  cmcTcMasterTc8Unit4SensorTable OBJECT-TYPE
    SYNTAX SEQUENCE OF CmcTcMasterTc8Unit4SensorEntry
    ACCESS not-accessible
    STATUS mandatory
    DESCRIPTION
      "Headline of sensor table"
    ::= { cmcTcMasterTc8StatusUnit4Sensors 2 }

  cmcTcMasterTc8Unit4SensorEntry OBJECT-TYPE
    SYNTAX CmcTcMasterTc8Unit4SensorEntry
    ACCESS not-accessible
    STATUS mandatory
    DESCRIPTION
      "Entries of sensor table"
    INDEX { cmcTcMasterTc8Unit4SensorIndex }
    ::= { cmcTcMasterTc8Unit4SensorTable 1 }

    CmcTcMasterTc8Unit4SensorEntry ::=
      SEQUENCE {
        cmcTcMasterTc8Unit4SensorIndex
          INTEGER,
        cmcTcMasterTc8Unit4SensorType
          INTEGER,
        cmcTcMasterTc8Unit4SensorText
          DisplayString (SIZE (0..20)),                
        cmcTcMasterTc8Unit4SensorStatus
          INTEGER,
        cmcTcMasterTc8Unit4SensorValue
          INTEGER,
        cmcTcMasterTc8Unit4SensorSetHigh
          INTEGER,
        cmcTcMasterTc8Unit4SensorSetLow
          INTEGER,                 
        cmcTcMasterTc8Unit4SensorSetWarn
          INTEGER  
      }

    cmcTcMasterTc8Unit4SensorIndex OBJECT-TYPE
      SYNTAX INTEGER (1..32000)
      ACCESS read-only
      STATUS mandatory
      DESCRIPTION
        "Index for the list of value entries. Its value ranges
         between 1 and the value of cmcTcMasterTc8Unit4NumberOfSensors." 
      ::= { cmcTcMasterTc8Unit4SensorEntry 1 }

    cmcTcMasterTc8Unit4SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 4 to sensor[cmcTcMasterTc8Unit4SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc8Unit4SensorEntry 2 }

    cmcTcMasterTc8Unit4SensorText OBJECT-TYPE
      SYNTAX DisplayString (SIZE (0..20))
      ACCESS read-write
      STATUS mandatory
      DESCRIPTION
        "Descriptional text for each sensor (entry in the table)"
      ::= { cmcTcMasterTc8Unit4SensorEntry 3 }
              
    cmcTcMasterTc8Unit4SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc8Unit4SensorEntry 4 }

    cmcTcMasterTc8Unit4SensorValue OBJECT-TYPE
      SYNTAX INTEGER 
      ACCESS read-only
      STATUS mandatory
      DESCRIPTION
        "Value of sensor"
      ::= { cmcTcMasterTc8Unit4SensorEntry 5 }

    cmcTcMasterTc8Unit4SensorSetHigh OBJECT-TYPE
      SYNTAX INTEGER (0..300) 
      ACCESS read-write
      STATUS mandatory
      DESCRIPTION
        "Value for high setpoint of sensor"
      ::= { cmcTcMasterTc8Unit4SensorEntry 6 }

    cmcTcMasterTc8Unit4SensorSetLow OBJECT-TYPE
      SYNTAX INTEGER (0..300) 
      ACCESS read-write
      STATUS mandatory
      DESCRIPTION
        "Value for low setpoint of sensor,
         also used as alarm delay"
      ::= { cmcTcMasterTc8Unit4SensorEntry 7 }

    cmcTcMasterTc8Unit4SensorSetWarn OBJECT-TYPE
      SYNTAX INTEGER (0..300) 
      ACCESS read-write
      STATUS mandatory
      DESCRIPTION
        "Value for warning setpoint of sensor,
         also used as fan threshold"
      ::= { cmcTcMasterTc8Unit4SensorEntry 8 }

-- Outputs              

  cmcTcMasterTc8Unit4NumberOfOutputs OBJECT-TYPE
    SYNTAX INTEGER 
    ACCESS read-only
    STATUS mandatory
    DESCRIPTION
      "Number of outputs available on sensor unit 4"
    ::= { cmcTcMasterTc8StatusUnit4Outputs 1 }

-- table with entry for each output available on this unit              
                
  cmcTcMasterTc8Unit4OutputTable OBJECT-TYPE
    SYNTAX SEQUENCE OF CmcTcMasterTc8Unit4OutputEntry
    ACCESS not-accessible
    STATUS mandatory
    DESCRIPTION
      "Headline of output table"
    ::= { cmcTcMasterTc8StatusUnit4Outputs 2 }

  cmcTcMasterTc8Unit4OutputEntry OBJECT-TYPE
    SYNTAX CmcTcMasterTc8Unit4OutputEntry
    ACCESS not-accessible
    STATUS mandatory
    DESCRIPTION
      "Entries of output table"
    INDEX { cmcTcMasterTc8Unit4OutputIndex }
    ::= { cmcTcMasterTc8Unit4OutputTable 1 }

    CmcTcMasterTc8Unit4OutputEntry ::=
      SEQUENCE {
        cmcTcMasterTc8Unit4OutputIndex
          INTEGER,
        cmcTcMasterTc8Unit4OutputType
          INTEGER,
        cmcTcMasterTc8Unit4OutputText
          DisplayString (SIZE (0..20)),                
        cmcTcMasterTc8Unit4OutputStatus
          INTEGER,
        cmcTcMasterTc8Unit4OutputValue
          INTEGER,
        cmcTcMasterTc8Unit4OutputSet
          INTEGER,
        cmcTcMasterTc8Unit4OutputConfig
          INTEGER,
        cmcTcMasterTc8Unit4OutputDelay
          INTEGER,
        cmcTcMasterTc8Unit4OutputTimeoutAction
          INTEGER
      }

    cmcTcMasterTc8Unit4OutputIndex OBJECT-TYPE
      SYNTAX INTEGER (1..32000)
      ACCESS read-only
      STATUS mandatory
      DESCRIPTION
        "Index for the list of output entries. Its value ranges
         between 1 and the value of cmcTcMasterTc8Unit4NumberOfOutputs." 
      ::= { cmcTcMasterTc8Unit4OutputEntry 1 }

    cmcTcMasterTc8Unit4OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 4 to output[cmcTcMasterTc8Unit4OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc8Unit4OutputEntry 2 }

    cmcTcMasterTc8Unit4OutputText OBJECT-TYPE
      SYNTAX DisplayString (SIZE (0..20))
      ACCESS read-write
      STATUS mandatory
      DESCRIPTION
        "Descriptional text for each output (entry in the table)"
      ::= { cmcTcMasterTc8Unit4OutputEntry 3 }
              
    cmcTcMasterTc8Unit4OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc8Unit4OutputEntry 4 }

    cmcTcMasterTc8Unit4OutputValue OBJECT-TYPE
      SYNTAX INTEGER (-32000..32000) 
      ACCESS read-write
      STATUS mandatory
      DESCRIPTION
        "Value for output"
      ::= { cmcTcMasterTc8Unit4OutputEntry 5 }

    cmcTcMasterTc8Unit4OutputSet OBJECT-TYPE
      SYNTAX INTEGER {
        off (1),
        on (2),
        lock (3),
        unlock (4),
        unlockDelay (5)
      }
      ACCESS read-write
      STATUS mandatory
      DESCRIPTION
        "Command for output"
      ::= { cmcTcMasterTc8Unit4OutputEntry 6 }

    cmcTcMasterTc8Unit4OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc8Unit4OutputEntry 7 }

    cmcTcMasterTc8Unit4OutputDelay OBJECT-TYPE
      SYNTAX INTEGER (0..999) 
      ACCESS read-write
      STATUS mandatory
      DESCRIPTION
        "Unsigned Value for delay, 
         after this time the output will fall into the previous state"
      ::= { cmcTcMasterTc8Unit4OutputEntry 8 }

    cmcTcMasterTc8Unit4OutputTimeoutAction OBJECT-TYPE
      SYNTAX INTEGER {
        stay (1),
        off (2),
        on (3)
      }
      ACCESS read-write
      STATUS mandatory
      DESCRIPTION
        "State for output if timeout (RS422) occurs"
      ::= { cmcTcMasterTc8Unit4OutputEntry 9 }

-- Messages
              
  cmcTcMasterTc8Unit4NumberOfMsgs OBJECT-TYPE
    SYNTAX INTEGER 
    ACCESS read-only
    STATUS mandatory
    DESCRIPTION
      "Number of messages that can be created with sensor unit 4"
    ::= { cmcTcMasterTc8StatusUnit4Msg 1 }

-- table with entry for each alarm available on this unit               
                
  cmcTcMasterTc8Unit4MsgTable OBJECT-TYPE
    SYNTAX SEQUENCE OF CmcTcMasterTc8Unit4MsgEntry
    ACCESS not-accessible
    STATUS mandatory
    DESCRIPTION
      "Headline of message table"
    ::= { cmcTcMasterTc8StatusUnit4Msg 2 }

  cmcTcMasterTc8Unit4MsgEntry OBJECT-TYPE
    SYNTAX CmcTcMasterTc8Unit4MsgEntry
    ACCESS not-accessible
    STATUS mandatory
    DESCRIPTION
      "Entries of message table"
    INDEX { cmcTcMasterTc8Unit4MsgIndex }
    ::= { cmcTcMasterTc8Unit4MsgTable 1 }

    CmcTcMasterTc8Unit4MsgEntry ::=
      SEQUENCE {
        cmcTcMasterTc8Unit4MsgIndex
          INTEGER,
        cmcTcMasterTc8Unit4MsgText
          DisplayString (SIZE (0..20)),                
        cmcTcMasterTc8Unit4MsgStatus
          INTEGER, 
        cmcTcMasterTc8Unit4MsgRelay
          INTEGER,
        cmcTcMasterTc8Unit4MsgBeeper
          INTEGER,
        cmcTcMasterTc8Unit4MsgTrap1
          INTEGER,
        cmcTcMasterTc8Unit4MsgTrap2
          INTEGER,
        cmcTcMasterTc8Unit4MsgTrap3
          INTEGER,
        cmcTcMasterTc8Unit4MsgTrap4
          INTEGER,                 
        cmcTcMasterTc8Unit4MsgQuit
          INTEGER              
      }

    cmcTcMasterTc8Unit4MsgIndex OBJECT-TYPE
      SYNTAX INTEGER (1..32000)
      ACCESS read-only
      STATUS mandatory
      DESCRIPTION
        "Index for the list of message entries. Its value ranges
         between 1 and the value of cmcTcMasterTc8Unit4NumberOfMsgs." 
      ::= { cmcTcMasterTc8Unit4MsgEntry 1 }

    cmcTcMasterTc8Unit4MsgText OBJECT-TYPE
      SYNTAX DisplayString (SIZE (0..20))
      ACCESS read-write
      STATUS mandatory
      DESCRIPTION
        "Descriptional text for each message (entry in the table)"
      ::= { cmcTcMasterTc8Unit4MsgEntry 2 }

    cmcTcMasterTc8Unit4MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc8Unit4OutputSet)
         17: door is unlocked by WEB
         18: door is unlocked by timer
         19: no access, wrong keycode or cardnumber
         20: orientation of PSM-Unit is circuit 1
         21: orientation of PSM-Unit is circuit 2"
      ::= { cmcTcMasterTc8Unit4MsgEntry 3 }

    cmcTcMasterTc8Unit4MsgRelay OBJECT-TYPE
      SYNTAX INTEGER {
        disable (1),
        enable (2)
      }
      ACCESS read-write
      STATUS mandatory
      DESCRIPTION
        "Setup of Alarm relay for this alarm
         1:        no switching of alarm relay             
         2:        switching of alarm relay" 
      ::= { cmcTcMasterTc8Unit4MsgEntry 4 }

    cmcTcMasterTc8Unit4MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc8Unit4MsgEntry 5 }

    cmcTcMasterTc8Unit4MsgTrap1 OBJECT-TYPE
      SYNTAX INTEGER {
        disable (1),
        enable (2)
      }
      ACCESS read-write
      STATUS mandatory
      DESCRIPTION
        "Trap receiver 1 activated"
      ::= { cmcTcMasterTc8Unit4MsgEntry 6 }

    cmcTcMasterTc8Unit4MsgTrap2 OBJECT-TYPE
      SYNTAX INTEGER {
        disable (1),
        enable (2)
      }
      ACCESS read-write
      STATUS mandatory
      DESCRIPTION
        "Trap receiver 2 activated"
      ::= { cmcTcMasterTc8Unit4MsgEntry 7 }
 
    cmcTcMasterTc8Unit4MsgTrap3 OBJECT-TYPE
      SYNTAX INTEGER {
        disable (1),
        enable (2)
      }
      ACCESS read-write
      STATUS mandatory
      DESCRIPTION
        "Trap receiver 3 activated"
      ::= { cmcTcMasterTc8Unit4MsgEntry 8 }

    cmcTcMasterTc8Unit4MsgTrap4 OBJECT-TYPE
      SYNTAX INTEGER {
        disable (1),
        enable (2)
      }
      ACCESS read-write
      STATUS mandatory
      DESCRIPTION
        "Trap receiver 4 and Event Logging activated"
      ::= { cmcTcMasterTc8Unit4MsgEntry 9 }

    cmcTcMasterTc8Unit4MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc8Unit4MsgEntry 10 }

--Status extension unit

  cmcTcMasterTc8ValuesRelay OBJECT-TYPE
    SYNTAX INTEGER {
      disable (1),
      enable (2)
    }
    ACCESS read-write
    STATUS mandatory
    DESCRIPTION
      "Setup of Alarm relay for alarm ext. unit(s)
       1:        no switching of alarm relay             
       2:        switching of alarm relay" 
    ::= { cmcTcMasterTc8StatusExtUnit 1 }

  cmcTcMasterTc8ValuesBeeper OBJECT-TYPE
    SYNTAX INTEGER {
      disable (1),
      enable (2)
    }
    ACCESS read-write
    STATUS mandatory
    DESCRIPTION
      "Setup of Alarm beeper for alarm ext. unit(s)
       1:        no audible alarm
       2:        audible alarm" 
    ::= { cmcTcMasterTc8StatusExtUnit 2 }

  cmcTcMasterTc8ValuesTrap1 OBJECT-TYPE
    SYNTAX INTEGER {
      disable (1),
      enable (2)
    }
    ACCESS read-write
    STATUS mandatory
    DESCRIPTION
      "Trap receiver 1 activated"
    ::= { cmcTcMasterTc8StatusExtUnit 3 }

  cmcTcMasterTc8ValuesTrap2 OBJECT-TYPE
    SYNTAX INTEGER {
      disable (1),
      enable (2)
    }
    ACCESS read-write
    STATUS mandatory
    DESCRIPTION
      "Trap receiver 2 activated"
    ::= { cmcTcMasterTc8StatusExtUnit 4 }
 
  cmcTcMasterTc8ValuesTrap3 OBJECT-TYPE
    SYNTAX INTEGER {
      disable (1),
      enable (2)
    }
    ACCESS read-write
    STATUS mandatory
    DESCRIPTION
      "Trap receiver 3 activated"
    ::= { cmcTcMasterTc8StatusExtUnit 5 }

  cmcTcMasterTc8ValuesTrap4 OBJECT-TYPE
    SYNTAX INTEGER {
      disable (1),
      enable (2)
    }
    ACCESS read-write
    STATUS mandatory
    DESCRIPTION
      "Trap receiver 4 and Event Logging activated"
    ::= { cmcTcMasterTc8StatusExtUnit 6 }
 
  cmcTcMasterTc8NumberOfValues OBJECT-TYPE
    SYNTAX INTEGER 
    ACCESS  read-only
    STATUS  mandatory
    DESCRIPTION
      "Number of values availabel on extension units connected to the CMC-TC"
    ::= { cmcTcMasterTc8StatusExtUnit 7 }

-- table with entry for each value available on extension units              

  cmcTcMasterTc8ValuesTable OBJECT-TYPE
    SYNTAX SEQUENCE OF CmcTcMasterTc8ValuesEntry
    ACCESS not-accessible
    STATUS mandatory
    DESCRIPTION
      "Headline of values-table"
    ::= { cmcTcMasterTc8StatusExtUnit 8 }

  cmcTcMasterTc8ValuesEntry OBJECT-TYPE
    SYNTAX CmcTcMasterTc8ValuesEntry
    ACCESS not-accessible
    STATUS mandatory
    DESCRIPTION
      "Entries of values-table"
    INDEX { cmcTcMasterTc8ValuesIndex }
    ::= { cmcTcMasterTc8ValuesTable 1 }

    CmcTcMasterTc8ValuesEntry ::=
      SEQUENCE {
        cmcTcMasterTc8ValuesIndex
          INTEGER,
        cmcTcMasterTc8ValuesText
          DisplayString (SIZE (0..20)),                
        cmcTcMasterTc8ValuesStatus
          INTEGER,
        cmcTcMasterTc8ValuesValue
          INTEGER,
        cmcTcMasterTc8ValuesSetHigh
          INTEGER,
        cmcTcMasterTc8ValuesSetLow
          INTEGER
      }

    cmcTcMasterTc8ValuesIndex OBJECT-TYPE
      SYNTAX INTEGER (1..32000)
      ACCESS read-only
      STATUS mandatory
      DESCRIPTION
        "Index for the list of value entries. Its value ranges
         between 1 and the value of cmcTcMasterTc8NumberOfValues." 
      ::= { cmcTcMasterTc8ValuesEntry 1 }

        
    cmcTcMasterTc8ValuesText OBJECT-TYPE
      SYNTAX DisplayString (SIZE (0..20))
      ACCESS read-write
      STATUS mandatory
      DESCRIPTION
        "Descriptional text for each value (entry in the table)
         of the extension card"
      ::= { cmcTcMasterTc8ValuesEntry 2 }
              
    cmcTcMasterTc8ValuesStatus OBJECT-TYPE
      SYNTAX INTEGER {
        notAvail(1),
        lost(2),
        changed(3),
        ok(4),
        tooLow(5),
        tooHigh(6),
        error(7)
      }
      ACCESS read-only
      STATUS mandatory
      DESCRIPTION
        "Actual status of the value of the extension card"
      ::= { cmcTcMasterTc8ValuesEntry 3 }

    cmcTcMasterTc8ValuesValue OBJECT-TYPE
      SYNTAX INTEGER 
      ACCESS read-only
      STATUS mandatory
      DESCRIPTION
        "Value of sensor"
      ::= { cmcTcMasterTc8ValuesEntry 4 }

    cmcTcMasterTc8ValuesSetHigh OBJECT-TYPE
      SYNTAX INTEGER (0..255) 
      ACCESS read-write
      STATUS mandatory
      DESCRIPTION
        "Value for high setpoint of sensor"
      ::= { cmcTcMasterTc8ValuesEntry 5 }

    cmcTcMasterTc8ValuesSetLow OBJECT-TYPE
      SYNTAX INTEGER (0..255) 
      ACCESS read-write
      STATUS mandatory
      DESCRIPTION
        "Value for low setpoint of sensor"
      ::= { cmcTcMasterTc8ValuesEntry 6 }

--cmcTcMasterTc8SetupGeneral-group

  cmcTcMasterTc8SetTempUnit OBJECT-TYPE
    SYNTAX INTEGER {
      celsius(1),
      fahrenheit(2)
    }
    ACCESS read-write
    STATUS mandatory
    DESCRIPTION
      "Unit of all temperature values and setpoints, Celsius or Fahrenheit"
   ::= { cmcTcMasterTc8SetupGeneral 1 }

  cmcTcMasterTc8SetBeeper OBJECT-TYPE
    SYNTAX INTEGER {
      off(1),
      on(2)
    }
    ACCESS read-write
    STATUS mandatory
    DESCRIPTION
      "Audible alarm in CMC-TC unit:
       (2): beeper is on
       (1): beeper is off (general)"
    ::= { cmcTcMasterTc8SetupGeneral 2 }


  cmcTcMasterTc8QuitRelay OBJECT-TYPE
    SYNTAX INTEGER {
      disabled(1),
      enabled(2)
    }
    ACCESS read-write
    STATUS mandatory
    DESCRIPTION
      "Enable or disable acknowledging currently active alarm relay 
       (with 'C' on CMC-TC)."
    ::= { cmcTcMasterTc8SetupGeneral 3 }

  cmcTcMasterTc8LogicRelay OBJECT-TYPE
    SYNTAX INTEGER {
      closeAtAlarm(1),
      openAtAlarm(2),
      off(3)
    }
    ACCESS read-write
    STATUS mandatory
    DESCRIPTION
      "Logic of alarm relay: 
       (1) Relay will pick up in case of an alarm
       (2) Relay will release in case of an alarm
       (3) Relay off (general)"
    ::= { cmcTcMasterTc8SetupGeneral 4 }

  cmcTcMasterTc8WebAccess OBJECT-TYPE
    SYNTAX INTEGER {
      viewOnly(1),
      fullAccess(2),
      off(3)
    }
    ACCESS read-write
    STATUS mandatory
    DESCRIPTION
      "Web access via HTTP: 
       (1) view only
       (2) full Access, read and set
       (3) Web disabled (general)"
    ::= { cmcTcMasterTc8SetupGeneral 5 }
 
  cmcTcMasterTc8SetupDate OBJECT-TYPE
    SYNTAX DisplayString (SIZE (0..10))
    ACCESS read-write
    STATUS mandatory
    DESCRIPTION
      "actual Date in format DD.MM.YYYY"
    ::= { cmcTcMasterTc8SetupGeneral 6 }

  cmcTcMasterTc8SetupTime OBJECT-TYPE
    SYNTAX DisplayString (SIZE (0..8))
    ACCESS read-write
    STATUS mandatory
    DESCRIPTION
      "actual Time in format HH:MM:SS, HH (0-23), MM (0-59), SS (0-59)"
    ::= { cmcTcMasterTc8SetupGeneral 7 }
 
-- table for timer function
 
  cmcTcMasterTc8TimerNumber OBJECT-TYPE
    SYNTAX INTEGER 
    ACCESS read-only
    STATUS mandatory
    DESCRIPTION
      "Number of timers available on this unit"
    ::= { cmcTcMasterTc8TimerTable1 1 }

  cmcTcMasterTc8TimerTable OBJECT-TYPE
    SYNTAX SEQUENCE OF CmcTcMasterTc8TimerEntry
    ACCESS not-accessible
    STATUS mandatory
    DESCRIPTION
      "Headline of timer-table"
    ::= { cmcTcMasterTc8TimerTable1 2 }

  cmcTcMasterTc8TimerEntry OBJECT-TYPE
    SYNTAX CmcTcMasterTc8TimerEntry
    ACCESS not-accessible
    STATUS mandatory
    DESCRIPTION
      "Entries of timer-table"
    INDEX { cmcTcMasterTc8TimerIndex }
    ::= { cmcTcMasterTc8TimerTable 1 }

    CmcTcMasterTc8TimerEntry ::=
      SEQUENCE {
        cmcTcMasterTc8TimerIndex
          INTEGER,
        cmcTcMasterTc8TimerStatus
          INTEGER,
        cmcTcMasterTc8TimerDayOfWeek
          INTEGER,  
        cmcTcMasterTc8TimeOn 
          DisplayString (SIZE (0..5)),                              
        cmcTcMasterTc8TimeOff 
          DisplayString (SIZE (0..5)),                              
        cmcTcMasterTc8TimeControl
          INTEGER,
        cmcTcMasterTc8TimerFunction
           INTEGER
      }

    cmcTcMasterTc8TimerIndex OBJECT-TYPE
      SYNTAX INTEGER (1..32000)
      ACCESS read-only
      STATUS mandatory
      DESCRIPTION
        "Index for the list of timer entries. Its value ranges
         between 1 and the value of cmcTcMasterTc8TimerNumber." 
      ::= { cmcTcMasterTc8TimerEntry 1 }

    cmcTcMasterTc8TimerStatus OBJECT-TYPE
      SYNTAX INTEGER {
        switchedOff(1),
        switchedOn(2),
        noTime(3) 
      }
      ACCESS read-only
      STATUS mandatory
      DESCRIPTION
        "Actual status of the timer"
      ::= { cmcTcMasterTc8TimerEntry 2 }

    cmcTcMasterTc8TimerDayOfWeek OBJECT-TYPE
      SYNTAX INTEGER {
        sun(1),
        mon(2),
        tue(3) ,
        wed(4),
        thu(5),
        fri(6),
        sat(7),
        sat-sun(8),
        mon-fri(9),
        mon-sun(10)
      }
      ACCESS read-write
      STATUS mandatory
      DESCRIPTION
        "Selection of day of week for timer to switch"
      ::= { cmcTcMasterTc8TimerEntry 3 }
             
    cmcTcMasterTc8TimeOn OBJECT-TYPE
      SYNTAX DisplayString (SIZE (0..5))
      ACCESS read-write
      STATUS mandatory
      DESCRIPTION
        "Time to switch on current function, 
         Format: HH:MM"
      ::= { cmcTcMasterTc8TimerEntry 4 }

    cmcTcMasterTc8TimeOff OBJECT-TYPE
      SYNTAX DisplayString (SIZE (0..5))
      ACCESS read-write
      STATUS mandatory
      DESCRIPTION
        "Time to switch off current function,
         Format: HH:MM"
      ::= { cmcTcMasterTc8TimerEntry 5 }

    cmcTcMasterTc8TimeControl OBJECT-TYPE
      SYNTAX INTEGER  {
        disabled(1),
        enabled(2)
      }
      ACCESS read-write
      STATUS mandatory
      DESCRIPTION
        "Control via RTC"
      ::= { cmcTcMasterTc8TimerEntry 6 }

    cmcTcMasterTc8TimerFunction OBJECT-TYPE
      SYNTAX INTEGER {
        disKeypad1-1 (1),
        disKeypad2-1 (2),
        disKeypad1-2 (3),
        disKeypad2-2 (4),
        disKeypad1-3 (5),
        disKeypad2-3 (6),
        disKeypad1-4 (7),
        disKeypad2-4 (8),
        unlDoor1-1 (9),
        unlDoor2-1 (10),
        unlDoor1-2 (11),
        unlDoor2-2 (12),
        unlDoor1-3 (13),
        unlDoor2-3 (14),
        unlDoor1-4 (15),
        unlDoor2-5 (16),
        disTrapRec1 (17),
        disTrapRec2 (18),
        disTrapRec3 (19),
        disTrapRec4 (20),
        disSMS (21),
        schedule1 (22),
        schedule2 (23),
        schedule3 (24),
        schedule4 (25)
      }
      ACCESS read-write
      STATUS mandatory
      DESCRIPTION
        "Function which is controlled via timer
         1:     unlock via keypad 1 on unit 1 or remote input lock 1 is disabled
         2:     unlock via keypad 2 on unit 1 or remote input lock 2 is disabled
         3      unlock via keypad 1 on unit 2 or remote input lock 1 is disabled
         4:     unlock via keypad 2 on unit 2 or remote input lock 2 is disabled
         5:     unlock via keypad 1 on unit 3 or remote input lock 1 is disabled
         6:     unlock via keypad 2 on unit 3 or remote input lock 2 is disabled
         7:     unlock via keypad 1 on unit 4 or remote input lock 1 is disabled
         8:     unlock via keypad 2 on unit 4 or remote input lock 2 is disabled
         9:     Lock of door 1 on unit 1 will be unlocked
         10:    Lock of door 2 on unit 1 will be unlocked
         11:    Lock of door 1 on unit 2 will be unlocked
         12:    Lock of door 2 on unit 2 will be unlocked
         13:    Lock of door 1 on unit 3 will be unlocked
         14:    Lock of door 2 on unit 3 will be unlocked
         15:    Lock of door 1 on unit 4 will be unlocked
         16:    Lock of door 2 on unit 4 will be unlocked
         17-20: sending Traps to this Trap receiver will be disabled
         21:    sending SMS will be disabled
         22-25: Scheduled alarm off"
      ::= { cmcTcMasterTc8TimerEntry 7 }

--cmcTcMasterTc8TrapTable-group

  cmcTcMasterTc8TraptableNumber OBJECT-TYPE
    SYNTAX INTEGER 
    ACCESS read-only
    STATUS mandatory
    DESCRIPTION
      "Number of trapTable entries. The number of trap-receiver"
    ::= { cmcTcMasterTc8Traps 1 }

  cmcTcMasterTc8TrapTableTable OBJECT-TYPE    
    SYNTAX SEQUENCE OF CmcTcMasterTc8TrapTableEntry
    ACCESS not-accessible
    STATUS mandatory
    DESCRIPTION
     "A list of trap-receiver entries"
    ::= { cmcTcMasterTc8Traps 2 }

  cmcTcMasterTc8TrapTableEntry OBJECT-TYPE
    SYNTAX CmcTcMasterTc8TrapTableEntry
    ACCESS not-accessible
    STATUS mandatory
    DESCRIPTION
      "Entries of cmcTcMasterTc8TrapTable"
    INDEX   { cmcTcMasterTc8TrapIndex }
    ::= { cmcTcMasterTc8TrapTableTable 1 }      
              
    CmcTcMasterTc8TrapTableEntry ::=
      SEQUENCE {
        cmcTcMasterTc8TrapIndex
          INTEGER,
        cmcTcMasterTc8TrapStatus
          INTEGER,
        cmcTcMasterTc8TrapIPaddress
          DisplayString
      }

    cmcTcMasterTc8TrapIndex OBJECT-TYPE
      SYNTAX INTEGER (1..32000)
      ACCESS read-only
      STATUS mandatory
      DESCRIPTION
        "Index for the trap-receiver-table. Its value ranges between
         1 and the value of cmcTcMasterTc8TraptableNumber "
      ::= { cmcTcMasterTc8TrapTableEntry 1 }

    cmcTcMasterTc8TrapStatus OBJECT-TYPE
      SYNTAX INTEGER {
        disabled(1),
        enabled(2)
      }
      ACCESS read-write
      STATUS mandatory
      DESCRIPTION
        "Enable or disable trap receiver"
      ::= { cmcTcMasterTc8TrapTableEntry 2 }

    cmcTcMasterTc8TrapIPaddress OBJECT-TYPE
      SYNTAX DisplayString (SIZE (0..15))
      ACCESS read-write
      STATUS mandatory
      DESCRIPTION
        "IP-address of trap-receiver"
      ::= { cmcTcMasterTc8TrapTableEntry 3 }

--cmcTcMasterTc8Control-group (Added in Version 1.1)

  cmcTcMasterTc1QuitUnit OBJECT-TYPE
    SYNTAX INTEGER {
      noQuit(1),
      quit(2),
    }
    ACCESS read-write
    STATUS mandatory
    DESCRIPTION
      "Command to quit (acknowledge) alarms of CMC-TC unit.
       Setting to 'quit' (2) will have same result as pressing 'C' on Units.
       Variable is automatically set back to 'noQuit' (1)."
    ::= { cmcTcMasterTc8Control 1 }

--cmcTcMasterDevice9-group

  cmcTcMasterDev9Type OBJECT-TYPE
    SYNTAX INTEGER {
      other (0),
      cmc (1),
      pcu (3),
      tc (4)
    }
    ACCESS read-only
    STATUS mandatory
    DESCRIPTION
      "Type of device9"
    ::= { cmcTcMasterDevice9 1 }

  cmcTcMasterDev9Status OBJECT-TYPE
    SYNTAX INTEGER {
      other (1),
      notConnected (2),
      normal (3),
      minor (4),
      major (5),
      configChanged (6),
      connectionLost (10)
    }
    ACCESS read-only
    STATUS mandatory
    DESCRIPTION
      "Status of device9"
    ::= { cmcTcMasterDevice9 2 }

  cmcTcMasterDev9Descr OBJECT-TYPE
    SYNTAX DisplayString (SIZE (0..255))
    ACCESS read-only
    STATUS mandatory
    DESCRIPTION
      "A textual description of the entity.  This value
       should include the full name and version
       identification of the system's hardware type,
       software operating-system, and networking
       software.  It is mandatory that this only contain
       printable ASCII characters."
    ::= { cmcTcMasterDevice9 3 }

  cmcTcMasterDev9UpTime OBJECT-TYPE
    SYNTAX TimeTicks
    ACCESS read-only
    STATUS mandatory
    DESCRIPTION
      "The time (in hundredths of a second) since the
       network management portion of the system was last
       re-initialized."
    ::= { cmcTcMasterDevice9 4 }

  cmcTcMasterDev9Contact OBJECT-TYPE
    SYNTAX DisplayString (SIZE (0..255))
    ACCESS read-write
    STATUS mandatory
    DESCRIPTION
      "The textual identification of the contact person
       for this managed node, together with information
       on how to contact this person."
    ::= { cmcTcMasterDevice9 5 }

  cmcTcMasterDev9Name OBJECT-TYPE
    SYNTAX DisplayString (SIZE (0..255))
    ACCESS read-write
    STATUS mandatory
    DESCRIPTION
      "An administratively-assigned name for this
       managed node.  By convention, this is the node's
       fully-qualified domain name."
    ::= { cmcTcMasterDevice9 6 }

  cmcTcMasterDev9Location OBJECT-TYPE
    SYNTAX DisplayString (SIZE (0..255))
    ACCESS read-write
    STATUS mandatory
    DESCRIPTION
      "The physical location of this node (e.g.,
       `telephone closet, 3rd floor')."
    ::= { cmcTcMasterDevice9 7 }

--cmcTcMasterCmc9Values-group

  cmcTcMasterCmc9ValueTemperature1 OBJECT-TYPE
    SYNTAX INTEGER
    ACCESS read-only
    STATUS mandatory
    DESCRIPTION
      "Actual value of temperature 1 in deg C"
    ::= { cmcTcMasterCmc9Values 1 }

  cmcTcMasterCmc9ValueTemperature2 OBJECT-TYPE
    SYNTAX INTEGER
    ACCESS read-only
    STATUS mandatory
    DESCRIPTION
      "Actual value of temperature 2 in deg C"
    ::= { cmcTcMasterCmc9Values 2 }

  cmcTcMasterCmc9ValuePowerSupply OBJECT-TYPE
    SYNTAX INTEGER
    ACCESS read-only
    STATUS mandatory
    DESCRIPTION
      "Actual value of power supply in V"
    ::= { cmcTcMasterCmc9Values 3 }

  cmcTcMasterCmc9ValueAnalogAux1 OBJECT-TYPE
    SYNTAX INTEGER
    ACCESS read-only
    STATUS mandatory
    DESCRIPTION
      "Actual value of aux. analog input 1
      (4-20mA = 0-100%)"
    ::= { cmcTcMasterCmc9Values 4 }

  cmcTcMasterCmc9ValueAnalogAux2 OBJECT-TYPE
    SYNTAX INTEGER
    ACCESS read-only
    STATUS mandatory
    DESCRIPTION
      "Actual value of aux. analog input 2
      (4-20mA = 0-100%)"
    ::= { cmcTcMasterCmc9Values 5 }

--cmcTcMasterCmc9Values-table-group

  cmcTcMasterCmc9ValuesNumber OBJECT-TYPE
    SYNTAX INTEGER
    ACCESS read-only
    STATUS mandatory
    DESCRIPTION
      "Number of value-table entries"
    ::= { cmcTcMasterCmc9Table1 1 }

  cmcTcMasterCmc9ValuesTable OBJECT-TYPE
    SYNTAX SEQUENCE OF CmcTcMasterCmc9ValuesEntry
    ACCESS not-accessible
    STATUS mandatory
    DESCRIPTION
      "Headline of value-table"
    ::= { cmcTcMasterCmc9Table1 2 }

  cmcTcMasterCmc9ValuesEntry OBJECT-TYPE
    SYNTAX CmcTcMasterCmc9ValuesEntry
    ACCESS not-accessible
    STATUS mandatory
    DESCRIPTION
      "Entries of value-table"
    INDEX { cmcTcMasterCmc9ValuesIndex }
    ::= { cmcTcMasterCmc9ValuesTable 1 }

  CmcTcMasterCmc9ValuesEntry ::=
    SEQUENCE {
      cmcTcMasterCmc9ValuesIndex
        INTEGER,
      cmcTcMasterCmc9ValuesText
        DisplayString (SIZE (0..31)),
      cmcTcMasterCmc9ValuesValue
        INTEGER,
      cmcTcMasterCmc9ValuesStatus
        INTEGER,
      cmcTcMasterCmc9ValuesMaxValue
        INTEGER,
      cmcTcMasterCmc9ValuesMinValue
        INTEGER
    }

    cmcTcMasterCmc9ValuesIndex OBJECT-TYPE
      SYNTAX INTEGER (1..32000)
      ACCESS read-only
      STATUS mandatory
      DESCRIPTION
        "Index for the list of value entries. Its value ranges
        between 1 and the value of valuesNumber."
      ::= { cmcTcMasterCmc9ValuesEntry 1 }

    cmcTcMasterCmc9ValuesText OBJECT-TYPE
      SYNTAX DisplayString (SIZE (0..31))
      ACCESS read-write
      STATUS mandatory
      DESCRIPTION
        "Text of the entry in the value-table"
      ::= { cmcTcMasterCmc9ValuesEntry 2 }

    cmcTcMasterCmc9ValuesValue OBJECT-TYPE
      SYNTAX INTEGER
      ACCESS read-only
      STATUS mandatory
      DESCRIPTION
        "Actual value of the value-table"
      ::= { cmcTcMasterCmc9ValuesEntry 3 }

    cmcTcMasterCmc9ValuesStatus OBJECT-TYPE
      SYNTAX INTEGER {
        valueOK(1),
        valueTooLow(2),
        valueTooHigh(3),
        valueERROR(4),
        notAvail(5)
      }
      ACCESS read-only
      STATUS mandatory
      DESCRIPTION
        "Status of the value"
      ::= { cmcTcMasterCmc9ValuesEntry 4 }

    cmcTcMasterCmc9ValuesMaxValue OBJECT-TYPE
      SYNTAX INTEGER
      ACCESS read-write
      STATUS mandatory
      DESCRIPTION
        "Value for max. alarm"
      ::= { cmcTcMasterCmc9ValuesEntry 5 }

    cmcTcMasterCmc9ValuesMinValue OBJECT-TYPE
      SYNTAX INTEGER
      ACCESS read-write
      STATUS mandatory
      DESCRIPTION
        "Value for min. alarm"
      ::= { cmcTcMasterCmc9ValuesEntry 6 }

--cmcTcMasterCmc9status-group

  cmcTcMasterCmc9StatusTemperature1 OBJECT-TYPE
    SYNTAX DisplayString (SIZE (0..31))
    ACCESS read-only
    STATUS mandatory
    DESCRIPTION
      "Status temperature 1, OK/ too low/ too high
       (see setpoints of temperature 1)"
    ::= { cmcTcMasterCmc9Status 1 }

  cmcTcMasterCmc9StatusTemperature2 OBJECT-TYPE
    SYNTAX DisplayString (SIZE (0..31))
    ACCESS read-only
    STATUS mandatory
    DESCRIPTION
      "Status temperature 2, OK/ too low/ too high
       (see setpoints of temperature 2)"
    ::= { cmcTcMasterCmc9Status 2 }

  cmcTcMasterCmc9StatusFan1 OBJECT-TYPE
    SYNTAX DisplayString (SIZE (0..31))
    ACCESS read-only
    STATUS mandatory
    DESCRIPTION
      "Status fan 1, Stop/ running/ fault"
    ::= { cmcTcMasterCmc9Status 3 }

  cmcTcMasterCmc9StatusFan2 OBJECT-TYPE
    SYNTAX DisplayString (SIZE (0..31))
    ACCESS read-only
    STATUS mandatory
    DESCRIPTION
      "Status fan 2, Stop/ running/ fault"
    ::= { cmcTcMasterCmc9Status 4 }

  cmcTcMasterCmc9StatusHeating OBJECT-TYPE
    SYNTAX DisplayString (SIZE (0..31))
    ACCESS read-only
    STATUS mandatory
    DESCRIPTION
      "Status heating, On/Off"
    ::= { cmcTcMasterCmc9Status 5 }

  cmcTcMasterCmc9StatusPowerSupply OBJECT-TYPE
    SYNTAX DisplayString (SIZE (0..31))
    ACCESS read-only
    STATUS mandatory
    DESCRIPTION
      "Status power supply, OK/ too low/ too high
       (see setpoints of power supply)"
    ::= { cmcTcMasterCmc9Status 6 }

  cmcTcMasterCmc9StatusAnalogAux1 OBJECT-TYPE
    SYNTAX DisplayString (SIZE (0..31))
    ACCESS read-only
    STATUS mandatory
    DESCRIPTION
      "Status aux analog input 1, OK/ too low/ too high"
    ::= { cmcTcMasterCmc9Status 7 }

  cmcTcMasterCmc9StatusAnalogAux2 OBJECT-TYPE
    SYNTAX DisplayString (SIZE (0..31))
    ACCESS read-only
    STATUS mandatory
    DESCRIPTION
      "Status aux analog input 2, OK/ too low/ too high"
    ::= { cmcTcMasterCmc9Status 8 }

  cmcTcMasterCmc9StatusDoor OBJECT-TYPE
    SYNTAX DisplayString (SIZE (0..31))
    ACCESS read-only
    STATUS mandatory
    DESCRIPTION
      "Status door, open/closed/locked"
    ::= { cmcTcMasterCmc9Status 9 }

  cmcTcMasterCmc9StatusUps1 OBJECT-TYPE
    SYNTAX DisplayString (SIZE (0..31))
    ACCESS read-only
    STATUS mandatory
    DESCRIPTION
      "Status UPS 1, OK/ fault"
    ::= { cmcTcMasterCmc9Status 10 }

  cmcTcMasterCmc9StatusUps2 OBJECT-TYPE
    SYNTAX DisplayString (SIZE (0..31))
    ACCESS read-only
    STATUS mandatory
    DESCRIPTION
      "Status UPS 2, OK/ fault"
    ::= { cmcTcMasterCmc9Status 11 }

  cmcTcMasterCmc9StatusSmokeSensor OBJECT-TYPE
    SYNTAX DisplayString (SIZE (0..31))
    ACCESS read-only
    STATUS mandatory
    DESCRIPTION
      "Status smoke-sensor, OK/ smoke"
    ::= { cmcTcMasterCmc9Status 12 }

  cmcTcMasterCmc9StatusVibrationSensor OBJECT-TYPE
    SYNTAX DisplayString (SIZE (0..31))
    ACCESS read-only
    STATUS mandatory
    DESCRIPTION
      "Status vibration sensor, OK/ vibration"
    ::= { cmcTcMasterCmc9Status 13 }

  cmcTcMasterCmc9StatusMessage OBJECT-TYPE
    SYNTAX DisplayString (SIZE (0..31))
    ACCESS read-only
    STATUS mandatory
    DESCRIPTION
      "Message from CMC"
    ::= { cmcTcMasterCmc9Status 14 }

  cmcTcMasterCmc9ValueOperatingTime OBJECT-TYPE
    SYNTAX DisplayString (SIZE (0..31))
    ACCESS read-only
    STATUS mandatory
    DESCRIPTION
      "Operating time CMC-unit"
    ::= { cmcTcMasterCmc9Status 15 }

  cmcTcMasterCmc9StatusUnit OBJECT-TYPE
    SYNTAX INTEGER {
      unitCelsius(1),
      unitFahrenheit(2)
    }
    ACCESS read-only
    STATUS mandatory
    DESCRIPTION
      "Unit of temperature-values, Celsius or Fahrenheit"
   ::= { cmcTcMasterCmc9Status 16 }


--cmcTcMasterCmc9Status-table-group

  cmcTcMasterCmc9StatusNumber OBJECT-TYPE
    SYNTAX INTEGER 
    ACCESS read-only
    STATUS mandatory
    DESCRIPTION
      "Number of status-table entries"
    ::= { cmcTcMasterCmc9Table 1 }

  cmcTcMasterCmc9StatusTable OBJECT-TYPE
    SYNTAX SEQUENCE OF CmcTcMasterCmc9StatusEntry
    ACCESS not-accessible
    STATUS mandatory
    DESCRIPTION
      "Headline of table"
    ::= { cmcTcMasterCmc9Table 2 }

  cmcTcMasterCmc9StatusEntry OBJECT-TYPE
    SYNTAX CmcTcMasterCmc9StatusEntry
    ACCESS not-accessible
    STATUS mandatory
    DESCRIPTION
      "A list of status entries.  The number of
       entries is given by the value of cmcTcMasterCmc9StatusNumber." 
    INDEX { cmcTcMasterCmc9StatusIndex }
    ::= { cmcTcMasterCmc9StatusTable 1 }

  CmcTcMasterCmc9StatusEntry ::=
    SEQUENCE {
      cmcTcMasterCmc9StatusIndex
        INTEGER,
      cmcTcMasterCmc9StatusText
        DisplayString (SIZE (0..31)),
      cmcTcMasterCmc9StatusStatus
        INTEGER              
    }

    cmcTcMasterCmc9StatusIndex OBJECT-TYPE
      SYNTAX INTEGER (1..32000)
      ACCESS read-only
      STATUS mandatory
      DESCRIPTION
        "Index fo the list of status entries. Its value ranges
         between 1 and the value of cmcTcMasterCmc9StatusNumber." 
      ::= { cmcTcMasterCmc9StatusEntry 1 }

    cmcTcMasterCmc9StatusText OBJECT-TYPE
      SYNTAX DisplayString (SIZE (0..31))
      ACCESS read-write
      STATUS mandatory
      DESCRIPTION
        "Text of the entry in the status-table"
      ::= { cmcTcMasterCmc9StatusEntry 2 }

    cmcTcMasterCmc9StatusStatus OBJECT-TYPE
      SYNTAX INTEGER  {
        statusOK(1),
        alarm(2),
        security(3),
        notAvail(4)
      }
      ACCESS read-only
      STATUS mandatory
      DESCRIPTION
        "Status of the table entry"
      ::= { cmcTcMasterCmc9StatusEntry 3 }

--******************************************************************************

--cmcTCMasterCmc9Set-group

  cmcTcMasterCmc9StatusAccess OBJECT-TYPE
    SYNTAX DisplayString (SIZE (0..31))
    ACCESS read-write
    STATUS mandatory
    DESCRIPTION
      "Status access"
    ::= { cmcTcMasterCmc9Set 1 }

  cmcTcMasterCmc9SetDoor OBJECT-TYPE
    SYNTAX INTEGER {
      lockDoor(1),
      openDoorTime(2),
      openDoorAccess(3),
      openDoor(4)
    }
    ACCESS read-write
    STATUS mandatory
    DESCRIPTION
      "Set door, see table"
    ::= { cmcTcMasterCmc9Set 2 }

  cmcTcMasterCmc9SetMessage OBJECT-TYPE
    SYNTAX DisplayString (SIZE (0..31))
    ACCESS read-write
    STATUS mandatory
    DESCRIPTION
      "Set message"
    ::= { cmcTcMasterCmc9Set 3 }

  cmcTcMasterCmc9SetFault        OBJECT-TYPE
    SYNTAX INTEGER {
      clearFault(1),
      setFault(2)
    }
    ACCESS read-write
    STATUS mandatory
    DESCRIPTION
      "Set fault, see table"
    ::= { cmcTcMasterCmc9Set 4 }

--cmcTcMasterCmc9RelayControl-group

  cmcTcMasterCmc9RelaytableMaxNum OBJECT-TYPE
    SYNTAX INTEGER 
    ACCESS read-only
    STATUS mandatory
    DESCRIPTION
      "Number of table entries"
    ::= { cmcTcMasterCmc9RelayControl 1 }

  cmcTcMasterCmc9RelayTable OBJECT-TYPE
    SYNTAX SEQUENCE OF CmcTcMasterCmc9RelayEntry
    ACCESS not-accessible
    STATUS mandatory
    DESCRIPTION
      "Headline of table for relay control"
    ::= { cmcTcMasterCmc9RelayControl 2 }

  cmcTcMasterCmc9RelayEntry OBJECT-TYPE
    SYNTAX CmcTcMasterCmc9RelayEntry
    ACCESS not-accessible
    STATUS mandatory
    DESCRIPTION
      "Entries"
    INDEX { cmcTcMasterCmc9RelaytableIndex }
    ::= { cmcTcMasterCmc9RelayTable 1 }

  CmcTcMasterCmc9RelayEntry ::=
    SEQUENCE {
      cmcTcMasterCmc9RelaytableIndex
        INTEGER,
      cmcTcMasterCmc9RelaytableText
	DisplayString (SIZE (0..31)),
      cmcTcMasterCmc9RelaytableStatus
        INTEGER              
    }

    cmcTcMasterCmc9RelaytableIndex OBJECT-TYPE
      SYNTAX INTEGER (1..32000)
      ACCESS read-only
      STATUS mandatory
      DESCRIPTION
        "Index for the relay-table. Its value ranges
         between 1 and cmcTcMasterCmc9RelaytableMaxNum"
      ::= { cmcTcMasterCmc9RelayEntry 1 }

    cmcTcMasterCmc9RelaytableText OBJECT-TYPE
      SYNTAX DisplayString (SIZE (0..31))
      ACCESS read-write
      STATUS mandatory
      DESCRIPTION
        "Description-Text for each relay in the table"
      ::= { cmcTcMasterCmc9RelayEntry 2 }

    cmcTcMasterCmc9RelaytableStatus OBJECT-TYPE
      SYNTAX INTEGER  {
        relayOFF(1),
        relayON(2),
        notAvail(3)
      }
      ACCESS read-write
      STATUS mandatory
      DESCRIPTION
        "Status of relays in the table"
      ::= { cmcTcMasterCmc9RelayEntry 3 }

--cmcTcMasterCmc9Setpoints-group

  cmcTcMasterCmc9SetpointFan1 OBJECT-TYPE
    SYNTAX INTEGER 
    ACCESS read-write
    STATUS mandatory
    DESCRIPTION
      "Setpoint Fan 1 in C, Fan 1 will start
       if temperature 1 exceeds this value"
    ::= { cmcTcMasterCmc9Setpoints 1 }

  cmcTcMasterCmc9SetpointFan2 OBJECT-TYPE
    SYNTAX INTEGER 
    ACCESS read-write
    STATUS mandatory
    DESCRIPTION
      "Setpoint Fan 2 in C, Fan 2 will start
       if temperature 2 exceeds this value"
    ::= { cmcTcMasterCmc9Setpoints 2 }

  cmcTcMasterCmc9SetpointHeating OBJECT-TYPE
    SYNTAX INTEGER 
    ACCESS read-write
    STATUS mandatory
    DESCRIPTION
      "Setpoint heating in C, heating will start
       if lowest value of temperature 1 and 2 falls below this value"
    ::= { cmcTcMasterCmc9Setpoints 3 }

  cmcTcMasterCmc9SetpointHighTemperature1 OBJECT-TYPE
    SYNTAX INTEGER 
    ACCESS read-write
    STATUS mandatory
    DESCRIPTION
      "Setpoint high value alarm temperature 1"
    ::= { cmcTcMasterCmc9Setpoints 4 }

  cmcTcMasterCmc9SetpointLowTemperature1 OBJECT-TYPE
    SYNTAX INTEGER 
    ACCESS read-write
    STATUS mandatory
    DESCRIPTION
      "Setpoint low value alarm temperature 1"
    ::= { cmcTcMasterCmc9Setpoints 5 }

  cmcTcMasterCmc9SetpointHighTemperature2 OBJECT-TYPE
    SYNTAX INTEGER 
    ACCESS read-write
    STATUS mandatory
    DESCRIPTION
      "Setpoint high value alarm temperature 2"
    ::= { cmcTcMasterCmc9Setpoints 6 }

  cmcTcMasterCmc9SetpointLowTemperature2 OBJECT-TYPE
    SYNTAX INTEGER 
    ACCESS read-write
    STATUS mandatory
    DESCRIPTION
      "Setpoint low value alarm temperature 2"
    ::= { cmcTcMasterCmc9Setpoints 7 }

  cmcTcMasterCmc9SetpointHighVoltage OBJECT-TYPE
    SYNTAX INTEGER 
    ACCESS read-write
    STATUS mandatory
    DESCRIPTION
      "Setpoint high value supply voltage alarm"
    ::= { cmcTcMasterCmc9Setpoints 8 }

  cmcTcMasterCmc9SetpointLowVoltage OBJECT-TYPE
    SYNTAX INTEGER
    ACCESS read-write
    STATUS mandatory
    DESCRIPTION
      "Setpoint low value supply voltage alarm"
    ::= { cmcTcMasterCmc9Setpoints 9 }

  cmcTcMasterCmc9SetpointLowAux1 OBJECT-TYPE
    SYNTAX INTEGER 
    ACCESS read-write
    STATUS mandatory
    DESCRIPTION
      "Setpoint low value Aux input 1 alarm"
    ::= { cmcTcMasterCmc9Setpoints 10 }

  cmcTcMasterCmc9SetpointHighAux1 OBJECT-TYPE
    SYNTAX INTEGER 
    ACCESS read-write
    STATUS mandatory
    DESCRIPTION
      "Setpoint high value Aux input 1 alarm"
    ::= { cmcTcMasterCmc9Setpoints 11 }

  cmcTcMasterCmc9SetpointLowAux2 OBJECT-TYPE
    SYNTAX INTEGER 
    ACCESS read-write
    STATUS mandatory
    DESCRIPTION
      "Setpoint low value Aux input 2 alarm"
    ::= { cmcTcMasterCmc9Setpoints 12 }

  cmcTcMasterCmc9SetpointHighAux2 OBJECT-TYPE
    SYNTAX INTEGER 
    ACCESS read-write
    STATUS mandatory
    DESCRIPTION
      "Setpoint high value Aux input alarm"
    ::= { cmcTcMasterCmc9Setpoints 13 }

--cmcTcMasterCmc9TrapControl-group

  cmcTcMasterCmc9SetTrapRepeat OBJECT-TYPE
    SYNTAX INTEGER {
      disableTrapRepeat(1),
      enableTrapRepeat(2)
    }
    ACCESS read-write
    STATUS mandatory
    DESCRIPTION
      "Enable/disable repeating of traps. If enabled, traps will
       be repeated after a repeat time, set in setTrapRepeatTime.
       Repeating can be stopped by setting setTrapQuit to quitTrap"
    ::= { cmcTcMasterCmc9TrapControl 1 }

  cmcTcMasterCmc9SetTrapRepeatTime OBJECT-TYPE
    SYNTAX INTEGER 
    ACCESS read-write
    STATUS mandatory
    DESCRIPTION
      "Time value (sec) for trap-repeating, if setTrapRepeat is enabled"
    ::= { cmcTcMasterCmc9TrapControl 2 }

  cmcTcMasterCmc9SetTrapQuit OBJECT-TYPE
    SYNTAX INTEGER {
      quitTrap(1),
      quitTrapOK(2),
      noTrapToQuit(3),
      trapToQuit(4)
    }
    ACCESS read-write
    STATUS mandatory
    DESCRIPTION
      "Quit trap to stop repeating."
    ::= { cmcTcMasterCmc9TrapControl 3 }

--cmcTcMasterCmc9TrapTable-group

  cmcTcMasterCmc9TraptableNumber OBJECT-TYPE
    SYNTAX INTEGER 
    ACCESS read-only
    STATUS mandatory
    DESCRIPTION
      "Number of trapTable entries. The number of trap-receiver"
    ::= { cmcTcMasterCmc9Traps 1 }

  cmcTcMasterCmc9TrapTable OBJECT-TYPE
    SYNTAX SEQUENCE OF CmcTcMasterCmc9TrapEntry
    ACCESS not-accessible
    STATUS mandatory
    DESCRIPTION
      "A list of trap-receiver entries"
    ::= { cmcTcMasterCmc9Traps 2 }

  cmcTcMasterCmc9TrapEntry OBJECT-TYPE
    SYNTAX CmcTcMasterCmc9TrapEntry
    ACCESS not-accessible
    STATUS mandatory
    DESCRIPTION
      "Entries of trapTable"
    INDEX { cmcTcMasterCmc9TrapIndex }
    ::= { cmcTcMasterCmc9TrapTable 1 }

  CmcTcMasterCmc9TrapEntry ::=
    SEQUENCE {
      cmcTcMasterCmc9TrapIndex
        INTEGER,
      cmcTcMasterCmc9TrapStatus
        INTEGER,
      cmcTcMasterCmc9TrapIPaddress
        DisplayString
    }

    cmcTcMasterCmc9TrapIndex OBJECT-TYPE
      SYNTAX INTEGER (1..32000)
      ACCESS read-only
      STATUS mandatory
      DESCRIPTION
        "Index for the trap-receiver-table. Its value ranges between
         1 and the value of cmcTcMasterCmc9TraptableNumber "
      ::= { cmcTcMasterCmc9TrapEntry 1 }

    cmcTcMasterCmc9TrapStatus OBJECT-TYPE
      SYNTAX INTEGER  {
        enabled(1),
        disabled(2)
      }
      ACCESS read-write
      STATUS mandatory
      DESCRIPTION
        "Enable or disable trap receiver"
      ::= { cmcTcMasterCmc9TrapEntry 2 }

    cmcTcMasterCmc9TrapIPaddress OBJECT-TYPE
      SYNTAX DisplayString (SIZE (0..31))
      ACCESS read-write
      STATUS mandatory
      DESCRIPTION
        "IP-address of trap-receiver"
      ::= { cmcTcMasterCmc9TrapEntry 3 }

--cmcTcMasterPcu9MibRev-group
          
  cmcTcMasterPcu9MibMajRev OBJECT-TYPE
    SYNTAX INTEGER (1..32000)
    ACCESS read-only
    STATUS mandatory
    DESCRIPTION
      "The Major Revision level.
       A change in the major revision level represents a major change
       in the architecture of the MIB. A change in the major revision 
       level may indicate a significant change in the information,
       correct interpretation of data may require a MIB document
       with the same major revision level."
    ::= { cmcTcMasterPcu9MibRev 1 }

  cmcTcMasterPcu9MibMinRev OBJECT-TYPE
    SYNTAX INTEGER (0..32000)
    ACCESS read-only
    STATUS mandatory
    DESCRIPTION
      "The Minor Revision level.
       A change in the minor revision level may represent some minor
       additional support, no changes to any pre-existing information
       has occurred."
    ::= { cmcTcMasterPcu9MibRev 2 }

  cmcTcMasterPcu9MibCondition OBJECT-TYPE
    SYNTAX INTEGER {
      other (1),
      ok (2),
      degraded (3),
      failed (4)
    }
    ACCESS read-only
    STATUS mandatory
    DESCRIPTION
      "The overall condition (status) of the system represented by
       this MIB. 
       (2) OK
       (3) a minor problem, warning condition (yellow LED on PCU)
       (4) a major problem (red LED on PCU)"
    ::= { cmcTcMasterPcu9MibRev 3 }

--cmcTcMasterPcu9Values-group

  cmcTcMasterPcu9ValueEnergy1 OBJECT-TYPE
    SYNTAX INTEGER 
    ACCESS read-only
    STATUS mandatory
    DESCRIPTION
      "Total value of the Energy (Wh), measured on IEC input 1"
    ::= { cmcTcMasterPcu9Values 1 }

  cmcTcMasterPcu9ValueEnergy2 OBJECT-TYPE
    SYNTAX INTEGER 
    ACCESS read-only
    STATUS mandatory
    DESCRIPTION
      "Actual value of the Energy (Wh), measured on IEC input 2"
    ::= { cmcTcMasterPcu9Values 2 }

  cmcTcMasterPcu9ValueEnergy1Time OBJECT-TYPE
    SYNTAX INTEGER 
    ACCESS read-only
    STATUS mandatory
    DESCRIPTION
      "Actual value of the Energy (Wh), measured on IEC input 1, can be set to 0
       Value can be used to calculate the energy over a fixed time"
    ::= { cmcTcMasterPcu9Values 3 }

  cmcTcMasterPcu9ValueEnergy2Time OBJECT-TYPE
    SYNTAX INTEGER 
    ACCESS read-only
    STATUS mandatory
    DESCRIPTION
      "Actual value of the Energy (Wh), measured on IEC input 2, can be set to 0.
       Value can be used to calculate the energy over a fixed time"
    ::= { cmcTcMasterPcu9Values 4 }

  cmcTcMasterPcu9ValuePower1 OBJECT-TYPE
    SYNTAX INTEGER 
    ACCESS read-only
    STATUS mandatory
    DESCRIPTION
      "Calculated actual power 1 (W). Calculated from cmcTcMasterPcu9ValueEnergy1/time"
    ::= { cmcTcMasterPcu9Values 5 }
          
  cmcTcMasterPcu9ValuePower2 OBJECT-TYPE
    SYNTAX INTEGER 
    ACCESS read-only
    STATUS mandatory
    DESCRIPTION
      "Calculated actual power 2 (W). Calculated from cmcTcMasterPcu9ValueEnergy2/time"
    ::= { cmcTcMasterPcu9Values 6 }
          
  cmcTcMasterPcu9ValueTemperature OBJECT-TYPE
    SYNTAX INTEGER 
    ACCESS read-only
    STATUS mandatory
    DESCRIPTION
      "Actual value of temperature 1 in deg C or deg F"
    ::= { cmcTcMasterPcu9Values 7 }
          
--cmcTcMasterPcu9Status-group

  cmcTcMasterPcu9StatusInput1 OBJECT-TYPE
    SYNTAX INTEGER {
      false(1),
      true(2),
      pending(3),
      notAvail(4)
    }
    ACCESS read-only
    STATUS mandatory
    DESCRIPTION
      "Status of digital Input 1
       (1) digital signal is true (contact closed if setup is NO)
       (2) digital signal is false(contact opened if setup is NO),
       note setup of input (NO/NC)
       (3) digital input is pending, note setup of delay"
    ::= { cmcTcMasterPcu9Status 1 }

  cmcTcMasterPcu9StatusInput2 OBJECT-TYPE
    SYNTAX INTEGER {
      false(1),
      true(2),
      pending(3),
      notAvail(4)
    }
    ACCESS read-only
    STATUS mandatory
    DESCRIPTION
      "Status of digital Input 2
       (1) digital signal is true (contact closed if setup is NO)
       (2) digital signal is false(contact opened if setup is NO),
       note setup of input (NO/NC)
       (3) digital input is pending, note setup of delay"
    ::= { cmcTcMasterPcu9Status 2 }

  cmcTcMasterPcu9StatusPower1 OBJECT-TYPE
    SYNTAX INTEGER {
      ok(1),
      tooHigh(2),
      tooLow(3),
      warning(4),
      error(5),
      notAvail(6)
    }
    ACCESS read-only
    STATUS mandatory
    DESCRIPTION
      "Status Power 1, see setpoints"
    ::= { cmcTcMasterPcu9Status 3 }

  cmcTcMasterPcu9StatusPower2 OBJECT-TYPE
    SYNTAX INTEGER {
      ok(1),
      tooHigh(2),
      tooLow(3),
      warning(4),
      error(5),
      notAvail(6)
    }
    ACCESS read-only
    STATUS mandatory
    DESCRIPTION
      "Status Power 2, see setpoints"
    ::= { cmcTcMasterPcu9Status 4 }

  cmcTcMasterPcu9StatusTemperature OBJECT-TYPE
    SYNTAX INTEGER {
      ok(1),
      tooHigh(2),
      tooLow(3),
      warning(4),
      error(5)
    }
    ACCESS read-only
    STATUS mandatory
    DESCRIPTION
      "Status temperature 1, OK/ too high/ too low
       (see setpoints of temperature 1)"
    ::= { cmcTcMasterPcu9Status 5 }

--cmcTcMasterPcu9Status-table-group

  cmcTcMasterPcu9OutletsNumber OBJECT-TYPE
    SYNTAX INTEGER 
    ACCESS read-only
    STATUS mandatory
    DESCRIPTION
      "Number of value-table entries=number of outlets available on this unit"
    ::= { cmcTcMasterPcu9StatusTable1 1 }

  cmcTcMasterPcu9StatusTable OBJECT-TYPE
    SYNTAX SEQUENCE OF CmcTcMasterPcu9StatusEntry
    ACCESS not-accessible
    STATUS mandatory
    DESCRIPTION
      "Headline of status-table"
    ::= { cmcTcMasterPcu9StatusTable1 2 }

  cmcTcMasterPcu9StatusEntry OBJECT-TYPE
    SYNTAX CmcTcMasterPcu9StatusEntry
    ACCESS not-accessible
    STATUS mandatory
    DESCRIPTION
      "Entries of status-table"
    INDEX { cmcTcMasterPcu9StatusIndex }
    ::= { cmcTcMasterPcu9StatusTable 1 }

    CmcTcMasterPcu9StatusEntry ::=
      SEQUENCE {
        cmcTcMasterPcu9StatusIndex
          INTEGER,
        cmcTcMasterPcu9StatusText
          DisplayString (SIZE (0..31)),                
        cmcTcMasterPcu9StatusStatus
          INTEGER,
        cmcTcMasterPcu9ControlSNMP
          INTEGER,
        cmcTcMasterPcu9FrontSwitch
          INTEGER,
        cmcTcMasterPcu9Delay
          INTEGER,
        cmcTcMasterPcu9Input1
          INTEGER,
        cmcTcMasterPcu9Input2
          INTEGER,
        cmcTcMasterPcu9Temperature
          INTEGER,          
        cmcTcMasterPcu9Power
          INTEGER,          
        cmcTcMasterPcu9RestoreOutputStatus
          INTEGER           
      }

    cmcTcMasterPcu9StatusIndex OBJECT-TYPE
      SYNTAX INTEGER (1..32000)
      ACCESS read-only
      STATUS mandatory
      DESCRIPTION
        "Index for the list of value entries. Its value ranges
         between 1 and the value of cmcTcMasterPcu9OutletsNumber."
      ::= { cmcTcMasterPcu9StatusEntry 1 }

    cmcTcMasterPcu9StatusText OBJECT-TYPE
      SYNTAX DisplayString (SIZE (0..31))
      ACCESS read-write
      STATUS mandatory
      DESCRIPTION
        "Descriptional text for each outlet (entry in the table)"
      ::= { cmcTcMasterPcu9StatusEntry 2 }
              
    cmcTcMasterPcu9StatusStatus OBJECT-TYPE
      SYNTAX INTEGER {
        ok(1),
        onFrontKey(2),
        offFrontKey(3),
        onWEB(4),
        offWEB(5),
        onInput1(6),
        offInput1(7),
        onInput2(8),
        offInput2(9),
        onTemp(10),
        offTemp(11),
        onSNMP(12),
        offSNMP(13),
        onTimer(14),
        offTimer(15),
        onDelay(16),
        onConsole(17),
        offConsole(18),
        onReboot(19), 
        offReboot(20),
        onPower(21),
        offPower(22)
      }
      ACCESS read-only
      STATUS mandatory
      DESCRIPTION
        "Actual status of the outlet"
      ::= { cmcTcMasterPcu9StatusEntry 3 }

    cmcTcMasterPcu9ControlSNMP OBJECT-TYPE
      SYNTAX INTEGER  {
        on(1),
        off(2)
      }
      ACCESS read-write
      STATUS mandatory
      DESCRIPTION
        "Control via SNMP"
      ::= { cmcTcMasterPcu9StatusEntry 4 }

    cmcTcMasterPcu9FrontSwitch OBJECT-TYPE
      SYNTAX INTEGER {
        disabled(1),
        enabled(2)
      }
      ACCESS read-write
      STATUS mandatory
      DESCRIPTION
        "Control via front switch"
      ::= { cmcTcMasterPcu9StatusEntry 5 }
 
    cmcTcMasterPcu9Delay OBJECT-TYPE
      SYNTAX INTEGER (0..300)
      ACCESS read-write
      STATUS mandatory
      DESCRIPTION
        "Value for delay time in seconds.
         Value>0: Output is switched off for this time (in sec)"
      ::= { cmcTcMasterPcu9StatusEntry 6 }

    cmcTcMasterPcu9Input1 OBJECT-TYPE
      SYNTAX INTEGER {
        disabled(1),
        switchOn(2),
        switchOff(3),
        switchOnOff(4)
      }
      ACCESS read-write
      STATUS mandatory
      DESCRIPTION
        "Control via digital input 1
         (1): disabled
         (2): output is switched on in case of input 1 alarm
         (3): output is switched off in case of input 1 alarm
         (4): output has same status as input 1"
      ::= { cmcTcMasterPcu9StatusEntry 7 }

    cmcTcMasterPcu9Input2 OBJECT-TYPE
      SYNTAX INTEGER {
        disabled(1),
        switchOn(2),
        switchOff(3),
        switchOnOff(4)
      }
      ACCESS read-write
      STATUS mandatory
      DESCRIPTION
        "Control via digital input 2
         (1): disabled
         (2): output is switched on in case of input 2 alarm
         (3): output is switched off in case of input 2 alarm
         (4): output has same status as input 2"             
      ::= { cmcTcMasterPcu9StatusEntry 8 }

    cmcTcMasterPcu9Temperature OBJECT-TYPE
      SYNTAX INTEGER {
        disabled(1),
        switchOffAlarm(2),
        switchOnAlarm(3),
        switchOffSetpoint(4),
        switchOnSetpoint(5)
      }
      ACCESS read-write
      STATUS mandatory
      DESCRIPTION
        "Control via temperature alarm or setpoint
         (1): disabled
         (2): output is switched off in case of temperature alarm
         (3): output is switched on in case of temperature alarm
         (4): output is switched off if temperature setpoint (cmcTcMasterPcu9SetpointTemperature)
              is reached
         (5): output is switched on if temperature setpoint (cmcTcMasterPcu9SetpointTemperature)
              is reached"
      ::= { cmcTcMasterPcu9StatusEntry 9 }   
    
    cmcTcMasterPcu9Power OBJECT-TYPE
      SYNTAX INTEGER {
        disabled(1),
        switchOffAlarm(2),
        switchOffWarning(3),
        switchOnAlarm(4),
        switchOnWarning(5)
      }
      ACCESS read-write
      STATUS mandatory
      DESCRIPTION
        "Control via power setpoint
         (1): disabled
         (2): output is switched off upon power high alarm (cmcTcMasterPcu9SetpointHighPower1)
         (3): output is switched off upon power warning (cmcTcMasterPcu9SetpointWarningPower1)
         (4): output is switched on upon power alarm (cmcTcMasterPcu9SetpointHigh(Low)Power1)
         (5): output is switched on upon power warning (cmcTcMasterPcu9SetpointWarningPower1)             "
      ::= { cmcTcMasterPcu9StatusEntry 10 }                

    cmcTcMasterPcu9RestoreOutputStatus OBJECT-TYPE
      SYNTAX INTEGER {
        disabled(1),
        enabled(2)
      }
      ACCESS read-write
      STATUS mandatory
      DESCRIPTION
        "Save last output status and switch output to this status after reboot"
      ::= { cmcTcMasterPcu9StatusEntry 11 }
                
--cmcTcMasterPcu9SetupGeneral-group

  cmcTcMasterPcu9SetTempUnit OBJECT-TYPE
    SYNTAX INTEGER {
      celsius(1),
      fahrenheit(2)
    }
    ACCESS read-write
    STATUS mandatory
    DESCRIPTION
      "Unit of all temperature values and setpoints, Celsius or Fahrenheit"
    ::= { cmcTcMasterPcu9SetupGeneral 1 }

  cmcTcMasterPcu9SetBeeper OBJECT-TYPE
    SYNTAX INTEGER {
      off(1),
      on(2),
      enableClear(3)
    }
    ACCESS read-write
    STATUS mandatory
    DESCRIPTION
      "Audible alarm in PCU unit:
       (1): beeper is off (general)
       (2): beeper is on (Alarm)
       (3): enable Clear (cmcTcMasterPcu9ClearAlarm)"
    ::= { cmcTcMasterPcu9SetupGeneral 2 }

  cmcTcMasterPcu9LogicRelay OBJECT-TYPE
    SYNTAX INTEGER {
      closeAtAlarm(1),
      openAtAlarm(2),
      off(3),
      enableRemote(4)
    }
    ACCESS read-write
    STATUS mandatory
    DESCRIPTION
      "Logic of alarm relay: 
       (1): Relay will pick up in case of an alarm
       (2): Relay will release in case of an alarm
       (3): Relay off (general)
       (4): enable remote relay control (SNMP set)"
    ::= { cmcTcMasterPcu9SetupGeneral 3 }
 
  cmcTcMasterPcu9ClearRelay OBJECT-TYPE
    SYNTAX INTEGER {
      disabled(1),
      enabled(2)
    }
    ACCESS read-write
    STATUS mandatory
    DESCRIPTION
      "Enable clear of alarm relay: 
       (1): Relay cannot be cleared by cmcTcMasterPcu9ClearAlarm
       (2): Relay can be cleared by cmcTcMasterPcu9ClearAlarm"
    ::= { cmcTcMasterPcu9SetupGeneral 4 }                  

  cmcTcMasterPcu9WebAccess OBJECT-TYPE
    SYNTAX INTEGER {
      viewOnly(1),
      fullAccess(2),
      off(3)
    }
    ACCESS read-write
    STATUS mandatory
    DESCRIPTION
      "Web access via HTTP: 
       (1): view only
       (2): full Access, read and set
       (3): Web disabled (general)"
    ::= { cmcTcMasterPcu9SetupGeneral 5 }
 
  cmcTcMasterPcu9SetupDate OBJECT-TYPE
    SYNTAX DisplayString (SIZE (0..10))
    ACCESS read-write
    STATUS mandatory
    DESCRIPTION
      "actual Date in format DD.MM.YYYY"
    ::= { cmcTcMasterPcu9SetupGeneral 6 }

  cmcTcMasterPcu9SetupTime OBJECT-TYPE
    SYNTAX DisplayString (SIZE (0..8))
    ACCESS read-write
    STATUS mandatory
    DESCRIPTION
      "actual Time in format HH:MM:SS, HH (0-23), MM (0-59), SS (0-59)"
    ::= { cmcTcMasterPcu9SetupGeneral 7 }

--cmcTcMasterPcu9TimerTable1-group
 
  cmcTcMasterPcu9TimerNumber OBJECT-TYPE
    SYNTAX INTEGER 
    ACCESS read-only
    STATUS mandatory
    DESCRIPTION
      "Number of timers available on this unit"
    ::= { cmcTcMasterPcu9TimerTable1 1 }

  cmcTcMasterPcu9TimerTable OBJECT-TYPE
    SYNTAX SEQUENCE OF CmcTcMasterPcu9TimerEntry
    ACCESS not-accessible
    STATUS mandatory
    DESCRIPTION
      "Headline of timer-table"
    ::= { cmcTcMasterPcu9TimerTable1 2 }

  cmcTcMasterPcu9TimerEntry OBJECT-TYPE
    SYNTAX CmcTcMasterPcu9TimerEntry
    ACCESS not-accessible
    STATUS mandatory
    DESCRIPTION
      "Entries of timer-table"
    INDEX { cmcTcMasterPcu9TimerIndex }
    ::= { cmcTcMasterPcu9TimerTable 1 }

    CmcTcMasterPcu9TimerEntry ::=
      SEQUENCE {
        cmcTcMasterPcu9TimerIndex
          INTEGER,
        cmcTcMasterPcu9TimerStatus
          INTEGER,
        cmcTcMasterPcu9TimerDayOfWeek
          INTEGER,  
        cmcTcMasterPcu9TimeOn 
          DisplayString (SIZE (0..5)),                              
        cmcTcMasterPcu9TimeOff 
          DisplayString (SIZE (0..5)),                              
        cmcTcMasterPcu9TimeControl
          INTEGER,
        cmcTcMasterPcu9TimerOutput1
          INTEGER,
        cmcTcMasterPcu9TimerOutput2
          INTEGER         
      }

    cmcTcMasterPcu9TimerIndex OBJECT-TYPE
      SYNTAX INTEGER (1..32000)
      ACCESS read-only
      STATUS mandatory
      DESCRIPTION
        "Index for the list of timer entries. Its value ranges
         between 1 and the value of cmcTcMasterPcu9TimerNumber." 
      ::= { cmcTcMasterPcu9TimerEntry 1 }

    cmcTcMasterPcu9TimerStatus OBJECT-TYPE
      SYNTAX INTEGER {
        switchedOff(1),
        switchedOn(2),
        noTime(3) 
      }
      ACCESS read-only
      STATUS mandatory
      DESCRIPTION
        "Actual status of the timer"
      ::= { cmcTcMasterPcu9TimerEntry 2 }

    cmcTcMasterPcu9TimerDayOfWeek OBJECT-TYPE
      SYNTAX INTEGER {
        sun(1),
        mon(2),
        tue(3) ,
        wed(4),
        thu(5),
        fre(6),
        sat(7),
        sat-sun(8),
        mo-fr(9),
        mo-su(10)
      }
      ACCESS read-write
      STATUS mandatory
      DESCRIPTION
        "Day when the timer is active"
      ::= { cmcTcMasterPcu9TimerEntry 3 }
             
    cmcTcMasterPcu9TimeOn OBJECT-TYPE
      SYNTAX DisplayString (SIZE (0..5))
      ACCESS read-write
      STATUS mandatory
      DESCRIPTION
        "Time to switch on current outlet, 
         Format: HH:MM"
      ::= { cmcTcMasterPcu9TimerEntry 4 }

    cmcTcMasterPcu9TimeOff OBJECT-TYPE
      SYNTAX DisplayString (SIZE (0..5))
      ACCESS read-write
      STATUS mandatory
      DESCRIPTION
        "Time to switch off current outlet,
         Format: HH:MM"
      ::= { cmcTcMasterPcu9TimerEntry 5 }

    cmcTcMasterPcu9TimeControl OBJECT-TYPE
      SYNTAX INTEGER {
        disabled(1),
        enabled(2)
      }
      ACCESS read-write
      STATUS mandatory
      DESCRIPTION
        "Control via RTC"
      ::= { cmcTcMasterPcu9TimerEntry 6 }

    cmcTcMasterPcu9TimerOutput1 OBJECT-TYPE
      SYNTAX INTEGER 
      ACCESS read-write
      STATUS mandatory
      DESCRIPTION
        "Output which is controlled via timer"
      ::= { cmcTcMasterPcu9TimerEntry 7 }

    cmcTcMasterPcu9TimerOutput2 OBJECT-TYPE
      SYNTAX INTEGER 
      ACCESS read-write
      STATUS mandatory
      DESCRIPTION
        "Output which is controlled via timer"
      ::= { cmcTcMasterPcu9TimerEntry 8 }

--cmcTcMasterPcu9SetupPower1-group                     

  cmcTcMasterPcu9SetupPower1Avail OBJECT-TYPE
    SYNTAX INTEGER {
      notAvailable(1),
      available(2)
    }
    ACCESS read-write
    STATUS mandatory
    DESCRIPTION
      "Energy sensor 1 sensor:   
       (1) not available
       (2) available"
    ::= { cmcTcMasterPcu9SetupPower1 1 }

  cmcTcMasterPcu9SetupPower1Relay OBJECT-TYPE
    SYNTAX INTEGER {
      disabled(1),
      enabled(2)
    }
    ACCESS read-write
    STATUS mandatory
    DESCRIPTION
      "Alert handling of Alarm Relay in case of an alarm condition
       of Power 1:  
       (1) no switching of Relays
       (2) Relay will switch"
    ::= { cmcTcMasterPcu9SetupPower1 2 }

  cmcTcMasterPcu9SetupPower1Beeper OBJECT-TYPE
    SYNTAX INTEGER {
      disabled(1),
      enabled(2)
    }
    ACCESS read-write
    STATUS mandatory
    DESCRIPTION
      "Alert handling of beeper of in case of an alarm condition
       of Power 1: 
       (1) No Audible Alarm
       (2) Start Audible Alarm"
    ::= { cmcTcMasterPcu9SetupPower1 3 }

--cmcTcMasterPcu9SetupPower2-group                     

  cmcTcMasterPcu9SetupPower2Avail OBJECT-TYPE
    SYNTAX INTEGER {
      notAvailable(1),
      available(2)
    }
    ACCESS read-write
    STATUS mandatory
    DESCRIPTION
      "Energy sensor 2:   
       (1) not available
       (2) available"
    ::= { cmcTcMasterPcu9SetupPower2 1 }

  cmcTcMasterPcu9SetupPower2Relay OBJECT-TYPE
    SYNTAX INTEGER {
      disabled(1),
      enabled(2)
    }
    ACCESS read-write
    STATUS mandatory
    DESCRIPTION
      "Alert handling of Alarm Relay in case of an alarm condition
       of Power 2:  
       (1) no switching of Relay
       (2) Relay will switch"
    ::= { cmcTcMasterPcu9SetupPower2 2 }

  cmcTcMasterPcu9SetupPower2Beeper OBJECT-TYPE
    SYNTAX INTEGER {
      disabled(1),
      enabled(2)
    }
    ACCESS read-write
    STATUS mandatory
    DESCRIPTION
      "Alert handling of beeper of in case of an alarm condition
       of Power 2: 
       (1) No Audible Alarm
       (2) Start Audible Alarm"
    ::= { cmcTcMasterPcu9SetupPower2 3 }

--cmcTcMasterPcu9SetupInput1-group

  cmcTcMasterPcu9SetupInput1Avail OBJECT-TYPE
    SYNTAX INTEGER {
      notAvailable(1),
      available(2)
    }
    ACCESS read-write
    STATUS mandatory
    DESCRIPTION
      "Input 1 sensor:   
       (1) not available
       (2) available"
    ::= { cmcTcMasterPcu9SetupInput1 1 }

  cmcTcMasterPcu9SetupInput1Relay OBJECT-TYPE
    SYNTAX INTEGER {
      disabled(1),
      enabled(2)
    }
    ACCESS read-write
    STATUS mandatory
    DESCRIPTION
      "Alert handling of Alarm Relay in case of an alarm condition
       of Input 1:  
       (1) no switching of Relay
       (2) Relay will switch"
    ::= { cmcTcMasterPcu9SetupInput1 2 }

  cmcTcMasterPcu9SetupInput1Beeper OBJECT-TYPE
    SYNTAX INTEGER {
      disabled(1),
      enabled(2)
    }
    ACCESS read-write
    STATUS mandatory
    DESCRIPTION
      "Alert handling of beeper of in case of an alarm condition
       of Input 1: 
       (1) No Audible Alarm
       (2) Start Audible Alarm"
    ::= { cmcTcMasterPcu9SetupInput1 3 }

  cmcTcMasterPcu9SetupInput1Contact OBJECT-TYPE
    SYNTAX INTEGER {
      contactNO(1),
      contactNC(2),
      notAvail(3)
    }
    ACCESS read-write
    STATUS mandatory
    DESCRIPTION
      "Setup of digital input 1"
    ::= { cmcTcMasterPcu9SetupInput1 4 }

  cmcTcMasterPcu9SetupInput1Delay OBJECT-TYPE
    SYNTAX INTEGER (0..60)
    ACCESS read-write
    STATUS mandatory
    DESCRIPTION
      "Delay for changing of input state"
    ::= { cmcTcMasterPcu9SetupInput1 5 }

--cmcTcMasterPcu9SetupInput2-group

  cmcTcMasterPcu9SetupInput2Avail OBJECT-TYPE
    SYNTAX INTEGER {
      notAvailable(1),
      available(2)
    }
    ACCESS read-write
    STATUS mandatory
    DESCRIPTION
      "Input 2 sensor:   
       (2) available
       (1) not available"
    ::= { cmcTcMasterPcu9SetupInput2 1 }

  cmcTcMasterPcu9SetupInput2Relay OBJECT-TYPE
    SYNTAX INTEGER {
      disabled(1),
      enabled(2)
    }
    ACCESS read-write
    STATUS mandatory
    DESCRIPTION
      "Alert handling of Alarm Relay in case of an alarm condition
       of Input 1:  
       (1) no switching of Relays
       (2) Relay will switch"
    ::= { cmcTcMasterPcu9SetupInput2 2 }

  cmcTcMasterPcu9SetupInput2Beeper OBJECT-TYPE
    SYNTAX INTEGER {
      disabled(1),
      enabled(2)
    }
    ACCESS read-write
    STATUS mandatory
    DESCRIPTION
      "Alert handling of beeper of in case of an alarm condition
       of Input 2: 
       (1) No Audible Alarm
       (2) Start Audible Alarm"
    ::= { cmcTcMasterPcu9SetupInput2 3 }

  cmcTcMasterPcu9SetupInput2Contact OBJECT-TYPE
    SYNTAX INTEGER {
      contactNO(1),
      contactNC(2),
      notAvail(3)
    }
    ACCESS read-write
    STATUS mandatory
    DESCRIPTION
      "Setup of digital input 2"
    ::= { cmcTcMasterPcu9SetupInput2 4 }

  cmcTcMasterPcu9SetupInput2Delay OBJECT-TYPE
    SYNTAX INTEGER (0..60)
    ACCESS read-write
    STATUS mandatory
    DESCRIPTION
      "Delay for changing of input state"
    ::= { cmcTcMasterPcu9SetupInput2 5 }

--cmcTcMasterPcu9SetupTemperature-group                     

  cmcTcMasterPcu9SetupTemperatureAvail OBJECT-TYPE
    SYNTAX INTEGER {
      notAvailable(1),
      available(2)
    }
    ACCESS read-write
    STATUS mandatory
    DESCRIPTION
      "Temp sensor 1:   
       (1) not available
       (2) available"
    ::= { cmcTcMasterPcu9SetupTemperature 1 }

  cmcTcMasterPcu9SetupTemperatureRelay OBJECT-TYPE
    SYNTAX INTEGER {
      disabled(1),
      enabled(2)
    }
    ACCESS read-write
    STATUS mandatory
    DESCRIPTION
      "Alert handling of Alarm Relay in case of an alarm condition
       of Temperature:  
       (1) no switching of Relays
       (2) Relay will switch"
    ::= { cmcTcMasterPcu9SetupTemperature 2 }

  cmcTcMasterPcu9SetupTemperatureBeeper OBJECT-TYPE
    SYNTAX INTEGER {
      disabled(1),
      enabled(2)
    }
    ACCESS read-write
    STATUS mandatory
    DESCRIPTION
      "Alert handling of beeper of in case of an alarm condition
       of Temperature: 
       (1) No Audible Alarm
       (2) Start Audible Alarm"
    ::= { cmcTcMasterPcu9SetupTemperature 3 }

--cmcTcMasterPcu9SetupGeneral-group

  cmcTcMasterPcu9SetMessage OBJECT-TYPE
    SYNTAX DisplayString (SIZE (0..31))
    ACCESS read-write
    STATUS mandatory
    DESCRIPTION
      "Set message"
    ::= { cmcTcMasterPcu9SetupDevice 1 }

--cmcTcMasterPcu9Setpoints-group

  cmcTcMasterPcu9SetpointHighPower1 OBJECT-TYPE
    SYNTAX INTEGER 
    ACCESS read-write
    STATUS mandatory
    DESCRIPTION
      "Setpoint high value power consumption 1 alarm"
    ::= { cmcTcMasterPcu9Setpoints 1 }

  cmcTcMasterPcu9SetpointWarningPower1 OBJECT-TYPE
    SYNTAX INTEGER 
    ACCESS read-write
    STATUS mandatory
    DESCRIPTION
      "Setpoint warning value power consumption 1 alarm"
    ::= { cmcTcMasterPcu9Setpoints 2 }

  cmcTcMasterPcu9SetpointLowPower1 OBJECT-TYPE
    SYNTAX INTEGER
    ACCESS read-write
    STATUS mandatory
    DESCRIPTION
      "Setpoint low value power consumption 1 alarm"
    ::= { cmcTcMasterPcu9Setpoints 3 }

  cmcTcMasterPcu9SetpointHighPower2 OBJECT-TYPE
    SYNTAX INTEGER 
    ACCESS read-write
    STATUS mandatory
    DESCRIPTION
      "Setpoint high value power consumption 2 alarm"
    ::= { cmcTcMasterPcu9Setpoints 4 }

  cmcTcMasterPcu9SetpointWarningPower2 OBJECT-TYPE
    SYNTAX INTEGER 
    ACCESS read-write
    STATUS mandatory
    DESCRIPTION
      "Setpoint warning value power consumption 2 alarm"
    ::= { cmcTcMasterPcu9Setpoints 5 }

  cmcTcMasterPcu9SetpointLowPower2 OBJECT-TYPE
    SYNTAX INTEGER
    ACCESS read-write
    STATUS mandatory
    DESCRIPTION
      "Setpoint low value power consumption 2 alarm"
    ::= { cmcTcMasterPcu9Setpoints 6 }

  cmcTcMasterPcu9SetpointHighTemperature OBJECT-TYPE
    SYNTAX INTEGER (0..200)
    ACCESS read-write
    STATUS mandatory
    DESCRIPTION
      "Setpoint high value alarm temperature "
    ::= { cmcTcMasterPcu9Setpoints 7 }

  cmcTcMasterPcu9SetpointLowTemperature OBJECT-TYPE
    SYNTAX INTEGER (0..50)
    ACCESS read-write
    STATUS mandatory
    DESCRIPTION
      "Setpoint low value alarm temperature "
    ::= { cmcTcMasterPcu9Setpoints 8 }
 
  cmcTcMasterPcu9SetpointTemperature OBJECT-TYPE
    SYNTAX INTEGER (0..200)
    ACCESS read-write
    STATUS mandatory
    DESCRIPTION
      "Setpoint temperature for outlet control 
       and temperature warning"
    ::= { cmcTcMasterPcu9Setpoints 9 }

  cmcTcMasterPcu9SetpointTemperatureHyst OBJECT-TYPE
    SYNTAX INTEGER (0..15)
    ACCESS read-write
    STATUS mandatory
    DESCRIPTION
      "Hysteresis for cmcTcMasterPcu9SetpointTemperature"
    ::= { cmcTcMasterPcu9Setpoints 10 }
 
--cmcTcMasterPcu9Control-group

  cmcTcMasterPcu9ResetEnergy1 OBJECT-TYPE
    SYNTAX INTEGER {
      noReset(1),
      reset(2)
    }
    ACCESS read-write
    STATUS mandatory
    DESCRIPTION
      "Reset value of cmcTcMasterPcu9ValueEnergy1Time"
    ::= { cmcTcMasterPcu9Control 1 }

  cmcTcMasterPcu9ResetEnergy2 OBJECT-TYPE
    SYNTAX INTEGER {
      noReset(1),
      reset(2)
    }
    ACCESS read-write
    STATUS mandatory
    DESCRIPTION
      "Reset value of cmcTcMasterPcu9ValueEnergy2Time"
    ::= { cmcTcMasterPcu9Control 2 }

  cmcTcMasterPcu9ControlAlarmRelay OBJECT-TYPE
    SYNTAX INTEGER {
      relayOff(1),
      relayOn(2)
    }
    ACCESS read-write
    STATUS mandatory
    DESCRIPTION
      "Control of Alarm relay"
    ::= { cmcTcMasterPcu9Control 3 }

  cmcTcMasterPcu9ClearAlarm OBJECT-TYPE
    SYNTAX INTEGER {
      noClear(1),
      clear(2)
    }
    ACCESS read-write
    STATUS mandatory
    DESCRIPTION
      "Clear alarm, beeper and relay"
    ::= { cmcTcMasterPcu9Control 4 }

--cmcTcMasterPcu9TrapTable-group

  cmcTcMasterPcu9TrapTableNumber OBJECT-TYPE
    SYNTAX INTEGER 
    ACCESS read-only
    STATUS mandatory
    DESCRIPTION
      "Number of cmcTcMasterPcu9TrapTable entries. The number of trap-receivers avail."
    ::= { cmcTcMasterPcu9Traps 1 }

  cmcTcMasterPcu9TrapTable OBJECT-TYPE
    SYNTAX SEQUENCE OF CmcTcMasterPcu9TrapEntry
    ACCESS not-accessible
    STATUS mandatory
    DESCRIPTION
      "A list of trap-receiver entries"
    ::= { cmcTcMasterPcu9Traps 2 }

  cmcTcMasterPcu9TrapEntry OBJECT-TYPE
    SYNTAX CmcTcMasterPcu9TrapEntry
    ACCESS not-accessible
    STATUS mandatory
    DESCRIPTION
      "Entries of cmcTcMasterPcu9TrapTable"
    INDEX { cmcTcMasterPcu9TrapIndex }
    ::= { cmcTcMasterPcu9TrapTable 1 }

    CmcTcMasterPcu9TrapEntry ::=
      SEQUENCE {
        cmcTcMasterPcu9TrapIndex
          INTEGER,
        cmcTcMasterPcu9TrapStatus
          INTEGER,
        cmcTcMasterPcu9TrapIPaddress
          DisplayString
      }

    cmcTcMasterPcu9TrapIndex OBJECT-TYPE
      SYNTAX INTEGER (1..32000)
      ACCESS read-only
      STATUS mandatory
      DESCRIPTION
        "Index for the trap-receiver-table. Its value ranges between
         1 and the value of cmcTcMasterPcu9TrapTableNumber "
      ::= { cmcTcMasterPcu9TrapEntry 1 }

    cmcTcMasterPcu9TrapStatus OBJECT-TYPE
      SYNTAX INTEGER {
        disabled(1),
        enabled(2)
      }
      ACCESS read-write
      STATUS mandatory
      DESCRIPTION
        "Enable or disable trap receiver"
      ::= { cmcTcMasterPcu9TrapEntry 2 }

    cmcTcMasterPcu9TrapIPaddress OBJECT-TYPE
      SYNTAX DisplayString (SIZE (0..15))
      ACCESS read-write
      STATUS mandatory
      DESCRIPTION
        "IP-address of trap-receiver"
      ::= { cmcTcMasterPcu9TrapEntry 3 }

--cmcTcMasterTc9MibRev-group
          
  cmcTcMasterTc9MibMajRev OBJECT-TYPE
    SYNTAX INTEGER (1..32000)
    ACCESS read-only
    STATUS mandatory
    DESCRIPTION
      "The Major Revision level.
       A change in the major revision level represents a major change
       in the architecture of the MIB. A change in the major revision 
       level may indicate a significant change in the information,
       correct interpretation of data may require a MIB document
       with the same major revision level."
    ::= { cmcTcMasterTc9MibRev 1 }

  cmcTcMasterTc9MibMinRev OBJECT-TYPE
    SYNTAX INTEGER (0..32000)
    ACCESS read-only
    STATUS mandatory
    DESCRIPTION
      "The Minor Revision level.
       A change in the minor revision level may represent some minor
       additional support, no changes to any pre-existing information
       has occurred."
    ::= { cmcTcMasterTc9MibRev 2 }

  cmcTcMasterTc9MibCondition OBJECT-TYPE
    SYNTAX INTEGER {
      other (1),
      ok (2),
      degraded (3),
      failed (4),
      configChanged (5)
    }
    ACCESS read-only
    STATUS mandatory
    DESCRIPTION
      "The overall condition (status) of the system represented by
       this MIB. 
       (2) OK
       (3) a minor problem, warning condition (yellow LED on CMC-TC)
       (4) a major problem (red LED on CMC-TC)
       (5) configuration of sensor units changed or
           unit detected (red/yellow/green LED on CMC-TC)"
    ::= { cmcTcMasterTc9MibRev 3 }
          
--cmcTcMasterTc9Status-group

  cmcTcMasterTc9StatusDeviceCMC OBJECT-TYPE
    SYNTAX INTEGER {
      failed(1),
      ok(2)
    }
    ACCESS read-only
    STATUS mandatory
    DESCRIPTION
      "General Status of CMC-TC unit itself
       (1) failed
       (2) OK"
    ::= { cmcTcMasterTc9Status 1 }

  cmcTcMasterTc9UnitsConnected OBJECT-TYPE
    SYNTAX INTEGER 
    ACCESS read-only
    STATUS mandatory
    DESCRIPTION
      "Number of sensor units connected to the CMC-TC, Port 1 to 4"
    ::= { cmcTcMasterTc9Status 2 }

--unit 1

  cmcTcMasterTc9Unit1TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 1"
    ::= { cmcTcMasterTc9StatusSensorUnit1 1 }

  cmcTcMasterTc9Unit1Text OBJECT-TYPE
    SYNTAX DisplayString (SIZE (0..10))
    ACCESS read-write
    STATUS mandatory
    DESCRIPTION
      "Descriptional text for sensor unit connected to port 1"
    ::= { cmcTcMasterTc9StatusSensorUnit1 2 }

  cmcTcMasterTc9Unit1Serial OBJECT-TYPE
    SYNTAX INTEGER 
    ACCESS read-only
    STATUS mandatory
    DESCRIPTION
      "Serialnumber of sensor unit connected to port 1"
    ::= { cmcTcMasterTc9StatusSensorUnit1 3 }

  cmcTcMasterTc9Unit1Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 1
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc9StatusSensorUnit1 4 }

-- Sensors
              
  cmcTcMasterTc9Unit1NumberOfSensors OBJECT-TYPE
    SYNTAX INTEGER 
    ACCESS read-only
    STATUS mandatory
    DESCRIPTION
      "Number of sensors connected to sensor unit 1"
    ::= { cmcTcMasterTc9StatusUnit1Sensors 1 }

-- table with entry for each sensor available on this unit              

  cmcTcMasterTc9Unit1SensorTable OBJECT-TYPE
    SYNTAX SEQUENCE OF CmcTcMasterTc9Unit1SensorEntry
    ACCESS not-accessible
    STATUS mandatory
    DESCRIPTION
      "Headline of sensor table"
    ::= { cmcTcMasterTc9StatusUnit1Sensors 2 }

  cmcTcMasterTc9Unit1SensorEntry OBJECT-TYPE
    SYNTAX CmcTcMasterTc9Unit1SensorEntry
    ACCESS not-accessible
    STATUS mandatory
    DESCRIPTION
      "Entries of sensor table"
    INDEX { cmcTcMasterTc9Unit1SensorIndex }
    ::= { cmcTcMasterTc9Unit1SensorTable 1 }

    CmcTcMasterTc9Unit1SensorEntry ::=
      SEQUENCE {
        cmcTcMasterTc9Unit1SensorIndex
          INTEGER,
        cmcTcMasterTc9Unit1SensorType
          INTEGER,
        cmcTcMasterTc9Unit1SensorText
          DisplayString (SIZE (0..20)),                
        cmcTcMasterTc9Unit1SensorStatus
          INTEGER,
        cmcTcMasterTc9Unit1SensorValue
          INTEGER,
        cmcTcMasterTc9Unit1SensorSetHigh
          INTEGER,
        cmcTcMasterTc9Unit1SensorSetLow
          INTEGER,
        cmcTcMasterTc9Unit1SensorSetWarn
          INTEGER                
      }

    cmcTcMasterTc9Unit1SensorIndex OBJECT-TYPE
      SYNTAX INTEGER (1..32000)
      ACCESS read-only
      STATUS mandatory
      DESCRIPTION
        "Index for the list of value entries. Its value ranges
         between 1 and the value of cmcTcMasterTc9Unit1NumberOfSensors." 
      ::= { cmcTcMasterTc9Unit1SensorEntry 1 }

    cmcTcMasterTc9Unit1SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 1 to sensor[cmcTcMasterTc9Unit1SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc9Unit1SensorEntry 2 }

    cmcTcMasterTc9Unit1SensorText OBJECT-TYPE
      SYNTAX DisplayString (SIZE (0..20))
      ACCESS read-write
      STATUS mandatory
      DESCRIPTION
        "Descriptional text for each sensor (entry in the table)"
      ::= { cmcTcMasterTc9Unit1SensorEntry 3 }
              
    cmcTcMasterTc9Unit1SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc9Unit1SensorEntry 4 }

    cmcTcMasterTc9Unit1SensorValue OBJECT-TYPE
      SYNTAX INTEGER 
      ACCESS read-only
      STATUS mandatory
      DESCRIPTION
        "Value of sensor"
      ::= { cmcTcMasterTc9Unit1SensorEntry 5 }

    cmcTcMasterTc9Unit1SensorSetHigh OBJECT-TYPE
      SYNTAX INTEGER (0..300) 
      ACCESS read-write
      STATUS mandatory
      DESCRIPTION
        "Value for high setpoint of sensor"
      ::= { cmcTcMasterTc9Unit1SensorEntry 6 }

    cmcTcMasterTc9Unit1SensorSetLow OBJECT-TYPE
      SYNTAX INTEGER (0..300) 
      ACCESS read-write
      STATUS mandatory
      DESCRIPTION
        "Value for low setpoint of sensor,
         also used as alarm delay"
      ::= { cmcTcMasterTc9Unit1SensorEntry 7 }

    cmcTcMasterTc9Unit1SensorSetWarn OBJECT-TYPE
      SYNTAX INTEGER (0..300) 
      ACCESS read-write
      STATUS mandatory
      DESCRIPTION
        "Value for warning setpoint of sensor, 
         also used as fan threshold"
      ::= { cmcTcMasterTc9Unit1SensorEntry 8 }
                
-- Outputs              

  cmcTcMasterTc9Unit1NumberOfOutputs OBJECT-TYPE
    SYNTAX INTEGER 
    ACCESS read-only
    STATUS mandatory
    DESCRIPTION
      "Number of outputs available on sensor unit 1"
    ::= { cmcTcMasterTc9StatusUnit1Outputs 1 }

-- table with entry for each output available on this unit              
                
  cmcTcMasterTc9Unit1OutputTable OBJECT-TYPE
    SYNTAX SEQUENCE OF CmcTcMasterTc9Unit1OutputEntry
    ACCESS not-accessible
    STATUS mandatory
    DESCRIPTION
      "Headline of output table"
    ::= { cmcTcMasterTc9StatusUnit1Outputs 2 }

  cmcTcMasterTc9Unit1OutputEntry OBJECT-TYPE
    SYNTAX CmcTcMasterTc9Unit1OutputEntry
    ACCESS not-accessible
    STATUS mandatory
    DESCRIPTION
      "Entries of output table"
    INDEX { cmcTcMasterTc9Unit1OutputIndex }
    ::= { cmcTcMasterTc9Unit1OutputTable 1 }

    CmcTcMasterTc9Unit1OutputEntry ::=
      SEQUENCE {
        cmcTcMasterTc9Unit1OutputIndex
          INTEGER,
        cmcTcMasterTc9Unit1OutputType
          INTEGER,
        cmcTcMasterTc9Unit1OutputText
          DisplayString (SIZE (0..20)),                
        cmcTcMasterTc9Unit1OutputStatus
          INTEGER,
        cmcTcMasterTc9Unit1OutputValue
          INTEGER,
        cmcTcMasterTc9Unit1OutputSet
          INTEGER,
        cmcTcMasterTc9Unit1OutputConfig
          INTEGER,                
        cmcTcMasterTc9Unit1OutputDelay
          INTEGER,
        cmcTcMasterTc9Unit1OutputTimeoutAction
          INTEGER
      }

    cmcTcMasterTc9Unit1OutputIndex OBJECT-TYPE
      SYNTAX INTEGER (1..32000)
      ACCESS read-only
      STATUS mandatory
      DESCRIPTION
        "Index for the list of output entries. Its value ranges
         between 1 and the value of cmcTcMasterTc9Unit1NumberOfOutputs." 
      ::= { cmcTcMasterTc9Unit1OutputEntry 1 }

    cmcTcMasterTc9Unit1OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 1 to output[cmcTcMasterTc9Unit1OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc9Unit1OutputEntry 2 }

    cmcTcMasterTc9Unit1OutputText OBJECT-TYPE
      SYNTAX DisplayString (SIZE (0..20))
      ACCESS read-write
      STATUS mandatory
      DESCRIPTION
        "Descriptional text for each output (entry in the table)"
      ::= { cmcTcMasterTc9Unit1OutputEntry 3 }
              
    cmcTcMasterTc9Unit1OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc9Unit1OutputEntry 4 }

    cmcTcMasterTc9Unit1OutputValue OBJECT-TYPE
      SYNTAX INTEGER (-32000..32000) 
      ACCESS read-write
      STATUS mandatory
      DESCRIPTION
        "Value for output"
      ::= { cmcTcMasterTc9Unit1OutputEntry 5 }

    cmcTcMasterTc9Unit1OutputSet OBJECT-TYPE
      SYNTAX INTEGER {
        off (1),
        on (2),
        lock (3),
        unlock (4),
        unlockDelay (5)
      }
      ACCESS read-write
      STATUS mandatory
      DESCRIPTION
        "Command for output"
      ::= { cmcTcMasterTc9Unit1OutputEntry 6 }

    cmcTcMasterTc9Unit1OutputConfig OBJECT-TYPE
      SYNTAX INTEGER {
        disRemote (1),
        enRemote (2)
      }
      ACCESS read-write
      STATUS mandatory
      DESCRIPTION
        "Configuration for output
         1: 	disable remote control (e.g. keypad)
         2: 	enable remote control"
      ::= { cmcTcMasterTc9Unit1OutputEntry 7 }

    cmcTcMasterTc9Unit1OutputDelay OBJECT-TYPE
      SYNTAX INTEGER (0..999) 
      ACCESS read-write
      STATUS mandatory
      DESCRIPTION
        "Unsigned Value for delay, 
         after this time the output will fall into the previous state"
      ::= { cmcTcMasterTc9Unit1OutputEntry 8 }

    cmcTcMasterTc9Unit1OutputTimeoutAction OBJECT-TYPE
      SYNTAX INTEGER {
        stay (1),
        off (2),
        on (3)
      }
      ACCESS read-write
      STATUS mandatory
      DESCRIPTION
        "State for output if timeout (RS422) occurs"
      ::= { cmcTcMasterTc9Unit1OutputEntry 9 }
 
-- Messages
              
  cmcTcMasterTc9Unit1NumberOfMsgs OBJECT-TYPE
    SYNTAX INTEGER 
    ACCESS read-only
    STATUS mandatory
    DESCRIPTION
      "Number of messages that can be created with sensor unit 1"
    ::= { cmcTcMasterTc9StatusUnit1Msg 1 }

-- table with entry for each alarm available on this unit               
                
  cmcTcMasterTc9Unit1MsgTable OBJECT-TYPE
    SYNTAX SEQUENCE OF CmcTcMasterTc9Unit1MsgEntry
    ACCESS not-accessible
    STATUS mandatory
    DESCRIPTION
      "Headline of message table"
    ::= { cmcTcMasterTc9StatusUnit1Msg 2 }

  cmcTcMasterTc9Unit1MsgEntry OBJECT-TYPE
    SYNTAX CmcTcMasterTc9Unit1MsgEntry
    ACCESS not-accessible
    STATUS mandatory
    DESCRIPTION
      "Entries of message table"
    INDEX { cmcTcMasterTc9Unit1MsgIndex }
    ::= { cmcTcMasterTc9Unit1MsgTable 1 }

    CmcTcMasterTc9Unit1MsgEntry ::=
      SEQUENCE {
        cmcTcMasterTc9Unit1MsgIndex
          INTEGER, 
        cmcTcMasterTc9Unit1MsgText
          DisplayString (SIZE (0..20)),                
        cmcTcMasterTc9Unit1MsgStatus
          INTEGER,                
        cmcTcMasterTc9Unit1MsgRelay
          INTEGER,
        cmcTcMasterTc9Unit1MsgBeeper
          INTEGER,
        cmcTcMasterTc9Unit1MsgTrap1
          INTEGER,
        cmcTcMasterTc9Unit1MsgTrap2
          INTEGER,
        cmcTcMasterTc9Unit1MsgTrap3
          INTEGER,
        cmcTcMasterTc9Unit1MsgTrap4
          INTEGER,                 
        cmcTcMasterTc9Unit1MsgQuit
          INTEGER              
      }

    cmcTcMasterTc9Unit1MsgIndex OBJECT-TYPE
      SYNTAX INTEGER (1..32000)
      ACCESS read-only
      STATUS mandatory
      DESCRIPTION
        "Index for the list of message entries. Its value ranges
         between 1 and the value of cmcTcMasterTc9Unit1NumberOfMsgs." 
      ::= { cmcTcMasterTc9Unit1MsgEntry 1 }

    cmcTcMasterTc9Unit1MsgText OBJECT-TYPE
      SYNTAX DisplayString (SIZE (0..20))
      ACCESS read-write
      STATUS mandatory
      DESCRIPTION
        "Descriptional text for each message (entry in the table)"
      ::= { cmcTcMasterTc9Unit1MsgEntry 2 }
              
    cmcTcMasterTc9Unit1MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc9Unit1OutputSet)
         17: door is unlocked by WEB
         18: door is unlocked by timer
         19: no access, wrong keycode or cardnumber
         20: orientation of PSM-Unit is circuit 1
         21: orientation of PSM-Unit is circuit 2"
      ::= { cmcTcMasterTc9Unit1MsgEntry 3 }
        
    cmcTcMasterTc9Unit1MsgRelay OBJECT-TYPE
      SYNTAX INTEGER {
        disable (1),
        enable (2)
      }
      ACCESS read-write
      STATUS mandatory
      DESCRIPTION
        "Setup of Alarm relay for this message/alarm
         1:        no switching of alarm relay             
         2:        switching of alarm relay" 
      ::= { cmcTcMasterTc9Unit1MsgEntry 4 }

    cmcTcMasterTc9Unit1MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc9Unit1MsgEntry 5 }

    cmcTcMasterTc9Unit1MsgTrap1 OBJECT-TYPE
      SYNTAX INTEGER {
        disable (1),
        enable (2)
      }
      ACCESS read-write
      STATUS mandatory
      DESCRIPTION
        "Trap receiver 1 activated"
      ::= { cmcTcMasterTc9Unit1MsgEntry 6 }

    cmcTcMasterTc9Unit1MsgTrap2 OBJECT-TYPE
      SYNTAX INTEGER {
        disable (1),
        enable (2)
      }
      ACCESS read-write
      STATUS mandatory
      DESCRIPTION
        "Trap receiver 2 activated"
      ::= { cmcTcMasterTc9Unit1MsgEntry 7 }
 
    cmcTcMasterTc9Unit1MsgTrap3 OBJECT-TYPE
      SYNTAX INTEGER {
        disable (1),
        enable (2)
      }
      ACCESS read-write
      STATUS mandatory
      DESCRIPTION
        "Trap receiver 3 activated"
      ::= { cmcTcMasterTc9Unit1MsgEntry 8 }

    cmcTcMasterTc9Unit1MsgTrap4 OBJECT-TYPE
      SYNTAX INTEGER {
        disable (1),
        enable (2)
      }
      ACCESS read-write
      STATUS mandatory
      DESCRIPTION
        "Trap receiver 4 and Event Logging activated"
      ::= { cmcTcMasterTc9Unit1MsgEntry 9 }

    cmcTcMasterTc9Unit1MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc9Unit1MsgEntry 10 }

-- unit2

  cmcTcMasterTc9Unit2TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 2"
    ::= { cmcTcMasterTc9StatusSensorUnit2 1 }

  cmcTcMasterTc9Unit2Text OBJECT-TYPE
    SYNTAX DisplayString (SIZE (0..10))
    ACCESS read-write
    STATUS mandatory
    DESCRIPTION
      "Descriptional text for sensor unit connected to port 2"
    ::= { cmcTcMasterTc9StatusSensorUnit2 2 }

  cmcTcMasterTc9Unit2Serial OBJECT-TYPE
    SYNTAX INTEGER 
    ACCESS read-only
    STATUS mandatory
    DESCRIPTION
      "Serialnumber of sensor unit connected to port 2"
    ::= { cmcTcMasterTc9StatusSensorUnit2 3 }

  cmcTcMasterTc9Unit2Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 2
       (1) OK
       (2) error
       (3) configuration of sensor unit has changed, confirmation required
       (4) Quit from sensor unit to confirm configuration changes
       (5) timeout of sensor unit, confirmation required
       (6) sensor unit detected, needs to be confirmed
       (8) supply voltage is too low"              
    ::= { cmcTcMasterTc9StatusSensorUnit2 4 }

-- unit 2 table

-- Sensors              

  cmcTcMasterTc9Unit2NumberOfSensors OBJECT-TYPE
    SYNTAX INTEGER 
    ACCESS read-only
    STATUS mandatory
    DESCRIPTION
      "Number of sensors connected to sensor unit 2"
    ::= { cmcTcMasterTc9StatusUnit2Sensors 1 }

-- table with entry for each sensor available on this unit              

  cmcTcMasterTc9Unit2SensorTable OBJECT-TYPE
    SYNTAX SEQUENCE OF CmcTcMasterTc9Unit2SensorEntry
    ACCESS not-accessible
    STATUS mandatory
    DESCRIPTION
      "Headline of sensor table"
    ::= { cmcTcMasterTc9StatusUnit2Sensors 2 }

  cmcTcMasterTc9Unit2SensorEntry OBJECT-TYPE
    SYNTAX CmcTcMasterTc9Unit2SensorEntry
    ACCESS not-accessible
    STATUS mandatory
    DESCRIPTION
      "Entries of sensor table"
    INDEX { cmcTcMasterTc9Unit2SensorIndex }
    ::= { cmcTcMasterTc9Unit2SensorTable 1 }

    CmcTcMasterTc9Unit2SensorEntry ::=
      SEQUENCE {
        cmcTcMasterTc9Unit2SensorIndex
          INTEGER,
        cmcTcMasterTc9Unit2SensorType
          INTEGER,
        cmcTcMasterTc9Unit2SensorText
          DisplayString (SIZE (0..20)),                
        cmcTcMasterTc9Unit2SensorStatus
          INTEGER,
        cmcTcMasterTc9Unit2SensorValue
          INTEGER,
        cmcTcMasterTc9Unit2SensorSetHigh
          INTEGER,
        cmcTcMasterTc9Unit2SensorSetLow
          INTEGER,                 
        cmcTcMasterTc9Unit2SensorSetWarn
          INTEGER  
      }

    cmcTcMasterTc9Unit2SensorIndex OBJECT-TYPE
      SYNTAX INTEGER (1..32000)
      ACCESS read-only
      STATUS mandatory
      DESCRIPTION
        "Index for the list of value entries. Its value ranges
         between 1 and the value of cmcTcMasterTc9Unit2NumberOfSensors." 
      ::= { cmcTcMasterTc9Unit2SensorEntry 1 }

    cmcTcMasterTc9Unit2SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 2 to sensor[cmcTcMasterTc9Unit2SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc9Unit2SensorEntry 2 }
        
    cmcTcMasterTc9Unit2SensorText OBJECT-TYPE
      SYNTAX DisplayString (SIZE (0..20))
      ACCESS read-write
      STATUS mandatory
      DESCRIPTION
        "Descriptional text for each sensor (entry in the table)"
      ::= { cmcTcMasterTc9Unit2SensorEntry 3 }
              
    cmcTcMasterTc9Unit2SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc9Unit2SensorEntry 4 }

    cmcTcMasterTc9Unit2SensorValue OBJECT-TYPE
      SYNTAX INTEGER 
      ACCESS read-only
      STATUS mandatory
      DESCRIPTION
        "Value of sensor"
      ::= { cmcTcMasterTc9Unit2SensorEntry 5 }

    cmcTcMasterTc9Unit2SensorSetHigh OBJECT-TYPE
      SYNTAX INTEGER (0..300) 
      ACCESS read-write
      STATUS mandatory
      DESCRIPTION
        "Value for high setpoint of sensor"
      ::= { cmcTcMasterTc9Unit2SensorEntry 6 }

    cmcTcMasterTc9Unit2SensorSetLow OBJECT-TYPE
      SYNTAX INTEGER (0..300) 
      ACCESS read-write
      STATUS mandatory
      DESCRIPTION
        "Value for low setpoint of sensor,
         also used as alarm delay"
      ::= { cmcTcMasterTc9Unit2SensorEntry 7 }

    cmcTcMasterTc9Unit2SensorSetWarn OBJECT-TYPE
      SYNTAX INTEGER (0..300) 
      ACCESS read-write
      STATUS mandatory
      DESCRIPTION
        "Value for warning setpoint of sensor,
         also used as fan threshold"
      ::= { cmcTcMasterTc9Unit2SensorEntry 8 }

-- Outputs              

  cmcTcMasterTc9Unit2NumberOfOutputs OBJECT-TYPE
    SYNTAX INTEGER 
    ACCESS read-only
    STATUS mandatory
    DESCRIPTION
      "Number of outputs available on sensor unit 2"
    ::= { cmcTcMasterTc9StatusUnit2Outputs 1 }

-- table with entry for each output available on this unit              
                
  cmcTcMasterTc9Unit2OutputTable OBJECT-TYPE
    SYNTAX SEQUENCE OF CmcTcMasterTc9Unit2OutputEntry
    ACCESS not-accessible
    STATUS mandatory
    DESCRIPTION
      "Headline of output table"
    ::= { cmcTcMasterTc9StatusUnit2Outputs 2 }

  cmcTcMasterTc9Unit2OutputEntry OBJECT-TYPE
    SYNTAX CmcTcMasterTc9Unit2OutputEntry
    ACCESS not-accessible
    STATUS mandatory
    DESCRIPTION
      "Entries of output table"
    INDEX { cmcTcMasterTc9Unit2OutputIndex }
    ::= { cmcTcMasterTc9Unit2OutputTable 1 }

    CmcTcMasterTc9Unit2OutputEntry ::=
      SEQUENCE {
        cmcTcMasterTc9Unit2OutputIndex
          INTEGER,
        cmcTcMasterTc9Unit2OutputType
          INTEGER,
        cmcTcMasterTc9Unit2OutputText
          DisplayString (SIZE (0..20)),                
        cmcTcMasterTc9Unit2OutputStatus
          INTEGER,
        cmcTcMasterTc9Unit2OutputValue
          INTEGER,
        cmcTcMasterTc9Unit2OutputSet
          INTEGER,
        cmcTcMasterTc9Unit2OutputConfig
          INTEGER,                
        cmcTcMasterTc9Unit2OutputDelay
          INTEGER,
        cmcTcMasterTc9Unit2OutputTimeoutAction
          INTEGER
      }

    cmcTcMasterTc9Unit2OutputIndex OBJECT-TYPE
      SYNTAX INTEGER (1..32000)
      ACCESS read-only
      STATUS mandatory
      DESCRIPTION
        "Index for the list of output entries. Its value ranges
         between 1 and the value of cmcTcMasterTc9Unit2NumberOfOutputs." 
      ::= { cmcTcMasterTc9Unit2OutputEntry 1 }

    cmcTcMasterTc9Unit2OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 2 to output[cmcTcMasterTc9Unit2OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc9Unit2OutputEntry 2 }

        
    cmcTcMasterTc9Unit2OutputText OBJECT-TYPE
      SYNTAX DisplayString (SIZE (0..20))
      ACCESS read-write
      STATUS mandatory
      DESCRIPTION
        "Descriptional text for each output (entry in the table)"
      ::= { cmcTcMasterTc9Unit2OutputEntry 3 }
              
    cmcTcMasterTc9Unit2OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc9Unit2OutputEntry 4 }

    cmcTcMasterTc9Unit2OutputValue OBJECT-TYPE
      SYNTAX INTEGER (-32000..32000) 
      ACCESS read-write
      STATUS mandatory
      DESCRIPTION
        "Value for output"
      ::= { cmcTcMasterTc9Unit2OutputEntry 5 }

    cmcTcMasterTc9Unit2OutputSet OBJECT-TYPE
      SYNTAX INTEGER {
        off (1),
        on (2),
        lock (3),
        unlock (4),
        unlockDelay (5)
      }
      ACCESS read-write
      STATUS mandatory
      DESCRIPTION
        "Command for output"
      ::= { cmcTcMasterTc9Unit2OutputEntry 6 }

    cmcTcMasterTc9Unit2OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc9Unit2OutputEntry 7 }

    cmcTcMasterTc9Unit2OutputDelay OBJECT-TYPE
      SYNTAX INTEGER (0..999) 
      ACCESS read-write
      STATUS mandatory
      DESCRIPTION
        "Unsigned Value for delay, 
         after this time the output will fall into the previous state"
      ::= { cmcTcMasterTc9Unit2OutputEntry 8 }

    cmcTcMasterTc9Unit2OutputTimeoutAction OBJECT-TYPE
      SYNTAX INTEGER {
        stay (1),
        off (2),
        on (3)
      }
      ACCESS read-write
      STATUS mandatory
      DESCRIPTION
        "State for output if timeout (RS422) occurs"
      ::= { cmcTcMasterTc9Unit2OutputEntry 9 }

-- Messages
              
  cmcTcMasterTc9Unit2NumberOfMsgs OBJECT-TYPE
    SYNTAX INTEGER 
    ACCESS read-only
    STATUS mandatory
    DESCRIPTION
      "Number of messages that can be created with sensor unit 2"
    ::= { cmcTcMasterTc9StatusUnit2Msg 1 }

-- table with entry for each alarm available on this unit               
                
  cmcTcMasterTc9Unit2MsgTable OBJECT-TYPE
    SYNTAX SEQUENCE OF CmcTcMasterTc9Unit2MsgEntry
    ACCESS not-accessible
    STATUS mandatory
    DESCRIPTION
      "Headline of message table"
    ::= { cmcTcMasterTc9StatusUnit2Msg 2 }

  cmcTcMasterTc9Unit2MsgEntry OBJECT-TYPE
    SYNTAX CmcTcMasterTc9Unit2MsgEntry
    ACCESS not-accessible
    STATUS mandatory
    DESCRIPTION
      "Entries of message table"
    INDEX { cmcTcMasterTc9Unit2MsgIndex }
    ::= { cmcTcMasterTc9Unit2MsgTable 1 }

    CmcTcMasterTc9Unit2MsgEntry ::=
      SEQUENCE {
        cmcTcMasterTc9Unit2MsgIndex
          INTEGER,
        cmcTcMasterTc9Unit2MsgText
          DisplayString (SIZE (0..20)),
        cmcTcMasterTc9Unit2MsgStatus
          INTEGER, 
        cmcTcMasterTc9Unit2MsgRelay
          INTEGER,
        cmcTcMasterTc9Unit2MsgBeeper
          INTEGER,
        cmcTcMasterTc9Unit2MsgTrap1
          INTEGER,
        cmcTcMasterTc9Unit2MsgTrap2
          INTEGER,
        cmcTcMasterTc9Unit2MsgTrap3
          INTEGER,
        cmcTcMasterTc9Unit2MsgTrap4
          INTEGER,                 
        cmcTcMasterTc9Unit2MsgQuit
          INTEGER              
      }

    cmcTcMasterTc9Unit2MsgIndex OBJECT-TYPE
      SYNTAX INTEGER (1..32000)
      ACCESS read-only
      STATUS mandatory
      DESCRIPTION
        "Index for the list of message entries. Its value ranges
         between 1 and the value of cmcTcMasterTc9Unit2NumberOfMsgs." 
      ::= { cmcTcMasterTc9Unit2MsgEntry 1 }

    cmcTcMasterTc9Unit2MsgText OBJECT-TYPE
      SYNTAX DisplayString (SIZE (0..20))
      ACCESS read-write
      STATUS mandatory
      DESCRIPTION
        "Descriptional text for each message (entry in the table)"
      ::= { cmcTcMasterTc9Unit2MsgEntry 2 }

    cmcTcMasterTc9Unit2MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc9Unit2OutputSet)
         17: door is unlocked by WEB
         18: door is unlocked by timer
         19: no access, wrong keycode or cardnumber
         20: orientation of PSM-Unit is circuit 1
         21: orientation of PSM-Unit is circuit 2"
      ::= { cmcTcMasterTc9Unit2MsgEntry 3 }

    cmcTcMasterTc9Unit2MsgRelay OBJECT-TYPE
      SYNTAX INTEGER {
        disable (1),
        enable (2)
      }
      ACCESS read-write
      STATUS mandatory
      DESCRIPTION
        "Setup of Alarm relay for this alarm
         2:        no switching of alarm relay             
         1:        switching of alarm relay" 
      ::= { cmcTcMasterTc9Unit2MsgEntry 4 }

    cmcTcMasterTc9Unit2MsgBeeper OBJECT-TYPE
      SYNTAX INTEGER {
        disable (1),
        enable (2)
      }
      ACCESS read-write
      STATUS mandatory
      DESCRIPTION
        "Setup of Alarm beeper for this alarm
         2:        no audible alarm
         1:        audible alarm" 
      ::= { cmcTcMasterTc9Unit2MsgEntry 5 }

    cmcTcMasterTc9Unit2MsgTrap1 OBJECT-TYPE
      SYNTAX INTEGER {
        disable (1),
        enable (2)
      }
      ACCESS read-write
      STATUS mandatory
      DESCRIPTION
        "Trap receiver 1 activated"
      ::= { cmcTcMasterTc9Unit2MsgEntry 6 }

    cmcTcMasterTc9Unit2MsgTrap2 OBJECT-TYPE
      SYNTAX INTEGER {
        disable (1),
        enable (2)
      }
      ACCESS read-write
      STATUS mandatory
      DESCRIPTION
        "Trap receiver 2 activated"
      ::= { cmcTcMasterTc9Unit2MsgEntry 7 }
 
    cmcTcMasterTc9Unit2MsgTrap3 OBJECT-TYPE
      SYNTAX INTEGER {
        disable (1),
        enable (2)
      }
      ACCESS read-write
      STATUS mandatory
      DESCRIPTION
        "Trap receiver 3 activated"
      ::= { cmcTcMasterTc9Unit2MsgEntry 8 }

    cmcTcMasterTc9Unit2MsgTrap4 OBJECT-TYPE
      SYNTAX INTEGER {
        disable (1),
        enable (2)
      }
      ACCESS read-write
      STATUS mandatory
      DESCRIPTION
        "Trap receiver 4 and Event Logging activated"
      ::= { cmcTcMasterTc9Unit2MsgEntry 9 }

    cmcTcMasterTc9Unit2MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc9Unit2MsgEntry 10 }

-- unit 3
  cmcTcMasterTc9Unit3TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 3"
    ::= { cmcTcMasterTc9StatusSensorUnit3 1 }

  cmcTcMasterTc9Unit3Text OBJECT-TYPE
    SYNTAX DisplayString (SIZE (0..10))
    ACCESS read-write
    STATUS mandatory
    DESCRIPTION
      "Descriptional text for sensor unit connected to port 3"
    ::= { cmcTcMasterTc9StatusSensorUnit3 2 }

  cmcTcMasterTc9Unit3Serial OBJECT-TYPE
    SYNTAX INTEGER 
    ACCESS  read-only
    STATUS  mandatory
    DESCRIPTION
      "Serialnumber of sensor unit connected to port 3"
    ::= { cmcTcMasterTc9StatusSensorUnit3 3 }

  cmcTcMasterTc9Unit3Status OBJECT-TYPE
    SYNTAX INTEGER {
      ok(1),
      error(2),
      changed(3),
      quit(4),
      timeout(5),
      detected(6),
      notAvail(7),
      lowPower(8)
    }
    ACCESS  read-only
    STATUS  mandatory
    DESCRIPTION
      "General Status sensor unit connected to port 3
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc9StatusSensorUnit3 4 }

-- Sensors              

  cmcTcMasterTc9Unit3NumberOfSensors OBJECT-TYPE
    SYNTAX INTEGER 
    ACCESS read-only
    STATUS mandatory
    DESCRIPTION
      "Number of sensors connected to sensor unit 3"
    ::= { cmcTcMasterTc9StatusUnit3Sensors 1 }

-- table with entry for each sensor available on this unit              
        
  cmcTcMasterTc9Unit3SensorTable OBJECT-TYPE
    SYNTAX SEQUENCE OF CmcTcMasterTc9Unit3SensorEntry
    ACCESS not-accessible
    STATUS mandatory
    DESCRIPTION
      "Headline of sensor table"
    ::= { cmcTcMasterTc9StatusUnit3Sensors 2 }

  cmcTcMasterTc9Unit3SensorEntry OBJECT-TYPE
    SYNTAX CmcTcMasterTc9Unit3SensorEntry
    ACCESS not-accessible
    STATUS mandatory
    DESCRIPTION
      "Entries of sensor table"
    INDEX { cmcTcMasterTc9Unit3SensorIndex }
    ::= { cmcTcMasterTc9Unit3SensorTable 1 }

    CmcTcMasterTc9Unit3SensorEntry ::=
      SEQUENCE {
        cmcTcMasterTc9Unit3SensorIndex
          INTEGER,
        cmcTcMasterTc9Unit3SensorType
          INTEGER,
        cmcTcMasterTc9Unit3SensorText
          DisplayString (SIZE (0..20)),                
        cmcTcMasterTc9Unit3SensorStatus
          INTEGER,
        cmcTcMasterTc9Unit3SensorValue
          INTEGER,
        cmcTcMasterTc9Unit3SensorSetHigh
          INTEGER,
        cmcTcMasterTc9Unit3SensorSetLow
          INTEGER,                 
        cmcTcMasterTc9Unit3SensorSetWarn
          INTEGER  
      }

    cmcTcMasterTc9Unit3SensorIndex OBJECT-TYPE
      SYNTAX INTEGER (1..32000)
      ACCESS read-only
      STATUS mandatory
      DESCRIPTION
        "Index for the list of value entries. Its value ranges
         between 1 and the value of cmcTcMasterTc9Unit3NumberOfSensors." 
      ::= { cmcTcMasterTc9Unit3SensorEntry 1 }

    cmcTcMasterTc9Unit3SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 3 to sensor[cmcTcMasterTc9Unit3SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc9Unit3SensorEntry 2 }

    cmcTcMasterTc9Unit3SensorText OBJECT-TYPE
      SYNTAX DisplayString (SIZE (0..20))
      ACCESS read-write
      STATUS mandatory
      DESCRIPTION
        "Descriptional text for each sensor (entry in the table)"
      ::= { cmcTcMasterTc9Unit3SensorEntry 3 }
              
    cmcTcMasterTc9Unit3SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc9Unit3SensorEntry 4 }

    cmcTcMasterTc9Unit3SensorValue OBJECT-TYPE
      SYNTAX INTEGER 
      ACCESS read-only
      STATUS mandatory
      DESCRIPTION
        "Value of sensor"
      ::= { cmcTcMasterTc9Unit3SensorEntry 5 }

    cmcTcMasterTc9Unit3SensorSetHigh OBJECT-TYPE
      SYNTAX INTEGER (0..300) 
      ACCESS read-write
      STATUS mandatory
      DESCRIPTION
        "Value for high setpoint of sensor"
      ::= { cmcTcMasterTc9Unit3SensorEntry 6 }

    cmcTcMasterTc9Unit3SensorSetLow OBJECT-TYPE
      SYNTAX INTEGER (0..300) 
      ACCESS read-write
      STATUS mandatory
      DESCRIPTION
        "Value for low setpoint of sensor,
         also used as alarm delay"
      ::= { cmcTcMasterTc9Unit3SensorEntry 7 }

    cmcTcMasterTc9Unit3SensorSetWarn OBJECT-TYPE
      SYNTAX INTEGER (0..300) 
      ACCESS read-write
      STATUS mandatory
      DESCRIPTION
        "Value for warning setpoint of sensor,
         also used as fan threshold"
      ::= { cmcTcMasterTc9Unit3SensorEntry 8 }
                
-- Outputs              

  cmcTcMasterTc9Unit3NumberOfOutputs OBJECT-TYPE
    SYNTAX INTEGER 
    ACCESS read-only
    STATUS mandatory
    DESCRIPTION
      "Number of outputs available on sensor unit 3"
    ::= { cmcTcMasterTc9StatusUnit3Outputs 1 }

-- table with entry for each output available on this unit              
                
  cmcTcMasterTc9Unit3OutputTable OBJECT-TYPE
    SYNTAX SEQUENCE OF CmcTcMasterTc9Unit3OutputEntry
    ACCESS not-accessible
    STATUS mandatory
    DESCRIPTION
      "Headline of output table"
    ::= { cmcTcMasterTc9StatusUnit3Outputs 2 }

  cmcTcMasterTc9Unit3OutputEntry OBJECT-TYPE
    SYNTAX CmcTcMasterTc9Unit3OutputEntry
    ACCESS not-accessible
    STATUS mandatory
    DESCRIPTION
      "Entries of output table"
    INDEX { cmcTcMasterTc9Unit3OutputIndex }
    ::= { cmcTcMasterTc9Unit3OutputTable 1 }

    CmcTcMasterTc9Unit3OutputEntry ::=
      SEQUENCE {
        cmcTcMasterTc9Unit3OutputIndex
          INTEGER,
        cmcTcMasterTc9Unit3OutputType
          INTEGER,
        cmcTcMasterTc9Unit3OutputText
          DisplayString (SIZE (0..20)),                
        cmcTcMasterTc9Unit3OutputStatus
          INTEGER,
        cmcTcMasterTc9Unit3OutputValue
          INTEGER,
        cmcTcMasterTc9Unit3OutputSet
          INTEGER,
        cmcTcMasterTc9Unit3OutputConfig
          INTEGER,
        cmcTcMasterTc9Unit3OutputDelay
          INTEGER,
        cmcTcMasterTc9Unit3OutputTimeoutAction
          INTEGER
      }

    cmcTcMasterTc9Unit3OutputIndex OBJECT-TYPE
      SYNTAX INTEGER (1..32000)
      ACCESS read-only
      STATUS mandatory
      DESCRIPTION
        "Index for the list of output entries. Its value ranges
         between 1 and the value of cmcTcMasterTc9Unit3NumberOfOutputs." 
      ::= { cmcTcMasterTc9Unit3OutputEntry 1 }

    cmcTcMasterTc9Unit3OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 3 to output[cmcTcMasterTc9Unit3OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc9Unit3OutputEntry 2 }

        
    cmcTcMasterTc9Unit3OutputText OBJECT-TYPE
      SYNTAX DisplayString (SIZE (0..20))
      ACCESS read-write
      STATUS mandatory
      DESCRIPTION
        "Descriptional text for each output (entry in the table)"
      ::= { cmcTcMasterTc9Unit3OutputEntry 3 }
              
    cmcTcMasterTc9Unit3OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc9Unit3OutputEntry 4 }

    cmcTcMasterTc9Unit3OutputValue OBJECT-TYPE
      SYNTAX INTEGER (-32000..32000) 
      ACCESS read-write
      STATUS mandatory
      DESCRIPTION
        "Value for output"
      ::= { cmcTcMasterTc9Unit3OutputEntry 5 }

    cmcTcMasterTc9Unit3OutputSet OBJECT-TYPE
      SYNTAX INTEGER {
        off (1),
        on (2),
        lock (3),
        unlock (4),
        unlockDelay (5)
      }
      ACCESS read-write
      STATUS mandatory
      DESCRIPTION
        "Command for output"
      ::= { cmcTcMasterTc9Unit3OutputEntry 6 }

    cmcTcMasterTc9Unit3OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc9Unit3OutputEntry 7 }

    cmcTcMasterTc9Unit3OutputDelay OBJECT-TYPE
      SYNTAX INTEGER (0..999) 
      ACCESS read-write
      STATUS mandatory
      DESCRIPTION
        "Unsigned Value for delay, 
         after this time the output will fall into the previous state"
      ::= { cmcTcMasterTc9Unit3OutputEntry 8 }

    cmcTcMasterTc9Unit3OutputTimeoutAction OBJECT-TYPE
      SYNTAX INTEGER {
        stay (1),
        off (2),
        on (3)
      }
      ACCESS read-write
      STATUS mandatory
      DESCRIPTION
        "State for output if timeout (RS422) occurs"
      ::= { cmcTcMasterTc9Unit3OutputEntry 9 }

-- Messages
              
  cmcTcMasterTc9Unit3NumberOfMsgs OBJECT-TYPE
    SYNTAX INTEGER 
    ACCESS read-only
    STATUS mandatory
    DESCRIPTION
      "Number of messages that can be created with sensor unit 3"
    ::= { cmcTcMasterTc9StatusUnit3Msg 1 }

-- table with entry for each alarm available on this unit               
                
  cmcTcMasterTc9Unit3MsgTable OBJECT-TYPE
    SYNTAX SEQUENCE OF CmcTcMasterTc9Unit3MsgEntry
    ACCESS not-accessible
    STATUS mandatory
    DESCRIPTION
      "Headline of message table"
    ::= { cmcTcMasterTc9StatusUnit3Msg 2 }

  cmcTcMasterTc9Unit3MsgEntry OBJECT-TYPE
    SYNTAX CmcTcMasterTc9Unit3MsgEntry
    ACCESS not-accessible
    STATUS mandatory
    DESCRIPTION
      "Entries of message table"
    INDEX { cmcTcMasterTc9Unit3MsgIndex }
    ::= { cmcTcMasterTc9Unit3MsgTable 1 }

    CmcTcMasterTc9Unit3MsgEntry ::=
      SEQUENCE {
        cmcTcMasterTc9Unit3MsgIndex
          INTEGER,
        cmcTcMasterTc9Unit3MsgText
          DisplayString (SIZE (0..20)),
        cmcTcMasterTc9Unit3MsgStatus
          INTEGER, 
        cmcTcMasterTc9Unit3MsgRelay
          INTEGER,
        cmcTcMasterTc9Unit3MsgBeeper
          INTEGER,
        cmcTcMasterTc9Unit3MsgTrap1
          INTEGER,
        cmcTcMasterTc9Unit3MsgTrap2
          INTEGER,
        cmcTcMasterTc9Unit3MsgTrap3
          INTEGER,
        cmcTcMasterTc9Unit3MsgTrap4
          INTEGER,                 
        cmcTcMasterTc9Unit3MsgQuit
          INTEGER              
      }

    cmcTcMasterTc9Unit3MsgIndex OBJECT-TYPE
      SYNTAX INTEGER (1..32000)
      ACCESS read-only
      STATUS mandatory
      DESCRIPTION
        "Index for the list of message entries. Its value ranges
         between 1 and the value of cmcTcMasterTc9Unit3NumberOfMsgs." 
      ::= { cmcTcMasterTc9Unit3MsgEntry 1 }

    cmcTcMasterTc9Unit3MsgText OBJECT-TYPE
      SYNTAX DisplayString (SIZE (0..20))
      ACCESS read-write
      STATUS mandatory
      DESCRIPTION
        "Descriptional text for each message (entry in the table)"
      ::= { cmcTcMasterTc9Unit3MsgEntry 2 }

    cmcTcMasterTc9Unit3MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc9Unit3OutputSet)
         17: door is unlocked by WEB
         18: door is unlocked by timer
         19: no access, wrong keycode or cardnumber
         20: orientation of PSM-Unit is circuit 1
         21: orientation of PSM-Unit is circuit 2"
      ::= { cmcTcMasterTc9Unit3MsgEntry 3 }

    cmcTcMasterTc9Unit3MsgRelay OBJECT-TYPE
      SYNTAX INTEGER {
        disable (1),
        enable (2)
      }
      ACCESS read-write
      STATUS mandatory
      DESCRIPTION
        "Setup of Alarm relay for this alarm
         1:        no switching of alarm relay             
         2:        switching of alarm relay" 
      ::= { cmcTcMasterTc9Unit3MsgEntry 4 }

    cmcTcMasterTc9Unit3MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc9Unit3MsgEntry 5 }

    cmcTcMasterTc9Unit3MsgTrap1 OBJECT-TYPE
      SYNTAX INTEGER {
        disable (1),
        enable (2)
      }
      ACCESS read-write
      STATUS mandatory
      DESCRIPTION
        "Trap receiver 1 activated"
      ::= { cmcTcMasterTc9Unit3MsgEntry 6 }

    cmcTcMasterTc9Unit3MsgTrap2 OBJECT-TYPE
      SYNTAX INTEGER {
        disable (1),
        enable (2)
      }
      ACCESS read-write
      STATUS mandatory
      DESCRIPTION
        "Trap receiver 2 activated"
      ::= { cmcTcMasterTc9Unit3MsgEntry 7 }
 
    cmcTcMasterTc9Unit3MsgTrap3 OBJECT-TYPE
      SYNTAX INTEGER {
        disable (1),
        enable (2)
      }
      ACCESS read-write
      STATUS mandatory
      DESCRIPTION
        "Trap receiver 3 activated"
      ::= { cmcTcMasterTc9Unit3MsgEntry 8 }

    cmcTcMasterTc9Unit3MsgTrap4 OBJECT-TYPE
      SYNTAX INTEGER {
        disable (1),
        enable (2)
      }
      ACCESS read-write
      STATUS mandatory
      DESCRIPTION
        "Trap receiver 4 and Event Logging activated"
      ::= { cmcTcMasterTc9Unit3MsgEntry 9 }

    cmcTcMasterTc9Unit3MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc9Unit3MsgEntry 10 }

-- unit4

  cmcTcMasterTc9Unit4TypeOfDevice OBJECT-TYPE
    SYNTAX INTEGER {
      notAvail (1),
      unitIO (2),
      unitAccess (3),
      unitClimate (4),
      unitFCS (5),
      unitRTT (6),
      unitRLCP (7),
      unitPSM (8)
    }
    ACCESS  read-only
    STATUS  mandatory
    DESCRIPTION
      "Type of sensor unit connected to port 4"
    ::= { cmcTcMasterTc9StatusSensorUnit4 1 }

  cmcTcMasterTc9Unit4Text OBJECT-TYPE
    SYNTAX DisplayString (SIZE (0..10))
    ACCESS read-write
    STATUS mandatory
    DESCRIPTION
      "Descriptional text for sensor unit connected to port 4"
    ::= { cmcTcMasterTc9StatusSensorUnit4 2 }

  cmcTcMasterTc9Unit4Serial OBJECT-TYPE
    SYNTAX INTEGER 
    ACCESS read-only
    STATUS mandatory
    DESCRIPTION
      "Serialnumber of sensor unit connected to port 4"
    ::= { cmcTcMasterTc9StatusSensorUnit4 3 }

  cmcTcMasterTc9Unit4Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 4
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc9StatusSensorUnit4 4 }

-- Sensors
              
  cmcTcMasterTc9Unit4NumberOfSensors OBJECT-TYPE
    SYNTAX INTEGER 
    ACCESS read-only
    STATUS mandatory
    DESCRIPTION
      "Number of sensors connected to sensor unit 4"
    ::= { cmcTcMasterTc9StatusUnit4Sensors 1 }

-- table with entry for each sensor available on this unit              
                
  cmcTcMasterTc9Unit4SensorTable OBJECT-TYPE
    SYNTAX SEQUENCE OF CmcTcMasterTc9Unit4SensorEntry
    ACCESS not-accessible
    STATUS mandatory
    DESCRIPTION
      "Headline of sensor table"
    ::= { cmcTcMasterTc9StatusUnit4Sensors 2 }

  cmcTcMasterTc9Unit4SensorEntry OBJECT-TYPE
    SYNTAX CmcTcMasterTc9Unit4SensorEntry
    ACCESS not-accessible
    STATUS mandatory
    DESCRIPTION
      "Entries of sensor table"
    INDEX { cmcTcMasterTc9Unit4SensorIndex }
    ::= { cmcTcMasterTc9Unit4SensorTable 1 }

    CmcTcMasterTc9Unit4SensorEntry ::=
      SEQUENCE {
        cmcTcMasterTc9Unit4SensorIndex
          INTEGER,
        cmcTcMasterTc9Unit4SensorType
          INTEGER,
        cmcTcMasterTc9Unit4SensorText
          DisplayString (SIZE (0..20)),                
        cmcTcMasterTc9Unit4SensorStatus
          INTEGER,
        cmcTcMasterTc9Unit4SensorValue
          INTEGER,
        cmcTcMasterTc9Unit4SensorSetHigh
          INTEGER,
        cmcTcMasterTc9Unit4SensorSetLow
          INTEGER,                 
        cmcTcMasterTc9Unit4SensorSetWarn
          INTEGER  
      }

    cmcTcMasterTc9Unit4SensorIndex OBJECT-TYPE
      SYNTAX INTEGER (1..32000)
      ACCESS read-only
      STATUS mandatory
      DESCRIPTION
        "Index for the list of value entries. Its value ranges
         between 1 and the value of cmcTcMasterTc9Unit4NumberOfSensors." 
      ::= { cmcTcMasterTc9Unit4SensorEntry 1 }

    cmcTcMasterTc9Unit4SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 4 to sensor[cmcTcMasterTc9Unit4SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc9Unit4SensorEntry 2 }

    cmcTcMasterTc9Unit4SensorText OBJECT-TYPE
      SYNTAX DisplayString (SIZE (0..20))
      ACCESS read-write
      STATUS mandatory
      DESCRIPTION
        "Descriptional text for each sensor (entry in the table)"
      ::= { cmcTcMasterTc9Unit4SensorEntry 3 }
              
    cmcTcMasterTc9Unit4SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc9Unit4SensorEntry 4 }

    cmcTcMasterTc9Unit4SensorValue OBJECT-TYPE
      SYNTAX INTEGER 
      ACCESS read-only
      STATUS mandatory
      DESCRIPTION
        "Value of sensor"
      ::= { cmcTcMasterTc9Unit4SensorEntry 5 }

    cmcTcMasterTc9Unit4SensorSetHigh OBJECT-TYPE
      SYNTAX INTEGER (0..300) 
      ACCESS read-write
      STATUS mandatory
      DESCRIPTION
        "Value for high setpoint of sensor"
      ::= { cmcTcMasterTc9Unit4SensorEntry 6 }

    cmcTcMasterTc9Unit4SensorSetLow OBJECT-TYPE
      SYNTAX INTEGER (0..300) 
      ACCESS read-write
      STATUS mandatory
      DESCRIPTION
        "Value for low setpoint of sensor,
         also used as alarm delay"
      ::= { cmcTcMasterTc9Unit4SensorEntry 7 }

    cmcTcMasterTc9Unit4SensorSetWarn OBJECT-TYPE
      SYNTAX INTEGER (0..300) 
      ACCESS read-write
      STATUS mandatory
      DESCRIPTION
        "Value for warning setpoint of sensor,
         also used as fan threshold"
      ::= { cmcTcMasterTc9Unit4SensorEntry 8 }

-- Outputs              

  cmcTcMasterTc9Unit4NumberOfOutputs OBJECT-TYPE
    SYNTAX INTEGER 
    ACCESS read-only
    STATUS mandatory
    DESCRIPTION
      "Number of outputs available on sensor unit 4"
    ::= { cmcTcMasterTc9StatusUnit4Outputs 1 }

-- table with entry for each output available on this unit              
                
  cmcTcMasterTc9Unit4OutputTable OBJECT-TYPE
    SYNTAX SEQUENCE OF CmcTcMasterTc9Unit4OutputEntry
    ACCESS not-accessible
    STATUS mandatory
    DESCRIPTION
      "Headline of output table"
    ::= { cmcTcMasterTc9StatusUnit4Outputs 2 }

  cmcTcMasterTc9Unit4OutputEntry OBJECT-TYPE
    SYNTAX CmcTcMasterTc9Unit4OutputEntry
    ACCESS not-accessible
    STATUS mandatory
    DESCRIPTION
      "Entries of output table"
    INDEX { cmcTcMasterTc9Unit4OutputIndex }
    ::= { cmcTcMasterTc9Unit4OutputTable 1 }

    CmcTcMasterTc9Unit4OutputEntry ::=
      SEQUENCE {
        cmcTcMasterTc9Unit4OutputIndex
          INTEGER,
        cmcTcMasterTc9Unit4OutputType
          INTEGER,
        cmcTcMasterTc9Unit4OutputText
          DisplayString (SIZE (0..20)),                
        cmcTcMasterTc9Unit4OutputStatus
          INTEGER,
        cmcTcMasterTc9Unit4OutputValue
          INTEGER,
        cmcTcMasterTc9Unit4OutputSet
          INTEGER,
        cmcTcMasterTc9Unit4OutputConfig
          INTEGER,
        cmcTcMasterTc9Unit4OutputDelay
          INTEGER,
        cmcTcMasterTc9Unit4OutputTimeoutAction
          INTEGER
      }

    cmcTcMasterTc9Unit4OutputIndex OBJECT-TYPE
      SYNTAX INTEGER (1..32000)
      ACCESS read-only
      STATUS mandatory
      DESCRIPTION
        "Index for the list of output entries. Its value ranges
         between 1 and the value of cmcTcMasterTc9Unit4NumberOfOutputs." 
      ::= { cmcTcMasterTc9Unit4OutputEntry 1 }

    cmcTcMasterTc9Unit4OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 4 to output[cmcTcMasterTc9Unit4OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc9Unit4OutputEntry 2 }

    cmcTcMasterTc9Unit4OutputText OBJECT-TYPE
      SYNTAX DisplayString (SIZE (0..20))
      ACCESS read-write
      STATUS mandatory
      DESCRIPTION
        "Descriptional text for each output (entry in the table)"
      ::= { cmcTcMasterTc9Unit4OutputEntry 3 }
              
    cmcTcMasterTc9Unit4OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc9Unit4OutputEntry 4 }

    cmcTcMasterTc9Unit4OutputValue OBJECT-TYPE
      SYNTAX INTEGER (-32000..32000) 
      ACCESS read-write
      STATUS mandatory
      DESCRIPTION
        "Value for output"
      ::= { cmcTcMasterTc9Unit4OutputEntry 5 }

    cmcTcMasterTc9Unit4OutputSet OBJECT-TYPE
      SYNTAX INTEGER {
        off (1),
        on (2),
        lock (3),
        unlock (4),
        unlockDelay (5)
      }
      ACCESS read-write
      STATUS mandatory
      DESCRIPTION
        "Command for output"
      ::= { cmcTcMasterTc9Unit4OutputEntry 6 }

    cmcTcMasterTc9Unit4OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc9Unit4OutputEntry 7 }

    cmcTcMasterTc9Unit4OutputDelay OBJECT-TYPE
      SYNTAX INTEGER (0..999) 
      ACCESS read-write
      STATUS mandatory
      DESCRIPTION
        "Unsigned Value for delay, 
         after this time the output will fall into the previous state"
      ::= { cmcTcMasterTc9Unit4OutputEntry 8 }

    cmcTcMasterTc9Unit4OutputTimeoutAction OBJECT-TYPE
      SYNTAX INTEGER {
        stay (1),
        off (2),
        on (3)
      }
      ACCESS read-write
      STATUS mandatory
      DESCRIPTION
        "State for output if timeout (RS422) occurs"
      ::= { cmcTcMasterTc9Unit4OutputEntry 9 }

-- Messages
              
  cmcTcMasterTc9Unit4NumberOfMsgs OBJECT-TYPE
    SYNTAX INTEGER 
    ACCESS read-only
    STATUS mandatory
    DESCRIPTION
      "Number of messages that can be created with sensor unit 4"
    ::= { cmcTcMasterTc9StatusUnit4Msg 1 }

-- table with entry for each alarm available on this unit               
                
  cmcTcMasterTc9Unit4MsgTable OBJECT-TYPE
    SYNTAX SEQUENCE OF CmcTcMasterTc9Unit4MsgEntry
    ACCESS not-accessible
    STATUS mandatory
    DESCRIPTION
      "Headline of message table"
    ::= { cmcTcMasterTc9StatusUnit4Msg 2 }

  cmcTcMasterTc9Unit4MsgEntry OBJECT-TYPE
    SYNTAX CmcTcMasterTc9Unit4MsgEntry
    ACCESS not-accessible
    STATUS mandatory
    DESCRIPTION
      "Entries of message table"
    INDEX { cmcTcMasterTc9Unit4MsgIndex }
    ::= { cmcTcMasterTc9Unit4MsgTable 1 }

    CmcTcMasterTc9Unit4MsgEntry ::=
      SEQUENCE {
        cmcTcMasterTc9Unit4MsgIndex
          INTEGER,
        cmcTcMasterTc9Unit4MsgText
          DisplayString (SIZE (0..20)),                
        cmcTcMasterTc9Unit4MsgStatus
          INTEGER, 
        cmcTcMasterTc9Unit4MsgRelay
          INTEGER,
        cmcTcMasterTc9Unit4MsgBeeper
          INTEGER,
        cmcTcMasterTc9Unit4MsgTrap1
          INTEGER,
        cmcTcMasterTc9Unit4MsgTrap2
          INTEGER,
        cmcTcMasterTc9Unit4MsgTrap3
          INTEGER,
        cmcTcMasterTc9Unit4MsgTrap4
          INTEGER,                 
        cmcTcMasterTc9Unit4MsgQuit
          INTEGER              
      }

    cmcTcMasterTc9Unit4MsgIndex OBJECT-TYPE
      SYNTAX INTEGER (1..32000)
      ACCESS read-only
      STATUS mandatory
      DESCRIPTION
        "Index for the list of message entries. Its value ranges
         between 1 and the value of cmcTcMasterTc9Unit4NumberOfMsgs." 
      ::= { cmcTcMasterTc9Unit4MsgEntry 1 }

    cmcTcMasterTc9Unit4MsgText OBJECT-TYPE
      SYNTAX DisplayString (SIZE (0..20))
      ACCESS read-write
      STATUS mandatory
      DESCRIPTION
        "Descriptional text for each message (entry in the table)"
      ::= { cmcTcMasterTc9Unit4MsgEntry 2 }

    cmcTcMasterTc9Unit4MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc9Unit4OutputSet)
         17: door is unlocked by WEB
         18: door is unlocked by timer
         19: no access, wrong keycode or cardnumber
         20: orientation of PSM-Unit is circuit 1
         21: orientation of PSM-Unit is circuit 2"
      ::= { cmcTcMasterTc9Unit4MsgEntry 3 }

    cmcTcMasterTc9Unit4MsgRelay OBJECT-TYPE
      SYNTAX INTEGER {
        disable (1),
        enable (2)
      }
      ACCESS read-write
      STATUS mandatory
      DESCRIPTION
        "Setup of Alarm relay for this alarm
         1:        no switching of alarm relay             
         2:        switching of alarm relay" 
      ::= { cmcTcMasterTc9Unit4MsgEntry 4 }

    cmcTcMasterTc9Unit4MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc9Unit4MsgEntry 5 }

    cmcTcMasterTc9Unit4MsgTrap1 OBJECT-TYPE
      SYNTAX INTEGER {
        disable (1),
        enable (2)
      }
      ACCESS read-write
      STATUS mandatory
      DESCRIPTION
        "Trap receiver 1 activated"
      ::= { cmcTcMasterTc9Unit4MsgEntry 6 }

    cmcTcMasterTc9Unit4MsgTrap2 OBJECT-TYPE
      SYNTAX INTEGER {
        disable (1),
        enable (2)
      }
      ACCESS read-write
      STATUS mandatory
      DESCRIPTION
        "Trap receiver 2 activated"
      ::= { cmcTcMasterTc9Unit4MsgEntry 7 }
 
    cmcTcMasterTc9Unit4MsgTrap3 OBJECT-TYPE
      SYNTAX INTEGER {
        disable (1),
        enable (2)
      }
      ACCESS read-write
      STATUS mandatory
      DESCRIPTION
        "Trap receiver 3 activated"
      ::= { cmcTcMasterTc9Unit4MsgEntry 8 }

    cmcTcMasterTc9Unit4MsgTrap4 OBJECT-TYPE
      SYNTAX INTEGER {
        disable (1),
        enable (2)
      }
      ACCESS read-write
      STATUS mandatory
      DESCRIPTION
        "Trap receiver 4 and Event Logging activated"
      ::= { cmcTcMasterTc9Unit4MsgEntry 9 }

    cmcTcMasterTc9Unit4MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc9Unit4MsgEntry 10 }

--Status extension unit

  cmcTcMasterTc9ValuesRelay OBJECT-TYPE
    SYNTAX INTEGER {
      disable (1),
      enable (2)
    }
    ACCESS read-write
    STATUS mandatory
    DESCRIPTION
      "Setup of Alarm relay for alarm ext. unit(s)
       1:        no switching of alarm relay             
       2:        switching of alarm relay" 
    ::= { cmcTcMasterTc9StatusExtUnit 1 }

  cmcTcMasterTc9ValuesBeeper OBJECT-TYPE
    SYNTAX INTEGER {
      disable (1),
      enable (2)
    }
    ACCESS read-write
    STATUS mandatory
    DESCRIPTION
      "Setup of Alarm beeper for alarm ext. unit(s)
       1:        no audible alarm
       2:        audible alarm" 
    ::= { cmcTcMasterTc9StatusExtUnit 2 }

  cmcTcMasterTc9ValuesTrap1 OBJECT-TYPE
    SYNTAX INTEGER {
      disable (1),
      enable (2)
    }
    ACCESS read-write
    STATUS mandatory
    DESCRIPTION
      "Trap receiver 1 activated"
    ::= { cmcTcMasterTc9StatusExtUnit 3 }

  cmcTcMasterTc9ValuesTrap2 OBJECT-TYPE
    SYNTAX INTEGER {
      disable (1),
      enable (2)
    }
    ACCESS read-write
    STATUS mandatory
    DESCRIPTION
      "Trap receiver 2 activated"
    ::= { cmcTcMasterTc9StatusExtUnit 4 }
 
  cmcTcMasterTc9ValuesTrap3 OBJECT-TYPE
    SYNTAX INTEGER {
      disable (1),
      enable (2)
    }
    ACCESS read-write
    STATUS mandatory
    DESCRIPTION
      "Trap receiver 3 activated"
    ::= { cmcTcMasterTc9StatusExtUnit 5 }

  cmcTcMasterTc9ValuesTrap4 OBJECT-TYPE
    SYNTAX INTEGER {
      disable (1),
      enable (2)
    }
    ACCESS read-write
    STATUS mandatory
    DESCRIPTION
      "Trap receiver 4 and Event Logging activated"
    ::= { cmcTcMasterTc9StatusExtUnit 6 }
 
  cmcTcMasterTc9NumberOfValues OBJECT-TYPE
    SYNTAX INTEGER 
    ACCESS  read-only
    STATUS  mandatory
    DESCRIPTION
      "Number of values availabel on extension units connected to the CMC-TC"
    ::= { cmcTcMasterTc9StatusExtUnit 7 }

-- table with entry for each value available on extension units              

  cmcTcMasterTc9ValuesTable OBJECT-TYPE
    SYNTAX SEQUENCE OF CmcTcMasterTc9ValuesEntry
    ACCESS not-accessible
    STATUS mandatory
    DESCRIPTION
      "Headline of values-table"
    ::= { cmcTcMasterTc9StatusExtUnit 8 }

  cmcTcMasterTc9ValuesEntry OBJECT-TYPE
    SYNTAX CmcTcMasterTc9ValuesEntry
    ACCESS not-accessible
    STATUS mandatory
    DESCRIPTION
      "Entries of values-table"
    INDEX { cmcTcMasterTc9ValuesIndex }
    ::= { cmcTcMasterTc9ValuesTable 1 }

    CmcTcMasterTc9ValuesEntry ::=
      SEQUENCE {
        cmcTcMasterTc9ValuesIndex
          INTEGER,
        cmcTcMasterTc9ValuesText
          DisplayString (SIZE (0..20)),                
        cmcTcMasterTc9ValuesStatus
          INTEGER,
        cmcTcMasterTc9ValuesValue
          INTEGER,
        cmcTcMasterTc9ValuesSetHigh
          INTEGER,
        cmcTcMasterTc9ValuesSetLow
          INTEGER
      }

    cmcTcMasterTc9ValuesIndex OBJECT-TYPE
      SYNTAX INTEGER (1..32000)
      ACCESS read-only
      STATUS mandatory
      DESCRIPTION
        "Index for the list of value entries. Its value ranges
         between 1 and the value of cmcTcMasterTc9NumberOfValues." 
      ::= { cmcTcMasterTc9ValuesEntry 1 }

        
    cmcTcMasterTc9ValuesText OBJECT-TYPE
      SYNTAX DisplayString (SIZE (0..20))
      ACCESS read-write
      STATUS mandatory
      DESCRIPTION
        "Descriptional text for each value (entry in the table)
         of the extension card"
      ::= { cmcTcMasterTc9ValuesEntry 2 }
              
    cmcTcMasterTc9ValuesStatus OBJECT-TYPE
      SYNTAX INTEGER {
        notAvail(1),
        lost(2),
        changed(3),
        ok(4),
        tooLow(5),
        tooHigh(6),
        error(7)
      }
      ACCESS read-only
      STATUS mandatory
      DESCRIPTION
        "Actual status of the value of the extension card"
      ::= { cmcTcMasterTc9ValuesEntry 3 }

    cmcTcMasterTc9ValuesValue OBJECT-TYPE
      SYNTAX INTEGER 
      ACCESS read-only
      STATUS mandatory
      DESCRIPTION
        "Value of sensor"
      ::= { cmcTcMasterTc9ValuesEntry 4 }

    cmcTcMasterTc9ValuesSetHigh OBJECT-TYPE
      SYNTAX INTEGER (0..255) 
      ACCESS read-write
      STATUS mandatory
      DESCRIPTION
        "Value for high setpoint of sensor"
      ::= { cmcTcMasterTc9ValuesEntry 5 }

    cmcTcMasterTc9ValuesSetLow OBJECT-TYPE
      SYNTAX INTEGER (0..255) 
      ACCESS read-write
      STATUS mandatory
      DESCRIPTION
        "Value for low setpoint of sensor"
      ::= { cmcTcMasterTc9ValuesEntry 6 }

--cmcTcMasterTc9SetupGeneral-group

  cmcTcMasterTc9SetTempUnit OBJECT-TYPE
    SYNTAX INTEGER {
      celsius(1),
      fahrenheit(2)
    }
    ACCESS read-write
    STATUS mandatory
    DESCRIPTION
      "Unit of all temperature values and setpoints, Celsius or Fahrenheit"
   ::= { cmcTcMasterTc9SetupGeneral 1 }

  cmcTcMasterTc9SetBeeper OBJECT-TYPE
    SYNTAX INTEGER {
      off(1),
      on(2)
    }
    ACCESS read-write
    STATUS mandatory
    DESCRIPTION
      "Audible alarm in CMC-TC unit:
       (2): beeper is on
       (1): beeper is off (general)"
    ::= { cmcTcMasterTc9SetupGeneral 2 }


  cmcTcMasterTc9QuitRelay OBJECT-TYPE
    SYNTAX INTEGER {
      disabled(1),
      enabled(2)
    }
    ACCESS read-write
    STATUS mandatory
    DESCRIPTION
      "Enable or disable acknowledging currently active alarm relay 
       (with 'C' on CMC-TC)."
    ::= { cmcTcMasterTc9SetupGeneral 3 }

  cmcTcMasterTc9LogicRelay OBJECT-TYPE
    SYNTAX INTEGER {
      closeAtAlarm(1),
      openAtAlarm(2),
      off(3)
    }
    ACCESS read-write
    STATUS mandatory
    DESCRIPTION
      "Logic of alarm relay: 
       (1) Relay will pick up in case of an alarm
       (2) Relay will release in case of an alarm
       (3) Relay off (general)"
    ::= { cmcTcMasterTc9SetupGeneral 4 }

  cmcTcMasterTc9WebAccess OBJECT-TYPE
    SYNTAX INTEGER {
      viewOnly(1),
      fullAccess(2),
      off(3)
    }
    ACCESS read-write
    STATUS mandatory
    DESCRIPTION
      "Web access via HTTP: 
       (1) view only
       (2) full Access, read and set
       (3) Web disabled (general)"
    ::= { cmcTcMasterTc9SetupGeneral 5 }
 
  cmcTcMasterTc9SetupDate OBJECT-TYPE
    SYNTAX DisplayString (SIZE (0..10))
    ACCESS read-write
    STATUS mandatory
    DESCRIPTION
      "actual Date in format DD.MM.YYYY"
    ::= { cmcTcMasterTc9SetupGeneral 6 }

  cmcTcMasterTc9SetupTime OBJECT-TYPE
    SYNTAX DisplayString (SIZE (0..8))
    ACCESS read-write
    STATUS mandatory
    DESCRIPTION
      "actual Time in format HH:MM:SS, HH (0-23), MM (0-59), SS (0-59)"
    ::= { cmcTcMasterTc9SetupGeneral 7 }
 
-- table for timer function
 
  cmcTcMasterTc9TimerNumber OBJECT-TYPE
    SYNTAX INTEGER 
    ACCESS read-only
    STATUS mandatory
    DESCRIPTION
      "Number of timers available on this unit"
    ::= { cmcTcMasterTc9TimerTable1 1 }

  cmcTcMasterTc9TimerTable OBJECT-TYPE
    SYNTAX SEQUENCE OF CmcTcMasterTc9TimerEntry
    ACCESS not-accessible
    STATUS mandatory
    DESCRIPTION
      "Headline of timer-table"
    ::= { cmcTcMasterTc9TimerTable1 2 }

  cmcTcMasterTc9TimerEntry OBJECT-TYPE
    SYNTAX CmcTcMasterTc9TimerEntry
    ACCESS not-accessible
    STATUS mandatory
    DESCRIPTION
      "Entries of timer-table"
    INDEX { cmcTcMasterTc9TimerIndex }
    ::= { cmcTcMasterTc9TimerTable 1 }

    CmcTcMasterTc9TimerEntry ::=
      SEQUENCE {
        cmcTcMasterTc9TimerIndex
          INTEGER,
        cmcTcMasterTc9TimerStatus
          INTEGER,
        cmcTcMasterTc9TimerDayOfWeek
          INTEGER,  
        cmcTcMasterTc9TimeOn 
          DisplayString (SIZE (0..5)),                              
        cmcTcMasterTc9TimeOff 
          DisplayString (SIZE (0..5)),                              
        cmcTcMasterTc9TimeControl
          INTEGER,
        cmcTcMasterTc9TimerFunction
           INTEGER
      }

    cmcTcMasterTc9TimerIndex OBJECT-TYPE
      SYNTAX INTEGER (1..32000)
      ACCESS read-only
      STATUS mandatory
      DESCRIPTION
        "Index for the list of timer entries. Its value ranges
         between 1 and the value of cmcTcMasterTc9TimerNumber." 
      ::= { cmcTcMasterTc9TimerEntry 1 }

    cmcTcMasterTc9TimerStatus OBJECT-TYPE
      SYNTAX INTEGER {
        switchedOff(1),
        switchedOn(2),
        noTime(3) 
      }
      ACCESS read-only
      STATUS mandatory
      DESCRIPTION
        "Actual status of the timer"
      ::= { cmcTcMasterTc9TimerEntry 2 }

    cmcTcMasterTc9TimerDayOfWeek OBJECT-TYPE
      SYNTAX INTEGER {
        sun(1),
        mon(2),
        tue(3) ,
        wed(4),
        thu(5),
        fri(6),
        sat(7),
        sat-sun(8),
        mon-fri(9),
        mon-sun(10)
      }
      ACCESS read-write
      STATUS mandatory
      DESCRIPTION
        "Selection of day of week for timer to switch"
      ::= { cmcTcMasterTc9TimerEntry 3 }
             
    cmcTcMasterTc9TimeOn OBJECT-TYPE
      SYNTAX DisplayString (SIZE (0..5))
      ACCESS read-write
      STATUS mandatory
      DESCRIPTION
        "Time to switch on current function, 
         Format: HH:MM"
      ::= { cmcTcMasterTc9TimerEntry 4 }

    cmcTcMasterTc9TimeOff OBJECT-TYPE
      SYNTAX DisplayString (SIZE (0..5))
      ACCESS read-write
      STATUS mandatory
      DESCRIPTION
        "Time to switch off current function,
         Format: HH:MM"
      ::= { cmcTcMasterTc9TimerEntry 5 }

    cmcTcMasterTc9TimeControl OBJECT-TYPE
      SYNTAX INTEGER  {
        disabled(1),
        enabled(2)
      }
      ACCESS read-write
      STATUS mandatory
      DESCRIPTION
        "Control via RTC"
      ::= { cmcTcMasterTc9TimerEntry 6 }

    cmcTcMasterTc9TimerFunction OBJECT-TYPE
      SYNTAX INTEGER {
        disKeypad1-1 (1),
        disKeypad2-1 (2),
        disKeypad1-2 (3),
        disKeypad2-2 (4),
        disKeypad1-3 (5),
        disKeypad2-3 (6),
        disKeypad1-4 (7),
        disKeypad2-4 (8),
        unlDoor1-1 (9),
        unlDoor2-1 (10),
        unlDoor1-2 (11),
        unlDoor2-2 (12),
        unlDoor1-3 (13),
        unlDoor2-3 (14),
        unlDoor1-4 (15),
        unlDoor2-5 (16),
        disTrapRec1 (17),
        disTrapRec2 (18),
        disTrapRec3 (19),
        disTrapRec4 (20),
        disSMS (21),
        schedule1 (22),
        schedule2 (23),
        schedule3 (24),
        schedule4 (25)
      }
      ACCESS read-write
      STATUS mandatory
      DESCRIPTION
        "Function which is controlled via timer
         1:     unlock via keypad 1 on unit 1 or remote input lock 1 is disabled
         2:     unlock via keypad 2 on unit 1 or remote input lock 2 is disabled
         3      unlock via keypad 1 on unit 2 or remote input lock 1 is disabled
         4:     unlock via keypad 2 on unit 2 or remote input lock 2 is disabled
         5:     unlock via keypad 1 on unit 3 or remote input lock 1 is disabled
         6:     unlock via keypad 2 on unit 3 or remote input lock 2 is disabled
         7:     unlock via keypad 1 on unit 4 or remote input lock 1 is disabled
         8:     unlock via keypad 2 on unit 4 or remote input lock 2 is disabled
         9:     Lock of door 1 on unit 1 will be unlocked
         10:    Lock of door 2 on unit 1 will be unlocked
         11:    Lock of door 1 on unit 2 will be unlocked
         12:    Lock of door 2 on unit 2 will be unlocked
         13:    Lock of door 1 on unit 3 will be unlocked
         14:    Lock of door 2 on unit 3 will be unlocked
         15:    Lock of door 1 on unit 4 will be unlocked
         16:    Lock of door 2 on unit 4 will be unlocked
         17-20: sending Traps to this Trap receiver will be disabled
         21:    sending SMS will be disabled
         22-25: Scheduled alarm off"
      ::= { cmcTcMasterTc9TimerEntry 7 }

--cmcTcMasterTc9TrapTable-group

  cmcTcMasterTc9TraptableNumber OBJECT-TYPE
    SYNTAX INTEGER 
    ACCESS read-only
    STATUS mandatory
    DESCRIPTION
      "Number of trapTable entries. The number of trap-receiver"
    ::= { cmcTcMasterTc9Traps 1 }

  cmcTcMasterTc9TrapTableTable OBJECT-TYPE    
    SYNTAX SEQUENCE OF CmcTcMasterTc9TrapTableEntry
    ACCESS not-accessible
    STATUS mandatory
    DESCRIPTION
     "A list of trap-receiver entries"
    ::= { cmcTcMasterTc9Traps 2 }

  cmcTcMasterTc9TrapTableEntry OBJECT-TYPE
    SYNTAX CmcTcMasterTc9TrapTableEntry
    ACCESS not-accessible
    STATUS mandatory
    DESCRIPTION
      "Entries of cmcTcMasterTc9TrapTable"
    INDEX   { cmcTcMasterTc9TrapIndex }
    ::= { cmcTcMasterTc9TrapTableTable 1 }      
              
    CmcTcMasterTc9TrapTableEntry ::=
      SEQUENCE {
        cmcTcMasterTc9TrapIndex
          INTEGER,
        cmcTcMasterTc9TrapStatus
          INTEGER,
        cmcTcMasterTc9TrapIPaddress
          DisplayString
      }

    cmcTcMasterTc9TrapIndex OBJECT-TYPE
      SYNTAX INTEGER (1..32000)
      ACCESS read-only
      STATUS mandatory
      DESCRIPTION
        "Index for the trap-receiver-table. Its value ranges between
         1 and the value of cmcTcMasterTc9TraptableNumber "
      ::= { cmcTcMasterTc9TrapTableEntry 1 }

    cmcTcMasterTc9TrapStatus OBJECT-TYPE
      SYNTAX INTEGER {
        disabled(1),
        enabled(2)
      }
      ACCESS read-write
      STATUS mandatory
      DESCRIPTION
        "Enable or disable trap receiver"
      ::= { cmcTcMasterTc9TrapTableEntry 2 }

    cmcTcMasterTc9TrapIPaddress OBJECT-TYPE
      SYNTAX DisplayString (SIZE (0..15))
      ACCESS read-write
      STATUS mandatory
      DESCRIPTION
        "IP-address of trap-receiver"
      ::= { cmcTcMasterTc9TrapTableEntry 3 }

--cmcTcMasterTc9Control-group (Added in Version 1.1)

  cmcTcMasterTc1QuitUnit OBJECT-TYPE
    SYNTAX INTEGER {
      noQuit(1),
      quit(2),
    }
    ACCESS read-write
    STATUS mandatory
    DESCRIPTION
      "Command to quit (acknowledge) alarms of CMC-TC unit.
       Setting to 'quit' (2) will have same result as pressing 'C' on Units.
       Variable is automatically set back to 'noQuit' (1)."
    ::= { cmcTcMasterTc9Control 1 }

--cmcTcMasterDevice10-group

  cmcTcMasterDev10Type OBJECT-TYPE
    SYNTAX INTEGER {
      other (0),
      cmc (1),
      pcu (3),
      tc (4)
    }
    ACCESS read-only
    STATUS mandatory
    DESCRIPTION
      "Type of device10"
    ::= { cmcTcMasterDevice10 1 }

  cmcTcMasterDev10Status OBJECT-TYPE
    SYNTAX INTEGER {
      other (1),
      notConnected (2),
      normal (3),
      minor (4),
      major (5),
      configChanged (6),
      connectionLost (10)
    }
    ACCESS read-only
    STATUS mandatory
    DESCRIPTION
      "Status of device10"
    ::= { cmcTcMasterDevice10 2 }

  cmcTcMasterDev10Descr OBJECT-TYPE
    SYNTAX DisplayString (SIZE (0..255))
    ACCESS read-only
    STATUS mandatory
    DESCRIPTION
      "A textual description of the entity.  This value
       should include the full name and version
       identification of the system's hardware type,
       software operating-system, and networking
       software.  It is mandatory that this only contain
       printable ASCII characters."
    ::= { cmcTcMasterDevice10 3 }

  cmcTcMasterDev10UpTime OBJECT-TYPE
    SYNTAX TimeTicks
    ACCESS read-only
    STATUS mandatory
    DESCRIPTION
      "The time (in hundredths of a second) since the
       network management portion of the system was last
       re-initialized."
    ::= { cmcTcMasterDevice10 4 }

  cmcTcMasterDev10Contact OBJECT-TYPE
    SYNTAX DisplayString (SIZE (0..255))
    ACCESS read-write
    STATUS mandatory
    DESCRIPTION
      "The textual identification of the contact person
       for this managed node, together with information
       on how to contact this person."
    ::= { cmcTcMasterDevice10 5 }

  cmcTcMasterDev10Name OBJECT-TYPE
    SYNTAX DisplayString (SIZE (0..255))
    ACCESS read-write
    STATUS mandatory
    DESCRIPTION
      "An administratively-assigned name for this
       managed node.  By convention, this is the node's
       fully-qualified domain name."
    ::= { cmcTcMasterDevice10 6 }

  cmcTcMasterDev10Location OBJECT-TYPE
    SYNTAX DisplayString (SIZE (0..255))
    ACCESS read-write
    STATUS mandatory
    DESCRIPTION
      "The physical location of this node (e.g.,
       `telephone closet, 3rd floor')."
    ::= { cmcTcMasterDevice10 7 }

--cmcTcMasterCmc10Values-group

  cmcTcMasterCmc10ValueTemperature1 OBJECT-TYPE
    SYNTAX INTEGER
    ACCESS read-only
    STATUS mandatory
    DESCRIPTION
      "Actual value of temperature 1 in deg C"
    ::= { cmcTcMasterCmc10Values 1 }

  cmcTcMasterCmc10ValueTemperature2 OBJECT-TYPE
    SYNTAX INTEGER
    ACCESS read-only
    STATUS mandatory
    DESCRIPTION
      "Actual value of temperature 2 in deg C"
    ::= { cmcTcMasterCmc10Values 2 }

  cmcTcMasterCmc10ValuePowerSupply OBJECT-TYPE
    SYNTAX INTEGER
    ACCESS read-only
    STATUS mandatory
    DESCRIPTION
      "Actual value of power supply in V"
    ::= { cmcTcMasterCmc10Values 3 }

  cmcTcMasterCmc10ValueAnalogAux1 OBJECT-TYPE
    SYNTAX INTEGER
    ACCESS read-only
    STATUS mandatory
    DESCRIPTION
      "Actual value of aux. analog input 1
      (4-20mA = 0-100%)"
    ::= { cmcTcMasterCmc10Values 4 }

  cmcTcMasterCmc10ValueAnalogAux2 OBJECT-TYPE
    SYNTAX INTEGER
    ACCESS read-only
    STATUS mandatory
    DESCRIPTION
      "Actual value of aux. analog input 2
      (4-20mA = 0-100%)"
    ::= { cmcTcMasterCmc10Values 5 }

--cmcTcMasterCmc10Values-table-group

  cmcTcMasterCmc10ValuesNumber OBJECT-TYPE
    SYNTAX INTEGER
    ACCESS read-only
    STATUS mandatory
    DESCRIPTION
      "Number of value-table entries"
    ::= { cmcTcMasterCmc10Table1 1 }

  cmcTcMasterCmc10ValuesTable OBJECT-TYPE
    SYNTAX SEQUENCE OF CmcTcMasterCmc10ValuesEntry
    ACCESS not-accessible
    STATUS mandatory
    DESCRIPTION
      "Headline of value-table"
    ::= { cmcTcMasterCmc10Table1 2 }

  cmcTcMasterCmc10ValuesEntry OBJECT-TYPE
    SYNTAX CmcTcMasterCmc10ValuesEntry
    ACCESS not-accessible
    STATUS mandatory
    DESCRIPTION
      "Entries of value-table"
    INDEX { cmcTcMasterCmc10ValuesIndex }
    ::= { cmcTcMasterCmc10ValuesTable 1 }

  CmcTcMasterCmc10ValuesEntry ::=
    SEQUENCE {
      cmcTcMasterCmc10ValuesIndex
        INTEGER,
      cmcTcMasterCmc10ValuesText
        DisplayString (SIZE (0..31)),
      cmcTcMasterCmc10ValuesValue
        INTEGER,
      cmcTcMasterCmc10ValuesStatus
        INTEGER,
      cmcTcMasterCmc10ValuesMaxValue
        INTEGER,
      cmcTcMasterCmc10ValuesMinValue
        INTEGER
    }

    cmcTcMasterCmc10ValuesIndex OBJECT-TYPE
      SYNTAX INTEGER (1..32000)
      ACCESS read-only
      STATUS mandatory
      DESCRIPTION
        "Index for the list of value entries. Its value ranges
        between 1 and the value of valuesNumber."
      ::= { cmcTcMasterCmc10ValuesEntry 1 }

    cmcTcMasterCmc10ValuesText OBJECT-TYPE
      SYNTAX DisplayString (SIZE (0..31))
      ACCESS read-write
      STATUS mandatory
      DESCRIPTION
        "Text of the entry in the value-table"
      ::= { cmcTcMasterCmc10ValuesEntry 2 }

    cmcTcMasterCmc10ValuesValue OBJECT-TYPE
      SYNTAX INTEGER
      ACCESS read-only
      STATUS mandatory
      DESCRIPTION
        "Actual value of the value-table"
      ::= { cmcTcMasterCmc10ValuesEntry 3 }

    cmcTcMasterCmc10ValuesStatus OBJECT-TYPE
      SYNTAX INTEGER {
        valueOK(1),
        valueTooLow(2),
        valueTooHigh(3),
        valueERROR(4),
        notAvail(5)
      }
      ACCESS read-only
      STATUS mandatory
      DESCRIPTION
        "Status of the value"
      ::= { cmcTcMasterCmc10ValuesEntry 4 }

    cmcTcMasterCmc10ValuesMaxValue OBJECT-TYPE
      SYNTAX INTEGER
      ACCESS read-write
      STATUS mandatory
      DESCRIPTION
        "Value for max. alarm"
      ::= { cmcTcMasterCmc10ValuesEntry 5 }

    cmcTcMasterCmc10ValuesMinValue OBJECT-TYPE
      SYNTAX INTEGER
      ACCESS read-write
      STATUS mandatory
      DESCRIPTION
        "Value for min. alarm"
      ::= { cmcTcMasterCmc10ValuesEntry 6 }

--cmcTcMasterCmc10status-group

  cmcTcMasterCmc10StatusTemperature1 OBJECT-TYPE
    SYNTAX DisplayString (SIZE (0..31))
    ACCESS read-only
    STATUS mandatory
    DESCRIPTION
      "Status temperature 1, OK/ too low/ too high
       (see setpoints of temperature 1)"
    ::= { cmcTcMasterCmc10Status 1 }

  cmcTcMasterCmc10StatusTemperature2 OBJECT-TYPE
    SYNTAX DisplayString (SIZE (0..31))
    ACCESS read-only
    STATUS mandatory
    DESCRIPTION
      "Status temperature 2, OK/ too low/ too high
       (see setpoints of temperature 2)"
    ::= { cmcTcMasterCmc10Status 2 }

  cmcTcMasterCmc10StatusFan1 OBJECT-TYPE
    SYNTAX DisplayString (SIZE (0..31))
    ACCESS read-only
    STATUS mandatory
    DESCRIPTION
      "Status fan 1, Stop/ running/ fault"
    ::= { cmcTcMasterCmc10Status 3 }

  cmcTcMasterCmc10StatusFan2 OBJECT-TYPE
    SYNTAX DisplayString (SIZE (0..31))
    ACCESS read-only
    STATUS mandatory
    DESCRIPTION
      "Status fan 2, Stop/ running/ fault"
    ::= { cmcTcMasterCmc10Status 4 }

  cmcTcMasterCmc10StatusHeating OBJECT-TYPE
    SYNTAX DisplayString (SIZE (0..31))
    ACCESS read-only
    STATUS mandatory
    DESCRIPTION
      "Status heating, On/Off"
    ::= { cmcTcMasterCmc10Status 5 }

  cmcTcMasterCmc10StatusPowerSupply OBJECT-TYPE
    SYNTAX DisplayString (SIZE (0..31))
    ACCESS read-only
    STATUS mandatory
    DESCRIPTION
      "Status power supply, OK/ too low/ too high
       (see setpoints of power supply)"
    ::= { cmcTcMasterCmc10Status 6 }

  cmcTcMasterCmc10StatusAnalogAux1 OBJECT-TYPE
    SYNTAX DisplayString (SIZE (0..31))
    ACCESS read-only
    STATUS mandatory
    DESCRIPTION
      "Status aux analog input 1, OK/ too low/ too high"
    ::= { cmcTcMasterCmc10Status 7 }

  cmcTcMasterCmc10StatusAnalogAux2 OBJECT-TYPE
    SYNTAX DisplayString (SIZE (0..31))
    ACCESS read-only
    STATUS mandatory
    DESCRIPTION
      "Status aux analog input 2, OK/ too low/ too high"
    ::= { cmcTcMasterCmc10Status 8 }

  cmcTcMasterCmc10StatusDoor OBJECT-TYPE
    SYNTAX DisplayString (SIZE (0..31))
    ACCESS read-only
    STATUS mandatory
    DESCRIPTION
      "Status door, open/closed/locked"
    ::= { cmcTcMasterCmc10Status 9 }

  cmcTcMasterCmc10StatusUps1 OBJECT-TYPE
    SYNTAX DisplayString (SIZE (0..31))
    ACCESS read-only
    STATUS mandatory
    DESCRIPTION
      "Status UPS 1, OK/ fault"
    ::= { cmcTcMasterCmc10Status 10 }

  cmcTcMasterCmc10StatusUps2 OBJECT-TYPE
    SYNTAX DisplayString (SIZE (0..31))
    ACCESS read-only
    STATUS mandatory
    DESCRIPTION
      "Status UPS 2, OK/ fault"
    ::= { cmcTcMasterCmc10Status 11 }

  cmcTcMasterCmc10StatusSmokeSensor OBJECT-TYPE
    SYNTAX DisplayString (SIZE (0..31))
    ACCESS read-only
    STATUS mandatory
    DESCRIPTION
      "Status smoke-sensor, OK/ smoke"
    ::= { cmcTcMasterCmc10Status 12 }

  cmcTcMasterCmc10StatusVibrationSensor OBJECT-TYPE
    SYNTAX DisplayString (SIZE (0..31))
    ACCESS read-only
    STATUS mandatory
    DESCRIPTION
      "Status vibration sensor, OK/ vibration"
    ::= { cmcTcMasterCmc10Status 13 }

  cmcTcMasterCmc10StatusMessage OBJECT-TYPE
    SYNTAX DisplayString (SIZE (0..31))
    ACCESS read-only
    STATUS mandatory
    DESCRIPTION
      "Message from CMC"
    ::= { cmcTcMasterCmc10Status 14 }

  cmcTcMasterCmc10ValueOperatingTime OBJECT-TYPE
    SYNTAX DisplayString (SIZE (0..31))
    ACCESS read-only
    STATUS mandatory
    DESCRIPTION
      "Operating time CMC-unit"
    ::= { cmcTcMasterCmc10Status 15 }

  cmcTcMasterCmc10StatusUnit OBJECT-TYPE
    SYNTAX INTEGER {
      unitCelsius(1),
      unitFahrenheit(2)
    }
    ACCESS read-only
    STATUS mandatory
    DESCRIPTION
      "Unit of temperature-values, Celsius or Fahrenheit"
   ::= { cmcTcMasterCmc10Status 16 }


--cmcTcMasterCmc10Status-table-group

  cmcTcMasterCmc10StatusNumber OBJECT-TYPE
    SYNTAX INTEGER 
    ACCESS read-only
    STATUS mandatory
    DESCRIPTION
      "Number of status-table entries"
    ::= { cmcTcMasterCmc10Table 1 }

  cmcTcMasterCmc10StatusTable OBJECT-TYPE
    SYNTAX SEQUENCE OF CmcTcMasterCmc10StatusEntry
    ACCESS not-accessible
    STATUS mandatory
    DESCRIPTION
      "Headline of table"
    ::= { cmcTcMasterCmc10Table 2 }

  cmcTcMasterCmc10StatusEntry OBJECT-TYPE
    SYNTAX CmcTcMasterCmc10StatusEntry
    ACCESS not-accessible
    STATUS mandatory
    DESCRIPTION
      "A list of status entries.  The number of
       entries is given by the value of cmcTcMasterCmc10StatusNumber." 
    INDEX { cmcTcMasterCmc10StatusIndex }
    ::= { cmcTcMasterCmc10StatusTable 1 }

  CmcTcMasterCmc10StatusEntry ::=
    SEQUENCE {
      cmcTcMasterCmc10StatusIndex
        INTEGER,
      cmcTcMasterCmc10StatusText
        DisplayString (SIZE (0..31)),
      cmcTcMasterCmc10StatusStatus
        INTEGER              
    }

    cmcTcMasterCmc10StatusIndex OBJECT-TYPE
      SYNTAX INTEGER (1..32000)
      ACCESS read-only
      STATUS mandatory
      DESCRIPTION
        "Index fo the list of status entries. Its value ranges
         between 1 and the value of cmcTcMasterCmc10StatusNumber." 
      ::= { cmcTcMasterCmc10StatusEntry 1 }

    cmcTcMasterCmc10StatusText OBJECT-TYPE
      SYNTAX DisplayString (SIZE (0..31))
      ACCESS read-write
      STATUS mandatory
      DESCRIPTION
        "Text of the entry in the status-table"
      ::= { cmcTcMasterCmc10StatusEntry 2 }

    cmcTcMasterCmc10StatusStatus OBJECT-TYPE
      SYNTAX INTEGER  {
        statusOK(1),
        alarm(2),
        security(3),
        notAvail(4)
      }
      ACCESS read-only
      STATUS mandatory
      DESCRIPTION
        "Status of the table entry"
      ::= { cmcTcMasterCmc10StatusEntry 3 }

--******************************************************************************

--cmcTCMasterCmc10Set-group

  cmcTcMasterCmc10StatusAccess OBJECT-TYPE
    SYNTAX DisplayString (SIZE (0..31))
    ACCESS read-write
    STATUS mandatory
    DESCRIPTION
      "Status access"
    ::= { cmcTcMasterCmc10Set 1 }

  cmcTcMasterCmc10SetDoor OBJECT-TYPE
    SYNTAX INTEGER {
      lockDoor(1),
      openDoorTime(2),
      openDoorAccess(3),
      openDoor(4)
    }
    ACCESS read-write
    STATUS mandatory
    DESCRIPTION
      "Set door, see table"
    ::= { cmcTcMasterCmc10Set 2 }

  cmcTcMasterCmc10SetMessage OBJECT-TYPE
    SYNTAX DisplayString (SIZE (0..31))
    ACCESS read-write
    STATUS mandatory
    DESCRIPTION
      "Set message"
    ::= { cmcTcMasterCmc10Set 3 }

  cmcTcMasterCmc10SetFault        OBJECT-TYPE
    SYNTAX INTEGER {
      clearFault(1),
      setFault(2)
    }
    ACCESS read-write
    STATUS mandatory
    DESCRIPTION
      "Set fault, see table"
    ::= { cmcTcMasterCmc10Set 4 }

--cmcTcMasterCmc10RelayControl-group

  cmcTcMasterCmc10RelaytableMaxNum OBJECT-TYPE
    SYNTAX INTEGER 
    ACCESS read-only
    STATUS mandatory
    DESCRIPTION
      "Number of table entries"
    ::= { cmcTcMasterCmc10RelayControl 1 }

  cmcTcMasterCmc10RelayTable OBJECT-TYPE
    SYNTAX SEQUENCE OF CmcTcMasterCmc10RelayEntry
    ACCESS not-accessible
    STATUS mandatory
    DESCRIPTION
      "Headline of table for relay control"
    ::= { cmcTcMasterCmc10RelayControl 2 }

  cmcTcMasterCmc10RelayEntry OBJECT-TYPE
    SYNTAX CmcTcMasterCmc10RelayEntry
    ACCESS not-accessible
    STATUS mandatory
    DESCRIPTION
      "Entries"
    INDEX { cmcTcMasterCmc10RelaytableIndex }
    ::= { cmcTcMasterCmc10RelayTable 1 }

  CmcTcMasterCmc10RelayEntry ::=
    SEQUENCE {
      cmcTcMasterCmc10RelaytableIndex
        INTEGER,
      cmcTcMasterCmc10RelaytableText
	DisplayString (SIZE (0..31)),
      cmcTcMasterCmc10RelaytableStatus
        INTEGER              
    }

    cmcTcMasterCmc10RelaytableIndex OBJECT-TYPE
      SYNTAX INTEGER (1..32000)
      ACCESS read-only
      STATUS mandatory
      DESCRIPTION
        "Index for the relay-table. Its value ranges
         between 1 and cmcTcMasterCmc10RelaytableMaxNum"
      ::= { cmcTcMasterCmc10RelayEntry 1 }

    cmcTcMasterCmc10RelaytableText OBJECT-TYPE
      SYNTAX DisplayString (SIZE (0..31))
      ACCESS read-write
      STATUS mandatory
      DESCRIPTION
        "Description-Text for each relay in the table"
      ::= { cmcTcMasterCmc10RelayEntry 2 }

    cmcTcMasterCmc10RelaytableStatus OBJECT-TYPE
      SYNTAX INTEGER  {
        relayOFF(1),
        relayON(2),
        notAvail(3)
      }
      ACCESS read-write
      STATUS mandatory
      DESCRIPTION
        "Status of relays in the table"
      ::= { cmcTcMasterCmc10RelayEntry 3 }

--cmcTcMasterCmc10Setpoints-group

  cmcTcMasterCmc10SetpointFan1 OBJECT-TYPE
    SYNTAX INTEGER 
    ACCESS read-write
    STATUS mandatory
    DESCRIPTION
      "Setpoint Fan 1 in C, Fan 1 will start
       if temperature 1 exceeds this value"
    ::= { cmcTcMasterCmc10Setpoints 1 }

  cmcTcMasterCmc10SetpointFan2 OBJECT-TYPE
    SYNTAX INTEGER 
    ACCESS read-write
    STATUS mandatory
    DESCRIPTION
      "Setpoint Fan 2 in C, Fan 2 will start
       if temperature 2 exceeds this value"
    ::= { cmcTcMasterCmc10Setpoints 2 }

  cmcTcMasterCmc10SetpointHeating OBJECT-TYPE
    SYNTAX INTEGER 
    ACCESS read-write
    STATUS mandatory
    DESCRIPTION
      "Setpoint heating in C, heating will start
       if lowest value of temperature 1 and 2 falls below this value"
    ::= { cmcTcMasterCmc10Setpoints 3 }

  cmcTcMasterCmc10SetpointHighTemperature1 OBJECT-TYPE
    SYNTAX INTEGER 
    ACCESS read-write
    STATUS mandatory
    DESCRIPTION
      "Setpoint high value alarm temperature 1"
    ::= { cmcTcMasterCmc10Setpoints 4 }

  cmcTcMasterCmc10SetpointLowTemperature1 OBJECT-TYPE
    SYNTAX INTEGER 
    ACCESS read-write
    STATUS mandatory
    DESCRIPTION
      "Setpoint low value alarm temperature 1"
    ::= { cmcTcMasterCmc10Setpoints 5 }

  cmcTcMasterCmc10SetpointHighTemperature2 OBJECT-TYPE
    SYNTAX INTEGER 
    ACCESS read-write
    STATUS mandatory
    DESCRIPTION
      "Setpoint high value alarm temperature 2"
    ::= { cmcTcMasterCmc10Setpoints 6 }

  cmcTcMasterCmc10SetpointLowTemperature2 OBJECT-TYPE
    SYNTAX INTEGER 
    ACCESS read-write
    STATUS mandatory
    DESCRIPTION
      "Setpoint low value alarm temperature 2"
    ::= { cmcTcMasterCmc10Setpoints 7 }

  cmcTcMasterCmc10SetpointHighVoltage OBJECT-TYPE
    SYNTAX INTEGER 
    ACCESS read-write
    STATUS mandatory
    DESCRIPTION
      "Setpoint high value supply voltage alarm"
    ::= { cmcTcMasterCmc10Setpoints 8 }

  cmcTcMasterCmc10SetpointLowVoltage OBJECT-TYPE
    SYNTAX INTEGER
    ACCESS read-write
    STATUS mandatory
    DESCRIPTION
      "Setpoint low value supply voltage alarm"
    ::= { cmcTcMasterCmc10Setpoints 9 }

  cmcTcMasterCmc10SetpointLowAux1 OBJECT-TYPE
    SYNTAX INTEGER 
    ACCESS read-write
    STATUS mandatory
    DESCRIPTION
      "Setpoint low value Aux input 1 alarm"
    ::= { cmcTcMasterCmc10Setpoints 10 }

  cmcTcMasterCmc10SetpointHighAux1 OBJECT-TYPE
    SYNTAX INTEGER 
    ACCESS read-write
    STATUS mandatory
    DESCRIPTION
      "Setpoint high value Aux input 1 alarm"
    ::= { cmcTcMasterCmc10Setpoints 11 }

  cmcTcMasterCmc10SetpointLowAux2 OBJECT-TYPE
    SYNTAX INTEGER 
    ACCESS read-write
    STATUS mandatory
    DESCRIPTION
      "Setpoint low value Aux input 2 alarm"
    ::= { cmcTcMasterCmc10Setpoints 12 }

  cmcTcMasterCmc10SetpointHighAux2 OBJECT-TYPE
    SYNTAX INTEGER 
    ACCESS read-write
    STATUS mandatory
    DESCRIPTION
      "Setpoint high value Aux input alarm"
    ::= { cmcTcMasterCmc10Setpoints 13 }

--cmcTcMasterCmc10TrapControl-group

  cmcTcMasterCmc10SetTrapRepeat OBJECT-TYPE
    SYNTAX INTEGER {
      disableTrapRepeat(1),
      enableTrapRepeat(2)
    }
    ACCESS read-write
    STATUS mandatory
    DESCRIPTION
      "Enable/disable repeating of traps. If enabled, traps will
       be repeated after a repeat time, set in setTrapRepeatTime.
       Repeating can be stopped by setting setTrapQuit to quitTrap"
    ::= { cmcTcMasterCmc10TrapControl 1 }

  cmcTcMasterCmc10SetTrapRepeatTime OBJECT-TYPE
    SYNTAX INTEGER 
    ACCESS read-write
    STATUS mandatory
    DESCRIPTION
      "Time value (sec) for trap-repeating, if setTrapRepeat is enabled"
    ::= { cmcTcMasterCmc10TrapControl 2 }

  cmcTcMasterCmc10SetTrapQuit OBJECT-TYPE
    SYNTAX INTEGER {
      quitTrap(1),
      quitTrapOK(2),
      noTrapToQuit(3),
      trapToQuit(4)
    }
    ACCESS read-write
    STATUS mandatory
    DESCRIPTION
      "Quit trap to stop repeating."
    ::= { cmcTcMasterCmc10TrapControl 3 }

--cmcTcMasterCmc10TrapTable-group

  cmcTcMasterCmc10TraptableNumber OBJECT-TYPE
    SYNTAX INTEGER 
    ACCESS read-only
    STATUS mandatory
    DESCRIPTION
      "Number of trapTable entries. The number of trap-receiver"
    ::= { cmcTcMasterCmc10Traps 1 }

  cmcTcMasterCmc10TrapTable OBJECT-TYPE
    SYNTAX SEQUENCE OF CmcTcMasterCmc10TrapEntry
    ACCESS not-accessible
    STATUS mandatory
    DESCRIPTION
      "A list of trap-receiver entries"
    ::= { cmcTcMasterCmc10Traps 2 }

  cmcTcMasterCmc10TrapEntry OBJECT-TYPE
    SYNTAX CmcTcMasterCmc10TrapEntry
    ACCESS not-accessible
    STATUS mandatory
    DESCRIPTION
      "Entries of trapTable"
    INDEX { cmcTcMasterCmc10TrapIndex }
    ::= { cmcTcMasterCmc10TrapTable 1 }

  CmcTcMasterCmc10TrapEntry ::=
    SEQUENCE {
      cmcTcMasterCmc10TrapIndex
        INTEGER,
      cmcTcMasterCmc10TrapStatus
        INTEGER,
      cmcTcMasterCmc10TrapIPaddress
        DisplayString
    }

    cmcTcMasterCmc10TrapIndex OBJECT-TYPE
      SYNTAX INTEGER (1..32000)
      ACCESS read-only
      STATUS mandatory
      DESCRIPTION
        "Index for the trap-receiver-table. Its value ranges between
         1 and the value of cmcTcMasterCmc10TraptableNumber "
      ::= { cmcTcMasterCmc10TrapEntry 1 }

    cmcTcMasterCmc10TrapStatus OBJECT-TYPE
      SYNTAX INTEGER  {
        enabled(1),
        disabled(2)
      }
      ACCESS read-write
      STATUS mandatory
      DESCRIPTION
        "Enable or disable trap receiver"
      ::= { cmcTcMasterCmc10TrapEntry 2 }

    cmcTcMasterCmc10TrapIPaddress OBJECT-TYPE
      SYNTAX DisplayString (SIZE (0..31))
      ACCESS read-write
      STATUS mandatory
      DESCRIPTION
        "IP-address of trap-receiver"
      ::= { cmcTcMasterCmc10TrapEntry 3 }

--cmcTcMasterPcu10MibRev-group
          
  cmcTcMasterPcu10MibMajRev OBJECT-TYPE
    SYNTAX INTEGER (1..32000)
    ACCESS read-only
    STATUS mandatory
    DESCRIPTION
      "The Major Revision level.
       A change in the major revision level represents a major change
       in the architecture of the MIB. A change in the major revision 
       level may indicate a significant change in the information,
       correct interpretation of data may require a MIB document
       with the same major revision level."
    ::= { cmcTcMasterPcu10MibRev 1 }

  cmcTcMasterPcu10MibMinRev OBJECT-TYPE
    SYNTAX INTEGER (0..32000)
    ACCESS read-only
    STATUS mandatory
    DESCRIPTION
      "The Minor Revision level.
       A change in the minor revision level may represent some minor
       additional support, no changes to any pre-existing information
       has occurred."
    ::= { cmcTcMasterPcu10MibRev 2 }

  cmcTcMasterPcu10MibCondition OBJECT-TYPE
    SYNTAX INTEGER {
      other (1),
      ok (2),
      degraded (3),
      failed (4)
    }
    ACCESS read-only
    STATUS mandatory
    DESCRIPTION
      "The overall condition (status) of the system represented by
       this MIB. 
       (2) OK
       (3) a minor problem, warning condition (yellow LED on PCU)
       (4) a major problem (red LED on PCU)"
    ::= { cmcTcMasterPcu10MibRev 3 }

--cmcTcMasterPcu10Values-group

  cmcTcMasterPcu10ValueEnergy1 OBJECT-TYPE
    SYNTAX INTEGER 
    ACCESS read-only
    STATUS mandatory
    DESCRIPTION
      "Total value of the Energy (Wh), measured on IEC input 1"
    ::= { cmcTcMasterPcu10Values 1 }

  cmcTcMasterPcu10ValueEnergy2 OBJECT-TYPE
    SYNTAX INTEGER 
    ACCESS read-only
    STATUS mandatory
    DESCRIPTION
      "Actual value of the Energy (Wh), measured on IEC input 2"
    ::= { cmcTcMasterPcu10Values 2 }

  cmcTcMasterPcu10ValueEnergy1Time OBJECT-TYPE
    SYNTAX INTEGER 
    ACCESS read-only
    STATUS mandatory
    DESCRIPTION
      "Actual value of the Energy (Wh), measured on IEC input 1, can be set to 0
       Value can be used to calculate the energy over a fixed time"
    ::= { cmcTcMasterPcu10Values 3 }

  cmcTcMasterPcu10ValueEnergy2Time OBJECT-TYPE
    SYNTAX INTEGER 
    ACCESS read-only
    STATUS mandatory
    DESCRIPTION
      "Actual value of the Energy (Wh), measured on IEC input 2, can be set to 0.
       Value can be used to calculate the energy over a fixed time"
    ::= { cmcTcMasterPcu10Values 4 }

  cmcTcMasterPcu10ValuePower1 OBJECT-TYPE
    SYNTAX INTEGER 
    ACCESS read-only
    STATUS mandatory
    DESCRIPTION
      "Calculated actual power 1 (W). Calculated from cmcTcMasterPcu10ValueEnergy1/time"
    ::= { cmcTcMasterPcu10Values 5 }
          
  cmcTcMasterPcu10ValuePower2 OBJECT-TYPE
    SYNTAX INTEGER 
    ACCESS read-only
    STATUS mandatory
    DESCRIPTION
      "Calculated actual power 2 (W). Calculated from cmcTcMasterPcu10ValueEnergy2/time"
    ::= { cmcTcMasterPcu10Values 6 }
          
  cmcTcMasterPcu10ValueTemperature OBJECT-TYPE
    SYNTAX INTEGER 
    ACCESS read-only
    STATUS mandatory
    DESCRIPTION
      "Actual value of temperature 1 in deg C or deg F"
    ::= { cmcTcMasterPcu10Values 7 }
          
--cmcTcMasterPcu10Status-group

  cmcTcMasterPcu10StatusInput1 OBJECT-TYPE
    SYNTAX INTEGER {
      false(1),
      true(2),
      pending(3),
      notAvail(4)
    }
    ACCESS read-only
    STATUS mandatory
    DESCRIPTION
      "Status of digital Input 1
       (1) digital signal is true (contact closed if setup is NO)
       (2) digital signal is false(contact opened if setup is NO),
       note setup of input (NO/NC)
       (3) digital input is pending, note setup of delay"
    ::= { cmcTcMasterPcu10Status 1 }

  cmcTcMasterPcu10StatusInput2 OBJECT-TYPE
    SYNTAX INTEGER {
      false(1),
      true(2),
      pending(3),
      notAvail(4)
    }
    ACCESS read-only
    STATUS mandatory
    DESCRIPTION
      "Status of digital Input 2
       (1) digital signal is true (contact closed if setup is NO)
       (2) digital signal is false(contact opened if setup is NO),
       note setup of input (NO/NC)
       (3) digital input is pending, note setup of delay"
    ::= { cmcTcMasterPcu10Status 2 }

  cmcTcMasterPcu10StatusPower1 OBJECT-TYPE
    SYNTAX INTEGER {
      ok(1),
      tooHigh(2),
      tooLow(3),
      warning(4),
      error(5),
      notAvail(6)
    }
    ACCESS read-only
    STATUS mandatory
    DESCRIPTION
      "Status Power 1, see setpoints"
    ::= { cmcTcMasterPcu10Status 3 }

  cmcTcMasterPcu10StatusPower2 OBJECT-TYPE
    SYNTAX INTEGER {
      ok(1),
      tooHigh(2),
      tooLow(3),
      warning(4),
      error(5),
      notAvail(6)
    }
    ACCESS read-only
    STATUS mandatory
    DESCRIPTION
      "Status Power 2, see setpoints"
    ::= { cmcTcMasterPcu10Status 4 }

  cmcTcMasterPcu10StatusTemperature OBJECT-TYPE
    SYNTAX INTEGER {
      ok(1),
      tooHigh(2),
      tooLow(3),
      warning(4),
      error(5)
    }
    ACCESS read-only
    STATUS mandatory
    DESCRIPTION
      "Status temperature 1, OK/ too high/ too low
       (see setpoints of temperature 1)"
    ::= { cmcTcMasterPcu10Status 5 }

--cmcTcMasterPcu10Status-table-group

  cmcTcMasterPcu10OutletsNumber OBJECT-TYPE
    SYNTAX INTEGER 
    ACCESS read-only
    STATUS mandatory
    DESCRIPTION
      "Number of value-table entries=number of outlets available on this unit"
    ::= { cmcTcMasterPcu10StatusTable1 1 }

  cmcTcMasterPcu10StatusTable OBJECT-TYPE
    SYNTAX SEQUENCE OF CmcTcMasterPcu10StatusEntry
    ACCESS not-accessible
    STATUS mandatory
    DESCRIPTION
      "Headline of status-table"
    ::= { cmcTcMasterPcu10StatusTable1 2 }

  cmcTcMasterPcu10StatusEntry OBJECT-TYPE
    SYNTAX CmcTcMasterPcu10StatusEntry
    ACCESS not-accessible
    STATUS mandatory
    DESCRIPTION
      "Entries of status-table"
    INDEX { cmcTcMasterPcu10StatusIndex }
    ::= { cmcTcMasterPcu10StatusTable 1 }

    CmcTcMasterPcu10StatusEntry ::=
      SEQUENCE {
        cmcTcMasterPcu10StatusIndex
          INTEGER,
        cmcTcMasterPcu10StatusText
          DisplayString (SIZE (0..31)),                
        cmcTcMasterPcu10StatusStatus
          INTEGER,
        cmcTcMasterPcu10ControlSNMP
          INTEGER,
        cmcTcMasterPcu10FrontSwitch
          INTEGER,
        cmcTcMasterPcu10Delay
          INTEGER,
        cmcTcMasterPcu10Input1
          INTEGER,
        cmcTcMasterPcu10Input2
          INTEGER,
        cmcTcMasterPcu10Temperature
          INTEGER,          
        cmcTcMasterPcu10Power
          INTEGER,          
        cmcTcMasterPcu10RestoreOutputStatus
          INTEGER           
      }

    cmcTcMasterPcu10StatusIndex OBJECT-TYPE
      SYNTAX INTEGER (1..32000)
      ACCESS read-only
      STATUS mandatory
      DESCRIPTION
        "Index for the list of value entries. Its value ranges
         between 1 and the value of cmcTcMasterPcu10OutletsNumber."
      ::= { cmcTcMasterPcu10StatusEntry 1 }

    cmcTcMasterPcu10StatusText OBJECT-TYPE
      SYNTAX DisplayString (SIZE (0..31))
      ACCESS read-write
      STATUS mandatory
      DESCRIPTION
        "Descriptional text for each outlet (entry in the table)"
      ::= { cmcTcMasterPcu10StatusEntry 2 }
              
    cmcTcMasterPcu10StatusStatus OBJECT-TYPE
      SYNTAX INTEGER {
        ok(1),
        onFrontKey(2),
        offFrontKey(3),
        onWEB(4),
        offWEB(5),
        onInput1(6),
        offInput1(7),
        onInput2(8),
        offInput2(9),
        onTemp(10),
        offTemp(11),
        onSNMP(12),
        offSNMP(13),
        onTimer(14),
        offTimer(15),
        onDelay(16),
        onConsole(17),
        offConsole(18),
        onReboot(19), 
        offReboot(20),
        onPower(21),
        offPower(22)
      }
      ACCESS read-only
      STATUS mandatory
      DESCRIPTION
        "Actual status of the outlet"
      ::= { cmcTcMasterPcu10StatusEntry 3 }

    cmcTcMasterPcu10ControlSNMP OBJECT-TYPE
      SYNTAX INTEGER  {
        on(1),
        off(2)
      }
      ACCESS read-write
      STATUS mandatory
      DESCRIPTION
        "Control via SNMP"
      ::= { cmcTcMasterPcu10StatusEntry 4 }

    cmcTcMasterPcu10FrontSwitch OBJECT-TYPE
      SYNTAX INTEGER {
        disabled(1),
        enabled(2)
      }
      ACCESS read-write
      STATUS mandatory
      DESCRIPTION
        "Control via front switch"
      ::= { cmcTcMasterPcu10StatusEntry 5 }
 
    cmcTcMasterPcu10Delay OBJECT-TYPE
      SYNTAX INTEGER (0..300)
      ACCESS read-write
      STATUS mandatory
      DESCRIPTION
        "Value for delay time in seconds.
         Value>0: Output is switched off for this time (in sec)"
      ::= { cmcTcMasterPcu10StatusEntry 6 }

    cmcTcMasterPcu10Input1 OBJECT-TYPE
      SYNTAX INTEGER {
        disabled(1),
        switchOn(2),
        switchOff(3),
        switchOnOff(4)
      }
      ACCESS read-write
      STATUS mandatory
      DESCRIPTION
        "Control via digital input 1
         (1): disabled
         (2): output is switched on in case of input 1 alarm
         (3): output is switched off in case of input 1 alarm
         (4): output has same status as input 1"
      ::= { cmcTcMasterPcu10StatusEntry 7 }

    cmcTcMasterPcu10Input2 OBJECT-TYPE
      SYNTAX INTEGER {
        disabled(1),
        switchOn(2),
        switchOff(3),
        switchOnOff(4)
      }
      ACCESS read-write
      STATUS mandatory
      DESCRIPTION
        "Control via digital input 2
         (1): disabled
         (2): output is switched on in case of input 2 alarm
         (3): output is switched off in case of input 2 alarm
         (4): output has same status as input 2"             
      ::= { cmcTcMasterPcu10StatusEntry 8 }

    cmcTcMasterPcu10Temperature OBJECT-TYPE
      SYNTAX INTEGER {
        disabled(1),
        switchOffAlarm(2),
        switchOnAlarm(3),
        switchOffSetpoint(4),
        switchOnSetpoint(5)
      }
      ACCESS read-write
      STATUS mandatory
      DESCRIPTION
        "Control via temperature alarm or setpoint
         (1): disabled
         (2): output is switched off in case of temperature alarm
         (3): output is switched on in case of temperature alarm
         (4): output is switched off if temperature setpoint (cmcTcMasterPcu10SetpointTemperature)
              is reached
         (5): output is switched on if temperature setpoint (cmcTcMasterPcu10SetpointTemperature)
              is reached"
      ::= { cmcTcMasterPcu10StatusEntry 9 }   
    
    cmcTcMasterPcu10Power OBJECT-TYPE
      SYNTAX INTEGER {
        disabled(1),
        switchOffAlarm(2),
        switchOffWarning(3),
        switchOnAlarm(4),
        switchOnWarning(5)
      }
      ACCESS read-write
      STATUS mandatory
      DESCRIPTION
        "Control via power setpoint
         (1): disabled
         (2): output is switched off upon power high alarm (cmcTcMasterPcu10SetpointHighPower1)
         (3): output is switched off upon power warning (cmcTcMasterPcu10SetpointWarningPower1)
         (4): output is switched on upon power alarm (cmcTcMasterPcu10SetpointHigh(Low)Power1)
         (5): output is switched on upon power warning (cmcTcMasterPcu10SetpointWarningPower1)             "
      ::= { cmcTcMasterPcu10StatusEntry 10 }                

    cmcTcMasterPcu10RestoreOutputStatus OBJECT-TYPE
      SYNTAX INTEGER {
        disabled(1),
        enabled(2)
      }
      ACCESS read-write
      STATUS mandatory
      DESCRIPTION
        "Save last output status and switch output to this status after reboot"
      ::= { cmcTcMasterPcu10StatusEntry 11 }
                
--cmcTcMasterPcu10SetupGeneral-group

  cmcTcMasterPcu10SetTempUnit OBJECT-TYPE
    SYNTAX INTEGER {
      celsius(1),
      fahrenheit(2)
    }
    ACCESS read-write
    STATUS mandatory
    DESCRIPTION
      "Unit of all temperature values and setpoints, Celsius or Fahrenheit"
    ::= { cmcTcMasterPcu10SetupGeneral 1 }

  cmcTcMasterPcu10SetBeeper OBJECT-TYPE
    SYNTAX INTEGER {
      off(1),
      on(2),
      enableClear(3)
    }
    ACCESS read-write
    STATUS mandatory
    DESCRIPTION
      "Audible alarm in PCU unit:
       (1): beeper is off (general)
       (2): beeper is on (Alarm)
       (3): enable Clear (cmcTcMasterPcu10ClearAlarm)"
    ::= { cmcTcMasterPcu10SetupGeneral 2 }

  cmcTcMasterPcu10LogicRelay OBJECT-TYPE
    SYNTAX INTEGER {
      closeAtAlarm(1),
      openAtAlarm(2),
      off(3),
      enableRemote(4)
    }
    ACCESS read-write
    STATUS mandatory
    DESCRIPTION
      "Logic of alarm relay: 
       (1): Relay will pick up in case of an alarm
       (2): Relay will release in case of an alarm
       (3): Relay off (general)
       (4): enable remote relay control (SNMP set)"
    ::= { cmcTcMasterPcu10SetupGeneral 3 }
 
  cmcTcMasterPcu10ClearRelay OBJECT-TYPE
    SYNTAX INTEGER {
      disabled(1),
      enabled(2)
    }
    ACCESS read-write
    STATUS mandatory
    DESCRIPTION
      "Enable clear of alarm relay: 
       (1): Relay cannot be cleared by cmcTcMasterPcu10ClearAlarm
       (2): Relay can be cleared by cmcTcMasterPcu10ClearAlarm"
    ::= { cmcTcMasterPcu10SetupGeneral 4 }                  

  cmcTcMasterPcu10WebAccess OBJECT-TYPE
    SYNTAX INTEGER {
      viewOnly(1),
      fullAccess(2),
      off(3)
    }
    ACCESS read-write
    STATUS mandatory
    DESCRIPTION
      "Web access via HTTP: 
       (1): view only
       (2): full Access, read and set
       (3): Web disabled (general)"
    ::= { cmcTcMasterPcu10SetupGeneral 5 }
 
  cmcTcMasterPcu10SetupDate OBJECT-TYPE
    SYNTAX DisplayString (SIZE (0..10))
    ACCESS read-write
    STATUS mandatory
    DESCRIPTION
      "actual Date in format DD.MM.YYYY"
    ::= { cmcTcMasterPcu10SetupGeneral 6 }

  cmcTcMasterPcu10SetupTime OBJECT-TYPE
    SYNTAX DisplayString (SIZE (0..8))
    ACCESS read-write
    STATUS mandatory
    DESCRIPTION
      "actual Time in format HH:MM:SS, HH (0-23), MM (0-59), SS (0-59)"
    ::= { cmcTcMasterPcu10SetupGeneral 7 }

--cmcTcMasterPcu10TimerTable1-group
 
  cmcTcMasterPcu10TimerNumber OBJECT-TYPE
    SYNTAX INTEGER 
    ACCESS read-only
    STATUS mandatory
    DESCRIPTION
      "Number of timers available on this unit"
    ::= { cmcTcMasterPcu10TimerTable1 1 }

  cmcTcMasterPcu10TimerTable OBJECT-TYPE
    SYNTAX SEQUENCE OF CmcTcMasterPcu10TimerEntry
    ACCESS not-accessible
    STATUS mandatory
    DESCRIPTION
      "Headline of timer-table"
    ::= { cmcTcMasterPcu10TimerTable1 2 }

  cmcTcMasterPcu10TimerEntry OBJECT-TYPE
    SYNTAX CmcTcMasterPcu10TimerEntry
    ACCESS not-accessible
    STATUS mandatory
    DESCRIPTION
      "Entries of timer-table"
    INDEX { cmcTcMasterPcu10TimerIndex }
    ::= { cmcTcMasterPcu10TimerTable 1 }

    CmcTcMasterPcu10TimerEntry ::=
      SEQUENCE {
        cmcTcMasterPcu10TimerIndex
          INTEGER,
        cmcTcMasterPcu10TimerStatus
          INTEGER,
        cmcTcMasterPcu10TimerDayOfWeek
          INTEGER,  
        cmcTcMasterPcu10TimeOn 
          DisplayString (SIZE (0..5)),                              
        cmcTcMasterPcu10TimeOff 
          DisplayString (SIZE (0..5)),                              
        cmcTcMasterPcu10TimeControl
          INTEGER,
        cmcTcMasterPcu10TimerOutput1
          INTEGER,
        cmcTcMasterPcu10TimerOutput2
          INTEGER         
      }

    cmcTcMasterPcu10TimerIndex OBJECT-TYPE
      SYNTAX INTEGER (1..32000)
      ACCESS read-only
      STATUS mandatory
      DESCRIPTION
        "Index for the list of timer entries. Its value ranges
         between 1 and the value of cmcTcMasterPcu10TimerNumber." 
      ::= { cmcTcMasterPcu10TimerEntry 1 }

    cmcTcMasterPcu10TimerStatus OBJECT-TYPE
      SYNTAX INTEGER {
        switchedOff(1),
        switchedOn(2),
        noTime(3) 
      }
      ACCESS read-only
      STATUS mandatory
      DESCRIPTION
        "Actual status of the timer"
      ::= { cmcTcMasterPcu10TimerEntry 2 }

    cmcTcMasterPcu10TimerDayOfWeek OBJECT-TYPE
      SYNTAX INTEGER {
        sun(1),
        mon(2),
        tue(3) ,
        wed(4),
        thu(5),
        fre(6),
        sat(7),
        sat-sun(8),
        mo-fr(9),
        mo-su(10)
      }
      ACCESS read-write
      STATUS mandatory
      DESCRIPTION
        "Day when the timer is active"
      ::= { cmcTcMasterPcu10TimerEntry 3 }
             
    cmcTcMasterPcu10TimeOn OBJECT-TYPE
      SYNTAX DisplayString (SIZE (0..5))
      ACCESS read-write
      STATUS mandatory
      DESCRIPTION
        "Time to switch on current outlet, 
         Format: HH:MM"
      ::= { cmcTcMasterPcu10TimerEntry 4 }

    cmcTcMasterPcu10TimeOff OBJECT-TYPE
      SYNTAX DisplayString (SIZE (0..5))
      ACCESS read-write
      STATUS mandatory
      DESCRIPTION
        "Time to switch off current outlet,
         Format: HH:MM"
      ::= { cmcTcMasterPcu10TimerEntry 5 }

    cmcTcMasterPcu10TimeControl OBJECT-TYPE
      SYNTAX INTEGER {
        disabled(1),
        enabled(2)
      }
      ACCESS read-write
      STATUS mandatory
      DESCRIPTION
        "Control via RTC"
      ::= { cmcTcMasterPcu10TimerEntry 6 }

    cmcTcMasterPcu10TimerOutput1 OBJECT-TYPE
      SYNTAX INTEGER 
      ACCESS read-write
      STATUS mandatory
      DESCRIPTION
        "Output which is controlled via timer"
      ::= { cmcTcMasterPcu10TimerEntry 7 }

    cmcTcMasterPcu10TimerOutput2 OBJECT-TYPE
      SYNTAX INTEGER 
      ACCESS read-write
      STATUS mandatory
      DESCRIPTION
        "Output which is controlled via timer"
      ::= { cmcTcMasterPcu10TimerEntry 8 }

--cmcTcMasterPcu10SetupPower1-group                     

  cmcTcMasterPcu10SetupPower1Avail OBJECT-TYPE
    SYNTAX INTEGER {
      notAvailable(1),
      available(2)
    }
    ACCESS read-write
    STATUS mandatory
    DESCRIPTION
      "Energy sensor 1 sensor:   
       (1) not available
       (2) available"
    ::= { cmcTcMasterPcu10SetupPower1 1 }

  cmcTcMasterPcu10SetupPower1Relay OBJECT-TYPE
    SYNTAX INTEGER {
      disabled(1),
      enabled(2)
    }
    ACCESS read-write
    STATUS mandatory
    DESCRIPTION
      "Alert handling of Alarm Relay in case of an alarm condition
       of Power 1:  
       (1) no switching of Relays
       (2) Relay will switch"
    ::= { cmcTcMasterPcu10SetupPower1 2 }

  cmcTcMasterPcu10SetupPower1Beeper OBJECT-TYPE
    SYNTAX INTEGER {
      disabled(1),
      enabled(2)
    }
    ACCESS read-write
    STATUS mandatory
    DESCRIPTION
      "Alert handling of beeper of in case of an alarm condition
       of Power 1: 
       (1) No Audible Alarm
       (2) Start Audible Alarm"
    ::= { cmcTcMasterPcu10SetupPower1 3 }

--cmcTcMasterPcu10SetupPower2-group                     

  cmcTcMasterPcu10SetupPower2Avail OBJECT-TYPE
    SYNTAX INTEGER {
      notAvailable(1),
      available(2)
    }
    ACCESS read-write
    STATUS mandatory
    DESCRIPTION
      "Energy sensor 2:   
       (1) not available
       (2) available"
    ::= { cmcTcMasterPcu10SetupPower2 1 }

  cmcTcMasterPcu10SetupPower2Relay OBJECT-TYPE
    SYNTAX INTEGER {
      disabled(1),
      enabled(2)
    }
    ACCESS read-write
    STATUS mandatory
    DESCRIPTION
      "Alert handling of Alarm Relay in case of an alarm condition
       of Power 2:  
       (1) no switching of Relay
       (2) Relay will switch"
    ::= { cmcTcMasterPcu10SetupPower2 2 }

  cmcTcMasterPcu10SetupPower2Beeper OBJECT-TYPE
    SYNTAX INTEGER {
      disabled(1),
      enabled(2)
    }
    ACCESS read-write
    STATUS mandatory
    DESCRIPTION
      "Alert handling of beeper of in case of an alarm condition
       of Power 2: 
       (1) No Audible Alarm
       (2) Start Audible Alarm"
    ::= { cmcTcMasterPcu10SetupPower2 3 }

--cmcTcMasterPcu10SetupInput1-group

  cmcTcMasterPcu10SetupInput1Avail OBJECT-TYPE
    SYNTAX INTEGER {
      notAvailable(1),
      available(2)
    }
    ACCESS read-write
    STATUS mandatory
    DESCRIPTION
      "Input 1 sensor:   
       (1) not available
       (2) available"
    ::= { cmcTcMasterPcu10SetupInput1 1 }

  cmcTcMasterPcu10SetupInput1Relay OBJECT-TYPE
    SYNTAX INTEGER {
      disabled(1),
      enabled(2)
    }
    ACCESS read-write
    STATUS mandatory
    DESCRIPTION
      "Alert handling of Alarm Relay in case of an alarm condition
       of Input 1:  
       (1) no switching of Relay
       (2) Relay will switch"
    ::= { cmcTcMasterPcu10SetupInput1 2 }

  cmcTcMasterPcu10SetupInput1Beeper OBJECT-TYPE
    SYNTAX INTEGER {
      disabled(1),
      enabled(2)
    }
    ACCESS read-write
    STATUS mandatory
    DESCRIPTION
      "Alert handling of beeper of in case of an alarm condition
       of Input 1: 
       (1) No Audible Alarm
       (2) Start Audible Alarm"
    ::= { cmcTcMasterPcu10SetupInput1 3 }

  cmcTcMasterPcu10SetupInput1Contact OBJECT-TYPE
    SYNTAX INTEGER {
      contactNO(1),
      contactNC(2),
      notAvail(3)
    }
    ACCESS read-write
    STATUS mandatory
    DESCRIPTION
      "Setup of digital input 1"
    ::= { cmcTcMasterPcu10SetupInput1 4 }

  cmcTcMasterPcu10SetupInput1Delay OBJECT-TYPE
    SYNTAX INTEGER (0..60)
    ACCESS read-write
    STATUS mandatory
    DESCRIPTION
      "Delay for changing of input state"
    ::= { cmcTcMasterPcu10SetupInput1 5 }

--cmcTcMasterPcu10SetupInput2-group

  cmcTcMasterPcu10SetupInput2Avail OBJECT-TYPE
    SYNTAX INTEGER {
      notAvailable(1),
      available(2)
    }
    ACCESS read-write
    STATUS mandatory
    DESCRIPTION
      "Input 2 sensor:   
       (2) available
       (1) not available"
    ::= { cmcTcMasterPcu10SetupInput2 1 }

  cmcTcMasterPcu10SetupInput2Relay OBJECT-TYPE
    SYNTAX INTEGER {
      disabled(1),
      enabled(2)
    }
    ACCESS read-write
    STATUS mandatory
    DESCRIPTION
      "Alert handling of Alarm Relay in case of an alarm condition
       of Input 1:  
       (1) no switching of Relays
       (2) Relay will switch"
    ::= { cmcTcMasterPcu10SetupInput2 2 }

  cmcTcMasterPcu10SetupInput2Beeper OBJECT-TYPE
    SYNTAX INTEGER {
      disabled(1),
      enabled(2)
    }
    ACCESS read-write
    STATUS mandatory
    DESCRIPTION
      "Alert handling of beeper of in case of an alarm condition
       of Input 2: 
       (1) No Audible Alarm
       (2) Start Audible Alarm"
    ::= { cmcTcMasterPcu10SetupInput2 3 }

  cmcTcMasterPcu10SetupInput2Contact OBJECT-TYPE
    SYNTAX INTEGER {
      contactNO(1),
      contactNC(2),
      notAvail(3)
    }
    ACCESS read-write
    STATUS mandatory
    DESCRIPTION
      "Setup of digital input 2"
    ::= { cmcTcMasterPcu10SetupInput2 4 }

  cmcTcMasterPcu10SetupInput2Delay OBJECT-TYPE
    SYNTAX INTEGER (0..60)
    ACCESS read-write
    STATUS mandatory
    DESCRIPTION
      "Delay for changing of input state"
    ::= { cmcTcMasterPcu10SetupInput2 5 }

--cmcTcMasterPcu10SetupTemperature-group                     

  cmcTcMasterPcu10SetupTemperatureAvail OBJECT-TYPE
    SYNTAX INTEGER {
      notAvailable(1),
      available(2)
    }
    ACCESS read-write
    STATUS mandatory
    DESCRIPTION
      "Temp sensor 1:   
       (1) not available
       (2) available"
    ::= { cmcTcMasterPcu10SetupTemperature 1 }

  cmcTcMasterPcu10SetupTemperatureRelay OBJECT-TYPE
    SYNTAX INTEGER {
      disabled(1),
      enabled(2)
    }
    ACCESS read-write
    STATUS mandatory
    DESCRIPTION
      "Alert handling of Alarm Relay in case of an alarm condition
       of Temperature:  
       (1) no switching of Relays
       (2) Relay will switch"
    ::= { cmcTcMasterPcu10SetupTemperature 2 }

  cmcTcMasterPcu10SetupTemperatureBeeper OBJECT-TYPE
    SYNTAX INTEGER {
      disabled(1),
      enabled(2)
    }
    ACCESS read-write
    STATUS mandatory
    DESCRIPTION
      "Alert handling of beeper of in case of an alarm condition
       of Temperature: 
       (1) No Audible Alarm
       (2) Start Audible Alarm"
    ::= { cmcTcMasterPcu10SetupTemperature 3 }

--cmcTcMasterPcu10SetupGeneral-group

  cmcTcMasterPcu10SetMessage OBJECT-TYPE
    SYNTAX DisplayString (SIZE (0..31))
    ACCESS read-write
    STATUS mandatory
    DESCRIPTION
      "Set message"
    ::= { cmcTcMasterPcu10SetupDevice 1 }

--cmcTcMasterPcu10Setpoints-group

  cmcTcMasterPcu10SetpointHighPower1 OBJECT-TYPE
    SYNTAX INTEGER 
    ACCESS read-write
    STATUS mandatory
    DESCRIPTION
      "Setpoint high value power consumption 1 alarm"
    ::= { cmcTcMasterPcu10Setpoints 1 }

  cmcTcMasterPcu10SetpointWarningPower1 OBJECT-TYPE
    SYNTAX INTEGER 
    ACCESS read-write
    STATUS mandatory
    DESCRIPTION
      "Setpoint warning value power consumption 1 alarm"
    ::= { cmcTcMasterPcu10Setpoints 2 }

  cmcTcMasterPcu10SetpointLowPower1 OBJECT-TYPE
    SYNTAX INTEGER
    ACCESS read-write
    STATUS mandatory
    DESCRIPTION
      "Setpoint low value power consumption 1 alarm"
    ::= { cmcTcMasterPcu10Setpoints 3 }

  cmcTcMasterPcu10SetpointHighPower2 OBJECT-TYPE
    SYNTAX INTEGER 
    ACCESS read-write
    STATUS mandatory
    DESCRIPTION
      "Setpoint high value power consumption 2 alarm"
    ::= { cmcTcMasterPcu10Setpoints 4 }

  cmcTcMasterPcu10SetpointWarningPower2 OBJECT-TYPE
    SYNTAX INTEGER 
    ACCESS read-write
    STATUS mandatory
    DESCRIPTION
      "Setpoint warning value power consumption 2 alarm"
    ::= { cmcTcMasterPcu10Setpoints 5 }

  cmcTcMasterPcu10SetpointLowPower2 OBJECT-TYPE
    SYNTAX INTEGER
    ACCESS read-write
    STATUS mandatory
    DESCRIPTION
      "Setpoint low value power consumption 2 alarm"
    ::= { cmcTcMasterPcu10Setpoints 6 }

  cmcTcMasterPcu10SetpointHighTemperature OBJECT-TYPE
    SYNTAX INTEGER (0..200)
    ACCESS read-write
    STATUS mandatory
    DESCRIPTION
      "Setpoint high value alarm temperature "
    ::= { cmcTcMasterPcu10Setpoints 7 }

  cmcTcMasterPcu10SetpointLowTemperature OBJECT-TYPE
    SYNTAX INTEGER (0..50)
    ACCESS read-write
    STATUS mandatory
    DESCRIPTION
      "Setpoint low value alarm temperature "
    ::= { cmcTcMasterPcu10Setpoints 8 }
 
  cmcTcMasterPcu10SetpointTemperature OBJECT-TYPE
    SYNTAX INTEGER (0..200)
    ACCESS read-write
    STATUS mandatory
    DESCRIPTION
      "Setpoint temperature for outlet control 
       and temperature warning"
    ::= { cmcTcMasterPcu10Setpoints 9 }

  cmcTcMasterPcu10SetpointTemperatureHyst OBJECT-TYPE
    SYNTAX INTEGER (0..15)
    ACCESS read-write
    STATUS mandatory
    DESCRIPTION
      "Hysteresis for cmcTcMasterPcu10SetpointTemperature"
    ::= { cmcTcMasterPcu10Setpoints 10 }
 
--cmcTcMasterPcu10Control-group

  cmcTcMasterPcu10ResetEnergy1 OBJECT-TYPE
    SYNTAX INTEGER {
      noReset(1),
      reset(2)
    }
    ACCESS read-write
    STATUS mandatory
    DESCRIPTION
      "Reset value of cmcTcMasterPcu10ValueEnergy1Time"
    ::= { cmcTcMasterPcu10Control 1 }

  cmcTcMasterPcu10ResetEnergy2 OBJECT-TYPE
    SYNTAX INTEGER {
      noReset(1),
      reset(2)
    }
    ACCESS read-write
    STATUS mandatory
    DESCRIPTION
      "Reset value of cmcTcMasterPcu10ValueEnergy2Time"
    ::= { cmcTcMasterPcu10Control 2 }

  cmcTcMasterPcu10ControlAlarmRelay OBJECT-TYPE
    SYNTAX INTEGER {
      relayOff(1),
      relayOn(2)
    }
    ACCESS read-write
    STATUS mandatory
    DESCRIPTION
      "Control of Alarm relay"
    ::= { cmcTcMasterPcu10Control 3 }

  cmcTcMasterPcu10ClearAlarm OBJECT-TYPE
    SYNTAX INTEGER {
      noClear(1),
      clear(2)
    }
    ACCESS read-write
    STATUS mandatory
    DESCRIPTION
      "Clear alarm, beeper and relay"
    ::= { cmcTcMasterPcu10Control 4 }

--cmcTcMasterPcu10TrapTable-group

  cmcTcMasterPcu10TrapTableNumber OBJECT-TYPE
    SYNTAX INTEGER 
    ACCESS read-only
    STATUS mandatory
    DESCRIPTION
      "Number of cmcTcMasterPcu10TrapTable entries. The number of trap-receivers avail."
    ::= { cmcTcMasterPcu10Traps 1 }

  cmcTcMasterPcu10TrapTable OBJECT-TYPE
    SYNTAX SEQUENCE OF CmcTcMasterPcu10TrapEntry
    ACCESS not-accessible
    STATUS mandatory
    DESCRIPTION
      "A list of trap-receiver entries"
    ::= { cmcTcMasterPcu10Traps 2 }

  cmcTcMasterPcu10TrapEntry OBJECT-TYPE
    SYNTAX CmcTcMasterPcu10TrapEntry
    ACCESS not-accessible
    STATUS mandatory
    DESCRIPTION
      "Entries of cmcTcMasterPcu10TrapTable"
    INDEX { cmcTcMasterPcu10TrapIndex }
    ::= { cmcTcMasterPcu10TrapTable 1 }

    CmcTcMasterPcu10TrapEntry ::=
      SEQUENCE {
        cmcTcMasterPcu10TrapIndex
          INTEGER,
        cmcTcMasterPcu10TrapStatus
          INTEGER,
        cmcTcMasterPcu10TrapIPaddress
          DisplayString
      }

    cmcTcMasterPcu10TrapIndex OBJECT-TYPE
      SYNTAX INTEGER (1..32000)
      ACCESS read-only
      STATUS mandatory
      DESCRIPTION
        "Index for the trap-receiver-table. Its value ranges between
         1 and the value of cmcTcMasterPcu10TrapTableNumber "
      ::= { cmcTcMasterPcu10TrapEntry 1 }

    cmcTcMasterPcu10TrapStatus OBJECT-TYPE
      SYNTAX INTEGER {
        disabled(1),
        enabled(2)
      }
      ACCESS read-write
      STATUS mandatory
      DESCRIPTION
        "Enable or disable trap receiver"
      ::= { cmcTcMasterPcu10TrapEntry 2 }

    cmcTcMasterPcu10TrapIPaddress OBJECT-TYPE
      SYNTAX DisplayString (SIZE (0..15))
      ACCESS read-write
      STATUS mandatory
      DESCRIPTION
        "IP-address of trap-receiver"
      ::= { cmcTcMasterPcu10TrapEntry 3 }

--cmcTcMasterTc10MibRev-group
          
  cmcTcMasterTc10MibMajRev OBJECT-TYPE
    SYNTAX INTEGER (1..32000)
    ACCESS read-only
    STATUS mandatory
    DESCRIPTION
      "The Major Revision level.
       A change in the major revision level represents a major change
       in the architecture of the MIB. A change in the major revision 
       level may indicate a significant change in the information,
       correct interpretation of data may require a MIB document
       with the same major revision level."
    ::= { cmcTcMasterTc10MibRev 1 }

  cmcTcMasterTc10MibMinRev OBJECT-TYPE
    SYNTAX INTEGER (0..32000)
    ACCESS read-only
    STATUS mandatory
    DESCRIPTION
      "The Minor Revision level.
       A change in the minor revision level may represent some minor
       additional support, no changes to any pre-existing information
       has occurred."
    ::= { cmcTcMasterTc10MibRev 2 }

  cmcTcMasterTc10MibCondition OBJECT-TYPE
    SYNTAX INTEGER {
      other (1),
      ok (2),
      degraded (3),
      failed (4),
      configChanged (5)
    }
    ACCESS read-only
    STATUS mandatory
    DESCRIPTION
      "The overall condition (status) of the system represented by
       this MIB. 
       (2) OK
       (3) a minor problem, warning condition (yellow LED on CMC-TC)
       (4) a major problem (red LED on CMC-TC)
       (5) configuration of sensor units changed or
           unit detected (red/yellow/green LED on CMC-TC)"
    ::= { cmcTcMasterTc10MibRev 3 }
          
--cmcTcMasterTc10Status-group

  cmcTcMasterTc10StatusDeviceCMC OBJECT-TYPE
    SYNTAX INTEGER {
      failed(1),
      ok(2)
    }
    ACCESS read-only
    STATUS mandatory
    DESCRIPTION
      "General Status of CMC-TC unit itself
       (1) failed
       (2) OK"
    ::= { cmcTcMasterTc10Status 1 }

  cmcTcMasterTc10UnitsConnected OBJECT-TYPE
    SYNTAX INTEGER 
    ACCESS read-only
    STATUS mandatory
    DESCRIPTION
      "Number of sensor units connected to the CMC-TC, Port 1 to 4"
    ::= { cmcTcMasterTc10Status 2 }

--unit 1

  cmcTcMasterTc10Unit1TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 1"
    ::= { cmcTcMasterTc10StatusSensorUnit1 1 }

  cmcTcMasterTc10Unit1Text OBJECT-TYPE
    SYNTAX DisplayString (SIZE (0..10))
    ACCESS read-write
    STATUS mandatory
    DESCRIPTION
      "Descriptional text for sensor unit connected to port 1"
    ::= { cmcTcMasterTc10StatusSensorUnit1 2 }

  cmcTcMasterTc10Unit1Serial OBJECT-TYPE
    SYNTAX INTEGER 
    ACCESS read-only
    STATUS mandatory
    DESCRIPTION
      "Serialnumber of sensor unit connected to port 1"
    ::= { cmcTcMasterTc10StatusSensorUnit1 3 }

  cmcTcMasterTc10Unit1Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 1
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc10StatusSensorUnit1 4 }

-- Sensors
              
  cmcTcMasterTc10Unit1NumberOfSensors OBJECT-TYPE
    SYNTAX INTEGER 
    ACCESS read-only
    STATUS mandatory
    DESCRIPTION
      "Number of sensors connected to sensor unit 1"
    ::= { cmcTcMasterTc10StatusUnit1Sensors 1 }

-- table with entry for each sensor available on this unit              

  cmcTcMasterTc10Unit1SensorTable OBJECT-TYPE
    SYNTAX SEQUENCE OF CmcTcMasterTc10Unit1SensorEntry
    ACCESS not-accessible
    STATUS mandatory
    DESCRIPTION
      "Headline of sensor table"
    ::= { cmcTcMasterTc10StatusUnit1Sensors 2 }

  cmcTcMasterTc10Unit1SensorEntry OBJECT-TYPE
    SYNTAX CmcTcMasterTc10Unit1SensorEntry
    ACCESS not-accessible
    STATUS mandatory
    DESCRIPTION
      "Entries of sensor table"
    INDEX { cmcTcMasterTc10Unit1SensorIndex }
    ::= { cmcTcMasterTc10Unit1SensorTable 1 }

    CmcTcMasterTc10Unit1SensorEntry ::=
      SEQUENCE {
        cmcTcMasterTc10Unit1SensorIndex
          INTEGER,
        cmcTcMasterTc10Unit1SensorType
          INTEGER,
        cmcTcMasterTc10Unit1SensorText
          DisplayString (SIZE (0..20)),                
        cmcTcMasterTc10Unit1SensorStatus
          INTEGER,
        cmcTcMasterTc10Unit1SensorValue
          INTEGER,
        cmcTcMasterTc10Unit1SensorSetHigh
          INTEGER,
        cmcTcMasterTc10Unit1SensorSetLow
          INTEGER,
        cmcTcMasterTc10Unit1SensorSetWarn
          INTEGER                
      }

    cmcTcMasterTc10Unit1SensorIndex OBJECT-TYPE
      SYNTAX INTEGER (1..32000)
      ACCESS read-only
      STATUS mandatory
      DESCRIPTION
        "Index for the list of value entries. Its value ranges
         between 1 and the value of cmcTcMasterTc10Unit1NumberOfSensors." 
      ::= { cmcTcMasterTc10Unit1SensorEntry 1 }

    cmcTcMasterTc10Unit1SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 1 to sensor[cmcTcMasterTc10Unit1SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc10Unit1SensorEntry 2 }

    cmcTcMasterTc10Unit1SensorText OBJECT-TYPE
      SYNTAX DisplayString (SIZE (0..20))
      ACCESS read-write
      STATUS mandatory
      DESCRIPTION
        "Descriptional text for each sensor (entry in the table)"
      ::= { cmcTcMasterTc10Unit1SensorEntry 3 }
              
    cmcTcMasterTc10Unit1SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc10Unit1SensorEntry 4 }

    cmcTcMasterTc10Unit1SensorValue OBJECT-TYPE
      SYNTAX INTEGER 
      ACCESS read-only
      STATUS mandatory
      DESCRIPTION
        "Value of sensor"
      ::= { cmcTcMasterTc10Unit1SensorEntry 5 }

    cmcTcMasterTc10Unit1SensorSetHigh OBJECT-TYPE
      SYNTAX INTEGER (0..300) 
      ACCESS read-write
      STATUS mandatory
      DESCRIPTION
        "Value for high setpoint of sensor"
      ::= { cmcTcMasterTc10Unit1SensorEntry 6 }

    cmcTcMasterTc10Unit1SensorSetLow OBJECT-TYPE
      SYNTAX INTEGER (0..300) 
      ACCESS read-write
      STATUS mandatory
      DESCRIPTION
        "Value for low setpoint of sensor,
         also used as alarm delay"
      ::= { cmcTcMasterTc10Unit1SensorEntry 7 }

    cmcTcMasterTc10Unit1SensorSetWarn OBJECT-TYPE
      SYNTAX INTEGER (0..300) 
      ACCESS read-write
      STATUS mandatory
      DESCRIPTION
        "Value for warning setpoint of sensor, 
         also used as fan threshold"
      ::= { cmcTcMasterTc10Unit1SensorEntry 8 }
                
-- Outputs              

  cmcTcMasterTc10Unit1NumberOfOutputs OBJECT-TYPE
    SYNTAX INTEGER 
    ACCESS read-only
    STATUS mandatory
    DESCRIPTION
      "Number of outputs available on sensor unit 1"
    ::= { cmcTcMasterTc10StatusUnit1Outputs 1 }

-- table with entry for each output available on this unit              
                
  cmcTcMasterTc10Unit1OutputTable OBJECT-TYPE
    SYNTAX SEQUENCE OF CmcTcMasterTc10Unit1OutputEntry
    ACCESS not-accessible
    STATUS mandatory
    DESCRIPTION
      "Headline of output table"
    ::= { cmcTcMasterTc10StatusUnit1Outputs 2 }

  cmcTcMasterTc10Unit1OutputEntry OBJECT-TYPE
    SYNTAX CmcTcMasterTc10Unit1OutputEntry
    ACCESS not-accessible
    STATUS mandatory
    DESCRIPTION
      "Entries of output table"
    INDEX { cmcTcMasterTc10Unit1OutputIndex }
    ::= { cmcTcMasterTc10Unit1OutputTable 1 }

    CmcTcMasterTc10Unit1OutputEntry ::=
      SEQUENCE {
        cmcTcMasterTc10Unit1OutputIndex
          INTEGER,
        cmcTcMasterTc10Unit1OutputType
          INTEGER,
        cmcTcMasterTc10Unit1OutputText
          DisplayString (SIZE (0..20)),                
        cmcTcMasterTc10Unit1OutputStatus
          INTEGER,
        cmcTcMasterTc10Unit1OutputValue
          INTEGER,
        cmcTcMasterTc10Unit1OutputSet
          INTEGER,
        cmcTcMasterTc10Unit1OutputConfig
          INTEGER,                
        cmcTcMasterTc10Unit1OutputDelay
          INTEGER,
        cmcTcMasterTc10Unit1OutputTimeoutAction
          INTEGER
      }

    cmcTcMasterTc10Unit1OutputIndex OBJECT-TYPE
      SYNTAX INTEGER (1..32000)
      ACCESS read-only
      STATUS mandatory
      DESCRIPTION
        "Index for the list of output entries. Its value ranges
         between 1 and the value of cmcTcMasterTc10Unit1NumberOfOutputs." 
      ::= { cmcTcMasterTc10Unit1OutputEntry 1 }

    cmcTcMasterTc10Unit1OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 1 to output[cmcTcMasterTc10Unit1OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc10Unit1OutputEntry 2 }

    cmcTcMasterTc10Unit1OutputText OBJECT-TYPE
      SYNTAX DisplayString (SIZE (0..20))
      ACCESS read-write
      STATUS mandatory
      DESCRIPTION
        "Descriptional text for each output (entry in the table)"
      ::= { cmcTcMasterTc10Unit1OutputEntry 3 }
              
    cmcTcMasterTc10Unit1OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc10Unit1OutputEntry 4 }

    cmcTcMasterTc10Unit1OutputValue OBJECT-TYPE
      SYNTAX INTEGER (-32000..32000) 
      ACCESS read-write
      STATUS mandatory
      DESCRIPTION
        "Value for output"
      ::= { cmcTcMasterTc10Unit1OutputEntry 5 }

    cmcTcMasterTc10Unit1OutputSet OBJECT-TYPE
      SYNTAX INTEGER {
        off (1),
        on (2),
        lock (3),
        unlock (4),
        unlockDelay (5)
      }
      ACCESS read-write
      STATUS mandatory
      DESCRIPTION
        "Command for output"
      ::= { cmcTcMasterTc10Unit1OutputEntry 6 }

    cmcTcMasterTc10Unit1OutputConfig OBJECT-TYPE
      SYNTAX INTEGER {
        disRemote (1),
        enRemote (2)
      }
      ACCESS read-write
      STATUS mandatory
      DESCRIPTION
        "Configuration for output
         1: 	disable remote control (e.g. keypad)
         2: 	enable remote control"
      ::= { cmcTcMasterTc10Unit1OutputEntry 7 }

    cmcTcMasterTc10Unit1OutputDelay OBJECT-TYPE
      SYNTAX INTEGER (0..999) 
      ACCESS read-write
      STATUS mandatory
      DESCRIPTION
        "Unsigned Value for delay, 
         after this time the output will fall into the previous state"
      ::= { cmcTcMasterTc10Unit1OutputEntry 8 }

    cmcTcMasterTc10Unit1OutputTimeoutAction OBJECT-TYPE
      SYNTAX INTEGER {
        stay (1),
        off (2),
        on (3)
      }
      ACCESS read-write
      STATUS mandatory
      DESCRIPTION
        "State for output if timeout (RS422) occurs"
      ::= { cmcTcMasterTc10Unit1OutputEntry 9 }
 
-- Messages
              
  cmcTcMasterTc10Unit1NumberOfMsgs OBJECT-TYPE
    SYNTAX INTEGER 
    ACCESS read-only
    STATUS mandatory
    DESCRIPTION
      "Number of messages that can be created with sensor unit 1"
    ::= { cmcTcMasterTc10StatusUnit1Msg 1 }

-- table with entry for each alarm available on this unit               
                
  cmcTcMasterTc10Unit1MsgTable OBJECT-TYPE
    SYNTAX SEQUENCE OF CmcTcMasterTc10Unit1MsgEntry
    ACCESS not-accessible
    STATUS mandatory
    DESCRIPTION
      "Headline of message table"
    ::= { cmcTcMasterTc10StatusUnit1Msg 2 }

  cmcTcMasterTc10Unit1MsgEntry OBJECT-TYPE
    SYNTAX CmcTcMasterTc10Unit1MsgEntry
    ACCESS not-accessible
    STATUS mandatory
    DESCRIPTION
      "Entries of message table"
    INDEX { cmcTcMasterTc10Unit1MsgIndex }
    ::= { cmcTcMasterTc10Unit1MsgTable 1 }

    CmcTcMasterTc10Unit1MsgEntry ::=
      SEQUENCE {
        cmcTcMasterTc10Unit1MsgIndex
          INTEGER, 
        cmcTcMasterTc10Unit1MsgText
          DisplayString (SIZE (0..20)),                
        cmcTcMasterTc10Unit1MsgStatus
          INTEGER,                
        cmcTcMasterTc10Unit1MsgRelay
          INTEGER,
        cmcTcMasterTc10Unit1MsgBeeper
          INTEGER,
        cmcTcMasterTc10Unit1MsgTrap1
          INTEGER,
        cmcTcMasterTc10Unit1MsgTrap2
          INTEGER,
        cmcTcMasterTc10Unit1MsgTrap3
          INTEGER,
        cmcTcMasterTc10Unit1MsgTrap4
          INTEGER,                 
        cmcTcMasterTc10Unit1MsgQuit
          INTEGER              
      }

    cmcTcMasterTc10Unit1MsgIndex OBJECT-TYPE
      SYNTAX INTEGER (1..32000)
      ACCESS read-only
      STATUS mandatory
      DESCRIPTION
        "Index for the list of message entries. Its value ranges
         between 1 and the value of cmcTcMasterTc10Unit1NumberOfMsgs." 
      ::= { cmcTcMasterTc10Unit1MsgEntry 1 }

    cmcTcMasterTc10Unit1MsgText OBJECT-TYPE
      SYNTAX DisplayString (SIZE (0..20))
      ACCESS read-write
      STATUS mandatory
      DESCRIPTION
        "Descriptional text for each message (entry in the table)"
      ::= { cmcTcMasterTc10Unit1MsgEntry 2 }
              
    cmcTcMasterTc10Unit1MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc10Unit1OutputSet)
         17: door is unlocked by WEB
         18: door is unlocked by timer
         19: no access, wrong keycode or cardnumber
         20: orientation of PSM-Unit is circuit 1
         21: orientation of PSM-Unit is circuit 2"
      ::= { cmcTcMasterTc10Unit1MsgEntry 3 }
        
    cmcTcMasterTc10Unit1MsgRelay OBJECT-TYPE
      SYNTAX INTEGER {
        disable (1),
        enable (2)
      }
      ACCESS read-write
      STATUS mandatory
      DESCRIPTION
        "Setup of Alarm relay for this message/alarm
         1:        no switching of alarm relay             
         2:        switching of alarm relay" 
      ::= { cmcTcMasterTc10Unit1MsgEntry 4 }

    cmcTcMasterTc10Unit1MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc10Unit1MsgEntry 5 }

    cmcTcMasterTc10Unit1MsgTrap1 OBJECT-TYPE
      SYNTAX INTEGER {
        disable (1),
        enable (2)
      }
      ACCESS read-write
      STATUS mandatory
      DESCRIPTION
        "Trap receiver 1 activated"
      ::= { cmcTcMasterTc10Unit1MsgEntry 6 }

    cmcTcMasterTc10Unit1MsgTrap2 OBJECT-TYPE
      SYNTAX INTEGER {
        disable (1),
        enable (2)
      }
      ACCESS read-write
      STATUS mandatory
      DESCRIPTION
        "Trap receiver 2 activated"
      ::= { cmcTcMasterTc10Unit1MsgEntry 7 }
 
    cmcTcMasterTc10Unit1MsgTrap3 OBJECT-TYPE
      SYNTAX INTEGER {
        disable (1),
        enable (2)
      }
      ACCESS read-write
      STATUS mandatory
      DESCRIPTION
        "Trap receiver 3 activated"
      ::= { cmcTcMasterTc10Unit1MsgEntry 8 }

    cmcTcMasterTc10Unit1MsgTrap4 OBJECT-TYPE
      SYNTAX INTEGER {
        disable (1),
        enable (2)
      }
      ACCESS read-write
      STATUS mandatory
      DESCRIPTION
        "Trap receiver 4 and Event Logging activated"
      ::= { cmcTcMasterTc10Unit1MsgEntry 9 }

    cmcTcMasterTc10Unit1MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc10Unit1MsgEntry 10 }

-- unit2

  cmcTcMasterTc10Unit2TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 2"
    ::= { cmcTcMasterTc10StatusSensorUnit2 1 }

  cmcTcMasterTc10Unit2Text OBJECT-TYPE
    SYNTAX DisplayString (SIZE (0..10))
    ACCESS read-write
    STATUS mandatory
    DESCRIPTION
      "Descriptional text for sensor unit connected to port 2"
    ::= { cmcTcMasterTc10StatusSensorUnit2 2 }

  cmcTcMasterTc10Unit2Serial OBJECT-TYPE
    SYNTAX INTEGER 
    ACCESS read-only
    STATUS mandatory
    DESCRIPTION
      "Serialnumber of sensor unit connected to port 2"
    ::= { cmcTcMasterTc10StatusSensorUnit2 3 }

  cmcTcMasterTc10Unit2Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 2
       (1) OK
       (2) error
       (3) configuration of sensor unit has changed, confirmation required
       (4) Quit from sensor unit to confirm configuration changes
       (5) timeout of sensor unit, confirmation required
       (6) sensor unit detected, needs to be confirmed
       (8) supply voltage is too low"              
    ::= { cmcTcMasterTc10StatusSensorUnit2 4 }

-- unit 2 table

-- Sensors              

  cmcTcMasterTc10Unit2NumberOfSensors OBJECT-TYPE
    SYNTAX INTEGER 
    ACCESS read-only
    STATUS mandatory
    DESCRIPTION
      "Number of sensors connected to sensor unit 2"
    ::= { cmcTcMasterTc10StatusUnit2Sensors 1 }

-- table with entry for each sensor available on this unit              

  cmcTcMasterTc10Unit2SensorTable OBJECT-TYPE
    SYNTAX SEQUENCE OF CmcTcMasterTc10Unit2SensorEntry
    ACCESS not-accessible
    STATUS mandatory
    DESCRIPTION
      "Headline of sensor table"
    ::= { cmcTcMasterTc10StatusUnit2Sensors 2 }

  cmcTcMasterTc10Unit2SensorEntry OBJECT-TYPE
    SYNTAX CmcTcMasterTc10Unit2SensorEntry
    ACCESS not-accessible
    STATUS mandatory
    DESCRIPTION
      "Entries of sensor table"
    INDEX { cmcTcMasterTc10Unit2SensorIndex }
    ::= { cmcTcMasterTc10Unit2SensorTable 1 }

    CmcTcMasterTc10Unit2SensorEntry ::=
      SEQUENCE {
        cmcTcMasterTc10Unit2SensorIndex
          INTEGER,
        cmcTcMasterTc10Unit2SensorType
          INTEGER,
        cmcTcMasterTc10Unit2SensorText
          DisplayString (SIZE (0..20)),                
        cmcTcMasterTc10Unit2SensorStatus
          INTEGER,
        cmcTcMasterTc10Unit2SensorValue
          INTEGER,
        cmcTcMasterTc10Unit2SensorSetHigh
          INTEGER,
        cmcTcMasterTc10Unit2SensorSetLow
          INTEGER,                 
        cmcTcMasterTc10Unit2SensorSetWarn
          INTEGER  
      }

    cmcTcMasterTc10Unit2SensorIndex OBJECT-TYPE
      SYNTAX INTEGER (1..32000)
      ACCESS read-only
      STATUS mandatory
      DESCRIPTION
        "Index for the list of value entries. Its value ranges
         between 1 and the value of cmcTcMasterTc10Unit2NumberOfSensors." 
      ::= { cmcTcMasterTc10Unit2SensorEntry 1 }

    cmcTcMasterTc10Unit2SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 2 to sensor[cmcTcMasterTc10Unit2SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc10Unit2SensorEntry 2 }
        
    cmcTcMasterTc10Unit2SensorText OBJECT-TYPE
      SYNTAX DisplayString (SIZE (0..20))
      ACCESS read-write
      STATUS mandatory
      DESCRIPTION
        "Descriptional text for each sensor (entry in the table)"
      ::= { cmcTcMasterTc10Unit2SensorEntry 3 }
              
    cmcTcMasterTc10Unit2SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc10Unit2SensorEntry 4 }

    cmcTcMasterTc10Unit2SensorValue OBJECT-TYPE
      SYNTAX INTEGER 
      ACCESS read-only
      STATUS mandatory
      DESCRIPTION
        "Value of sensor"
      ::= { cmcTcMasterTc10Unit2SensorEntry 5 }

    cmcTcMasterTc10Unit2SensorSetHigh OBJECT-TYPE
      SYNTAX INTEGER (0..300) 
      ACCESS read-write
      STATUS mandatory
      DESCRIPTION
        "Value for high setpoint of sensor"
      ::= { cmcTcMasterTc10Unit2SensorEntry 6 }

    cmcTcMasterTc10Unit2SensorSetLow OBJECT-TYPE
      SYNTAX INTEGER (0..300) 
      ACCESS read-write
      STATUS mandatory
      DESCRIPTION
        "Value for low setpoint of sensor,
         also used as alarm delay"
      ::= { cmcTcMasterTc10Unit2SensorEntry 7 }

    cmcTcMasterTc10Unit2SensorSetWarn OBJECT-TYPE
      SYNTAX INTEGER (0..300) 
      ACCESS read-write
      STATUS mandatory
      DESCRIPTION
        "Value for warning setpoint of sensor,
         also used as fan threshold"
      ::= { cmcTcMasterTc10Unit2SensorEntry 8 }

-- Outputs              

  cmcTcMasterTc10Unit2NumberOfOutputs OBJECT-TYPE
    SYNTAX INTEGER 
    ACCESS read-only
    STATUS mandatory
    DESCRIPTION
      "Number of outputs available on sensor unit 2"
    ::= { cmcTcMasterTc10StatusUnit2Outputs 1 }

-- table with entry for each output available on this unit              
                
  cmcTcMasterTc10Unit2OutputTable OBJECT-TYPE
    SYNTAX SEQUENCE OF CmcTcMasterTc10Unit2OutputEntry
    ACCESS not-accessible
    STATUS mandatory
    DESCRIPTION
      "Headline of output table"
    ::= { cmcTcMasterTc10StatusUnit2Outputs 2 }

  cmcTcMasterTc10Unit2OutputEntry OBJECT-TYPE
    SYNTAX CmcTcMasterTc10Unit2OutputEntry
    ACCESS not-accessible
    STATUS mandatory
    DESCRIPTION
      "Entries of output table"
    INDEX { cmcTcMasterTc10Unit2OutputIndex }
    ::= { cmcTcMasterTc10Unit2OutputTable 1 }

    CmcTcMasterTc10Unit2OutputEntry ::=
      SEQUENCE {
        cmcTcMasterTc10Unit2OutputIndex
          INTEGER,
        cmcTcMasterTc10Unit2OutputType
          INTEGER,
        cmcTcMasterTc10Unit2OutputText
          DisplayString (SIZE (0..20)),                
        cmcTcMasterTc10Unit2OutputStatus
          INTEGER,
        cmcTcMasterTc10Unit2OutputValue
          INTEGER,
        cmcTcMasterTc10Unit2OutputSet
          INTEGER,
        cmcTcMasterTc10Unit2OutputConfig
          INTEGER,                
        cmcTcMasterTc10Unit2OutputDelay
          INTEGER,
        cmcTcMasterTc10Unit2OutputTimeoutAction
          INTEGER
      }

    cmcTcMasterTc10Unit2OutputIndex OBJECT-TYPE
      SYNTAX INTEGER (1..32000)
      ACCESS read-only
      STATUS mandatory
      DESCRIPTION
        "Index for the list of output entries. Its value ranges
         between 1 and the value of cmcTcMasterTc10Unit2NumberOfOutputs." 
      ::= { cmcTcMasterTc10Unit2OutputEntry 1 }

    cmcTcMasterTc10Unit2OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 2 to output[cmcTcMasterTc10Unit2OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc10Unit2OutputEntry 2 }

        
    cmcTcMasterTc10Unit2OutputText OBJECT-TYPE
      SYNTAX DisplayString (SIZE (0..20))
      ACCESS read-write
      STATUS mandatory
      DESCRIPTION
        "Descriptional text for each output (entry in the table)"
      ::= { cmcTcMasterTc10Unit2OutputEntry 3 }
              
    cmcTcMasterTc10Unit2OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc10Unit2OutputEntry 4 }

    cmcTcMasterTc10Unit2OutputValue OBJECT-TYPE
      SYNTAX INTEGER (-32000..32000) 
      ACCESS read-write
      STATUS mandatory
      DESCRIPTION
        "Value for output"
      ::= { cmcTcMasterTc10Unit2OutputEntry 5 }

    cmcTcMasterTc10Unit2OutputSet OBJECT-TYPE
      SYNTAX INTEGER {
        off (1),
        on (2),
        lock (3),
        unlock (4),
        unlockDelay (5)
      }
      ACCESS read-write
      STATUS mandatory
      DESCRIPTION
        "Command for output"
      ::= { cmcTcMasterTc10Unit2OutputEntry 6 }

    cmcTcMasterTc10Unit2OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc10Unit2OutputEntry 7 }

    cmcTcMasterTc10Unit2OutputDelay OBJECT-TYPE
      SYNTAX INTEGER (0..999) 
      ACCESS read-write
      STATUS mandatory
      DESCRIPTION
        "Unsigned Value for delay, 
         after this time the output will fall into the previous state"
      ::= { cmcTcMasterTc10Unit2OutputEntry 8 }

    cmcTcMasterTc10Unit2OutputTimeoutAction OBJECT-TYPE
      SYNTAX INTEGER {
        stay (1),
        off (2),
        on (3)
      }
      ACCESS read-write
      STATUS mandatory
      DESCRIPTION
        "State for output if timeout (RS422) occurs"
      ::= { cmcTcMasterTc10Unit2OutputEntry 9 }

-- Messages
              
  cmcTcMasterTc10Unit2NumberOfMsgs OBJECT-TYPE
    SYNTAX INTEGER 
    ACCESS read-only
    STATUS mandatory
    DESCRIPTION
      "Number of messages that can be created with sensor unit 2"
    ::= { cmcTcMasterTc10StatusUnit2Msg 1 }

-- table with entry for each alarm available on this unit               
                
  cmcTcMasterTc10Unit2MsgTable OBJECT-TYPE
    SYNTAX SEQUENCE OF CmcTcMasterTc10Unit2MsgEntry
    ACCESS not-accessible
    STATUS mandatory
    DESCRIPTION
      "Headline of message table"
    ::= { cmcTcMasterTc10StatusUnit2Msg 2 }

  cmcTcMasterTc10Unit2MsgEntry OBJECT-TYPE
    SYNTAX CmcTcMasterTc10Unit2MsgEntry
    ACCESS not-accessible
    STATUS mandatory
    DESCRIPTION
      "Entries of message table"
    INDEX { cmcTcMasterTc10Unit2MsgIndex }
    ::= { cmcTcMasterTc10Unit2MsgTable 1 }

    CmcTcMasterTc10Unit2MsgEntry ::=
      SEQUENCE {
        cmcTcMasterTc10Unit2MsgIndex
          INTEGER,
        cmcTcMasterTc10Unit2MsgText
          DisplayString (SIZE (0..20)),
        cmcTcMasterTc10Unit2MsgStatus
          INTEGER, 
        cmcTcMasterTc10Unit2MsgRelay
          INTEGER,
        cmcTcMasterTc10Unit2MsgBeeper
          INTEGER,
        cmcTcMasterTc10Unit2MsgTrap1
          INTEGER,
        cmcTcMasterTc10Unit2MsgTrap2
          INTEGER,
        cmcTcMasterTc10Unit2MsgTrap3
          INTEGER,
        cmcTcMasterTc10Unit2MsgTrap4
          INTEGER,                 
        cmcTcMasterTc10Unit2MsgQuit
          INTEGER              
      }

    cmcTcMasterTc10Unit2MsgIndex OBJECT-TYPE
      SYNTAX INTEGER (1..32000)
      ACCESS read-only
      STATUS mandatory
      DESCRIPTION
        "Index for the list of message entries. Its value ranges
         between 1 and the value of cmcTcMasterTc10Unit2NumberOfMsgs." 
      ::= { cmcTcMasterTc10Unit2MsgEntry 1 }

    cmcTcMasterTc10Unit2MsgText OBJECT-TYPE
      SYNTAX DisplayString (SIZE (0..20))
      ACCESS read-write
      STATUS mandatory
      DESCRIPTION
        "Descriptional text for each message (entry in the table)"
      ::= { cmcTcMasterTc10Unit2MsgEntry 2 }

    cmcTcMasterTc10Unit2MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc10Unit2OutputSet)
         17: door is unlocked by WEB
         18: door is unlocked by timer
         19: no access, wrong keycode or cardnumber
         20: orientation of PSM-Unit is circuit 1
         21: orientation of PSM-Unit is circuit 2"
      ::= { cmcTcMasterTc10Unit2MsgEntry 3 }

    cmcTcMasterTc10Unit2MsgRelay OBJECT-TYPE
      SYNTAX INTEGER {
        disable (1),
        enable (2)
      }
      ACCESS read-write
      STATUS mandatory
      DESCRIPTION
        "Setup of Alarm relay for this alarm
         2:        no switching of alarm relay             
         1:        switching of alarm relay" 
      ::= { cmcTcMasterTc10Unit2MsgEntry 4 }

    cmcTcMasterTc10Unit2MsgBeeper OBJECT-TYPE
      SYNTAX INTEGER {
        disable (1),
        enable (2)
      }
      ACCESS read-write
      STATUS mandatory
      DESCRIPTION
        "Setup of Alarm beeper for this alarm
         2:        no audible alarm
         1:        audible alarm" 
      ::= { cmcTcMasterTc10Unit2MsgEntry 5 }

    cmcTcMasterTc10Unit2MsgTrap1 OBJECT-TYPE
      SYNTAX INTEGER {
        disable (1),
        enable (2)
      }
      ACCESS read-write
      STATUS mandatory
      DESCRIPTION
        "Trap receiver 1 activated"
      ::= { cmcTcMasterTc10Unit2MsgEntry 6 }

    cmcTcMasterTc10Unit2MsgTrap2 OBJECT-TYPE
      SYNTAX INTEGER {
        disable (1),
        enable (2)
      }
      ACCESS read-write
      STATUS mandatory
      DESCRIPTION
        "Trap receiver 2 activated"
      ::= { cmcTcMasterTc10Unit2MsgEntry 7 }
 
    cmcTcMasterTc10Unit2MsgTrap3 OBJECT-TYPE
      SYNTAX INTEGER {
        disable (1),
        enable (2)
      }
      ACCESS read-write
      STATUS mandatory
      DESCRIPTION
        "Trap receiver 3 activated"
      ::= { cmcTcMasterTc10Unit2MsgEntry 8 }

    cmcTcMasterTc10Unit2MsgTrap4 OBJECT-TYPE
      SYNTAX INTEGER {
        disable (1),
        enable (2)
      }
      ACCESS read-write
      STATUS mandatory
      DESCRIPTION
        "Trap receiver 4 and Event Logging activated"
      ::= { cmcTcMasterTc10Unit2MsgEntry 9 }

    cmcTcMasterTc10Unit2MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc10Unit2MsgEntry 10 }

-- unit 3
  cmcTcMasterTc10Unit3TypeOfDevice OBJECT-TYPE
    SYNTAX INTEGER {
      notAvail (1),
      unitIO (2),
      unitAccess (3),
      unitClimate (4),
      unitFCS (5),
      unitRTT (6),
      unitRLCP (7),
      unitPSM (8)
    }
    ACCESS read-only
    STATUS mandatory
    DESCRIPTION
      "Type of sensor unit connected to port 3"
    ::= { cmcTcMasterTc10StatusSensorUnit3 1 }

  cmcTcMasterTc10Unit3Text OBJECT-TYPE
    SYNTAX DisplayString (SIZE (0..10))
    ACCESS read-write
    STATUS mandatory
    DESCRIPTION
      "Descriptional text for sensor unit connected to port 3"
    ::= { cmcTcMasterTc10StatusSensorUnit3 2 }

  cmcTcMasterTc10Unit3Serial OBJECT-TYPE
    SYNTAX INTEGER 
    ACCESS  read-only
    STATUS  mandatory
    DESCRIPTION
      "Serialnumber of sensor unit connected to port 3"
    ::= { cmcTcMasterTc10StatusSensorUnit3 3 }

  cmcTcMasterTc10Unit3Status OBJECT-TYPE
    SYNTAX INTEGER {
      ok(1),
      error(2),
      changed(3),
      quit(4),
      timeout(5),
      detected(6),
      notAvail(7),
      lowPower(8)
    }
    ACCESS  read-only
    STATUS  mandatory
    DESCRIPTION
      "General Status sensor unit connected to port 3
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc10StatusSensorUnit3 4 }

-- Sensors              

  cmcTcMasterTc10Unit3NumberOfSensors OBJECT-TYPE
    SYNTAX INTEGER 
    ACCESS read-only
    STATUS mandatory
    DESCRIPTION
      "Number of sensors connected to sensor unit 3"
    ::= { cmcTcMasterTc10StatusUnit3Sensors 1 }

-- table with entry for each sensor available on this unit              
        
  cmcTcMasterTc10Unit3SensorTable OBJECT-TYPE
    SYNTAX SEQUENCE OF CmcTcMasterTc10Unit3SensorEntry
    ACCESS not-accessible
    STATUS mandatory
    DESCRIPTION
      "Headline of sensor table"
    ::= { cmcTcMasterTc10StatusUnit3Sensors 2 }

  cmcTcMasterTc10Unit3SensorEntry OBJECT-TYPE
    SYNTAX CmcTcMasterTc10Unit3SensorEntry
    ACCESS not-accessible
    STATUS mandatory
    DESCRIPTION
      "Entries of sensor table"
    INDEX { cmcTcMasterTc10Unit3SensorIndex }
    ::= { cmcTcMasterTc10Unit3SensorTable 1 }

    CmcTcMasterTc10Unit3SensorEntry ::=
      SEQUENCE {
        cmcTcMasterTc10Unit3SensorIndex
          INTEGER,
        cmcTcMasterTc10Unit3SensorType
          INTEGER,
        cmcTcMasterTc10Unit3SensorText
          DisplayString (SIZE (0..20)),                
        cmcTcMasterTc10Unit3SensorStatus
          INTEGER,
        cmcTcMasterTc10Unit3SensorValue
          INTEGER,
        cmcTcMasterTc10Unit3SensorSetHigh
          INTEGER,
        cmcTcMasterTc10Unit3SensorSetLow
          INTEGER,                 
        cmcTcMasterTc10Unit3SensorSetWarn
          INTEGER  
      }

    cmcTcMasterTc10Unit3SensorIndex OBJECT-TYPE
      SYNTAX INTEGER (1..32000)
      ACCESS read-only
      STATUS mandatory
      DESCRIPTION
        "Index for the list of value entries. Its value ranges
         between 1 and the value of cmcTcMasterTc10Unit3NumberOfSensors." 
      ::= { cmcTcMasterTc10Unit3SensorEntry 1 }

    cmcTcMasterTc10Unit3SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 3 to sensor[cmcTcMasterTc10Unit3SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc10Unit3SensorEntry 2 }

    cmcTcMasterTc10Unit3SensorText OBJECT-TYPE
      SYNTAX DisplayString (SIZE (0..20))
      ACCESS read-write
      STATUS mandatory
      DESCRIPTION
        "Descriptional text for each sensor (entry in the table)"
      ::= { cmcTcMasterTc10Unit3SensorEntry 3 }
              
    cmcTcMasterTc10Unit3SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc10Unit3SensorEntry 4 }

    cmcTcMasterTc10Unit3SensorValue OBJECT-TYPE
      SYNTAX INTEGER 
      ACCESS read-only
      STATUS mandatory
      DESCRIPTION
        "Value of sensor"
      ::= { cmcTcMasterTc10Unit3SensorEntry 5 }

    cmcTcMasterTc10Unit3SensorSetHigh OBJECT-TYPE
      SYNTAX INTEGER (0..300) 
      ACCESS read-write
      STATUS mandatory
      DESCRIPTION
        "Value for high setpoint of sensor"
      ::= { cmcTcMasterTc10Unit3SensorEntry 6 }

    cmcTcMasterTc10Unit3SensorSetLow OBJECT-TYPE
      SYNTAX INTEGER (0..300) 
      ACCESS read-write
      STATUS mandatory
      DESCRIPTION
        "Value for low setpoint of sensor,
         also used as alarm delay"
      ::= { cmcTcMasterTc10Unit3SensorEntry 7 }

    cmcTcMasterTc10Unit3SensorSetWarn OBJECT-TYPE
      SYNTAX INTEGER (0..300) 
      ACCESS read-write
      STATUS mandatory
      DESCRIPTION
        "Value for warning setpoint of sensor,
         also used as fan threshold"
      ::= { cmcTcMasterTc10Unit3SensorEntry 8 }
                
-- Outputs              

  cmcTcMasterTc10Unit3NumberOfOutputs OBJECT-TYPE
    SYNTAX INTEGER 
    ACCESS read-only
    STATUS mandatory
    DESCRIPTION
      "Number of outputs available on sensor unit 3"
    ::= { cmcTcMasterTc10StatusUnit3Outputs 1 }

-- table with entry for each output available on this unit              
                
  cmcTcMasterTc10Unit3OutputTable OBJECT-TYPE
    SYNTAX SEQUENCE OF CmcTcMasterTc10Unit3OutputEntry
    ACCESS not-accessible
    STATUS mandatory
    DESCRIPTION
      "Headline of output table"
    ::= { cmcTcMasterTc10StatusUnit3Outputs 2 }

  cmcTcMasterTc10Unit3OutputEntry OBJECT-TYPE
    SYNTAX CmcTcMasterTc10Unit3OutputEntry
    ACCESS not-accessible
    STATUS mandatory
    DESCRIPTION
      "Entries of output table"
    INDEX { cmcTcMasterTc10Unit3OutputIndex }
    ::= { cmcTcMasterTc10Unit3OutputTable 1 }

    CmcTcMasterTc10Unit3OutputEntry ::=
      SEQUENCE {
        cmcTcMasterTc10Unit3OutputIndex
          INTEGER,
        cmcTcMasterTc10Unit3OutputType
          INTEGER,
        cmcTcMasterTc10Unit3OutputText
          DisplayString (SIZE (0..20)),                
        cmcTcMasterTc10Unit3OutputStatus
          INTEGER,
        cmcTcMasterTc10Unit3OutputValue
          INTEGER,
        cmcTcMasterTc10Unit3OutputSet
          INTEGER,
        cmcTcMasterTc10Unit3OutputConfig
          INTEGER,
        cmcTcMasterTc10Unit3OutputDelay
          INTEGER,
        cmcTcMasterTc10Unit3OutputTimeoutAction
          INTEGER
      }

    cmcTcMasterTc10Unit3OutputIndex OBJECT-TYPE
      SYNTAX INTEGER (1..32000)
      ACCESS read-only
      STATUS mandatory
      DESCRIPTION
        "Index for the list of output entries. Its value ranges
         between 1 and the value of cmcTcMasterTc10Unit3NumberOfOutputs." 
      ::= { cmcTcMasterTc10Unit3OutputEntry 1 }

    cmcTcMasterTc10Unit3OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 3 to output[cmcTcMasterTc10Unit3OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc10Unit3OutputEntry 2 }

        
    cmcTcMasterTc10Unit3OutputText OBJECT-TYPE
      SYNTAX DisplayString (SIZE (0..20))
      ACCESS read-write
      STATUS mandatory
      DESCRIPTION
        "Descriptional text for each output (entry in the table)"
      ::= { cmcTcMasterTc10Unit3OutputEntry 3 }
              
    cmcTcMasterTc10Unit3OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc10Unit3OutputEntry 4 }

    cmcTcMasterTc10Unit3OutputValue OBJECT-TYPE
      SYNTAX INTEGER (-32000..32000) 
      ACCESS read-write
      STATUS mandatory
      DESCRIPTION
        "Value for output"
      ::= { cmcTcMasterTc10Unit3OutputEntry 5 }

    cmcTcMasterTc10Unit3OutputSet OBJECT-TYPE
      SYNTAX INTEGER {
        off (1),
        on (2),
        lock (3),
        unlock (4),
        unlockDelay (5)
      }
      ACCESS read-write
      STATUS mandatory
      DESCRIPTION
        "Command for output"
      ::= { cmcTcMasterTc10Unit3OutputEntry 6 }

    cmcTcMasterTc10Unit3OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc10Unit3OutputEntry 7 }

    cmcTcMasterTc10Unit3OutputDelay OBJECT-TYPE
      SYNTAX INTEGER (0..999) 
      ACCESS read-write
      STATUS mandatory
      DESCRIPTION
        "Unsigned Value for delay, 
         after this time the output will fall into the previous state"
      ::= { cmcTcMasterTc10Unit3OutputEntry 8 }

    cmcTcMasterTc10Unit3OutputTimeoutAction OBJECT-TYPE
      SYNTAX INTEGER {
        stay (1),
        off (2),
        on (3)
      }
      ACCESS read-write
      STATUS mandatory
      DESCRIPTION
        "State for output if timeout (RS422) occurs"
      ::= { cmcTcMasterTc10Unit3OutputEntry 9 }

-- Messages
              
  cmcTcMasterTc10Unit3NumberOfMsgs OBJECT-TYPE
    SYNTAX INTEGER 
    ACCESS read-only
    STATUS mandatory
    DESCRIPTION
      "Number of messages that can be created with sensor unit 3"
    ::= { cmcTcMasterTc10StatusUnit3Msg 1 }

-- table with entry for each alarm available on this unit               
                
  cmcTcMasterTc10Unit3MsgTable OBJECT-TYPE
    SYNTAX SEQUENCE OF CmcTcMasterTc10Unit3MsgEntry
    ACCESS not-accessible
    STATUS mandatory
    DESCRIPTION
      "Headline of message table"
    ::= { cmcTcMasterTc10StatusUnit3Msg 2 }

  cmcTcMasterTc10Unit3MsgEntry OBJECT-TYPE
    SYNTAX CmcTcMasterTc10Unit3MsgEntry
    ACCESS not-accessible
    STATUS mandatory
    DESCRIPTION
      "Entries of message table"
    INDEX { cmcTcMasterTc10Unit3MsgIndex }
    ::= { cmcTcMasterTc10Unit3MsgTable 1 }

    CmcTcMasterTc10Unit3MsgEntry ::=
      SEQUENCE {
        cmcTcMasterTc10Unit3MsgIndex
          INTEGER,
        cmcTcMasterTc10Unit3MsgText
          DisplayString (SIZE (0..20)),
        cmcTcMasterTc10Unit3MsgStatus
          INTEGER, 
        cmcTcMasterTc10Unit3MsgRelay
          INTEGER,
        cmcTcMasterTc10Unit3MsgBeeper
          INTEGER,
        cmcTcMasterTc10Unit3MsgTrap1
          INTEGER,
        cmcTcMasterTc10Unit3MsgTrap2
          INTEGER,
        cmcTcMasterTc10Unit3MsgTrap3
          INTEGER,
        cmcTcMasterTc10Unit3MsgTrap4
          INTEGER,                 
        cmcTcMasterTc10Unit3MsgQuit
          INTEGER              
      }

    cmcTcMasterTc10Unit3MsgIndex OBJECT-TYPE
      SYNTAX INTEGER (1..32000)
      ACCESS read-only
      STATUS mandatory
      DESCRIPTION
        "Index for the list of message entries. Its value ranges
         between 1 and the value of cmcTcMasterTc10Unit3NumberOfMsgs." 
      ::= { cmcTcMasterTc10Unit3MsgEntry 1 }

    cmcTcMasterTc10Unit3MsgText OBJECT-TYPE
      SYNTAX DisplayString (SIZE (0..20))
      ACCESS read-write
      STATUS mandatory
      DESCRIPTION
        "Descriptional text for each message (entry in the table)"
      ::= { cmcTcMasterTc10Unit3MsgEntry 2 }

    cmcTcMasterTc10Unit3MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc10Unit3OutputSet)
         17: door is unlocked by WEB
         18: door is unlocked by timer
         19: no access, wrong keycode or cardnumber
         20: orientation of PSM-Unit is circuit 1
         21: orientation of PSM-Unit is circuit 2"
      ::= { cmcTcMasterTc10Unit3MsgEntry 3 }

    cmcTcMasterTc10Unit3MsgRelay OBJECT-TYPE
      SYNTAX INTEGER {
        disable (1),
        enable (2)
      }
      ACCESS read-write
      STATUS mandatory
      DESCRIPTION
        "Setup of Alarm relay for this alarm
         1:        no switching of alarm relay             
         2:        switching of alarm relay" 
      ::= { cmcTcMasterTc10Unit3MsgEntry 4 }

    cmcTcMasterTc10Unit3MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc10Unit3MsgEntry 5 }

    cmcTcMasterTc10Unit3MsgTrap1 OBJECT-TYPE
      SYNTAX INTEGER {
        disable (1),
        enable (2)
      }
      ACCESS read-write
      STATUS mandatory
      DESCRIPTION
        "Trap receiver 1 activated"
      ::= { cmcTcMasterTc10Unit3MsgEntry 6 }

    cmcTcMasterTc10Unit3MsgTrap2 OBJECT-TYPE
      SYNTAX INTEGER {
        disable (1),
        enable (2)
      }
      ACCESS read-write
      STATUS mandatory
      DESCRIPTION
        "Trap receiver 2 activated"
      ::= { cmcTcMasterTc10Unit3MsgEntry 7 }
 
    cmcTcMasterTc10Unit3MsgTrap3 OBJECT-TYPE
      SYNTAX INTEGER {
        disable (1),
        enable (2)
      }
      ACCESS read-write
      STATUS mandatory
      DESCRIPTION
        "Trap receiver 3 activated"
      ::= { cmcTcMasterTc10Unit3MsgEntry 8 }

    cmcTcMasterTc10Unit3MsgTrap4 OBJECT-TYPE
      SYNTAX INTEGER {
        disable (1),
        enable (2)
      }
      ACCESS read-write
      STATUS mandatory
      DESCRIPTION
        "Trap receiver 4 and Event Logging activated"
      ::= { cmcTcMasterTc10Unit3MsgEntry 9 }

    cmcTcMasterTc10Unit3MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc10Unit3MsgEntry 10 }

-- unit4

  cmcTcMasterTc10Unit4TypeOfDevice OBJECT-TYPE
    SYNTAX INTEGER {
      notAvail (1),
      unitIO (2),
      unitAccess (3),
      unitClimate (4),
      unitFCS (5),
      unitRTT (6),
      unitRLCP (7),
      unitPSM (8)
    }
    ACCESS  read-only
    STATUS  mandatory
    DESCRIPTION
      "Type of sensor unit connected to port 4"
    ::= { cmcTcMasterTc10StatusSensorUnit4 1 }

  cmcTcMasterTc10Unit4Text OBJECT-TYPE
    SYNTAX DisplayString (SIZE (0..10))
    ACCESS read-write
    STATUS mandatory
    DESCRIPTION
      "Descriptional text for sensor unit connected to port 4"
    ::= { cmcTcMasterTc10StatusSensorUnit4 2 }

  cmcTcMasterTc10Unit4Serial OBJECT-TYPE
    SYNTAX INTEGER 
    ACCESS read-only
    STATUS mandatory
    DESCRIPTION
      "Serialnumber of sensor unit connected to port 4"
    ::= { cmcTcMasterTc10StatusSensorUnit4 3 }

  cmcTcMasterTc10Unit4Status OBJECT-TYPE
    SYNTAX INTEGER {
      ok(1),
      error(2),
      changed(3),
      quit(4),
      timeout(5),
      detected(6),
      notAvail(7),
      lowPower(8)
    }
    ACCESS read-only
    STATUS mandatory
    DESCRIPTION
      "General Status sensor unit connected to port 4
       (1) OK
       (2) error, e. g. value overflow
       (3) configuration of sensor unit has changed, confirmation required
       (4) Quit from sensor unit to confirm configuration changes
       (5) timeout of sensor unit, confirmation required to unload this unit
       (6) sensor unit detected, needs to be confirmed
       (7) unit is not available
       (8) supply voltage is too low"
    ::= { cmcTcMasterTc10StatusSensorUnit4 4 }

-- Sensors
              
  cmcTcMasterTc10Unit4NumberOfSensors OBJECT-TYPE
    SYNTAX INTEGER 
    ACCESS read-only
    STATUS mandatory
    DESCRIPTION
      "Number of sensors connected to sensor unit 4"
    ::= { cmcTcMasterTc10StatusUnit4Sensors 1 }

-- table with entry for each sensor available on this unit              
                
  cmcTcMasterTc10Unit4SensorTable OBJECT-TYPE
    SYNTAX SEQUENCE OF CmcTcMasterTc10Unit4SensorEntry
    ACCESS not-accessible
    STATUS mandatory
    DESCRIPTION
      "Headline of sensor table"
    ::= { cmcTcMasterTc10StatusUnit4Sensors 2 }

  cmcTcMasterTc10Unit4SensorEntry OBJECT-TYPE
    SYNTAX CmcTcMasterTc10Unit4SensorEntry
    ACCESS not-accessible
    STATUS mandatory
    DESCRIPTION
      "Entries of sensor table"
    INDEX { cmcTcMasterTc10Unit4SensorIndex }
    ::= { cmcTcMasterTc10Unit4SensorTable 1 }

    CmcTcMasterTc10Unit4SensorEntry ::=
      SEQUENCE {
        cmcTcMasterTc10Unit4SensorIndex
          INTEGER,
        cmcTcMasterTc10Unit4SensorType
          INTEGER,
        cmcTcMasterTc10Unit4SensorText
          DisplayString (SIZE (0..20)),                
        cmcTcMasterTc10Unit4SensorStatus
          INTEGER,
        cmcTcMasterTc10Unit4SensorValue
          INTEGER,
        cmcTcMasterTc10Unit4SensorSetHigh
          INTEGER,
        cmcTcMasterTc10Unit4SensorSetLow
          INTEGER,                 
        cmcTcMasterTc10Unit4SensorSetWarn
          INTEGER  
      }

    cmcTcMasterTc10Unit4SensorIndex OBJECT-TYPE
      SYNTAX INTEGER (1..32000)
      ACCESS read-only
      STATUS mandatory
      DESCRIPTION
        "Index for the list of value entries. Its value ranges
         between 1 and the value of cmcTcMasterTc10Unit4NumberOfSensors." 
      ::= { cmcTcMasterTc10Unit4SensorEntry 1 }

    cmcTcMasterTc10Unit4SensorType OBJECT-TYPE
      SYNTAX INTEGER {
        notAvail (1),
        failure (2),
        overflow (3),
        access (4),
        vibration (5),
        motion (6),
        smoke (7),
        airFlow (8),
        type6 (9),
        temperature(10),
        current4to20(11),
        humidity(12),
        userNO (13),
        userNC (14),
        lock (15),
        unlock (16),
        voltOK (17),
        voltage (18),
        fanOK (19),
        readerKeypad (20),
        dutyPWM (21),
        fanStatus (22),
        leakage (23),
        warningRTT (24),
        alarmRTT (25),
        filterRTT (26),
        heatflowRLCP (27),
        alarmRLCP (28),
        warningRLCP (29),
        currentPSM (30),
        statusPSM (31),
        positionPSM (32)
      }
      ACCESS read-only
      STATUS mandatory
      DESCRIPTION
        "Type of sensor which is connected to sensor unit 4 to sensor[cmcTcMasterTc10Unit4SensorIndex]
         1:        no sensor connected
         2:        sensor failure
         3:        value overflow
         4:        sensor type 1, access sensor
         5:        sensor type 2, vibration sensor
         6:        sensor type 3, motion sensor
         7:        sensor type 4, smoke sensor
         8:        sensor type 5, air flow sensor
         9:        sensor type 6, reserved
         10:       sensor type 7, temperature sensor
         11:       sensor type 8, 4..20mA sensor
         12:       sensor type 9, humidity sensor  
         13:       user sensor with normally opened contact
         14:       user sensor with normally closed contact
         15:       door locked sensor from locking device
         16:       remote unlock sensor (e.g. external keypad)
         17:       voltage sensor, indicates status of main voltage (OK, NOK)
         18:       voltage value
         19:       fan status, from CMC-TC-FAS-Unit
         20:       cardreader or keypad, connected to I2C port 
         21:       duty cycle of fan, FCS-Unit
         22:       status of fan, FCS-Unit
         23:       leakage sensor
         24:       warning, RittalTopTherm(RTT)-Unit
         25:       alarm, RittalTopTherm-Unit
         26:       temperature difference filter monitor, RTT-Unit
         27:       heatflow RLCP-Unit
         28:       alarm RLCP-Unit
         29:       warning RLCP-Unit
         30:       actual current*10, PSM-Unit
         31:       status PSM-Unit
         32:       position PSM-Unit, normal/reversed = circuit 1/2" 
      ::= { cmcTcMasterTc10Unit4SensorEntry 2 }

    cmcTcMasterTc10Unit4SensorText OBJECT-TYPE
      SYNTAX DisplayString (SIZE (0..20))
      ACCESS read-write
      STATUS mandatory
      DESCRIPTION
        "Descriptional text for each sensor (entry in the table)"
      ::= { cmcTcMasterTc10Unit4SensorEntry 3 }
              
    cmcTcMasterTc10Unit4SensorStatus OBJECT-TYPE
      SYNTAX INTEGER {
        notAvail(1),
        lost(2),
        changed(3),
        ok(4),
        off(5),
        on(6),
        warning(7),
        tooLow(8),
        tooHigh(9)
      }
      ACCESS read-only
      STATUS mandatory
      DESCRIPTION
        "Actual status of the sensor"
      ::= { cmcTcMasterTc10Unit4SensorEntry 4 }

    cmcTcMasterTc10Unit4SensorValue OBJECT-TYPE
      SYNTAX INTEGER 
      ACCESS read-only
      STATUS mandatory
      DESCRIPTION
        "Value of sensor"
      ::= { cmcTcMasterTc10Unit4SensorEntry 5 }

    cmcTcMasterTc10Unit4SensorSetHigh OBJECT-TYPE
      SYNTAX INTEGER (0..300) 
      ACCESS read-write
      STATUS mandatory
      DESCRIPTION
        "Value for high setpoint of sensor"
      ::= { cmcTcMasterTc10Unit4SensorEntry 6 }

    cmcTcMasterTc10Unit4SensorSetLow OBJECT-TYPE
      SYNTAX INTEGER (0..300) 
      ACCESS read-write
      STATUS mandatory
      DESCRIPTION
        "Value for low setpoint of sensor,
         also used as alarm delay"
      ::= { cmcTcMasterTc10Unit4SensorEntry 7 }

    cmcTcMasterTc10Unit4SensorSetWarn OBJECT-TYPE
      SYNTAX INTEGER (0..300) 
      ACCESS read-write
      STATUS mandatory
      DESCRIPTION
        "Value for warning setpoint of sensor,
         also used as fan threshold"
      ::= { cmcTcMasterTc10Unit4SensorEntry 8 }

-- Outputs              

  cmcTcMasterTc10Unit4NumberOfOutputs OBJECT-TYPE
    SYNTAX INTEGER 
    ACCESS read-only
    STATUS mandatory
    DESCRIPTION
      "Number of outputs available on sensor unit 4"
    ::= { cmcTcMasterTc10StatusUnit4Outputs 1 }

-- table with entry for each output available on this unit              
                
  cmcTcMasterTc10Unit4OutputTable OBJECT-TYPE
    SYNTAX SEQUENCE OF CmcTcMasterTc10Unit4OutputEntry
    ACCESS not-accessible
    STATUS mandatory
    DESCRIPTION
      "Headline of output table"
    ::= { cmcTcMasterTc10StatusUnit4Outputs 2 }

  cmcTcMasterTc10Unit4OutputEntry OBJECT-TYPE
    SYNTAX CmcTcMasterTc10Unit4OutputEntry
    ACCESS not-accessible
    STATUS mandatory
    DESCRIPTION
      "Entries of output table"
    INDEX { cmcTcMasterTc10Unit4OutputIndex }
    ::= { cmcTcMasterTc10Unit4OutputTable 1 }

    CmcTcMasterTc10Unit4OutputEntry ::=
      SEQUENCE {
        cmcTcMasterTc10Unit4OutputIndex
          INTEGER,
        cmcTcMasterTc10Unit4OutputType
          INTEGER,
        cmcTcMasterTc10Unit4OutputText
          DisplayString (SIZE (0..20)),                
        cmcTcMasterTc10Unit4OutputStatus
          INTEGER,
        cmcTcMasterTc10Unit4OutputValue
          INTEGER,
        cmcTcMasterTc10Unit4OutputSet
          INTEGER,
        cmcTcMasterTc10Unit4OutputConfig
          INTEGER,
        cmcTcMasterTc10Unit4OutputDelay
          INTEGER,
        cmcTcMasterTc10Unit4OutputTimeoutAction
          INTEGER
      }

    cmcTcMasterTc10Unit4OutputIndex OBJECT-TYPE
      SYNTAX INTEGER (1..32000)
      ACCESS read-only
      STATUS mandatory
      DESCRIPTION
        "Index for the list of output entries. Its value ranges
         between 1 and the value of cmcTcMasterTc10Unit4NumberOfOutputs." 
      ::= { cmcTcMasterTc10Unit4OutputEntry 1 }

    cmcTcMasterTc10Unit4OutputType OBJECT-TYPE
      SYNTAX INTEGER {
        notAvail (1),
        failure (2),
        overflow (3),
        doorLock (4),
        doorLock1 (5),
        doorLock2 (6),
        fan (7),
        fanSpeedContr (8),
        universalOut (9),
        roomLock(10),
        powerOut(11),
        doorLockMaster(12),
        doorLockFRi(13),
        setpoint (14),
        setpointTimax (15),
        hysteresisRLCP (16),
        commandRLCP (17),
        relayPSM (18),
        setHighPSM (19),
        setLowPSM (20)
      }
      ACCESS read-only
      STATUS mandatory
      DESCRIPTION
        "Type of output which is connected to sensor unit 4 to output[cmcTcMasterTc10Unit4OutputIndex]
         1:        no output connected
         2:        output failure
         3:        value overflow
         4:        output type 1, door locking TS8,Ergoform
         5:        output type 2, universal lock 1, lock with power
         6:        output type 3, universal lock 2, unlock with power
         7:        output type 4, fan relay
         8:        output type 5, fan controlled
         9:        output type 6, universal relay output
         10:       output type 7, room door lock 
         11:       output type 8, power output
         12:       output type 9, door lock with Master key
         13:       output type 10, door lock FR(i)
         14:       setpoint (FCS, RTT)
         15:       setpoint temperature monitoring (RTT) 
         16:       hysteresis of setpoint (RLCP)
         17:       command for remote control of RLCP
         18:       relay PSM, 1=On, 0=Off
         19:       high setpoint current monitoring PSM
         20:       low setpoint current monitoring PSM" 
      ::= { cmcTcMasterTc10Unit4OutputEntry 2 }

    cmcTcMasterTc10Unit4OutputText OBJECT-TYPE
      SYNTAX DisplayString (SIZE (0..20))
      ACCESS read-write
      STATUS mandatory
      DESCRIPTION
        "Descriptional text for each output (entry in the table)"
      ::= { cmcTcMasterTc10Unit4OutputEntry 3 }
              
    cmcTcMasterTc10Unit4OutputStatus OBJECT-TYPE
      SYNTAX INTEGER {
        notAvail(1),
        lost(2),
        changed(3),
        ok(4),
        off(5),
        on(6),
        setOff(7),
        setOn(8)
      }
      ACCESS read-write
      STATUS mandatory
      DESCRIPTION
        "Actual status of the output"
      ::= { cmcTcMasterTc10Unit4OutputEntry 4 }

    cmcTcMasterTc10Unit4OutputValue OBJECT-TYPE
      SYNTAX INTEGER (-32000..32000) 
      ACCESS read-write
      STATUS mandatory
      DESCRIPTION
        "Value for output"
      ::= { cmcTcMasterTc10Unit4OutputEntry 5 }

    cmcTcMasterTc10Unit4OutputSet OBJECT-TYPE
      SYNTAX INTEGER {
        off (1),
        on (2),
        lock (3),
        unlock (4),
        unlockDelay (5)
      }
      ACCESS read-write
      STATUS mandatory
      DESCRIPTION
        "Command for output"
      ::= { cmcTcMasterTc10Unit4OutputEntry 6 }

    cmcTcMasterTc10Unit4OutputConfig OBJECT-TYPE
      SYNTAX INTEGER {
        disRemote (1),
        enRemote (2)
      }
      ACCESS read-write
      STATUS mandatory
      DESCRIPTION
        "Configuration for output
         1: 	disable remote control (e.g. keypad)
         2: 	enable remote control "
      ::= { cmcTcMasterTc10Unit4OutputEntry 7 }

    cmcTcMasterTc10Unit4OutputDelay OBJECT-TYPE
      SYNTAX INTEGER (0..999) 
      ACCESS read-write
      STATUS mandatory
      DESCRIPTION
        "Unsigned Value for delay, 
         after this time the output will fall into the previous state"
      ::= { cmcTcMasterTc10Unit4OutputEntry 8 }

    cmcTcMasterTc10Unit4OutputTimeoutAction OBJECT-TYPE
      SYNTAX INTEGER {
        stay (1),
        off (2),
        on (3)
      }
      ACCESS read-write
      STATUS mandatory
      DESCRIPTION
        "State for output if timeout (RS422) occurs"
      ::= { cmcTcMasterTc10Unit4OutputEntry 9 }

-- Messages
              
  cmcTcMasterTc10Unit4NumberOfMsgs OBJECT-TYPE
    SYNTAX INTEGER 
    ACCESS read-only
    STATUS mandatory
    DESCRIPTION
      "Number of messages that can be created with sensor unit 4"
    ::= { cmcTcMasterTc10StatusUnit4Msg 1 }

-- table with entry for each alarm available on this unit               
                
  cmcTcMasterTc10Unit4MsgTable OBJECT-TYPE
    SYNTAX SEQUENCE OF CmcTcMasterTc10Unit4MsgEntry
    ACCESS not-accessible
    STATUS mandatory
    DESCRIPTION
      "Headline of message table"
    ::= { cmcTcMasterTc10StatusUnit4Msg 2 }

  cmcTcMasterTc10Unit4MsgEntry OBJECT-TYPE
    SYNTAX CmcTcMasterTc10Unit4MsgEntry
    ACCESS not-accessible
    STATUS mandatory
    DESCRIPTION
      "Entries of message table"
    INDEX { cmcTcMasterTc10Unit4MsgIndex }
    ::= { cmcTcMasterTc10Unit4MsgTable 1 }

    CmcTcMasterTc10Unit4MsgEntry ::=
      SEQUENCE {
        cmcTcMasterTc10Unit4MsgIndex
          INTEGER,
        cmcTcMasterTc10Unit4MsgText
          DisplayString (SIZE (0..20)),                
        cmcTcMasterTc10Unit4MsgStatus
          INTEGER, 
        cmcTcMasterTc10Unit4MsgRelay
          INTEGER,
        cmcTcMasterTc10Unit4MsgBeeper
          INTEGER,
        cmcTcMasterTc10Unit4MsgTrap1
          INTEGER,
        cmcTcMasterTc10Unit4MsgTrap2
          INTEGER,
        cmcTcMasterTc10Unit4MsgTrap3
          INTEGER,
        cmcTcMasterTc10Unit4MsgTrap4
          INTEGER,                 
        cmcTcMasterTc10Unit4MsgQuit
          INTEGER              
      }

    cmcTcMasterTc10Unit4MsgIndex OBJECT-TYPE
      SYNTAX INTEGER (1..32000)
      ACCESS read-only
      STATUS mandatory
      DESCRIPTION
        "Index for the list of message entries. Its value ranges
         between 1 and the value of cmcTcMasterTc10Unit4NumberOfMsgs." 
      ::= { cmcTcMasterTc10Unit4MsgEntry 1 }

    cmcTcMasterTc10Unit4MsgText OBJECT-TYPE
      SYNTAX DisplayString (SIZE (0..20))
      ACCESS read-write
      STATUS mandatory
      DESCRIPTION
        "Descriptional text for each message (entry in the table)"
      ::= { cmcTcMasterTc10Unit4MsgEntry 2 }

    cmcTcMasterTc10Unit4MsgStatus OBJECT-TYPE
      SYNTAX INTEGER {
        notAvail(1),
        configChanged(2),
        error(3),
        ok(4),
        alarm(5),
        warning(6),
        tooLow(7),
        tooHigh(8),
        setOff(9),
        setOn(10),
        open(11),
        closed(12),
        locked(13),
        unlRemote(14),
        unlReaderKeypad(15),
        unlSNMP(16),
        unlWEB(17),
        unlTimer(18),
        noAccess(19),
        circuit1 (20),
        circuit2 (21)             
      }
      ACCESS read-only
      STATUS mandatory
      DESCRIPTION
        "Actual message status
         1: not available
         2: configuration has changed (sensor new, changed, lost)
         3: error
         4: OK
         5: alarm, e.g. smoke, vibration...
         6: warning of analog value, value reached warning threshold
         7: analog value too low, value reached low threshold
         8: analog value too high, value reached high threshold
         9: output is set to ON
         10: output is set to OFF
         11: door is open
         12: door is closed
         13: door is locked
         14: door is unlocked by remote input, e.g. external cardreader
         15: door is unlocked by reader or keypad connected to I2C
         16: door is unlocked by SNMP set command (cmcTcMasterTc10Unit4OutputSet)
         17: door is unlocked by WEB
         18: door is unlocked by timer
         19: no access, wrong keycode or cardnumber
         20: orientation of PSM-Unit is circuit 1
         21: orientation of PSM-Unit is circuit 2"
      ::= { cmcTcMasterTc10Unit4MsgEntry 3 }

    cmcTcMasterTc10Unit4MsgRelay OBJECT-TYPE
      SYNTAX INTEGER {
        disable (1),
        enable (2)
      }
      ACCESS read-write
      STATUS mandatory
      DESCRIPTION
        "Setup of Alarm relay for this alarm
         1:        no switching of alarm relay             
         2:        switching of alarm relay" 
      ::= { cmcTcMasterTc10Unit4MsgEntry 4 }

    cmcTcMasterTc10Unit4MsgBeeper OBJECT-TYPE
      SYNTAX INTEGER {
        disable (1),
        enable (2)
      }
      ACCESS read-write
      STATUS mandatory
      DESCRIPTION
        "Setup of Alarm beeper for this alarm
         1:        no audible alarm
         2:        audible alarm" 
      ::= { cmcTcMasterTc10Unit4MsgEntry 5 }

    cmcTcMasterTc10Unit4MsgTrap1 OBJECT-TYPE
      SYNTAX INTEGER {
        disable (1),
        enable (2)
      }
      ACCESS read-write
      STATUS mandatory
      DESCRIPTION
        "Trap receiver 1 activated"
      ::= { cmcTcMasterTc10Unit4MsgEntry 6 }

    cmcTcMasterTc10Unit4MsgTrap2 OBJECT-TYPE
      SYNTAX INTEGER {
        disable (1),
        enable (2)
      }
      ACCESS read-write
      STATUS mandatory
      DESCRIPTION
        "Trap receiver 2 activated"
      ::= { cmcTcMasterTc10Unit4MsgEntry 7 }
 
    cmcTcMasterTc10Unit4MsgTrap3 OBJECT-TYPE
      SYNTAX INTEGER {
        disable (1),
        enable (2)
      }
      ACCESS read-write
      STATUS mandatory
      DESCRIPTION
        "Trap receiver 3 activated"
      ::= { cmcTcMasterTc10Unit4MsgEntry 8 }

    cmcTcMasterTc10Unit4MsgTrap4 OBJECT-TYPE
      SYNTAX INTEGER {
        disable (1),
        enable (2)
      }
      ACCESS read-write
      STATUS mandatory
      DESCRIPTION
        "Trap receiver 4 and Event Logging activated"
      ::= { cmcTcMasterTc10Unit4MsgEntry 9 }

    cmcTcMasterTc10Unit4MsgQuit OBJECT-TYPE
      SYNTAX INTEGER {
        auto (1),
        manual (2)
      }
      ACCESS read-write
      STATUS mandatory
      DESCRIPTION
        "Reset of this alarm
         1:        auto
         2:        manual, alarm needs confirmation, e. g. with 'C' key"
      ::= { cmcTcMasterTc10Unit4MsgEntry 10 }

--Status extension unit

  cmcTcMasterTc10ValuesRelay OBJECT-TYPE
    SYNTAX INTEGER {
      disable (1),
      enable (2)
    }
    ACCESS read-write
    STATUS mandatory
    DESCRIPTION
      "Setup of Alarm relay for alarm ext. unit(s)
       1:        no switching of alarm relay             
       2:        switching of alarm relay" 
    ::= { cmcTcMasterTc10StatusExtUnit 1 }

  cmcTcMasterTc10ValuesBeeper OBJECT-TYPE
    SYNTAX INTEGER {
      disable (1),
      enable (2)
    }
    ACCESS read-write
    STATUS mandatory
    DESCRIPTION
      "Setup of Alarm beeper for alarm ext. unit(s)
       1:        no audible alarm
       2:        audible alarm" 
    ::= { cmcTcMasterTc10StatusExtUnit 2 }

  cmcTcMasterTc10ValuesTrap1 OBJECT-TYPE
    SYNTAX INTEGER {
      disable (1),
      enable (2)
    }
    ACCESS read-write
    STATUS mandatory
    DESCRIPTION
      "Trap receiver 1 activated"
    ::= { cmcTcMasterTc10StatusExtUnit 3 }

  cmcTcMasterTc10ValuesTrap2 OBJECT-TYPE
    SYNTAX INTEGER {
      disable (1),
      enable (2)
    }
    ACCESS read-write
    STATUS mandatory
    DESCRIPTION
      "Trap receiver 2 activated"
    ::= { cmcTcMasterTc10StatusExtUnit 4 }
 
  cmcTcMasterTc10ValuesTrap3 OBJECT-TYPE
    SYNTAX INTEGER {
      disable (1),
      enable (2)
    }
    ACCESS read-write
    STATUS mandatory
    DESCRIPTION
      "Trap receiver 3 activated"
    ::= { cmcTcMasterTc10StatusExtUnit 5 }

  cmcTcMasterTc10ValuesTrap4 OBJECT-TYPE
    SYNTAX INTEGER {
      disable (1),
      enable (2)
    }
    ACCESS read-write
    STATUS mandatory
    DESCRIPTION
      "Trap receiver 4 and Event Logging activated"
    ::= { cmcTcMasterTc10StatusExtUnit 6 }
 
  cmcTcMasterTc10NumberOfValues OBJECT-TYPE
    SYNTAX INTEGER 
    ACCESS  read-only
    STATUS  mandatory
    DESCRIPTION
      "Number of values availabel on extension units connected to the CMC-TC"
    ::= { cmcTcMasterTc10StatusExtUnit 7 }

-- table with entry for each value available on extension units              

  cmcTcMasterTc10ValuesTable OBJECT-TYPE
    SYNTAX SEQUENCE OF CmcTcMasterTc10ValuesEntry
    ACCESS not-accessible
    STATUS mandatory
    DESCRIPTION
      "Headline of values-table"
    ::= { cmcTcMasterTc10StatusExtUnit 8 }

  cmcTcMasterTc10ValuesEntry OBJECT-TYPE
    SYNTAX CmcTcMasterTc10ValuesEntry
    ACCESS not-accessible
    STATUS mandatory
    DESCRIPTION
      "Entries of values-table"
    INDEX { cmcTcMasterTc10ValuesIndex }
    ::= { cmcTcMasterTc10ValuesTable 1 }

    CmcTcMasterTc10ValuesEntry ::=
      SEQUENCE {
        cmcTcMasterTc10ValuesIndex
          INTEGER,
        cmcTcMasterTc10ValuesText
          DisplayString (SIZE (0..20)),                
        cmcTcMasterTc10ValuesStatus
          INTEGER,
        cmcTcMasterTc10ValuesValue
          INTEGER,
        cmcTcMasterTc10ValuesSetHigh
          INTEGER,
        cmcTcMasterTc10ValuesSetLow
          INTEGER
      }

    cmcTcMasterTc10ValuesIndex OBJECT-TYPE
      SYNTAX INTEGER (1..32000)
      ACCESS read-only
      STATUS mandatory
      DESCRIPTION
        "Index for the list of value entries. Its value ranges
         between 1 and the value of cmcTcMasterTc10NumberOfValues." 
      ::= { cmcTcMasterTc10ValuesEntry 1 }

        
    cmcTcMasterTc10ValuesText OBJECT-TYPE
      SYNTAX DisplayString (SIZE (0..20))
      ACCESS read-write
      STATUS mandatory
      DESCRIPTION
        "Descriptional text for each value (entry in the table)
         of the extension card"
      ::= { cmcTcMasterTc10ValuesEntry 2 }
              
    cmcTcMasterTc10ValuesStatus OBJECT-TYPE
      SYNTAX INTEGER {
        notAvail(1),
        lost(2),
        changed(3),
        ok(4),
        tooLow(5),
        tooHigh(6),
        error(7)
      }
      ACCESS read-only
      STATUS mandatory
      DESCRIPTION
        "Actual status of the value of the extension card"
      ::= { cmcTcMasterTc10ValuesEntry 3 }

    cmcTcMasterTc10ValuesValue OBJECT-TYPE
      SYNTAX INTEGER 
      ACCESS read-only
      STATUS mandatory
      DESCRIPTION
        "Value of sensor"
      ::= { cmcTcMasterTc10ValuesEntry 4 }

    cmcTcMasterTc10ValuesSetHigh OBJECT-TYPE
      SYNTAX INTEGER (0..255) 
      ACCESS read-write
      STATUS mandatory
      DESCRIPTION
        "Value for high setpoint of sensor"
      ::= { cmcTcMasterTc10ValuesEntry 5 }

    cmcTcMasterTc10ValuesSetLow OBJECT-TYPE
      SYNTAX INTEGER (0..255) 
      ACCESS read-write
      STATUS mandatory
      DESCRIPTION
        "Value for low setpoint of sensor"
      ::= { cmcTcMasterTc10ValuesEntry 6 }

--cmcTcMasterTc10SetupGeneral-group

  cmcTcMasterTc10SetTempUnit OBJECT-TYPE
    SYNTAX INTEGER {
      celsius(1),
      fahrenheit(2)
    }
    ACCESS read-write
    STATUS mandatory
    DESCRIPTION
      "Unit of all temperature values and setpoints, Celsius or Fahrenheit"
   ::= { cmcTcMasterTc10SetupGeneral 1 }

  cmcTcMasterTc10SetBeeper OBJECT-TYPE
    SYNTAX INTEGER {
      off(1),
      on(2)
    }
    ACCESS read-write
    STATUS mandatory
    DESCRIPTION
      "Audible alarm in CMC-TC unit:
       (2): beeper is on
       (1): beeper is off (general)"
    ::= { cmcTcMasterTc10SetupGeneral 2 }


  cmcTcMasterTc10QuitRelay OBJECT-TYPE
    SYNTAX INTEGER {
      disabled(1),
      enabled(2)
    }
    ACCESS read-write
    STATUS mandatory
    DESCRIPTION
      "Enable or disable acknowledging currently active alarm relay 
       (with 'C' on CMC-TC)."
    ::= { cmcTcMasterTc10SetupGeneral 3 }

  cmcTcMasterTc10LogicRelay OBJECT-TYPE
    SYNTAX INTEGER {
      closeAtAlarm(1),
      openAtAlarm(2),
      off(3)
    }
    ACCESS read-write
    STATUS mandatory
    DESCRIPTION
      "Logic of alarm relay: 
       (1) Relay will pick up in case of an alarm
       (2) Relay will release in case of an alarm
       (3) Relay off (general)"
    ::= { cmcTcMasterTc10SetupGeneral 4 }

  cmcTcMasterTc10WebAccess OBJECT-TYPE
    SYNTAX INTEGER {
      viewOnly(1),
      fullAccess(2),
      off(3)
    }
    ACCESS read-write
    STATUS mandatory
    DESCRIPTION
      "Web access via HTTP: 
       (1) view only
       (2) full Access, read and set
       (3) Web disabled (general)"
    ::= { cmcTcMasterTc10SetupGeneral 5 }
 
  cmcTcMasterTc10SetupDate OBJECT-TYPE
    SYNTAX DisplayString (SIZE (0..10))
    ACCESS read-write
    STATUS mandatory
    DESCRIPTION
      "actual Date in format DD.MM.YYYY"
    ::= { cmcTcMasterTc10SetupGeneral 6 }

  cmcTcMasterTc10SetupTime OBJECT-TYPE
    SYNTAX DisplayString (SIZE (0..8))
    ACCESS read-write
    STATUS mandatory
    DESCRIPTION
      "actual Time in format HH:MM:SS, HH (0-23), MM (0-59), SS (0-59)"
    ::= { cmcTcMasterTc10SetupGeneral 7 }
 
-- table for timer function
 
  cmcTcMasterTc10TimerNumber OBJECT-TYPE
    SYNTAX INTEGER 
    ACCESS read-only
    STATUS mandatory
    DESCRIPTION
      "Number of timers available on this unit"
    ::= { cmcTcMasterTc10TimerTable1 1 }

  cmcTcMasterTc10TimerTable OBJECT-TYPE
    SYNTAX SEQUENCE OF CmcTcMasterTc10TimerEntry
    ACCESS not-accessible
    STATUS mandatory
    DESCRIPTION
      "Headline of timer-table"
    ::= { cmcTcMasterTc10TimerTable1 2 }

  cmcTcMasterTc10TimerEntry OBJECT-TYPE
    SYNTAX CmcTcMasterTc10TimerEntry
    ACCESS not-accessible
    STATUS mandatory
    DESCRIPTION
      "Entries of timer-table"
    INDEX { cmcTcMasterTc10TimerIndex }
    ::= { cmcTcMasterTc10TimerTable 1 }

    CmcTcMasterTc10TimerEntry ::=
      SEQUENCE {
        cmcTcMasterTc10TimerIndex
          INTEGER,
        cmcTcMasterTc10TimerStatus
          INTEGER,
        cmcTcMasterTc10TimerDayOfWeek
          INTEGER,  
        cmcTcMasterTc10TimeOn 
          DisplayString (SIZE (0..5)),                              
        cmcTcMasterTc10TimeOff 
          DisplayString (SIZE (0..5)),                              
        cmcTcMasterTc10TimeControl
          INTEGER,
        cmcTcMasterTc10TimerFunction
           INTEGER
      }

    cmcTcMasterTc10TimerIndex OBJECT-TYPE
      SYNTAX INTEGER (1..32000)
      ACCESS read-only
      STATUS mandatory
      DESCRIPTION
        "Index for the list of timer entries. Its value ranges
         between 1 and the value of cmcTcMasterTc10TimerNumber." 
      ::= { cmcTcMasterTc10TimerEntry 1 }

    cmcTcMasterTc10TimerStatus OBJECT-TYPE
      SYNTAX INTEGER {
        switchedOff(1),
        switchedOn(2),
        noTime(3) 
      }
      ACCESS read-only
      STATUS mandatory
      DESCRIPTION
        "Actual status of the timer"
      ::= { cmcTcMasterTc10TimerEntry 2 }

    cmcTcMasterTc10TimerDayOfWeek OBJECT-TYPE
      SYNTAX INTEGER {
        sun(1),
        mon(2),
        tue(3) ,
        wed(4),
        thu(5),
        fri(6),
        sat(7),
        sat-sun(8),
        mon-fri(9),
        mon-sun(10)
      }
      ACCESS read-write
      STATUS mandatory
      DESCRIPTION
        "Selection of day of week for timer to switch"
      ::= { cmcTcMasterTc10TimerEntry 3 }
             
    cmcTcMasterTc10TimeOn OBJECT-TYPE
      SYNTAX DisplayString (SIZE (0..5))
      ACCESS read-write
      STATUS mandatory
      DESCRIPTION
        "Time to switch on current function, 
         Format: HH:MM"
      ::= { cmcTcMasterTc10TimerEntry 4 }

    cmcTcMasterTc10TimeOff OBJECT-TYPE
      SYNTAX DisplayString (SIZE (0..5))
      ACCESS read-write
      STATUS mandatory
      DESCRIPTION
        "Time to switch off current function,
         Format: HH:MM"
      ::= { cmcTcMasterTc10TimerEntry 5 }

    cmcTcMasterTc10TimeControl OBJECT-TYPE
      SYNTAX INTEGER  {
        disabled(1),
        enabled(2)
      }
      ACCESS read-write
      STATUS mandatory
      DESCRIPTION
        "Control via RTC"
      ::= { cmcTcMasterTc10TimerEntry 6 }

    cmcTcMasterTc10TimerFunction OBJECT-TYPE
      SYNTAX INTEGER {
        disKeypad1-1 (1),
        disKeypad2-1 (2),
        disKeypad1-2 (3),
        disKeypad2-2 (4),
        disKeypad1-3 (5),
        disKeypad2-3 (6),
        disKeypad1-4 (7),
        disKeypad2-4 (8),
        unlDoor1-1 (9),
        unlDoor2-1 (10),
        unlDoor1-2 (11),
        unlDoor2-2 (12),
        unlDoor1-3 (13),
        unlDoor2-3 (14),
        unlDoor1-4 (15),
        unlDoor2-5 (16),
        disTrapRec1 (17),
        disTrapRec2 (18),
        disTrapRec3 (19),
        disTrapRec4 (20),
        disSMS (21),
        schedule1 (22),
        schedule2 (23),
        schedule3 (24),
        schedule4 (25)
      }
      ACCESS read-write
      STATUS mandatory
      DESCRIPTION
        "Function which is controlled via timer
         1:     unlock via keypad 1 on unit 1 or remote input lock 1 is disabled
         2:     unlock via keypad 2 on unit 1 or remote input lock 2 is disabled
         3      unlock via keypad 1 on unit 2 or remote input lock 1 is disabled
         4:     unlock via keypad 2 on unit 2 or remote input lock 2 is disabled
         5:     unlock via keypad 1 on unit 3 or remote input lock 1 is disabled
         6:     unlock via keypad 2 on unit 3 or remote input lock 2 is disabled
         7:     unlock via keypad 1 on unit 4 or remote input lock 1 is disabled
         8:     unlock via keypad 2 on unit 4 or remote input lock 2 is disabled
         9:     Lock of door 1 on unit 1 will be unlocked
         10:    Lock of door 2 on unit 1 will be unlocked
         11:    Lock of door 1 on unit 2 will be unlocked
         12:    Lock of door 2 on unit 2 will be unlocked
         13:    Lock of door 1 on unit 3 will be unlocked
         14:    Lock of door 2 on unit 3 will be unlocked
         15:    Lock of door 1 on unit 4 will be unlocked
         16:    Lock of door 2 on unit 4 will be unlocked
         17-20: sending Traps to this Trap receiver will be disabled
         21:    sending SMS will be disabled
         22-25: Scheduled alarm off"
      ::= { cmcTcMasterTc10TimerEntry 7 }

--cmcTcMasterTc10TrapTable-group

  cmcTcMasterTc10TraptableNumber OBJECT-TYPE
    SYNTAX INTEGER 
    ACCESS read-only
    STATUS mandatory
    DESCRIPTION
      "Number of trapTable entries. The number of trap-receiver"
    ::= { cmcTcMasterTc10Traps 1 }

  cmcTcMasterTc10TrapTableTable OBJECT-TYPE    
    SYNTAX SEQUENCE OF CmcTcMasterTc10TrapTableEntry
    ACCESS not-accessible
    STATUS mandatory
    DESCRIPTION
     "A list of trap-receiver entries"
    ::= { cmcTcMasterTc10Traps 2 }

  cmcTcMasterTc10TrapTableEntry OBJECT-TYPE
    SYNTAX CmcTcMasterTc10TrapTableEntry
    ACCESS not-accessible
    STATUS mandatory
    DESCRIPTION
      "Entries of cmcTcMasterTc10TrapTable"
    INDEX   { cmcTcMasterTc10TrapIndex }
    ::= { cmcTcMasterTc10TrapTableTable 1 }      
              
    CmcTcMasterTc10TrapTableEntry ::=
      SEQUENCE {
        cmcTcMasterTc10TrapIndex
          INTEGER,
        cmcTcMasterTc10TrapStatus
          INTEGER,
        cmcTcMasterTc10TrapIPaddress
          DisplayString
      }

    cmcTcMasterTc10TrapIndex OBJECT-TYPE
      SYNTAX INTEGER (1..32000)
      ACCESS read-only
      STATUS mandatory
      DESCRIPTION
        "Index for the trap-receiver-table. Its value ranges between
         1 and the value of cmcTcMasterTc10TraptableNumber "
      ::= { cmcTcMasterTc10TrapTableEntry 1 }

    cmcTcMasterTc10TrapStatus OBJECT-TYPE
      SYNTAX INTEGER {
        disabled(1),
        enabled(2)
      }
      ACCESS read-write
      STATUS mandatory
      DESCRIPTION
        "Enable or disable trap receiver"
      ::= { cmcTcMasterTc10TrapTableEntry 2 }

    cmcTcMasterTc10TrapIPaddress OBJECT-TYPE
      SYNTAX DisplayString (SIZE (0..15))
      ACCESS read-write
      STATUS mandatory
      DESCRIPTION
        "IP-address of trap-receiver"
      ::= { cmcTcMasterTc10TrapTableEntry 3 }

--cmcTcMasterTc10Control-group (Added in Version 1.1)

  cmcTcMasterTc1QuitUnit OBJECT-TYPE
    SYNTAX INTEGER {
      noQuit(1),
      quit(2),
    }
    ACCESS read-write
    STATUS mandatory
    DESCRIPTION
      "Command to quit (acknowledge) alarms of CMC-TC unit.
       Setting to 'quit' (2) will have same result as pressing 'C' on Units.
       Variable is automatically set back to 'noQuit' (1)."
    ::= { cmcTcMasterTc10Control 1 }

--trapControl-group

  cmcTcMasterTrapMessage OBJECT-TYPE
    SYNTAX DisplayString (SIZE (0..200))
    ACCESS read-only
    STATUS mandatory
    DESCRIPTION
      "Trap message"
    ::= { cmcTcMasterTrapControl 1 }

  cmcTcMasterTrapTableNumber OBJECT-TYPE
    SYNTAX INTEGER 
    ACCESS read-only
    STATUS mandatory
    DESCRIPTION
      "Number of cmcTcMasterTrapTable entries. The number of trap-receivers avail."
    ::= { cmcTcMasterTraps 1 }

  cmcTcMasterTrapTable OBJECT-TYPE
    SYNTAX SEQUENCE OF CmcTcMasterTrapEntry
    ACCESS not-accessible
    STATUS mandatory
    DESCRIPTION
      "A list of trap-receiver entries"
    ::= { cmcTcMasterTraps 2 }

  cmcTcMasterTrapEntry OBJECT-TYPE
    SYNTAX CmcTcMasterTrapEntry
    ACCESS not-accessible
    STATUS mandatory
    DESCRIPTION
      "Entries of trapTable"
     INDEX   { cmcTcMasterTrapIndex }
     ::= { cmcTcMasterTrapTable 1 }

    CmcTcMasterTrapEntry ::=
      SEQUENCE {
        cmcTcMasterTrapIndex
          INTEGER,
        cmcTcMasterTrapStatus
          INTEGER,
        cmcTcMasterTrapIPaddress
          DisplayString
      }

      cmcTcMasterTrapIndex OBJECT-TYPE
        SYNTAX INTEGER (1..10)
        ACCESS read-only
        STATUS mandatory
        DESCRIPTION
          "Index for the trap-receiver-table. Its value ranges between
          1 and the value of trapNumber "
        ::= { cmcTcMasterTrapEntry 1 }

      cmcTcMasterTrapStatus OBJECT-TYPE
        SYNTAX INTEGER  {
          disabled(1),
          enabled(2)
        }
        ACCESS read-write
        STATUS mandatory
        DESCRIPTION
          "Enable or disable trap receiver"
        ::= { cmcTcMasterTrapEntry 2 }

      cmcTcMasterTrapIPaddress OBJECT-TYPE
        SYNTAX DisplayString (SIZE (0..15))
        ACCESS read-write
        STATUS mandatory
        DESCRIPTION
          "IP-address of trap-receiver"
        ::= { cmcTcMasterTrapEntry 3 }

--Traps

  alarmDev1 TRAP-TYPE
    ENTERPRISE cmcTcMaster
    VARIABLES { cmcTcMasterDev1Type, cmcTcMasterDev1Name, cmcTcMasterDev1Location, cmcTcMasterDev1Status, cmcTcMasterTrapMessage }
    DESCRIPTION
      "Alarm trap from Device1"
    ::= 1

  alarmDev2 TRAP-TYPE
    ENTERPRISE cmcTcMaster
    VARIABLES { cmcTcMasterDev2Type, cmcTcMasterDev2Name, cmcTcMasterDev2Location, cmcTcMasterDev2Status, cmcTcMasterTrapMessage }
    DESCRIPTION
      "Alarm trap from Device2"
    ::= 2

  alarmDev3 TRAP-TYPE
    ENTERPRISE cmcTcMaster
    VARIABLES { cmcTcMasterDev3Type, cmcTcMasterDev3Name, cmcTcMasterDev3Location, cmcTcMasterDev3Status, cmcTcMasterTrapMessage }
    DESCRIPTION
      "Alarm trap from Device3"
    ::= 3

  alarmDev4 TRAP-TYPE
    ENTERPRISE cmcTcMaster
    VARIABLES { cmcTcMasterDev4Type, cmcTcMasterDev4Name, cmcTcMasterDev4Location, cmcTcMasterDev4Status, cmcTcMasterTrapMessage }
    DESCRIPTION
      "Alarm trap from Device4"
    ::= 4

  alarmDev5 TRAP-TYPE
    ENTERPRISE cmcTcMaster
    VARIABLES { cmcTcMasterDev5Type, cmcTcMasterDev5Name, cmcTcMasterDev5Location, cmcTcMasterDev5Status, cmcTcMasterTrapMessage }
    DESCRIPTION
      "Alarm trap from Device5"
    ::= 5

  alarmDev6 TRAP-TYPE
    ENTERPRISE cmcTcMaster
    VARIABLES { cmcTcMasterDev6Type, cmcTcMasterDev6Name, cmcTcMasterDev6Location, cmcTcMasterDev6Status, cmcTcMasterTrapMessage }
    DESCRIPTION
      "Alarm trap from Device6"
    ::= 6

  alarmDev7 TRAP-TYPE
    ENTERPRISE cmcTcMaster
    VARIABLES { cmcTcMasterDev7Type, cmcTcMasterDev7Name, cmcTcMasterDev7Location, cmcTcMasterDev7Status, cmcTcMasterTrapMessage }
    DESCRIPTION
      "Alarm trap from Device7"
    ::= 7

  alarmDev8 TRAP-TYPE
    ENTERPRISE cmcTcMaster
    VARIABLES { cmcTcMasterDev8Type, cmcTcMasterDev8Name, cmcTcMasterDev8Location, cmcTcMasterDev8Status, cmcTcMasterTrapMessage }
    DESCRIPTION
      "Alarm trap from Device8"
    ::= 8

  alarmDev9 TRAP-TYPE
    ENTERPRISE cmcTcMaster
    VARIABLES { cmcTcMasterDev9Type, cmcTcMasterDev9Name, cmcTcMasterDev9Location, cmcTcMasterDev9Status, cmcTcMasterTrapMessage }
    DESCRIPTION
      "Alarm trap from Device9"
    ::= 9

  alarmDev10 TRAP-TYPE
    ENTERPRISE cmcTcMaster
    VARIABLES { cmcTcMasterDev10Type, cmcTcMasterDev10Name, cmcTcMasterDev10Location, cmcTcMasterDev10Status, cmcTcMasterTrapMessage }
    DESCRIPTION
      "Alarm trap from Device10"
    ::= 10

  alarmMaster TRAP-TYPE
    ENTERPRISE cmcTcMaster
    VARIABLES { sysName, sysLocation, cmcTcMasterMibCondition, cmcTcMasterTrapMessage }
    DESCRIPTION
      "Alarm trap generated by the TC-Master"
    ::= 11

  alarmTemperature TRAP-TYPE
    ENTERPRISE cmcTcMaster
    VARIABLES { sysName, sysLocation, cmcTcMasterStatusTemperature }
    DESCRIPTION
      "Temperature alarm"
    ::= 12

	END
